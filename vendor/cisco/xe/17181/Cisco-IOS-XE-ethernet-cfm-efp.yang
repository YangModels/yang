submodule Cisco-IOS-XE-ethernet-cfm-efp {
  yang-version 1.1;
  belongs-to Cisco-IOS-XE-ethernet {
    prefix ios-eth;
  }

  import cisco-semver {
    prefix cisco-semver;
  }
  import Cisco-IOS-XE-types {
    prefix ios-types;
  }
  import Cisco-IOS-XE-features {
    prefix ios-features;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Yang model for the following sub modules,
        * ethernet-cfm
        * ethernet-efp
     Copyright (c) 2018-2024 by Cisco Systems, Inc.
     All rights reserved.";

  revision 2025-03-01 {
    description
      "- Replaced when condition under rewrite with must";
    cisco-semver:module-version "8.0.0";
  }
  revision 2024-11-01 {
    description
      "- Obsolete nodes deprecated before 17.9 release
       - Removed when condition under rewrite to ensure explicit cli ordering
       - Obsolete Bridge-Domain nodes deprecated before 17.9 release
       - when constraint of encapsulation added under rewrite
       - Increased range for track configurable under EFP to 32767";
    cisco-semver:module-version "7.0.0";
  }
  revision 2024-03-01 {
    description
      "- Added support for lck logging
       - Obsolete nodes deprecated before 17.6 release";
    cisco-semver:module-version "6.0.0";
  }
  revision 2023-07-01 {
    description
      "- Added a leaf to support track config under service instance";
    cisco-semver:module-version "5.3.0";
  }
  revision 2022-11-01 {
    description
      "- Update yang-version to 1.1";
    cisco-semver:module-version "5.2.0";
  }
  revision 2022-07-01 {
    description
      "- Added support for bpdu, cfm, stp, mrp.";
    cisco-semver:module-version "5.1.0";
  }
  revision 2022-03-01 {
    description
      "- Added leaf dot1ad, vlan-type under rewrite push, translate containers";
    cisco-semver:module-version "5.0.0";
  }
  revision 2021-11-01 {
    description
      "- Added container slm, lck. Leaf sender-id, lower-mep-only added for mip-vlan, mip-evc lists
       - Deprecated container mip-level, added container level-config
       - Container tag-config added and container tag deprecated
       - Add mac security address,aging,sticky under interface GigabitEthernet
         * service instance * ethernet";
    cisco-semver:module-version "4.2.0";
  }
  revision 2021-07-01 {
    description
      "- Initial revision for 17.6.1";
    cisco-semver:module-version "4.1.0";
  }
  revision 2021-03-01 {
    description
      "- Extend untagged encapsulation container";
    cisco-semver:module-version "4.0.0";
  }
  revision 2020-11-01 {
    description
      "- Extend untagged encapsulation container
       - Container mip-config added and leaf mip deprecated";
    cisco-semver:module-version "3.0.0";
  }
  revision 2020-07-01 {
    description
      "- Change split-horizon to presence container
       - Leaf completion for CFM Domain mode commands
       - New ccm fast-age and hold-time commands
       - New config-interface-ethernet-cfm-grouping Added";
    cisco-semver:module-version "2.2.0";
  }
  revision 2020-03-01 {
    description
      "- Added EFD (Ethernet Fault Detection) Support";
    cisco-semver:module-version "2.1.0";
  }
  revision 2019-11-01 {
    description
      "Added latching loopback config";
    cisco-semver:module-version "2.0.0";
  }
  revision 2019-07-01 {
    description
      "Establish semantic version baseline";
    cisco-semver:module-version "1.0.0";
  }
  revision 2019-03-11 {
    description
      "This revision has changes for EVC-CFM mep mode additions";
  }
  revision 2019-02-18 {
    description
      "This revision has changes for CFM additions";
  }
  revision 2018-12-13 {
    description
      "Initial revision";
  }

  grouping config-interface-srv-ecfm-mep-grouping {
    container alarm {
      description
        "CFM Alarm";
      leaf delay {
        description
          "msec (default 2500 msec)";
        type uint16 {
          range "2500..10000";
        }
        default "2500";
      }
      leaf notification {
        description
          "CFM alarm notification";
        type enumeration {
          enum all;
          enum error-xcon;
          enum mac-remote-error-xcon;
          enum none;
          enum remote-error-xcon;
          enum xcon;
        }
        default "mac-remote-error-xcon";
      }
      leaf reset {
        description
          "msec (default 10000 msec)";
        type uint16 {
          range "2500..10000";
        }
        default "10000";
      }
    }
    leaf cos {
      description
        "Specify Class of Service sent in CFM messages for EFP MEP";
      type uint16 {
        range "1..7";
      }
    }
    container continuity-check {
      description
        "Configure Continuity Check for MA";
      container static {
        description
          "Verify MEP in received CCM is valid";
        leaf rmep {
          description
            "MEP defined using mep mpid";
          type empty;
        }
      }
    }
    list rmep {
      description
        "Static Remote MEP associated with this DOWN MEP";
      key "id";
      leaf id {
        description
          "Maintenance End Point Identifier";
        type uint16 {
          range "1..8191";
        }
      }
      leaf mpid {
        description
          "Maintenance End Point Identifier";
        type empty;
      }
    }
  }

  grouping config-interface-efp-l2protocol-grouping {
    leaf-list protocol {
      type enumeration {
        enum R4;
        enum R5;
        enum R6;
        enum R8;
        enum R9;
        enum RA;
        enum RB;
        enum RC;
        enum RD;
        enum RF;
        enum cdp;
        enum dtp;
        enum elmi;
        enum esmc;
        enum lacp;
        enum lldp;
        enum loam;
        enum pagp;
        enum ptppd;
        enum stp;
        enum udld;
        enum vtp;
        enum dot1x;
        enum mmrp;
        enum mvrp;
        enum mrpb;
        enum cbpdu;
        enum cstp;
        enum ccfm;
      }
    }
  }

  grouping config-ethernet-cfm-alarm-grouping-deprecated {
    leaf delay {
      status obsolete;
      description
        "msec (default 2500 msec)  (OBSOLETE)
         Please use delay leaf under alarm-config";
      type uint16 {
        range "2500..10000";
      }
    }
    container notification {
      status obsolete;
      description
        "CFM alarm notification";
      leaf all {
        status obsolete;
        description
          "Report all defects: DefRDI, DefMACStatus, DefRemote, DefError, DefXcon (OBSOLETE)
           Please use notification leaf under alarm-config";
        type empty;
      }
      leaf error-xcon {
        status obsolete;
        description
          "Report only: DefError and DefXcon (OBSOLETE)
           Please use notification leaf under alarm-config";
        type empty;
      }
      leaf mac-remote-error-xcon {
        status obsolete;
        description
          "Report only: DefMACStatus, DefRemote, DefError and DefXcon (default) (OBSOLETE)
           Please use notification leaf under alarm-config";
        type empty;
      }
      leaf none {
        status obsolete;
        description
          "No defects to be reported (OBSOLETE)
           Please use notification leaf under alarm-config";
        type empty;
      }
      leaf remote-error-xcon {
        status obsolete;
        description
          "Report only: DefRemote, DefError and DefXcon (OBSOLETE)
           Please use notification leaf under alarm-config";
        type empty;
      }
      leaf xcon {
        status obsolete;
        description
          "Report only: DefXcon (OBSOLETE)
           Please use notification leaf under alarm-config";
        type empty;
      }
    }
    leaf reset {
      status obsolete;
      description
        "msec (default 10000 msec) (OBSOLETE)
         Please use reset leaf under alarm-config";
      type uint16 {
        range "2500..10000";
      }
    }
  }

  grouping config-ecfm-domain-service-grouping {
    leaf port {
      description
        "DOWN service direction with no vlan association";
      type empty;
    }
    leaf evc {
      if-feature "ios-features:eth-evc";
      description
        "Specify EVC";
      type string;
    }
    leaf vlan {
      description
        "VLAN id";
      type uint16 {
        range "1..4094";
      }
    }
    leaf direction {
      description
        "Service direction- Down: Towards the LAN";
      type enumeration {
        enum down;
      }
    }
    container ais {
      description
        "AIS Maintenance Condition";
      leaf expiry-threshold {
        description
          "AIS Expiry Threshold";
        type uint8 {
          range "2..255";
        }
        default "3";
      }
      leaf level {
        description
          "Maintenance Level to send AIS";
        type uint8 {
          range "0..7";
        }
      }
      leaf period {
        description
          "AIS Transmission period";
        type enumeration {
          enum 1;
          enum 60;
        }
        default "60";
      }
      leaf suppress-alarms {
        description
          "Suppress Alarms";
        type empty;
      }
    }
    leaf cfm-continuity-check {
      description
        "Enable Continuity Check for Maintenance Association";
      type empty;
    }
    container continuity-check-conf {
      container continuity-check {
        description
          "Configure Continuity Check for MA";
        leaf interval {
          description
            "Interval Continuity Check messages transmitted";
          type enumeration {
            enum 100ms;
            enum 10m;
            enum 10ms;
            enum 10s;
            enum 1m;
            enum 1s;
            enum 3.3ms;
          }
          default "10s";
        }
        leaf loss-threshold {
          description
            "Specifies when a MEP is down or unreachable";
          type uint8 {
            range "2..255";
          }
          default "3";
        }
        container static {
          description
            "Verify MEP in received CCM is valid";
          leaf rmep {
            description
              "MEP defined using mep mpid";
            type empty;
          }
        }
      }
    }
    container continuity-check {
      status obsolete;
      description
        "OBSOLETE :Enable Continuity Check for Maintenance Association
         Please use cfm-continuity-check leaf and continuity-check-conf container";
      presence "true";
    }
    container efd {
      description
        "Ethernet Fault Detection";
      container notify {
        description
          "EFD Notification Registration";
        choice notify-choice {
          leaf g8032 {
            description
              "Notify G.8032 Controller of EFD events";
            type empty;
          }
          leaf rep {
            description
              "Notify REP Controller of EFD events";
            type empty;
          }
        }
      }
      leaf line-protocol {
        description
          "EFD line-protocol action";
        type empty;
      }
    }
    container lck {
      description
        "LCK Maintenance Condition";
      leaf expiry-threshold {
        description
          "LCK Expiry Threshold";
        type uint8 {
          range "2..255";
        }
        default "3";
      }
      leaf level {
        description
          "Maintenance Level to send LCK";
        type uint8 {
          range "0..7";
        }
      }
      leaf period {
        description
          "LCK Transmission period";
        type enumeration {
          enum 1;
          enum 60;
        }
        default "60";
      }
    }
    container maximum {
      description
        "Maximum MEPs allowed across network";
      leaf meps {
        description
          "Maximum meps";
        type uint16 {
          range "1..65535";
        }
        default "100";
      }
    }
    container mep {
      description
        "Static MEP within a Maintenance Association";
      when 'not (current()/../ios-eth:direction)';
      leaf mpid {
        description
          "Maintenance End Point Identifier";
        type uint16 {
          range "1..8191";
        }
      }
    }
    container mip {
      description
        "MIP commands";
      when 'not (current()/../ios-eth:direction)';
      container auto-create {
        description
          "Specify MIP auto creation policy";
        presence "true";
        choice mip-case {
          case lower-mep-case {
            leaf lower-mep-only {
              description
                "Create auto MIP only if lower MEP found";
              type empty;
            }
          }
          case none-case {
            leaf none {
              description
                "No MIP auto create";
              type empty;
            }
          }
        }
      }
    }
    container offload {
      description
        "Offload options";
      leaf sampling {
        description
          "Sampling rate";
        type uint16 {
          range "10..10000";
        }
      }
    }
    leaf sender-id {
      description
        "Include Sender ID TLV";
      type enumeration {
        enum chassis;
        enum none;
      }
    }
  }

  grouping config-ecfm-domain-service-number-grouping {
    container ais {
      description
        "AIS Maintenance Condition";
      leaf expiry-threshold {
        description
          "AIS Expiry Threshold";
        type uint8 {
          range "2..255";
        }
        default "3";
      }
      leaf level {
        description
          "Maintenance Level to send AIS";
        type uint8 {
          range "0..7";
        }
      }
      leaf period {
        description
          "AIS Transmission period";
        type enumeration {
          enum 1;
          enum 60;
        }
        default "60";
      }
      leaf suppress-alarms {
        description
          "Suppress Alarms";
        type boolean;
        default "true";
      }
    }
    leaf continuity-check {
      description
        "Enable Continuity Check for Maintenance Association";
      type empty;
    }
    container continuity-check-conf {
      container continuity-check {
        description
          "Configure Continuity Check for MA";
        leaf interval {
          description
            "Interval Continuity Check messages transmitted";
          type enumeration {
            enum 100ms;
            enum 10m;
            enum 10ms;
            enum 10s;
            enum 1m;
            enum 1s;
            enum 3.3ms;
          }
          default "10s";
        }
        leaf loss-threshold {
          description
            "Specifies when a MEP is down or unreachable";
          type uint8 {
            range "2..255";
          }
          default "3";
        }
        container static {
          description
            "Verify MEP in received CCM is valid";
          leaf rmep {
            description
              "MEP defined using mep mpid";
            type empty;
          }
        }
      }
    }
    container efd {
      description
        "Ethernet Fault Detection";
      leaf notify {
        description
          "EFD Notification Registration";
        type enumeration {
          enum g8032;
          enum rep;
        }
      }
      leaf line-protocol {
        description
          "EFD line-protocol action";
        type empty;
      }
    }
    leaf lck {
      description
        "LCK Maintenance Condition";
      type boolean;
      default "true";
    }
    container lck-conf {
      container lck {
        description
          "Configure LCK Maintenance Condition";
        leaf expiry-threshold {
          description
            "LCK Expiry Threshold";
          type uint8 {
            range "2..255";
          }
          default "3";
        }
        leaf level {
          description
            "Maintenance Level to send LCK";
          type uint8 {
            range "0..7";
          }
        }
        leaf period {
          description
            "LCK Transmission period";
          type enumeration {
            enum 1;
            enum 60;
          }
          default "60";
        }
      }
    }
    container maximum {
      description
        "Maximum MEPs allowed across network";
      leaf meps {
        description
          "Maximum meps";
        type uint16 {
          range "1..65535";
        }
        default "100";
      }
    }
    container mep {
      description
        "Static MEP within a Maintenance Association";
      when 'not ((../ios-eth:direction) or (../ios-eth:port))';
      leaf mpid {
        description
          "Maintenance End Point Identifier";
        type uint16 {
          range "1..8191";
        }
      }
    }
    container mip {
      description
        "MIP commands";
      when 'not ((../ios-eth:direction) or (../ios-eth:port))';
      container auto-create {
        description
          "Specify MIP auto creation policy";
        presence "true";
        leaf auto-create-type {
          type enumeration {
            enum lower-mep-only;
            enum none;
          }
        }
      }
    }
    container offload {
      description
        "Offload options";
      leaf sampling {
        description
          "Sampling rate";
        type uint16 {
          range "10..10000";
        }
      }
    }
    leaf sender-id {
      description
        "Include Sender ID TLV";
      type enumeration {
        enum chassis;
        enum none;
      }
    }
  }

  grouping config-interface-ethernet-cfm-grouping {
    container cfm {
      description
        "Ethernet cfm parameters";
      container ais {
        description
          "AIS Maintenance Condition";
        container link-status {
          description
            "8023ah SMEP or link status up/down transmission";
          leaf level {
            description
              "Maintenance Level";
            type uint8 {
              range "0..7";
            }
          }
          leaf period {
            description
              "AIS Transmission period in seconds";
            type enumeration {
              enum 1;
              enum 60;
            }
          }
        }
      }
      leaf interface {
        description
          "CFM interface enable";
        type empty;
      }
      container mep {
        description
          "Maintenance End Point";
        list domain {
          description
            "Domain list";
          key "name";
          leaf name {
            description
              "Configure a domain for this mep";
            must "((/ios:native/ios:ethernet/ios-eth:cfm/ios-eth:ieee)
                  and (/ios:native/ios:ethernet/ios-eth:cfm/ios-eth:domain[ios-eth:name=current()]))" {
              error-message "Preconfig for this Command is not completed yet";
            }
            type string;
          }
          list mpid {
            description
              "Maintenance End Point Identifier";
            key "mpid-number";
            leaf mpid-number {
              description
                "Maintenance End Point Identifier";
              type uint16 {
                range "1..8191";
              }
            }
            container service {
              description
                "Maintenance Association within Domain";
              choice service-type {
                list named-service {
                  description
                    "Service instance";
                  key "service-name";
                  leaf service-name {
                    description
                      "service instance id";
                    must '(/ios:native/ios:ethernet/ios-eth:cfm/ios-eth:domain/ios-eth:service[ios-eth:name=current()])' {
                      error-message "This service-instance is not created yet";
                    }
                    type string;
                  }
                  uses config-interface-srv-ecfm-mep-grouping;
                }
                list icc {
                  description
                    "ITU-T Y.1731 ICC-based MEG ID";
                  key "code";
                  leaf code {
                    description
                      "ITU Carrier Code (1-6 characters)";
                    type string;
                  }
                  leaf meg-id {
                    description
                      "Unique MEG ID Code (1-12 characters)";
                    type string;
                  }
                  uses config-interface-srv-ecfm-mep-grouping;
                }
                list number {
                  description
                    "Maintenance Association number value";
                  key "ma-num";
                  leaf ma-num {
                    type uint16 {
                      range "0..65535";
                    }
                  }
                  uses config-interface-srv-ecfm-mep-grouping;
                }
                list vlan-id {
                  description
                    "primary VLAN id";
                  key "vlan-num";
                  leaf vlan-num {
                    description
                      "primary VLAN id";
                    type uint16 {
                      range "1..4094";
                    }
                  }
                  uses config-interface-srv-ecfm-mep-grouping;
                }
                list vpn-id {
                  description
                    "vpn id";
                  key "vpn";
                  leaf vpn {
                    description
                      "vpn id";
                    type uint16 {
                      range "1..32767";
                    }
                  }
                  uses config-interface-srv-ecfm-mep-grouping;
                }
              }
            }
            leaf port {
              description
                "DOWN service direction with no vlan association";
              type empty;
            }
            leaf vlan {
              description
                "VLAN id";
              type uint16 {
                range "1..4094";
              }
            }
          }
        }
      }
      container mip {
        description
          "Maintenance Intermediate Point";
        list level {
          description
            "Maintenance Level";
          key "level-number";
          leaf level-number {
            description
              "maintenance level number";
            type uint8 {
              range "0..7";
            }
          }
          leaf vlan {
            description
              "VLAN id";
            type string;
          }
        }
      }
    }
    container uni {
      description
        "Configure Ether UNI";
      choice uni-choice {
        container bundle {
          description
            "bundling service without multiplexing";
          presence "true";
          leaf all-to-one {
            description
              "all-to-one bundling service";
            type empty;
          }
        }
        leaf multiplex {
          description
            "multiplexing service without bundling";
          type empty;
        }
      }
      leaf id {
        description
          "Configure Ether UNI ID";
        type string {
          length "1..64";
        }
      }
    }
  }

  grouping ext-etype-option-grouping {
    container ext-etype {
      description
        "payload ethertype after Vlan Field";
      leaf ipv4 {
        description
          "IPv4";
        type empty;
      }
      leaf ipv6 {
        description
          "IPv6";
        type empty;
      }
      leaf pppoe-all {
        description
          "PPPoE ALL";
        type empty;
      }
      leaf pppoe-discovery {
        description
          "PPPoE Discovery Stage";
        type empty;
      }
      leaf pppoe-session {
        description
          "PPPoE Session Stage";
        type empty;
      }
    }
  }

  grouping ethernet-cfm-untagged-encap-grouping {
    container untagged {
      description
        "Untagged encapsulation";
      presence "true";
      leaf comma {
        type enumeration {
          enum ,;
        }
      }
      container priority-tagged {
        description
          "Priority tagged EFP";
        presence "true";
        leaf comma {
          type enumeration {
            enum ,;
          }
        }
      }
      container dot1ad {
        description
          "802.1ad - Provider Bridges";
        leaf-list id {
          type union {
            type uint16 {
              range "1..4094";
            }
            type enumeration {
              enum any;
              enum ,;
              enum -;
            }
          }
        }
        leaf-list cos {
          description
            "CoS value to use for CFM packets";
          type uint8 {
            range "0..7";
          }
        }
        leaf-list dot1q {
          description
            "Second tag (dot1q)";
          type union {
            type uint16 {
              range "1..4094";
            }
            type enumeration {
              enum any;
              enum ,;
              enum -;
            }
          }
        }
        container cos2 {
          leaf-list cos {
            description
              "CoS value to use for CFM packets";
            type uint8 {
              range "0..7";
            }
          }
        }
        uses ext-etype-option-grouping;
        leaf exact {
          description
            "payload Ethertype does not include 802.1q/802.1ad Tags.";
          type empty;
        }
      }
      container dot1q {
        description
          "IEEE 802.1Q Virtual LAN or S-VLAN";
        leaf-list id {
          type union {
            type uint16 {
              range "1..4094";
            }
            type enumeration {
              enum any;
              enum ,;
              enum -;
            }
          }
        }
        leaf-list cos {
          description
            "cos Vlan";
          type uint8 {
            range "0..7";
          }
        }
        leaf-list second-dot1q {
          description
            "inner 802.1Q Virtual LAN or C-VLAN";
          type union {
            type uint16 {
              range "1..4094";
            }
            type enumeration {
              enum any;
              enum ,;
              enum -;
            }
          }
        }
        container cos2 {
          leaf-list cos {
            description
              "cos Vlan";
            type uint8 {
              range "0..7";
            }
          }
        }
        uses ext-etype-option-grouping;
        leaf exact {
          description
            "payload Ethertype does not include 802.1q/802.1ad Tags.";
          type empty;
        }
        leaf vlan-type {
          description
            "Vlan Protocol Type";
          type enumeration {
            enum 0x88A8;
            enum 0x9100;
            enum 0x9200;
          }
        }
      }
      uses ext-etype-option-grouping;
    }
  }

  grouping config-interface-ethernet-cfm-efp-grouping {
    container service {
      description
        "Configure Ether Service";
      list instance {
        description
          "Configure Ether Service Instance";
        key "id";
        leaf id {
          type uint32 {
            range "1..8000";
          }
        }
        leaf trunk {
          description
            "Trunk Service Instance";
          type empty;
        }
        leaf GigabitEthernet {
          description
            "Configure an GigabitEthernet Instance";
          type empty;
        }
        leaf ethernet {
          description
            "Configure an Ethernet Instance";
          type empty;
        }
        leaf ethernet-evc-name {
          if-feature "ios-features:eth-evc";
          type string;
        }
        leaf description {
          description
            "Service instance specific description";
          type string {
            length "0..240";
          }
        }
        leaf evc-name {
          type string {
            length "1..100";
          }
        }
        leaf track {
          description
            "Configure Service instance as Track client";
          type uint16 {
            range "1..32767";
          }
        }
        container encapsulation {
          description
            "Configure ethernet frame match criteria";
          leaf default {
            description
              "catch-all unconfigured encapsulation";
            type empty;
          }
          container dot1ad {
            description
              "802.1ad - Provider Bridges";
            leaf-list id {
              type union {
                type uint16 {
                  range "1..4094";
                }
                type enumeration {
                  enum any;
                }
                type string;
              }
            }
            leaf-list cos {
              description
                "CoS value to use for CFM packets";
              type uint8 {
                range "0..7";
              }
            }
            leaf-list dot1q {
              description
                "Second tag (dot1q)";
              type union {
                type uint16 {
                  range "1..4094";
                }
                type enumeration {
                  enum any;
                }
                type string;
              }
            }
            container cos2 {
              leaf-list cos {
                description
                  "CoS value to use for CFM packets";
                type uint8 {
                  range "0..7";
                }
              }
            }
            uses ext-etype-option-grouping;
            leaf ethertype {
              description
                "payload ethertype after Vlan Field";
              type union {
                type enumeration {
                  enum ipv4;
                  enum ipv6;
                  enum pppoe-all;
                  enum pppoe-discovery;
                  enum pppoe-session;
                }
                type string;
              }
            }
            leaf-list etype {
              description
                "payload ethertype after Vlan Field (OBSOLETE)
                 Please use ethertype";
              status obsolete;
              type enumeration {
                enum ipv4;
                enum ipv6;
                enum pppoe-all;
                enum pppoe-discovery;
                enum pppoe-session;
              }
            }
            leaf exact {
              description
                "payload Ethertype does not include 802.1q/802.1ad Tags.";
              type empty;
            }
          }
          container dot1q {
            description
              "IEEE 802.1Q Virtual LAN or S-VLAN";
            leaf-list id {
              type union {
                type uint16 {
                  range "1..4094";
                }
                type enumeration {
                  enum any;
                }
                type string;
              }
            }
            leaf-list cos {
              description
                "cos Vlan";
              type uint8 {
                range "0..7";
              }
            }
            leaf-list second-dot1q {
              description
                "inner 802.1Q Virtual LAN or C-VLAN";
              type union {
                type uint16 {
                  range "1..4094";
                }
                type enumeration {
                  enum any;
                }
                type string;
              }
            }
            container cos2 {
              leaf-list cos {
                description
                  "cos Vlan";
                type uint8 {
                  range "0..7";
                }
              }
            }
            uses ext-etype-option-grouping;
            leaf ethertype {
              description
                "payload ethertype after Vlan Field";
              type union {
                type enumeration {
                  enum ipv4;
                  enum ipv6;
                  enum pppoe-all;
                  enum pppoe-discovery;
                  enum pppoe-session;
                }
                type string;
              }
            }
            leaf-list etype {
              description
                "payload ethertype after Vlan Field (OBSOLETE)
                 Please use ethertype";
              status obsolete;
              type enumeration {
                enum ipv4;
                enum ipv6;
                enum pppoe-all;
                enum pppoe-discovery;
                enum pppoe-session;
              }
            }
            leaf exact {
              description
                "payload Ethertype does not include 802.1q/802.1ad Tags.";
              type empty;
            }
            leaf vlan-type {
              description
                "Vlan Protocol Type";
              type enumeration {
                enum 0x88A8;
                enum 0x9100;
                enum 0x9200;
              }
            }
          }
          container priority-tagged {
            description
              "Priority tagged EFP";
            presence "true";
            leaf-list cos {
              description
                "cos Vlan";
              type uint8 {
                range "0..7";
              }
            }
            uses ext-etype-option-grouping;
            leaf ethertype {
              description
                "payload ethertype after Vlan Field";
              type union {
                type enumeration {
                  enum ipv4;
                  enum ipv6;
                  enum pppoe-all;
                  enum pppoe-discovery;
                  enum pppoe-session;
                }
                type string;
              }
            }
            leaf-list etype {
              description
                "payload ethertype after Vlan Field (OBSOLETE)
                 Please use ethertype";
              status obsolete;
              type enumeration {
                enum ipv4;
                enum ipv6;
                enum pppoe-all;
                enum pppoe-discovery;
                enum pppoe-session;
              }
            }
          }
          uses ethernet-cfm-untagged-encap-grouping;
        }
        container ip {
          description
            "Interface Internet Protocol config commands";
          list access-group-list {
            description
              "Access control list for packets";
            key "direction";
            leaf direction {
              type enumeration {
                enum in;
                enum out;
              }
            }
            leaf access-list {
              type string;
            }
          }
          container acl {
            status obsolete;
            leaf access-group {
              status obsolete;
              description
                "OBSOLETE:Specify access control for packets";
              type ios-types:exp-acl-type;
            }
            leaf in {
              status obsolete;
              description
                "OBSOLETE:inbound packets";
              type empty;
            }
            leaf out {
              status obsolete;
              description
                "OBSOLETE:outbound packets";
              type empty;
            }
          }
          container dhcp {
            description
              "DHCP";
            container relay {
              description
                "DHCP relay";
              container information {
                description
                  "DHCP relay information";
                container option {
                  description
                    "DHCP relay information option";
                  leaf subscriber-id {
                    description
                      "DHCP relay information option subscriber-id";
                    type string;
                  }
                }
              }
            }
          }
          container verify {
            description
              "verify";
            leaf source {
              description
                "source address";
              type empty;
            }
            leaf vlan {
              description
                "vlan specification";
              type empty;
            }
            leaf dhcp-snooping {
              description
                "snooping enable vlan";
              type empty;
            }
            leaf port-security {
              description
                "port security";
              type empty;
            }
          }
        }
        container eapol {
          description
            "eapol";
          container destination-address {
            choice destination-type {
              description
                "Configure destination MAC address";
              leaf mac-address {
                description
                  "MAC address";
                type ios-types:cisco-mac-address-type;
              }
              leaf bridge-group-address {
                description
                  "Configure bridge group address";
                type empty;
              }
              leaf broadcast-address {
                description
                  "Configure broadcast MAC address";
                type empty;
              }
              leaf lldp-multicast-address {
                description
                  "Configure lldp multicast address";
                type empty;
              }
            }
          }
          container eth-type {
            description
              "Configure Ethernet Type for EAPOL frame";
            leaf eth-876F {
              description
                "Alternate Eth Value";
              type empty;
            }
          }
        }
        container storm-control {
          description
            "storm configuration";
          container broadcast {
            description
              "Broadcast address storm control";
            leaf cir {
              description
                "Committed Information Rate";
              type uint32 {
                range "8000..1000000000";
              }
            }
          }
          container multicast {
            description
              "Multicast address storm control";
            leaf cir {
              description
                "Committed Information Rate";
              type uint32 {
                range "8000..1000000000";
              }
            }
          }
          container unicast {
            description
              "Unknown unicast address storm control";
            leaf cir {
              description
                "Committed Information Rate";
              type uint32 {
                range "8000..1000000000";
              }
            }
          }
        }
        container ipv6 {
          description
            "IPv6 interface subcommands";
          list traffic-filter-list {
            description
              "Access control list for packets";
            key "direction";
            leaf direction {
              type enumeration {
                enum in;
                enum out;
              }
            }
            leaf access-list {
              type string;
            }
          }
          leaf traffic-filter {
            status obsolete;
            description
              "OBSOLETE:Access control list for packets";
            type string;
          }
          leaf in {
            status obsolete;
            description
              "OBSOLETE:inbound packets";
            type empty;
          }
          leaf out {
            status obsolete;
            description
              "OBSOLETE:outbound packets";
            type empty;
          }
        }
        container rewrite {
          description
            "Configure ethernet rewrite criteria";
          container ingress {
            description
              "Ingress Rewrite";
            container tag-config {
              description
                "Configure Rewrite Tag";
              choice rewrite-op {
                case pop-op {
                  container pop-op {
                    description
                      "Pop the tag";
                    must "(../../../../ios-eth:encapsulation/ios-eth:dot1q/ios-eth:id
                           or ../../../../ios-eth:encapsulation/ios-eth:default
                           or ../../../../ios-eth:encapsulation/ios-eth:dot1ad/ios-eth:id
                           or ../../../../ios-eth:encapsulation/ios-eth:priority-tagged
                           or ../../../../ios-eth:encapsulation/ios-eth:untagged)" {
                      error-message "Configure encapsulation before rewrite operation. Delete rewrite before removing encapsulation";
                    }
                    leaf way {
                      type enumeration {
                        enum 1;
                        enum 2;
                      }
                    }
                    leaf mode {
                      type enumeration {
                        enum symmetric;
                      }
                    }
                  }
                }
                case push-op {
                  container push-op {
                    description
                      "Rewrite Operation of push";
                    must "(../../../../ios-eth:encapsulation/ios-eth:dot1q/ios-eth:id
                           or ../../../../ios-eth:encapsulation/ios-eth:default
                           or ../../../../ios-eth:encapsulation/ios-eth:dot1ad/ios-eth:id
                           or ../../../../ios-eth:encapsulation/ios-eth:priority-tagged
                           or ../../../../ios-eth:encapsulation/ios-eth:untagged)" {
                      error-message "Configure encapsulation before rewrite operation. Delete rewrite before removing encapsulation";
                    }
                    leaf dot1ad {
                      description
                        "Push dot1ad tag";
                      type uint16 {
                        range "1..4094";
                      }
                    }
                    leaf dot1q {
                      description
                        "Push dot1q tag";
                      type uint16 {
                        range "1..4094";
                      }
                    }
                    leaf vlan-type {
                      description
                        "Vlan protocol type";
                      when 'not (../dot1ad)';
                      type enumeration {
                        enum 0x88A8;
                        enum 0x9100;
                        enum 0x9200;
                      }
                    }
                    leaf second-dot1q {
                      description
                        "Push second dot1q tag";
                      when 'not (../dot1ad)';
                      type uint16 {
                        range "1..4094";
                      }
                    }
                    leaf mode {
                      type enumeration {
                        enum symmetric;
                      }
                    }
                  }
                }
                case translate-op {
                  container translate-op {
                    description
                      "Translate Tag";
                    must "(../../../../ios-eth:encapsulation/ios-eth:dot1q/ios-eth:id
                           or ../../../../ios-eth:encapsulation/ios-eth:default
                           or ../../../../ios-eth:encapsulation/ios-eth:dot1ad/ios-eth:id
                           or ../../../../ios-eth:encapsulation/ios-eth:priority-tagged
                           or ../../../../ios-eth:encapsulation/ios-eth:untagged)" {
                      error-message "Configure encapsulation before rewrite operation. Delete rewrite before removing encapsulation";
                    }
                    choice translate-operation {
                      case t1-to-1 {
                        container t1-to-1 {
                          description
                            "Translate 1-to-1";
                          leaf dot1ad {
                            description
                              "Push dot1ad tag";
                            type uint16 {
                              range "1..4094";
                            }
                          }
                          leaf dot1q {
                            description
                              "Ethertype dot1q of the translation";
                            when 'not (../dot1ad)';
                            type uint16 {
                              range "1..4094";
                            }
                          }
                          leaf vlan-type {
                            description
                              "Vlan protocol type";
                            when 'not (../dot1ad)';
                            type enumeration {
                              enum 0x88A8;
                              enum 0x9100;
                              enum 0x9200;
                            }
                          }
                          leaf mode {
                            type enumeration {
                              enum symmetric;
                            }
                          }
                        }
                      }
                      case t1-to-2 {
                        container t1-to-2 {
                          description
                            "Translate 1-to-2";
                          leaf dot1ad {
                            description
                              "Push dot1ad tag";
                            type uint16 {
                              range "1..4094";
                            }
                          }
                          leaf dot1q {
                            description
                              "Translate ethertype of dot1q";
                            type uint16 {
                              range "1..4094";
                            }
                          }
                          leaf vlan-type {
                            description
                              "Vlan protocol type";
                            when 'not (../dot1ad)';
                            type enumeration {
                              enum 0x88A8;
                              enum 0x9100;
                              enum 0x9200;
                            }
                          }
                          leaf second-dot1q {
                            description
                              "Second dot1q tag";
                            when 'not (../dot1ad)';
                            type uint16 {
                              range "1..4094";
                            }
                          }
                          leaf mode {
                            type enumeration {
                              enum symmetric;
                            }
                          }
                        }
                      }
                      case t2-to-1 {
                        container t2-to-1 {
                          description
                            "Translate 2-to-1";
                          leaf dot1ad {
                            description
                              "Push dot1ad tag";
                            type uint16 {
                              range "1..4094";
                            }
                          }
                          leaf dot1q {
                            description
                              "Ethertype dot1q of the translation";
                            when 'not (../dot1ad)';
                            type uint16 {
                              range "1..4094";
                            }
                          }
                          leaf vlan-type {
                            description
                              "Vlan protocol type";
                            when 'not (../dot1ad)';
                            type enumeration {
                              enum 0x88A8;
                              enum 0x9100;
                              enum 0x9200;
                            }
                          }
                          leaf mode {
                            type enumeration {
                              enum symmetric;
                            }
                          }
                        }
                      }
                      case t2-to-2 {
                        container t2-to-2 {
                          description
                            "Translate 2-to-2";
                          leaf dot1ad {
                            description
                              "Push dot1ad tag";
                            type uint16 {
                              range "1..4094";
                            }
                          }
                          leaf dot1q {
                            description
                              "Translate ethertype of dot1q";
                            type uint16 {
                              range "1..4094";
                            }
                          }
                          leaf vlan-type {
                            description
                              "Vlan protocol type";
                            when 'not (../dot1ad)';
                            type enumeration {
                              enum 0x88A8;
                              enum 0x9100;
                              enum 0x9200;
                            }
                          }
                          leaf second-dot1q {
                            description
                              "Second dot1q tag";
                            when 'not (../dot1ad)';
                            type uint16 {
                              range "1..4094";
                            }
                          }
                          leaf mode {
                            type enumeration {
                              enum symmetric;
                            }
                          }
                        }
                      }
                    }
                  }
                }
              }
            }
            container tag {
              description
                "Configure Rewrite Tag (OBSOLETE)";
              status obsolete;
              container pop {
                description
                  "Pop the tag (OBSOLETE)";
                status obsolete;
                leaf way {
                  status obsolete;
                  type enumeration {
                    enum 1;
                    enum 2;
                  }
                }
                leaf mode {
                  status obsolete;
                  type enumeration {
                    enum symmetric;
                  }
                }
              }
              container push {
                description
                  "Rewrite Operation of push (OBSOLETE)";
                status obsolete;
                leaf dot1q {
                  description
                    "Push dot1q tag (OBSOLETE)";
                  status obsolete;
                  type uint16 {
                    range "1..4094";
                  }
                }
                leaf mode {
                  status obsolete;
                  type enumeration {
                    enum symmetric;
                  }
                }
              }
              container translate {
                description
                  "Translate Tag (OBSOLETE)";
                status obsolete;
                container t1-to-1 {
                  description
                    "Translate 1-to-1 (OBSOLETE)";
                  status obsolete;
                  leaf dot1q {
                    description
                      "Ethertype dot1q of the translation (OBSOLETE)";
                    status obsolete;
                    type uint16 {
                      range "1..4094";
                    }
                  }
                  leaf mode {
                    status obsolete;
                    type enumeration {
                      enum symmetric;
                    }
                  }
                }
                container t1-to-2 {
                  description
                    "Translate 1-to-2 (OBSOLETE)";
                  status obsolete;
                  leaf dot1q {
                    description
                      "Translate ethertype of dot1q (OBSOLETE)";
                    status obsolete;
                    type uint16 {
                      range "1..4094";
                    }
                  }
                  leaf second-dot1q {
                    description
                      "Second dot1q tag (OBSOLETE)";
                    status obsolete;
                    type uint16 {
                      range "1..4094";
                    }
                  }
                  leaf mode {
                    status obsolete;
                    type enumeration {
                      enum symmetric;
                    }
                  }
                }
                container t2-to-1 {
                  description
                    "Translate 2-to-1 (OBSOLETE)";
                  status obsolete;
                  leaf dot1q {
                    description
                      "Ethertype dot1q of the translation (OBSOLETE)";
                    status obsolete;
                    type uint16 {
                      range "1..4094";
                    }
                  }
                  leaf mode {
                    status obsolete;
                    type enumeration {
                      enum symmetric;
                    }
                  }
                }
                container t2-to-2 {
                  description
                    "Translate 2-to-2 (OBSOLETE)";
                  status obsolete;
                  leaf dot1q {
                    description
                      "Translate ethertype of dot1q (OBSOLETE)";
                    status obsolete;
                    type uint16 {
                      range "1..4094";
                    }
                  }
                  leaf second-dot1q {
                    description
                      "Second dot1q tag (OBSOLETE)";
                    status obsolete;
                    type uint16 {
                      range "1..4094";
                    }
                  }
                  leaf mode {
                    status obsolete;
                    type enumeration {
                      enum symmetric;
                    }
                  }
                }
              }
            }
          }
        }
        leaf group {
          type uint32;
        }
        container errdisable {
          description
            "Configure error disable";
          container recovery {
            description
              "enable auto recovery";
            container cause {
              description
                "error disable cause";
              leaf mac-security {
                description
                  "mac-security violation";
                type uint32 {
                  range "30..86400";
                }
              }
              leaf l2proto-tunnel {
                description
                  "l2 protocol-tunnel violation";
                type uint32 {
                  range "30..86400";
                }
              }
              leaf storm-control {
                description
                  "storm-control violation";
                type uint32 {
                  range "30..86400";
                }
              }
            }
          }
        }
        container ethernet-container {
          container ethernet {
            description
              "ethernet";
            container lmi {
              description
                "Configure ether lmi parameters";
              container ce-vlan {
                description
                  "Configure ether lmi customer vlans";
                container map {
                  description
                    "Configure ether lmi ce-vlan/evc map";
                  choice map-choice {
                    leaf any {
                      description
                        "For all VLANS [1-4094,untagged]";
                      type empty;
                    }
                    leaf default {
                      description
                        "Default EFP";
                      type empty;
                    }
                    leaf untagged {
                      description
                        "Untagged frames";
                      type empty;
                    }
                    leaf vlan-range {
                      type string {
                        pattern '(\d+(.*-.*\d+)?)(,.*\d+(.*-.*\d+)?)*(,.*untagged)?';
                      }
                    }
                  }
                }
              }
            }
            container loopback {
              description
                "Ethernet Dataplane Loopback";
              container permit {
                description
                  "Allow data plane loopback to be activated";
                leaf external {
                  description
                    "Allow to loopback the traffic from the wire";
                  type empty;
                }
                leaf internal {
                  description
                    "Allow to loopback the traffic from the relay";
                  type empty;
                }
              }
            }
          }
        }
        container snmp {
          description
            "Modify SNMP service instance parameters";
          container trap {
            description
              "Allow a specific SNMP trap";
            leaf link-status {
              description
                "Allow SNMP LINKUP and LINKDOWN traps";
              type empty;
            }
          }
          container ifindex-persistence {
            choice persistence {
              default "clear";
              leaf persist {
                type empty;
              }
              leaf clear {
                type empty;
              }
            }
          }
          container ifindex {
            status obsolete;
            description
              "Persist ifindex for the service instance (OBSOLETE)
               Please use ifindex-persistence";
            leaf persist {
              status obsolete;
              description
                "DEPRECATED: Enable/Disable ifIndex persistence(OBSOLETE)
                 Please use ifindex-persistence";
              type empty;
            }
          }
        }
        container bridge-domain {
          description
            "Bridge-domain";
          leaf bridge-id {
            type uint16 {
              range "0..16000";
            }
          }
          container split-horizon-presence {
            presence "true";
            description
              "Configure this port as a member of a split horizon group";
            leaf group {
              description
                "Split-horizon group";
              type uint8 {
                range "0..13";
              }
              default "0";
            }
          }
          container split-horizon {
            status obsolete;
            description
              "Configure this port as a member of a split horizon group, obsolete and replaced by split-horizon-presence";
            leaf group {
              status obsolete;
              description
                "Split-horizon group, obsolete and replaced by split-horizon-presence/group";
              type uint8 {
                range "0..13";
              }
            }
          }
          leaf from-encapsulation {
            description
              "from-encapsulation";
            type empty;
          }
        }
        container mac {
          description
            "Commands for MAC Address-based features";
          container security {
            description
              "MAC Security commands";
            presence "true";
            container address {
              description
                "MAC Address";
              list deny {
                description
                  "Specify an address that must not be learnt";
                key "mac";
                leaf mac {
                  description
                    "MAC address to deny";
                  type ios-types:cisco-mac-address-type;
                }
              }
              list permit {
                description
                  "Specify an address to statically configure in the MAC table";
                key "mac";
                leaf mac {
                  description
                    "MAC address to permit";
                  type ios-types:cisco-mac-address-type;
                }
              }
            }
            container aging {
              description
                "Specify aging controls for secured MAC addresses";
              leaf static {
                description
                  "Apply aging controls to statically configured addresses also";
                type empty;
              }
              leaf sticky {
                description
                  "Apply aging controls to persistent (\"sticky\") addresses also";
                type empty;
              }
              container time {
                description
                  "Configure aging time";
                must '(duration) or (not(duration) and not(inactivity))';
                leaf duration {
                  description
                    "Duration (in minutes) after which secured MAC addresses will be aged out";
                  type uint16 {
                    range "0..1440";
                  }
                }
                leaf inactivity {
                  description
                    "Calculate address age from time of last frame (not first frame)";
                  type empty;
                }
              }
            }
            container maximum {
              description
                "Configure an upper bound";
              leaf addresses {
                description
                  "Maximum addresses that can be learnt on this service instance";
                type uint16 {
                  range "1..1000";
                }
              }
            }
            leaf sticky {
              description
                "Make dynamically learnt MAC addresses persistent";
              type empty;
            }
            leaf violation {
              description
                "Configure the response when a MAC security policy is violated";
              type enumeration {
                enum protect;
                enum restrict;
              }
            }
          }
          list access-group {
            description
              "Specify access control for packets";
            key "acl-name";
            leaf acl-name {
              description
                "ACL name";
              type string;
            }
            leaf in {
              description
                "Apply to ingress";
              type empty;
            }
            leaf out {
              description
                "Apply to Egress";
              type empty;
            }
          }
        }
        container service-policy {
          description
            "Attach a policy-map to an EFP";
          list input {
            description
              "service policy input";
            key "name";
            leaf name {
              type string;
            }
          }
          list output {
            description
              "service policy output";
            key "name";
            leaf name {
              type string;
            }
          }
        }
        leaf shutdown {
          description
            "Take the Service Instance out of Service";
          type empty;
        }
        container cfm {
          description
            "Ethernet CFM EFP subcommands";
          container encapsulation {
            description
              "Configure CFM ethernet frame encapsulation";
            container dot1ad {
              description
                "802.1ad - Provider Bridges";
              leaf vlan-id {
                type uint16 {
                  range "1..4094";
                }
              }
              leaf cos {
                description
                  "CoS value to use for CFM packets";
                type uint8 {
                  range "0..7";
                }
              }
              leaf dot1q {
                description
                  "Second tag (dot1q)";
                type uint16 {
                  range "1..4094";
                }
              }
              container cos2 {
                leaf cos {
                  description
                    "CoS value to use for CFM packets";
                  type uint8 {
                    range "0..7";
                  }
                }
              }
            }
            container dot1q {
              description
                "IEEE 802.1Q Virtual LAN or S-VLAN";
              leaf vlan-id {
                type uint16 {
                  range "1..4094";
                }
              }
              leaf cos {
                description
                  "CoS value to use for CFM packets";
                type uint8 {
                  range "0..7";
                }
              }
              leaf second-dot1q {
                description
                  "inner 802.1Q Virtual LAN or C-VLAN";
                type uint16 {
                  range "1..4094";
                }
              }
              container cos2 {
                leaf cos {
                  description
                    "CoS value to use for CFM packets";
                  type uint8 {
                    range "0..7";
                  }
                }
              }
            }
          }
          container mep-list {
            description
              "Maintenance End Point";
            list domain {
              description
                "Domain list";
              key "name";
              leaf name {
                description
                  "Configure a domain for this mep";
                type string;
              }
              leaf mpid {
                description
                  "Maintenance End Point Identifier";
                type uint16 {
                  range "1..8191";
                }
                mandatory true;
              }
              leaf unicast {
                description
                  "Unicast CCM enabler";
                type empty;
              }
              leaf mac-address {
                description
                  "MAC Address";
                type ios-types:cisco-mac-address-type;
              }
              container alarm {
                description
                  "CFM Alarm";
                leaf delay {
                  description
                    "msec (default 2500 msec)";
                  type uint16 {
                    range "2500..10000";
                  }
                }
                leaf notification {
                  description
                    "CFM alarm notification";
                  type enumeration {
                    enum all;
                    enum error-xcon;
                    enum mac-remote-error-xcon;
                    enum none;
                    enum remote-error-xcon;
                    enum xcon;
                  }
                  default "none";
                }
                leaf reset {
                  description
                    "msec (default 10000 msec)";
                  type uint16 {
                    range "2500..10000";
                  }
                }
              }
              leaf cos {
                description
                  "Specify Class of Service sent in CFM messages for EFP MEP";
                type uint16 {
                  range "1..7";
                }
              }
              container continuity-check {
                description
                  "Configure Continuity Check for MA";
                container static {
                  description
                    "Verify MEP in received CCM is valid";
                  leaf rmep {
                    description
                      "MEP defined using mep mpid";
                    type empty;
                  }
                }
              }
              container rmep {
                description
                  "Static Remote MEP associated with this DOWN MEP";
                leaf mpid {
                  description
                    "Maintenance End Point Identifier";
                  type uint16 {
                    range "1..8191";
                  }
                }
              }
            }
          }
          container mep {
            description
              "Maintenance End Point (OBSOLETE)
               Please use mep-list";
            status obsolete;
            leaf domain {
              status obsolete;
              description
                "Configure a domain for this mep (OBSOLETE)
                 Please use domain node under mep-list";
              type string;
            }
            leaf mpid {
              status obsolete;
              description
                "Maintenance End Point Identifier (OBSOLETE)
                 Please use mpid node under mep-list";
              type uint16 {
                range "1..8191";
              }
            }
            container alarm {
              status obsolete;
              description
                "CFM Alarm (OBSOLETE)
                 Please use alarm node under mep-list";
              uses config-ethernet-cfm-alarm-grouping-deprecated;
            }
            leaf cos {
              status obsolete;
              description
                "Specify Class of Service sent in CFM messages for EFP MEP (OBSOLETE)
                 Please use cos node under mep-list";
              type uint16 {
                range "1..7";
              }
            }
            container continuity-check {
              status obsolete;
              description
                "Configure Continuity Check for MA (OBSOLETE)
                 Please use continuity-check node under mep-list";
              container static {
                description
                  "Verify MEP in received CCM is valid (OBSOLETE)
                   Please use static node under continuity-check";
                leaf rmep {
                  status obsolete;
                  description
                    "MEP defined using mep mpid (OBSOLETE)
                     Please use nodes in mep-list";
                  type empty;
                }
              }
            }
            container rmep {
              status obsolete;
              description
                "Static Remote MEP associated with this DOWN MEP (OBSOLETE)
                 Please use nodes in mep-list";
              leaf mpid {
                status obsolete;
                description
                  "Maintenance End Point Identifier (OBSOLETE)
                   Please use nodes in mep-list";
                type uint16 {
                  range "1..8191";
                }
              }
            }
          }
          container mip {
            description
              "Maintenance Intermediate Point";
            leaf level {
              description
                "Maintenance Level";
              type uint8 {
                range "0..7";
              }
            }
          }
          container latching-loopback {
            description
              "Ethernet CFM Latching Loopback";
            if-feature "ios-features:ecfm-llb";
            leaf domain {
              description
                "Domain-name";
              type string;
            }
            leaf responder {
              description
                "Latching-loopback responder";
              type empty;
            }
            container controller {
              description
                "Latching-loopback controller";
              leaf discover-interval {
                description
                  "Controller discover-interval";
                type uint8 {
                  range "1..10";
                }
                default "2";
              }
            }
          }
        }
        container l2protocol {
          description
            "Configure l2 control protocol processing";
          container discard {
            description
              "discard L2 control protocol packets as data";
            presence "true";
            uses config-interface-efp-l2protocol-grouping;
          }
          container peer {
            description
              "peer L2 control protocol packets as data";
            presence "true";
            uses config-interface-efp-l2protocol-grouping;
          }
          container forward {
            description
              "forward L2 control protocol packets as data";
            presence "true";
            uses config-interface-efp-l2protocol-grouping;
          }
          container tunnel {
            description
              "tunnel L2 control protocol packets as data";
            presence "true";
            uses config-interface-efp-l2protocol-grouping;
          }
        }
        container lldp {
          leaf enable {
            description
              "Enable LLDP on service instance";
            type empty;
          }
        }
      }
    }
  }

  grouping config-ethernet-cfm-efp-grouping {
    list evc {
      if-feature "ios-features:eth-evc";
      description
        "define an Ethernet virtual connection (EVC)";
      key "name";
      leaf name {
        type string {
          length "1..100";
        }
      }
      container oam {
        description
          "OAM Protocol";
        container protocol {
          description
            "Protocol for EVC status reporting";
          choice protocol-type {
            container cfm {
              description
                "Protocol CFM";
              leaf domain {
                description
                  "domain name";
                type string;
              }
            }
            leaf ldp {
              description
                "Protocol LDP";
              type empty;
            }
          }
        }
      }
      container uni {
        description
          "Configure UNI Count for EVC";
        leaf count {
          description
            "UNI Count required, range 2 - 1024";
          type uint16 {
            range "2..1024";
          }
          default "2";
        }
      }
    }
    container cfm {
      description
        "Connectivity Fault Management";
      container ais {
        description
          "AIS Maintenance Condition";
        container link-status {
          description
            "8023ah SMEP or link state up/down";
          container global {
            description
              "8023ah SMEP or link state state up/down AIS global configuration";
            presence "true";
            container cfm-Mode__config-ais-link-cfm {
              leaf disable {
                description
                  "Disable AIS transmission";
                type empty;
              }
              leaf level {
                description
                  "Maintenance Level";
                type uint8 {
                  range "0..7";
                }
              }
              leaf ais-period {
                description
                  "AIS Transmission period in seconds";
                type enumeration {
                  enum 1;
                  enum 60;
                }
              }
              container period {
                status obsolete;
                description
                  "AIS Transmission period (OBSOLETE)
                   Please use ais-period";
                leaf tp-1 {
                  status obsolete;
                  description
                    "Seconds (OBSOLETE)
                     Please use ais-period";
                  type empty;
                }
                leaf tp-60 {
                  status obsolete;
                  description
                    "Seconds (OBSOLETE)
                     Please use ais-period";
                  type empty;
                }
              }
            }
          }
        }
      }
      container alarm-config {
        description
          "CFM Alarm";
        leaf delay {
          description
            "msec (default 2500 msec)";
          type uint16 {
            range "2500..10000";
          }
          default "2500";
        }
        leaf notification {
          description
            "CFM alarm notification";
          type enumeration {
            enum all;
            enum error-xcon;
            enum mac-remote-error-xcon;
            enum none;
            enum remote-error-xcon;
            enum xcon;
          }
        }
        leaf reset {
          description
            "msec (default 10000 msec)";
          type uint16 {
            range "2500..10000";
          }
          default "10000";
        }
        leaf packet {
          description
            "max DefError and DefXcon packets";
          type uint16 {
            range "1..65535";
          }
        }
      }
      container alarm {
        status obsolete;
        description
          "CFM Alarm (OBSOLETE)
           Please use alarm-config";
        uses config-ethernet-cfm-alarm-grouping-deprecated;
        leaf packet {
          status obsolete;
          description
            "max DefError and DefXcon packets (OBSOLETE)
             Please use alarm-config/packet";
          type uint16 {
            range "1..65535";
          }
        }
      }
      leaf ieee {
        description
          "CFM IEEE enable";
        type empty;
      }
      leaf global {
        description
          "CFM global enable";
        type empty;
      }
      list domain {
        description
          "Configure a domain";
        key "name";
        leaf name {
          description
            "Domain Name";
          type string;
        }
        leaf level {
          description
            "Maintenance Level";
          type uint8 {
            range "0..7";
          }
        }
        list service {
          description
            "Maintenance Association within Domain";
          key "name";
          leaf name {
            type string;
          }
          uses config-ecfm-domain-service-grouping;
        }
        container service-vlan {
          list service-vlan {
            description
              "Maintenance Association within Domain";
            key "id";
            leaf id {
              type uint16 {
                range "1..4094";
              }
            }
            leaf vlan-id {
              description
                "VLAN Identifier";
              type empty;
            }
            uses config-ecfm-domain-service-grouping;
          }
        }
        container service-number {
          list service-number {
            description
              "Maintenance Association within Domain";
            key "id";
            leaf id {
              type uint16 {
                range "0..65535";
              }
            }
            leaf number {
              description
                "number Identifier";
              type empty;
            }
            leaf port {
              description
                "DOWN service direction with no vlan association";
              type empty;
            }
            leaf evc {
              if-feature "ios-features:eth-evc";
              description
                "Specify EVC";
              type string;
            }
            leaf vlan {
              description
                "VLAN id";
              type uint16 {
                range "1..4094";
              }
            }
            leaf direction {
              description
                "Service direction- Down: Towards the LAN";
              type enumeration {
                enum down;
              }
            }
            uses config-ecfm-domain-service-number-grouping;
          }
        }
        container service-vpn {
          list service-vpn {
            description
              "Maintenance Association within Domain";
            key "id";
            leaf id {
              type uint16 {
                range "1..32767";
              }
            }
            leaf vpn-id {
              description
                "VPN Identifier";
              type empty;
            }
            uses config-ecfm-domain-service-grouping;
          }
        }
        container service-icc {
          list service-icc {
            description
              "Maintenance Association within Domain";
            key "icc-code megid";
            leaf icc-code {
              type string;
            }
            leaf megid {
              type string;
            }
            leaf icc {
              description
                "VLAN Identifier";
              type empty;
            }
            uses config-ecfm-domain-service-grouping;
          }
        }
        container mep {
          description
            "Maintenance End Point commands";
          leaf archive-hold-time {
            description
              "Time in minutes for entry to be retained";
            type uint16 {
              range "1..65535";
            }
          }
          leaf ccm-fastage {
            description
              "Enable/Disable CCM learning database fast-age";
            type enumeration {
              enum enable;
            }
          }
          leaf ccm-hold-time {
            description
              "Time in hours for CCM entry to be retained";
            type uint16 {
              range "1..48";
            }
            default "24";
            units "hours";
          }
        }
        container id {
          description
            "Maintenance Domain Identifier";
          choice id-type {
            leaf dns {
              description
                "DNS Name based string (max 43 chars)";
              type string;
            }
            leaf null {
              description
                "Null ID";
              type empty;
            }
            container mac-id {
              description
                "Mac Address based id";
              leaf mac-address {
                description
                  "MAC Address";
                type ios-types:cisco-mac-address-type;
              }
              leaf id {
                description
                  "Domain number";
                type uint16 {
                  range "1..65535";
                }
              }
            }
          }
        }
        container mip-config {
          description
            "MIP configuration for Domain";
          container auto-create {
            description
              "Enable auto MIP creation at Domain Level";
            presence "true";
            leaf lower-mep-only {
              description
                "Only for lower MEPs";
              type empty;
            }
          }
        }
        leaf mip {
          description
            "MIP configuration for Domain (OBSOLETE)
             Please use mip-config container";
          status obsolete;
          type enumeration {
            enum auto-create;
          }
        }
        leaf sender-id {
          description
            "Include Sender ID TLV";
          type enumeration {
            enum chassis;
          }
        }
      }
      container logging {
        description
          "Enable CFM syslog messages";
        presence "true";
        leaf ais {
          description
            "AIS logging";
          type empty;
        }
        container alarm {
          description
            "Alarm logging";
          leaf cisco {
            description
              "Cisco MIB syslogs";
            type empty;
          }
          leaf ieee {
            description
              "IEEE MIB syslogs";
            type empty;
          }
        }
        leaf lck {
          description
            "LCK logging";
          type empty;
        }
      }
      container mep {
        description
          "Maintenance End Point";
        container crosscheck {
          description
            "Cross Check remote MEPs";
          leaf start-delay {
            description
              "seconds (30 seconds default)";
            type uint16 {
              range "1..65535";
            }
          }
        }
      }
      container mip {
        description
          "CFM MIP commands";
        container auto-create {
          description
            "CFM MIP auto creation";
          container level-config {
            description
              "Maintenance Level";
            list mip-vlan {
              key "vlan";
              leaf mef-num {
                description
                  "maintenance level number";
                type uint8 {
                  range "0..7";
                }
              }
              leaf vlan {
                description
                  "VLAN Id";
                type uint16 {
                  range "1..4094";
                }
              }
              leaf lower-mep-only {
                description
                  "Create MIP only if MEP at next lower MD level";
                type empty;
              }
              leaf sender-id {
                description
                  "Include Sender ID TLV";
                type enumeration {
                  enum chassis;
                }
              }
            }
            list mip-evc {
              key "evc";
              leaf mef-num {
                description
                  "maintenance level number";
                type uint8 {
                  range "0..7";
                }
              }
              leaf evc {
                description
                  "EVC name";
                type string;
              }
              leaf lower-mep-only {
                description
                  "Create MIP only if MEP at next lower MD level";
                type empty;
              }
              leaf sender-id {
                description
                  "Include Sender ID TLV";
                type enumeration {
                  enum chassis;
                }
              }
            }
          }
          container mip-level {
            status obsolete;
            description
              "Maintenance Level (OBSOLETE)";
            list mip-vlan {
              status obsolete;
              key "mef-num";
              leaf mef-num {
                status obsolete;
                description
                  "maintenance level number (OBSOLETE)";
                type uint8 {
                  range "0..7";
                }
              }
              leaf-list vlan {
                status obsolete;
                description
                  "VLAN Id or List of VLAN IDs in the form a-b,c,d,e-f,g (OBSOLETE)";
                type uint16 {
                  range "1..4094";
                }
                min-elements 1;
              }
            }
            list mip-evc {
              status obsolete;
              key "mef-num evc";
              leaf mef-num {
                status obsolete;
                description
                  "maintenance level number (OBSOLETE)";
                type uint8 {
                  range "0..7";
                }
              }
              leaf evc {
                status obsolete;
                description
                  "EVC name (OBSOLETE)";
                type string;
              }
            }
          }
          container level {
            status obsolete;
            description
              "Maintenance Level (OBSOLETE)
               Please use level-config container";
            list mef-num {
              status obsolete;
              key "mef-num";
              leaf mef-num {
                status obsolete;
                description
                  "maintenance level number (OBSOLETE)
                   Please use level-config container";
                type uint8 {
                  range "0..7";
                }
              }
              leaf evc {
                status obsolete;
                description
                  "EVC name (OBSOLETE)
                   Please use level-config/mip-evc node";
                type string;
              }
              leaf vlan {
                status obsolete;
                description
                  "VLAN id (OBSOLETE)
                   Please use level-config/mip-vlan node";
                type uint16 {
                  range "1..4094";
                }
              }
            }
          }
        }
        leaf filter {
          description
            "CFM MIP filter";
          type empty;
        }
      }
      container lck {
        description
          "LCK Maintenance Condition";
        container link-status {
          description
            "8023ah SMEP or link state up/down";
          container global {
            description
              "8023ah SMEP or link state state up/down AIS global configuration";
            presence "true";
            leaf disable {
              description
                "Disable LCK transmission";
              type empty;
            }
            leaf level {
              description
                "Maintenance Level to send LCK";
              type uint8 {
                range "0..7";
              }
            }
            leaf period {
              description
                "LCK Transmission period";
              type enumeration {
                enum 1;
                enum 60;
              }
            }
          }
        }
      }
      container slm {
        description
          "Synthetic Loss Measurement";
        container max {
          description
            "Maximum SLM Responder session";
          leaf value {
            description
              "SLM Responder session";
            type uint16 {
              range "100..32000";
            }
          }
        }
        container timeout {
          description
            "Maximum session";
          leaf value {
            description
              "SLM Responder session idle timeout in minute";
            type uint16 {
              range "5..2400";
            }
          }
        }
      }
      container traceroute {
        description
          "CFM Traceroute";
        container cache {
          description
            "CFM Traceroute Cache";
          presence "true";
          leaf hold-time {
            description
              "minutes (default 100)";
            type uint16 {
              range "1..65535";
            }
          }
          leaf size {
            description
              "Number of cached lines (default 100)";
            type uint16 {
              range "1..4095";
            }
          }
        }
      }
    }
  }
}
