module Cisco-IOS-XE-ipv6-nd-oper {
  yang-version 1.1;
  namespace "http://cisco.com/ns/yang/Cisco-IOS-XE-ipv6-nd-oper";
  prefix ipv6-nd-ios-xe-oper;

  import Cisco-IOS-XE-common-types {
    prefix common-types-ios-xe;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for IPv6 ND operational data. Compared to other model
     Cisco-IOS-XE-ipv6-oper, this model supports high scale queries
     and on-change telemetry subscriptions.
     Copyright (c) 2025 by Cisco Systems, Inc.
     All rights reserved.";

  revision 2025-07-01 {
    description
      "Initial revision";
    reference
      "1.0.0";
    cisco-semver:module-version "1.0.0";
  }

  typedef ipv6-nd-en-state {
    type enumeration {
      enum v6-nd-st-incomplete {
        value 0;
        description
          "Address resolution is in progress and the
           link-layer address of the neighbor has not
           yet been determined.";
      }
      enum v6-nd-st-reachable {
        value 1;
        description
          "The neighbor is known to have been reachable
           recently (within tens of seconds ago).";
      }
      enum v6-nd-st-stale {
        value 2;
        description
          "The neighbor is no longer known to be reachable
           but until traffic is sent to the neighbor, no
           attempt should be made to verify its reachability";
      }
      enum v6-nd-st-glean {
        value 3;
        description
          "Received neighbor messages containing link layer information.
           Based on this information, entry is created. In this case, there
           is no initiation of active neighbor resolution from current node";
      }
      enum v6-nd-st-delay {
        value 4;
        description
          "The neighbor is no longer known to be reachable, and traffic
           has recently been sent to the neighbor. Rather than probe the
           neighbor immediately, however, delay sending probes for a short
           while in order to give upper layer protocols a chance to provide
           reachability confirmation.";
      }
      enum v6-nd-st-probe {
        value 5;
        description
          "The neighbor is no longer known to be reachable, and unicast
           Neighbor Solicitation probes are being sent to verify
           reachability.";
      }
    }
    description
      "Indicate the current state of
       the Neighbor-Discovery entry.";
  }

  typedef ipv6-nd-mode {
    type enumeration {
      enum v6-nd-mode-static {
        value 0;
        description
          "Static Neighbor-Discovery entry";
      }
      enum v6-nd-mode-dyn {
        value 1;
        description
          "Entry has been learned dynamically";
      }
      enum v6-nd-mode-other {
        value 2;
        description
          "Other entry";
      }
    }
    description
      "The mode that this entry is running in";
  }

  grouping ipv6-nd-entry-key {
    description
      "Key for IPv6 Neighbour entry";
    leaf v6addr {
      type inet:ipv6-address;
      description
        "IPv6 address of this neighbor entry";
    }
    leaf if-name {
      type string;
      description
        "Interface associated with this IPv6 Neighbor-Discovery entry";
    }
  }

  grouping ipv6-nd-entry {
    description
      "Value for IPv6 neighbor table entry";
    leaf mac-addr {
      type yang:mac-address;
      description
        "MAC address of this neighbor entry";
    }
    leaf mode {
      type ipv6-nd-ios-xe-oper:ipv6-nd-mode;
      description
        "The mode that this entry is running in";
    }
    leaf state {
      type ipv6-nd-ios-xe-oper:ipv6-nd-en-state;
      description
        "Neighboring state of this entry";
    }
    leaf update-time {
      type yang:date-and-time;
      description
        "Update time of IPv6 Neighbour entry";
    }
    leaf is-router {
      type boolean;
      description
        "The device is router or not";
    }
  }

  grouping ni-ipv6-nd {
    description
      "IPv6 Neighbour Table Parent Network Instance";
    leaf ni-name {
      type string;
      description
        "Network Instance name that the IPv6 Neighbour table entries are tied to";
    }
    leaf ni-type {
      type common-types-ios-xe:net-inst-type;
      description
        "Network Instance type that the IPv6 Neighbour table entries are tied to";
    }
    list ipv6-nd-entry {
      key "v6addr if-name";
      description
        "List of IPv6 Neighbour entries associated with this Network Instance";
      uses ipv6-nd-ios-xe-oper:ipv6-nd-entry-key;
      uses ipv6-nd-ios-xe-oper:ipv6-nd-entry;
    }
  }

  container ipv6-nd-oper-data {
    config false;
    description
      "This module contains a collection of YANG definitions for
       monitoring the operation of IOS-XE IPv6 Neighbour.
       Copyright (c) 2025 by Cisco Systems, Inc.
       All rights reserved.";
    list ni-ipv6-nd {
      key "ni-name";
      description
        "List of Network Instances with IPv6 Neighbour table entries";
      uses ipv6-nd-ios-xe-oper:ni-ipv6-nd;
    }
  }
}
