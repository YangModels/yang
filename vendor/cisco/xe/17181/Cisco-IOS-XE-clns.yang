module Cisco-IOS-XE-clns {
  yang-version 1.1;
  namespace "http://cisco.com/ns/yang/Cisco-IOS-XE-clns";
  prefix ios-clns;

  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native CLNS Yang model.
     Copyright (c) 2023 by Cisco Systems, Inc.
     All rights reserved.";

  revision 2024-07-01 {
    description
      "- Initial version";
  }

  grouping config-clns-main-grouping {
    container cache-invalidate-delay {
      description
        "Delay-time configuration for CLNS route cache invalidation";
      presence "true";
      leaf min-delay {
        description
          "Minimum delay in seconds";
        default "2";
        type uint32 {
          range "0 .. 300";
        }
      }
      leaf max-delay {
        description
          "Maximum delay in seconds";
        default "5";
        type uint32 {
          range "0 .. 300";
        }
      }
      leaf quiet-interval {
        description
          "Quiet interval in seconds";
        default "3";
        type uint32 {
          range "1 .. 600";
        }
      }
      leaf quiet-threshold {
        description
          "Invalidation request quiet threshold, number of requests within quiet-interval";
        default "0";
        type uint32 {
          range "0 .. 4294967295";
        }
      }
    }
    leaf packet-rate {
      description
        "Rate at which ESH and ISH packets are sent per second";
      default "1";
      type uint32 {
        range "1 .. 65535";
      }
    }
    leaf holding-time {
      description
        "Holdtime in seconds advertised in ESH/ISH PDUs";
      default "1";
      type uint32 {
        range "1 .. 65535";
      }
    }
    leaf packet-lifetime {
      description
        "Initial lifetime in seconds for locally generated packets";
      default "64";
      type uint32 {
        range "1 .. 255";
      }
    }
    leaf queue-depth {
      description
        "CLNS queue depth, number of packets CLNS can hold and process";
      default "100";
      type uint32 {
        range "1 .. 2147483647";
      }
    }
    container security {
      leaf pass-through {
        description
          "Set security option";
        type empty;
      }
    }
    leaf routing {
      description
        "Enable CLNS routing";
      type empty;
    }
    leaf want-erpdu {
      description
        "Request error PDUs on packets sourced by router";
      default "true";
      type boolean;
    }
  }

  augment "/ios:native/ios:clns" {
    uses config-clns-main-grouping;
  }
}
