module Cisco-IOS-XE-aws-common-oper {
  yang-version 1.1;
  namespace "http://cisco.com/ns/yang/Cisco-IOS-XE-aws-common-oper";
  prefix aws-common-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for AWS S3/cloudwatch common operational data.
     Copyright (c) 2023-2025 by Cisco Systems, Inc.
     All rights reserved.";

  revision 2025-07-01 {
    description
      "Initial revision";
    reference
      "1.0.0";
    cisco-semver:module-version "1.0.0";
  }

  typedef aws-agent-state {
    type enumeration {
      enum aws-agent-state-stopped {
        value 0;
        description
          "AWS agent state : Stopped";
      }
      enum aws-agent-state-active {
        value 1;
        description
          "AWS agent state : Active";
      }
      enum aws-agent-state-inactive {
        value 2;
        description
          "AWS agent state : Inactive";
      }
    }
    description
      "AWS agent state";
  }

  typedef aws-agent-trace {
    type enumeration {
      enum aws-agent-trace-notice {
        value 0;
        description
          "AWS agent trace level : Notice";
      }
      enum aws-agent-trace-debug {
        value 1;
        description
          "AWS agent trace level : Debug";
      }
      enum aws-agent-trace-emerg {
        value 2;
        description
          "AWS agent trace level : Emergency";
      }
      enum aws-agent-trace-err {
        value 3;
        description
          "AWS agent trace level : Error";
      }
      enum aws-agent-trace-info {
        value 4;
        description
          "AWS agent trace level : Info";
      }
      enum aws-agent-trace-noise {
        value 5;
        description
          "AWS agent trace level : Noise";
      }
      enum aws-agent-trace-verbose {
        value 6;
        description
          "AWS agent trace level : Verbose";
      }
      enum aws-agent-trace-warning {
        value 7;
        description
          "AWS agent trace level : warning";
      }
    }
    description
      "AWS agent trace level";
  }

  typedef aws-vrf-name {
    type enumeration {
      enum aws-mgmt-vrf {
        value 0;
        description
          "Management VRF";
      }
      enum aws-global-vrf {
        value 1;
        description
          "Global VRF";
      }
    }
    description
      "AWS VRF Type";
  }

  grouping aws-proxy-config {
    description
      "AWS proxy configuration";
    leaf http-url {
      type string;
      description
        "HTTP URL";
    }
    leaf http-port {
      type uint16;
      description
        "HTTP port";
    }
    leaf https-url {
      type string;
      description
        "HTTPS URL";
    }
    leaf https-port {
      type uint16;
      description
        "HTTPS port";
    }
  }
}
