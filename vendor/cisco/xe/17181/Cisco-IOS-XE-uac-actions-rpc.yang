module Cisco-IOS-XE-uac-actions-rpc {
  yang-version 1.1;
  namespace "http://cisco.com/ns/yang/Cisco-IOS-XE-uac-actions-rpc";
  prefix uac-actions-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for uplink auto config RPC action data.
     Copyright (c) 2025 by Cisco Systems, Inc.
     All rights reserved.";

  revision 2025-07-01 {
    description
      "Initial revision";
    reference
      "1.0.0";
    cisco-semver:module-version "1.0.0";
  }

  typedef uplink-ip-type {
    type enumeration {
      enum uplink-ipv4 {
        value 0;
        description
          "IPv4 uplink";
      }
      enum uplink-ipv6 {
        value 1;
        description
          "IPv6 uplink";
      }
      enum uplink-both {
        value 2;
        description
          "IPv4 uplink and IPv6 uplink";
      }
    }
    description
      "Uplink IP type";
  }

  grouping prefer-uplink {
    description
      "The user configures the preferred uplink for the device to connect to the dashboard";
    leaf ip-type {
      type uac-actions-rpc:uplink-ip-type;
      mandatory true;
      description
        "Type of IP uplink";
    }
  }

  rpc uac-prefer-uplink {
    description
      "In case the preferred uplink interface is down, device auto-selects a non-preferred
       interface for uplink. Once the preferred uplink interface is brought up, this RPC
       can be used to force the device to check cloud connectivity via preferred uplink
       interface and select it for uplink";
    input {
      uses uac-actions-rpc:prefer-uplink;
    }
  }
}
