submodule Cisco-IOS-XE-voice-register {
  yang-version 1.1;
  belongs-to Cisco-IOS-XE-voice {
    prefix ios-voice;
  }

  import Cisco-IOS-XE-native {
    prefix ios;
  }
  import cisco-semver {
    prefix cisco-semver;
  }
  import ietf-inet-types {
    prefix inet;
  }
  import Cisco-IOS-XE-types {
    prefix ios-types;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Voice Register Yang model.
     Copyright (c) 2019-2020 by Cisco Systems, Inc.
     All rights reserved.";

  revision 2024-07-01 {
    description
      "- Added transport-tcp-tls to call manager fallback";
    cisco-semver:module-version "3.5.0";
  }
  revision 2024-03-01 {
    description
      "Converted absolute xpath to relative xpath";
    cisco-semver:module-version "3.4.0";
  }
  revision 2022-11-01 {
    description
      "- Update yang-version to 1.1
       - Added security-policy to voice register global
       - Added translation-profile to voice register pool
       - Added voice-class srtp-crypto to voice register pool";
    cisco-semver:module-version "3.3.0";
  }
  revision 2021-11-01 {
    description
      "- Modified the model to conform to yang 1.1 standard";
    cisco-semver:module-version "3.2.0";
  }
  revision 2021-07-01 {
    description
      "- Modified noan leaf to handle the no form properly
       - Added cor incoming/outgoing under voice register pool";
    cisco-semver:module-version "3.1.0";
  }
  revision 2020-07-01 {
    description
      "- Added dependency of pool configuration on global and max-pool configurations
       - Adding tailf flag to the global container to avoid removing its configuration before pool list
       - Increasing the range for configuring max-pool to 2500";
    cisco-semver:module-version "3.0.0";
  }
  revision 2020-03-01 {
    description
      "- Removed statement mandatory for leaves";
    cisco-semver:module-version "2.1.0";
  }
  revision 2019-11-01 {
    description
      "- Added call-forward All, Busy, Mailbox and noan
       - Added statement mandatory for leaves";
    cisco-semver:module-version "2.0.0";
  }
  revision 2019-07-01 {
    description
      "Establish semantic version baseline";
    cisco-semver:module-version "1.0.0";
  }

  typedef config-voice-register-corlist-tag {
    type union {
      type uint8 {
        range "1..20";
      }
      type enumeration {
        enum default;
      }
    }
  }

  typedef config-e164-number {
    type string {
      length "1..32";
      pattern '((((\^)(\+))?([0-9,#*A-F])*T?)($)?)' {
        error-message
          "Incorrect format for E.164 Number: regular expression
                                  must be of the form (((\\^)(\\+))?([0-9,#*A-F])*T?)($)?";
      }
    }
  }

  grouping config-voice-register-pool-cor {
    leaf name {
      description
        "cor list name";
      type leafref {
        path "../../../../../../../ios:native/ios-voice:dial-peer/ios-voice:cor/ios-voice:list/id";
      }
    }
    leaf lowerbound {
      description
        "cor list matched number or lower bound number";
      when "../id != 'default'";
      type config-e164-number;
    }
    leaf hyphen {
      description
        "number range";
      when '../lowerbound';
      type enumeration {
        enum -;
      }
    }
    leaf upperbound {
      description
        "cor list matched number or lower bound number";
      when '../hyphen';
      type config-e164-number;
    }
  }

  grouping config-voice-register-grouping {
    container register {
      description
        "voice register commands";
      container global {
        description
          "Define global commands";
        presence "true";
        leaf max-dn {
          description
            "Maximum directory numbers supported";
          type uint32 {
            range "1..3500";
          }
        }
        leaf max-pool {
          description
            "Maximum pools to support";
          type uint16 {
            range "1..2500";
          }
        }
        container system {
          description
            "Define system message";
          leaf message {
            description
              "Define system message";
            type string {
              length "1..32";
            }
          }
        }
        container security-policy {
          description
            "Configure SIP registration security policy";
          leaf secure {
            description
              "Only SIP TLS registration allowed";
            type boolean;
            default "false";
          }
        }
      }
      list pool {
        description
          "voice-register-pool tag";
        when '../global and ../global/max-pool';
        key "pool-tag";
        leaf pool-tag {
          description
            "voice register pool commands";
          must '. <= ../../global/max-pool' {
            error-message "pool-tag cannot exceed max-pool value set under voice register global";
          }
          type uint16 {
            range "1..2500";
          }
        }
        container id {
          description
            "define phone or device id";
          container network {
            description
              "define phone or device network address";
            choice ipaddress {
              case ipv4 {
                container ipv4address {
                  leaf address {
                    description
                      "IPv4 Address";
                    type inet:ipv4-address;
                  }
                  leaf mask {
                    description
                      "IPv4 Address Mask";
                    type inet:ipv4-address;
                  }
                }
              }
              case ipv6 {
                leaf ippv6 {
                  description
                    "IPv6 network and mask";
                  type ios-types:ipv6-prefix;
                }
              }
            }
          }
        }
        container call-forward {
          description
            "Define E.164 telephone number for call forward";
          container b2bua {
            description
              "Define call forward for B2BUA (back-to-back user agent)";
            leaf all {
              description
                "forward all calls";
              type string {
                pattern '([0-9,A-F#*.?+%()-]*T?)' {
                  error-message "Incorrect format for E.164 Number: regular expression must be of the form  [0-9,A-F#*.?+%()-]*T?";
                }
              }
            }
            leaf busy {
              description
                "forward call on busy";
              type string {
                pattern '([0-9,A-F#*.?+%()-]*T?)' {
                  error-message "Incorrect format for E.164 Number: regular expression must be of the form  [0-9,A-F#*.?+%()-]*T?";
                }
              }
            }
            leaf mailbox {
              description
                "mailbox number";
              type string {
                pattern '([0-9,A-F#*.?+%()-]*T?)' {
                  error-message "Incorrect format for E.164 Number: regular expression must be of the form  [0-9,A-F#*.?+%()-]*T?";
                }
              }
            }
            container noan-config {
              leaf noan {
                description
                  "forward call on no-answer";
                type string {
                  pattern '([0-9,A-F#*.?+%()-]*T?)' {
                    error-message "Incorrect format for E.164 Number: regular expression must be of the form  [0-9,A-F#*.?+%()-]*T?";
                  }
                }
              }
              leaf timeout {
                description
                  "Ringing no answer timeout duration";
                type uint32 {
                  range "3..60000";
                }
              }
            }
          }
        }
        container voice-class {
          description
            "Set voice class parameters";
          leaf codec {
            description
              "Set Global Codec parameters";
            type leafref {
              path "../../../../ios-voice:class/ios-voice:codec/codec-tag";
            }
          }
          leaf srtp-crypto {
            description
              "Associates an SRTP cipher list with this pool";
            type leafref {
              path "../../../../ios-voice:class/ios-voice:srtp-crypto/ios-voice:id";
            }
          }
        }
        container dtmf-relay {
          description
            "Transport DTMF digits across IP link";
          leaf rtp-nte {
            description
              "RTP Named Telephone Event RFC 2833";
            type empty;
          }
          leaf sip-kpml {
            description
              "DTMF Relay via KPML messages";
            type empty;
          }
          leaf sip-notify {
            description
              "DTMF Relay via SIP NOTIFY messages";
            type empty;
          }
        }
        container cor {
          description
            "Class of Restriction on dial-peer for this dn";
          list incoming {
            description
              "incoming class of restriction list";
            key "id";
            leaf id {
              description
                "corlist tag";
              type config-voice-register-corlist-tag;
            }
            uses config-voice-register-pool-cor;
          }
          list outgoing {
            description
              "outgoing class of restriction list";
            key "id";
            leaf id {
              description
                "cor list tag";
              type config-voice-register-corlist-tag;
            }
            uses config-voice-register-pool-cor;
          }
        }
        container translation-profile {
          description
            "Translation profile";
          leaf incoming {
            description
              "Translation Profile for incoming call leg";
            type leafref {
              path "../../../../ios-voice:translation-profile/ios-voice:id";
            }
          }
          leaf outgoing {
            description
              "Translation Profile for outgoing call leg";
            type leafref {
              path "../../../../ios-voice:translation-profile/ios-voice:id";
            }
          }
        }
      }
    }
  }

  grouping config-voice-moh-file-location-grouping {
    leaf filename {
      description
        "Example: bootflash:MOH filename";
      type string {
        pattern '(((bootflash:)|(flash:)|(nvram:)|(webui:)).*)';
      }
    }
  }

  grouping config-voice-call-manager-fallback-grouping {
    container call-manager-fallback {
      description
        "SRST for Cisco Call Manager fallback";
      presence "true";
      container moh {
        description
          "Define music-on-hold filename";
        container g729 {
          description
            "File for G.729/G.729A";
          uses config-voice-moh-file-location-grouping;
        }
        uses config-voice-moh-file-location-grouping;
      }
      choice tls-choice {
        description
          "TLS options";
        default "transport-tcp-tls-case";
        case transport-tcp-tls-case {
          description
            "Default TLS option";
          leaf transport-tcp-tls {
            description
              "Default TLS over TCP for SCCP User Agent";
            type empty;
          }
        }
        case transport-tcp-tls-version-case {
          description
            "Various TLS version options";
          container transport-tcp-tls-version {
            container transport-tcp-tls {
              description
                "Various TLS version over TCP for SCCP User Agent";
              choice tlsver-choice {
                description
                  "TLS Version options";
                case tlsv1.0-case {
                  description
                    "TLS Version 1.0 option";
                  leaf v1.0 {
                    description
                      "TLS Version 1.0";
                    type empty;
                  }
                }
                case tlsv1.1-case {
                  description
                    "TLS Version 1.1 option";
                  leaf v1.1 {
                    description
                      "TLS Version 1.1";
                    type empty;
                  }
                }
                case tlsv1.2-case {
                  description
                    "TLS Version 1.2 option";
                  container v1.2 {
                    description
                      "TLS Version 1.2";
                    presence "true";
                    leaf sha2 {
                      description
                        "SHA2 ciphers config";
                      type empty;
                    }
                  }
                }
                case tlsv1.3-case {
                  description
                    "TLS Version 1.3 option";
                  container v1.3 {
                    description
                      "TLS Version 1.3";
                    presence "true";
                    leaf sha2 {
                      description
                        "SHA2 ciphers config";
                      type empty;
                    }
                  }
                }
              }
            }
          }
        }
      }
    }
  }
}
