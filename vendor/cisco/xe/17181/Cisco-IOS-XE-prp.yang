module Cisco-IOS-XE-prp {
  yang-version 1.1;
  namespace "http://cisco.com/ns/yang/Cisco-IOS-XE-prp";
  prefix prp;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE prp (Parallel redundancy protocol) model";

  revision 2024-11-01 {
    description
      "- Added support for PRP VLAN aware";
    cisco-semver:module-version "1.2.0";
  }
  revision 2022-11-01 {
    description
      "- Update yang-version to 1.1";
    cisco-semver:module-version "1.1.0";
  }
  revision 2022-07-01 {
    description
      "Initially created";
    cisco-semver:module-version "1.0.0";
  }

  typedef int-vlan {
    description
      "custom int data type for vlan with required range";
    type uint16 {
      range "0..4095";
    }
  }

  typedef mac-address {
    description
      "The mac-address type represents an IEEE 802 MAC address.";
    type string {
      pattern '[0-9a-fA-F]{4}(.[0-9a-fA-F]{4}){2}';
    }
  }

  grouping config-prp-grouping {
    container prp {
      list channel-group {
        key "id";
        leaf id {
          description
            "Denotes channel number";
          type uint8 {
            range "1..2";
          }
        }
        container supervisionFrameOption {
          description
            "Enables VLAN-tagged supervision frames";
          leaf vlan-id {
            description
              "vlan-id";
            type int-vlan;
          }
          leaf vlan-cos {
            description
              "vlan class of service value";
            type uint8 {
              range "1..7";
            }
          }
          leaf vlan-tagged {
            description
              "vlan-tagged enable/disable";
            type empty;
          }
          leaf mac-da {
            description
              "MAC DA last two bit option value";
            type uint8 {
              range "1..255";
            }
          }
          leaf vlan-aware-enable {
            description
              "VLAN aware feature enable/disable";
            type empty;
          }
          leaf vlan-aware-reject-untagged {
            description
              "Disable Node Table Learning of Untagged Sup frame";
            type empty;
          }
          leaf vlan-aware-allowed-vlan {
            description
              "Allowed VLANs in VLAN Aware mode";
            type string {
              pattern '(((409[0-4]|40[0-8][0-9]|[1-3][0-9]{3}|[1-9][0-9]{1,2}|[1-9])(\-(409[0-4]|40[0-8][0-9]|[1-3][0-9]{3}|[1-9][0-9]{1,2}|[1-9]))?)(,((409[0-4]|40[0-8][0-9]|[1-3][0-9]{3}|[1-9][0-9]{1,2}|[1-9])(\-(409[0-4]|40[0-8][0-9]|[1-3][0-9]{3}|[1-9][0-9]{1,2}|[1-9]))?))*)';
            }
          }
        }
        container nodeTableMacaddress {
          leaf mac-address {
            description
              "MAC address";
            type mac-address;
          }
          leaf attachment-type {
            description
              "Connection type";
            type enumeration {
              enum dan;
              enum lan-a;
              enum lan-b;
            }
          }
        }
        leaf vdanMacaddress {
          description
            "MAC address";
          type mac-address;
        }
        leaf passRCT {
          description
            "passRCT enable/disable";
          type empty;
        }
        container igmpquerier {
          description
            "sendGQOnLANRecovery enable/disable";
          leaf sendGQOnLANRecovery {
            type empty;
          }
        }
        leaf supervisionFrameRedboxMacaddress {
          description
            "MAC address";
          type mac-address;
        }
        leaf supervisionFrameLifeCheckInterval {
          description
            "Interval time";
          type uint16 {
            range "0..65535";
          }
        }
        leaf supervisionFrameTime {
          description
            "Frame life time";
          type uint16 {
            range "0..65535";
          }
          default "3";
        }
      }
    }
  }

  grouping config-interface-GigE-prp-grouping {
    container prp-channel-group {
      leaf id {
        description
          "Denotes channel number";
        type uint8;
      }
    }
  }

  augment "/ios:native" {
    uses config-prp-grouping;
  }

  augment "/ios:native/ios:interface/ios:GigabitEthernet" {
    uses config-interface-GigE-prp-grouping;
  }
}
