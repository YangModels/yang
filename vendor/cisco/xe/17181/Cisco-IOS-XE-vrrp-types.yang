module Cisco-IOS-XE-vrrp-types {
  yang-version 1.1;
  namespace "http://cisco.com/ns/yang/Cisco-IOS-XE-vrrp-types";
  prefix vrrp-ios-xe-types;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of common YANG definitions
     for VRRP BFD operational data.
     Copyright (c) 2020, 2022 by Cisco Systems, Inc.
     All rights reserved.";

  revision 2022-11-01 {
    description
      "Update yang-version to 1.1";
    reference
      "1.1.0";
    cisco-semver:module-version "1.1.0";
  }
  revision 2021-03-01 {
    description
      "Initial revision";
    reference
      "1.0.0";
    cisco-semver:module-version "1.0.0";
  }

  typedef vrrp-bfd-state-type {
    type enumeration {
      enum bfd-none {
        value 0;
        description
          "No BFD session is present.";
      }
      enum bfd-inactive {
        value 1;
        description
          "VRRP BFD State is Inactive";
      }
      enum bfd-down {
        value 2;
        description
          "VRRP BFD State is Down";
      }
      enum bfd-up {
        value 3;
        description
          "VRRP BFD State is Up";
      }
    }
    description
      "VRRP BFD State ";
  }
}
