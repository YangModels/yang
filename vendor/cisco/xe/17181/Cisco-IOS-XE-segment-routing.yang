module Cisco-IOS-XE-segment-routing {
  yang-version 1.1;
  namespace "http://cisco.com/ns/yang/Cisco-IOS-XE-segment-routing";
  prefix ios-segment-routing;

  import cisco-semver {
    prefix cisco-semver;
  }
  import ietf-inet-types {
    prefix inet;
  }
  import Cisco-IOS-XE-native {
    prefix ios;
  }
  import Cisco-IOS-XE-isis {
    prefix ios-isis;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Segment Routing Yang model.
     Copyright (c) 2016, 2018-2023 by Cisco Systems, Inc.
     All rights reserved.";

  revision 2025-07-01 {
    description
      "- Added transit-node-ptb-relay for srv6
       - Removed must statement and tailf annotations for vrf-name leaf";
    cisco-semver:module-version "5.1.0";
  }
  revision 2025-03-01 {
    description
      "- Added algorithm for locator
       - Deprecated nodes on and before 17.11 need to be obsolete";
    cisco-semver:module-version "5.0.0";
  }
  revision 2024-07-01 {
    description
      "- Added END.X explicit SID
       - Added MTU under encapsulation for srv6";
    cisco-semver:module-version "4.0.0";
  }
  revision 2024-03-01 {
    description
      "- Obsolete nodes related to sr-policy-mgr that are deprecated in 17.6 or before";
    cisco-semver:module-version "3.0.0";
  }
  revision 2023-07-01 {
    description
      "- Added choice option to Policy end-point to support IPv6 in addition to IPv4
       - Deprecated old Policy end-point leaf
       - Added ipv6 prefix list to On Demand grouping
       - Added ISIS SRv6 CLIs";
    cisco-semver:module-version "2.5.0";
  }
  revision 2023-03-01 {
    description
      "- Changed cli-flat-list-syntax to cli-list-syntax";
    cisco-semver:module-version "2.4.1";
  }
  revision 2022-11-01 {
    description
      "- Changed cli-flat-list-syntax to cli-list-syntax
       - Update yang-version to 1.1";
    cisco-semver:module-version "2.4.0";
  }
  revision 2022-07-01 {
    description
      "- Added choice options to Forward Class to support rib as well as color option
       - Deprecated old Forward Class color leaf";
    cisco-semver:module-version "2.3.0";
  }
  revision 2021-11-01 {
    description
      "- Added segment-routing traffic-eng path disable-algo-check strict-spf";
    cisco-semver:module-version "2.2.0";
  }
  revision 2021-07-01 {
    description
      "- Added performance measurement pcc profile grouping for auto-rotate configuration
       - Update error-message for leaf mpls
       - Added cli-exit-command for segment-routing mpls container";
    cisco-semver:module-version "2.1.0";
  }
  revision 2021-03-01 {
    description
      "- Add PM Liveness
       - Add must constraint for interface leaf";
    cisco-semver:module-version "2.0.0";
  }
  revision 2020-11-01 {
    description
      "- Added SR policy dynamic path Margin and sid-limit
       - Added SR policy autoroute announce";
    cisco-semver:module-version "1.3.0";
  }
  revision 2020-07-01 {
    description
      "- Add per-flow-grouping in on-demand-color-config-grouping
       - Added flex-algo";
    cisco-semver:module-version "1.2.0";
  }
  revision 2020-03-01 {
    description
      "Add performance-measurement container under policy container";
    cisco-semver:module-version "1.1.0";
  }
  revision 2019-07-01 {
    description
      "- Establish semantic version baseline
       - Added default values
       - Added local-block leaf in SR-MPLS";
    cisco-semver:module-version "1.0.0";
  }
  revision 2018-11-07 {
    description
      "Cleanup spelling errors in description statements";
  }
  revision 2018-10-18 {
    description
      "Update SR policy manager segment-list config";
  }
  revision 2018-09-20 {
    description
      "Update SR policy manager config";
  }
  revision 2018-07-27 {
    description
      "Add policy manager config";
  }
  revision 2017-02-07 {
    description
      "Initial revision";
  }

  grouping mcfg-srmpls-sidmap {
    container address-family {
      container ipv4 {
        uses srcfg-srmpls-conn-af;
      }
      container ipv4-strict-spf {
        container ipv4 {
          description
            "Address Family";
          container strict-spf {
            uses srcfg-srmpls-conn-af;
          }
        }
      }
      container ipv4-algorithm {
        container ipv4 {
          description
            "Address Family";
          list algorithm {
            key "flex-algo-number";
            leaf flex-algo-number {
              description
                "Flex algorithm value";
              type uint32 {
                range "128..255";
              }
            }
            uses srcfg-srmpls-conn-af;
          }
        }
      }
    }
  }

  grouping mcfg-srmpls-sidmap-attach {
    container address-family {
      container ipv4 {
        uses srcfg-srmpls-conn-af-attach;
      }
      container ipv4-strict-spf {
        container ipv4 {
          description
            "Address Family";
          container strict-spf {
            uses srcfg-srmpls-conn-af-attach;
          }
        }
      }
      container ipv4-algorithm {
        container ipv4 {
          description
            "Address Family";
          list algorithm {
            key "flex-algo-number";
            leaf flex-algo-number {
              description
                "Flex algorithm value";
              type uint32 {
                range "128..255";
              }
            }
            uses srcfg-srmpls-conn-af;
          }
        }
      }
    }
  }

  grouping srcfg-srmpls-attr-af {
    leaf explicit-null {
      type empty;
    }
    leaf sr-label-preferred {
      type empty;
    }
  }

  grouping sr-range {
    leaf range-start {
      type uint32 {
        range "0..1048575";
      }
    }
    leaf range {
      description
        "Range value";
      default "1";
      type uint32 {
        range "1..1048575";
      }
    }
  }

  grouping srcfg-srmpls-conn-af {
    list prefixes {
      key "ipprefix";
      leaf ipprefix {
        type inet:ipv4-prefix;
      }
      choice label-type {
        container index {
          uses sr-range;
        }
        container absolute {
          uses sr-range;
        }
      }
    }
  }

  grouping srcfg-srmpls-conn-af-attach {
    list prefixes {
      key "ipprefix";
      leaf ipprefix {
        type inet:ipv4-prefix;
      }
      choice label-type {
        container index {
          uses sr-range;
          leaf attach {
            type empty;
          }
        }
        container absolute {
          uses sr-range;
          leaf attach {
            type empty;
          }
        }
      }
    }
  }

  grouping affinity-map-config-grouping {
    list name {
      description
        "List of color configurations";
      key "color-name";
      leaf color-name {
        description
          "Color name";
        type string;
      }
      leaf bit-position {
        description
          "Bit position";
        type uint8 {
          range "0..31";
        }
      }
    }
  }

  grouping interface-config-grouping {
    leaf metric {
      description
        "TE metric value";
      type uint32 {
        range "1..2147483647";
      }
    }
    container affinity {
      description
        "Affinity command mode";
      leaf-list name {
        description
          "Color name";
        type string;
      }
    }
  }

  grouping restrict-on-demand-color-config-grouping {
    container ipv4 {
      description
        "On-demand color authorize restrict ipv4";
      leaf prefix-list {
        description
          "Prefix-list name";
        type string;
      }
    }
    container ipv6 {
      description
        "On-demand color authorize restrict ipv6";
      leaf prefix-list {
        description
          "Prefix-list name";
        type string;
      }
    }
  }

  grouping dynamic-config-policy-grouping {
    container metric {
      description
        "Metric configuration";
      leaf type {
        description
          "Specify metric type configuration";
        type enumeration {
          enum igp {
            description
              "IGP metric type";
          }
          enum te {
            description
              "TE metric type";
          }
          enum delay {
            description
              "Delay metric type";
          }
        }
      }
      leaf sid-limit {
        description
          "Maximum number of sid's";
        type uint8 {
          range "1..255";
        }
      }
      container margin {
        description
          "Margin configuration";
        leaf absolute {
          description
            "Absolute margin";
          type uint32 {
            range "0..2147483647";
          }
        }
        leaf relative {
          description
            "Relative margin";
          type uint8 {
            range "0..100";
          }
        }
      }
    }
    leaf pcep {
      description
        "Use PCE for path calculation";
      type empty;
    }
  }

  grouping dynamic-config-on-demand-grouping {
    container metric {
      description
        "Metric configuration";
      leaf type {
        description
          "Specify metric type configuration";
        type enumeration {
          enum igp {
            description
              "IGP metric type";
          }
          enum te {
            description
              "TE metric type";
          }
          enum delay {
            description
              "Delay metric type";
          }
        }
      }
      container margin {
        description
          "Margin configuration";
        leaf absolute {
          description
            "Absolute margin";
          type uint32 {
            range "0..2147483647";
          }
        }
        leaf relative {
          description
            "Relative margin";
          type uint8 {
            range "0..100";
          }
        }
      }
      leaf sid-limit {
        description
          "Maximum number of sid's";
        type uint8 {
          range "1..255";
        }
      }
    }
    leaf pcep {
      description
        "Use PCE for path calculation";
      type empty;
    }
  }

  grouping forward-class-grouping {
    container forward-class {
      description
        "Specify forward class for per-flow based routing";
      list value {
        description
          "Forward-class";
        key "forward-class-value";
        leaf forward-class-value {
          description
            "Forward-class value";
          type uint32 {
            range "0..7";
          }
        }
        choice options {
          case color-case {
            leaf color-option {
              description
                "Specify corresponding policy color for the forwarding class";
              type uint32 {
                range "1..4294967295";
              }
            }
          }
          case rib-case {
            leaf rib {
              type empty;
            }
          }
        }
        leaf color {
          status obsolete;
          description
            "This node is obsolete and replaced by color-option";
          type uint32 {
            range "1..4294967295";
          }
        }
      }
    }
  }

  grouping preference-config-path-choice-grouping {
    container explicit {
      description
        "Preconfigured path";
      list segment-list {
        description
          "Specify Segment-list";
        key "name";
        leaf name {
          description
            "Identifying name for Segment-list";
          type string;
        }
        leaf weight {
          description
            "Path weight";
          type uint32 {
            range "1..4294967295";
          }
        }
      }
    }
  }

  grouping preference-config-policy-grouping {
    container constraints {
      description
        "Constraints configuration";
      container affinity {
        description
          "Assign affinities to path";
        container exclude-any {
          description
            "Affinity attributes to exclude - presence of at least one excludes link";
          leaf-list name {
            description
              "Affinity color name";
            type string;
          }
        }
        container include-all {
          description
            "Affinity attributes - all must be included";
          leaf-list name {
            description
              "Affinity color name";
            type string;
          }
        }
        container include-any {
          description
            "Affinity attributes - at least one must be included";
          leaf-list name {
            description
              "Affinity color name";
            type string;
          }
        }
      }
      container association-group {
        description
          "Association group constraints";
        presence "true";
        container disjointness {
          description
            "Disjointness parameters";
          leaf type {
            description
              "Type of disjointness among paths";
            type enumeration {
              enum link {
                description
                  "Link disjointness";
              }
              enum node {
                description
                  "Node disjointness";
              }
              enum srlg {
                description
                  "SRLG disjointness";
              }
            }
          }
        }
        leaf identifier {
          description
            "Association group identifier";
          type uint16 {
            range "1..65535";
          }
        }
        leaf source {
          description
            "Association source";
          type inet:ipv4-address;
        }
      }
      leaf bandwidth {
        description
          "Bandwidth value in kbps";
        type uint32 {
          range "1..4294967295";
        }
      }
      container segments {
        description
          "Segments constraints";
        leaf dataplane {
          description
            "Dataplane type";
          type enumeration {
            enum mpls {
              description
                "Specify MPLS dataplane";
            }
            enum srv6 {
              description
                "Specify SRv6 dataplane";
            }
          }
        }
        leaf type {
          description
            "Specify segment type configuration";
          type enumeration {
            enum protected {
              description
                "Protected segment";
            }
            enum unprotected {
              description
                "Unprotected segment";
            }
          }
        }
        leaf algorithm {
          description
            "Specify algorithm";
          type uint32 {
            range "128..255";
          }
        }
      }
    }
    leaf description {
      description
        "Up to 200 characters describing this path preference";
      type string {
        length "1..200";
      }
    }
    choice path-choice {
      case dynamic {
        container dynamic {
          description
            "Dynamic configuration";
          presence "true";
          uses dynamic-config-policy-grouping;
        }
      }
      case explicit {
        container explicit {
          description
            "Preconfigured path";
          list segment-list {
            description
              "Specify Segment-list";
            key "name";
            leaf name {
              description
                "Identifying name for Segment-list";
              type string;
            }
            leaf weight {
              description
                "Path weight";
              type uint32 {
                range "1..4294967295";
              }
            }
          }
        }
      }
      case per-flow {
        container per-flow {
          description
            "Per-flow configuration";
          presence "true";
          uses forward-class-grouping;
        }
      }
    }
  }

  grouping preference-config-on-demand-grouping {
    container constraints {
      description
        "Constraints configuration";
      container affinity {
        description
          "Assign affinities to path";
        container exclude-any {
          description
            "Affinity attributes to exclude - presence of at least one excludes link";
          leaf-list name {
            description
              "Affinity color name";
            type string;
          }
        }
        container include-all {
          description
            "Affinity attributes - all must be included";
          leaf-list name {
            description
              "Affinity color name";
            type string;
          }
        }
        container include-any {
          description
            "Affinity attributes - at least one must be included";
          leaf-list name {
            description
              "Affinity color name";
            type string;
          }
        }
      }
      container association-group {
        description
          "Association group constraints";
        presence "true";
        container disjointness {
          description
            "Disjointness parameters";
          leaf type {
            description
              "Type of disjointness among paths";
            type enumeration {
              enum link {
                description
                  "Link disjointness";
              }
              enum node {
                description
                  "Node disjointness";
              }
              enum srlg {
                description
                  "SRLG disjointness";
              }
            }
          }
        }
        leaf identifier {
          description
            "Association group identifier";
          type uint16 {
            range "1..65535";
          }
        }
        leaf source {
          description
            "Association source";
          type inet:ipv4-address;
        }
      }
      leaf bandwidth {
        description
          "Bandwidth value in kbps";
        type uint32 {
          range "1..4294967295";
        }
      }
      container segments {
        description
          "Segments constraints";
        leaf dataplane {
          description
            "Dataplane type";
          type enumeration {
            enum mpls {
              description
                "Specify MPLS dataplane";
            }
            enum srv6 {
              description
                "Specify SRv6 dataplane";
            }
          }
        }
        leaf type {
          description
            "Specify segment type configuration";
          type enumeration {
            enum protected {
              description
                "Protected segment";
            }
            enum unprotected {
              description
                "Unprotected segment";
            }
          }
        }
        leaf algorithm {
          description
            "Specify algorithm";
          type uint32 {
            range "128..255";
          }
        }
      }
    }
    leaf description {
      description
        "Up to 200 characters describing this path preference";
      type string {
        length "1..200";
      }
    }
    choice path-choice {
      case dynamic {
        container dynamic {
          description
            "Dynamic configuration";
          presence "true";
          uses dynamic-config-on-demand-grouping;
        }
      }
      case explicit {
        container explicit {
          description
            "Preconfigured path";
          list segment-list {
            description
              "Specify Segment-list";
            key "name";
            leaf name {
              description
                "Identifying name for Segment-list";
              type string;
            }
            leaf weight {
              description
                "Path weight";
              type uint32 {
                range "1..4294967295";
              }
            }
          }
        }
      }
      case per-flow {
        container per-flow {
          description
            "Per-flow configuration";
          presence "true";
          uses forward-class-grouping;
        }
      }
    }
  }

  grouping candidate-paths-policy-grouping {
    container candidate-paths {
      description
        "Candidate-paths configuration";
      presence "true";
      list preference {
        description
          "Policy path-option preference entry";
        key "preference";
        leaf preference {
          description
            "Path-option preference";
          type uint32 {
            range "1..65535";
          }
        }
        uses preference-config-policy-grouping;
      }
    }
  }

  grouping candidate-paths-on-demand-grouping {
    container candidate-paths {
      description
        "Candidate-paths configuration";
      presence "true";
      list preference {
        description
          "Policy path-option preference entry";
        key "preference";
        leaf preference {
          description
            "Path-option preference";
          type uint32 {
            range "1..65535";
          }
        }
        uses preference-config-on-demand-grouping;
      }
    }
  }

  grouping performance-measurement-policy-grouping {
    container performance-measurement {
      description
        "Performance Measurement configuration";
      container delay-measurement-config {
        presence "true";
        description
          "Delay Measurement configuration";
        leaf profile {
          description
            "name of the profile template to be used";
          type string;
        }
        container liveness-detection {
          presence "true";
          description
            "Liveness detection";
          container invalidation-action {
            description
              "Action to be taken when PM liveness session is invalidated";
            choice mode-choice {
              case none {
                leaf none {
                  type empty;
                  description
                    "PM liveness session state does not affect LSP state";
                }
              }
              case down {
                leaf down {
                  type empty;
                  description
                    "LSP can only be operationally up if the PM liveness session is up";
                }
              }
            }
          }
        }
        container reverse-path {
          description
            "Specifies parameters about the reverse path back to the head-end";
          leaf label {
            description
              "DM packets return to head-end using this label";
            type uint32 {
              range "16..1048575";
            }
          }
        }
      }
      leaf delay-measurement {
        status obsolete;
        description
          "This node is obsolete and replaced by delay-measurement-config";
        type empty;
      }
    }
  }

  grouping performance-measurement-on-demand-grouping {
    container performance-measurement {
      description
        "Performance Measurement configuration";
      container delay-measurement-config {
        presence "true";
        description
          "Delay Measurement configuration";
        leaf profile {
          description
            "name of the profile template to be used";
          type string;
        }
        container liveness-detection {
          presence "true";
          description
            "Liveness detection";
          container invalidation-action {
            description
              "Action to be taken when PM liveness session is invalidated";
            choice mode-choice {
              case none {
                leaf none {
                  type empty;
                  description
                    "PM liveness session state does not affect LSP state";
                }
              }
              case down {
                leaf down {
                  type empty;
                  description
                    "LSP can only be operationally up if the PM liveness session is up";
                }
              }
            }
          }
        }
        container reverse-path {
          description
            "Specifies parameters about the reverse path back to the head-end";
          leaf label {
            description
              "DM packets return to head-end using this label";
            type uint32 {
              range "16..1048575";
            }
          }
        }
      }
      leaf delay-measurement {
        status obsolete;
        description
          "This node is obsolete and replaced by delay-measurement-config";
        type empty;
      }
    }
  }

  grouping performance-measurement-pcc-profile-grouping {
    container performance-measurement {
      description
        "Performance Measurement configuration";
      container delay-measurement {
        presence "true";
        description
          "Delay Measurement configuration";
        leaf profile {
          description
            "name of the profile template to be used";
          type string;
        }
        container liveness-detection {
          presence "true";
          description
            "Liveness detection";
          container invalidation-action {
            description
              "Action to be taken when PM liveness session is invalidated";
            choice mode-choice {
              case none {
                leaf none {
                  type empty;
                  description
                    "PM liveness session state does not affect LSP state";
                }
              }
              case down {
                leaf down {
                  type empty;
                  description
                    "LSP can only be operationally up if the PM liveness session is up";
                }
              }
            }
          }
        }
        container reverse-path {
          description
            "Specifies parameters about the reverse path back to the head-end";
          leaf label {
            description
              "DM packets return to head-end using this label";
            type uint32 {
              range "16..1048575";
            }
          }
        }
      }
    }
  }

  grouping path-inval-grouping {
    container path-invalidation {
      description
        "Path invalidation option configuration";
      leaf drop {
        description
          "Keep policy up, but drop all traffic sent on the policy";
        type empty;
      }
    }
  }

  grouping steering-policy-grouping {
    container steering {
      description
        "Steering options configuration";
      uses path-inval-grouping;
    }
  }

  grouping steering-odn-grouping {
    container steering {
      description
        "Steering options configuration";
      uses path-inval-grouping;
    }
  }

  grouping steering-pcc-grouping {
    container steering {
      description
        "Steering options configuration";
      uses path-inval-grouping;
    }
  }

  grouping on-demand-color-config-grouping {
    container authorize {
      description
        "Authorize colour";
      presence "true";
      container restrict {
        description
          "Restrict";
        presence "true";
        uses restrict-on-demand-color-config-grouping;
      }
    }
    uses candidate-paths-on-demand-grouping;
    uses performance-measurement-on-demand-grouping;
    uses steering-odn-grouping;
    leaf description {
      description
        "On-demand color template specific description";
      type string;
    }
  }

  grouping policy-config-grouping {
    container binding-sid {
      description
        "Static binding SID";
      leaf mpls {
        description
          "MPLS label";
        type uint32 {
          range "16..1048575";
        }
      }
    }
    uses candidate-paths-policy-grouping;
    uses performance-measurement-policy-grouping;
    uses steering-policy-grouping;
    container color-endpoint {
      description
        "Specify color and end-point for policy";
      leaf color {
        description
          "Specify color for policy";
        type uint32 {
          range "1..4294967295";
        }
      }
      leaf end-point-v2 {
        description
          "Policy endpoint address";
        type inet:ip-address;
      }
      leaf end-point {
        status deprecated;
        description
          "Policy endpoint address";
        type inet:ipv4-address;
      }
    }
    leaf description {
      description
        "Up to 200 characters describing this policy";
      type string {
        length "1..200";
      }
    }
    leaf shutdown {
      description
        "Shutdown";
      type empty;
    }
    container autoroute {
      description
        "Autoroute configuration";
      container include {
        description
          "Prefixes for which routes will be installed";
        leaf all {
          description
            "Include all eligible prefixes";
          type empty;
        }
      }
      container metric {
        description
          "Autoroute metric";
        choice metric-type {
          case constant {
            leaf constant {
              description
                "Set metric mode constant";
              type uint32 {
                range "1..2147483647";
              }
            }
          }
          case relative {
            leaf relative {
              description
                "Set metric mode relative";
              type int32 {
                range "-10..10";
              }
            }
          }
        }
      }
    }
  }

  grouping password-grouping {
    container password {
      description
        "Configure PCE MD5 password";
      choice password-choice {
        case clear {
          leaf clear {
            description
              "Cleartext password";
            type string;
          }
        }
        case encrypted {
          leaf encrypted {
            description
              "Hidden password";
            type string;
          }
        }
      }
    }
  }

  grouping pcc-config-grouping {
    container pce {
      description
        "List of Path Computation Element (PCE) servers";
      choice pce-address-choice {
        case pce-ipv4-address {
          list pce-ipv4-list {
            key "address";
            leaf address {
              description
                "IPv4 address";
              type inet:ipv4-address;
            }
            leaf source-address {
              description
                "IPv4 source address";
              type inet:ipv4-address;
            }
            leaf preference {
              description
                "Lower preference number makes the PCE more preferred";
              type uint8 {
                range "1..255";
              }
            }
            uses password-grouping;
          }
        }
        case pce-ipv6-address {
          list pce-ipv6-list {
            key "address";
            leaf address {
              description
                "IPv6 address";
              type inet:ipv6-address;
            }
            leaf source-address {
              description
                "IPv6 source address";
              type inet:ipv6-address;
            }
            leaf preference {
              description
                "Lower preference number makes the PCE more preferred";
              type uint8 {
                range "1..255";
              }
            }
            uses password-grouping;
          }
        }
      }
    }
    leaf report-all {
      description
        "Report all local SR policies to connected PCEP peers";
      type empty;
    }
    list profile {
      key "id";
      leaf id {
        description
          "numeric identifier for the profile";
        type uint32 {
          range "1..65534";
        }
      }
      container autoroute {
        description
          "Autoroute configuration";
        container include {
          description
            "Prefixes for which routes will be installed";
          leaf all {
            description
              "Include all eligible prefixes";
            type empty;
          }
        }
      }
      uses steering-pcc-grouping;
      uses performance-measurement-pcc-profile-grouping;
    }
  }

  grouping segment-list-config-grouping {
    list index {
      key "index";
      leaf index {
        description
          "Specify the next entry index to add, edit (or delete)";
        type uint32 {
          range "1..4294967295";
        }
      }
      container mpls {
        description
          "MPLS configuration";
        choice sid-type {
          case adjacency {
            leaf adjacency {
              description
                "IPv4 address of MPLS adjacency";
              type inet:ipv4-address;
            }
          }
          case label {
            leaf label {
              description
                "Value of MPLS label";
              type uint32 {
                range "16..1048575";
              }
            }
          }
          case prefix {
            container prefix {
              description
                "MPLS prefix configuration";
              leaf ipv4-prefix {
                description
                  "IPv4 address";
                type inet:ipv4-address;
              }
              leaf algorithm {
                description
                  "SR algorithm to be used for calculating reachability to the prefix";
                type enumeration {
                  enum 0 {
                    description
                      "Shortest-Path-First (SPF) algorithm which permits nodes to overwrite SPF path with a different path based on local policy";
                  }
                  enum 1 {
                    description
                      "Strict-Shortest-Path-First (Strict-SPF) algorithm which ensures all nodes along the path will honor the SPF routing decision";
                  }
                }
              }
            }
          }
        }
      }
    }
  }

  grouping config-segment-routing-isis-srv6-grouping {
    container segment-routing {
      description
        "Enter IPv6 segment-routing mode";
      container srv6 {
        description
          "Segment Routing SRv6";
        must '../../../../ios-isis:net' {
          error-message
            "Net-id must be configured before
             configuring segment-routing srv6 on router isis";
        }
        presence "true";
        list locator {
          description
            "Locator configuration";
          key "name";
          leaf name {
            description
              "locator name";
            type string;
          }
          choice levels {
            leaf level-1 {
              description
                "Apply to level-1 only";
              type empty;
            }
            leaf level-2 {
              description
                "Apply to level-2 only";
              type empty;
            }
          }
          container metric {
            description
              "Configure metric for the locator";
            list metric-list {
              key "levels";
              leaf levels {
                type enumeration {
                  enum level-1;
                  enum level-2;
                }
              }
              leaf value {
                mandatory true;
                type uint32 {
                  range "1..16777214";
                }
              }
            }
          }
        }
      }
    }
  }

  grouping config-segment-routing-isis-grouping {
    container segment-routing {
      description
        "Enable Segment Routing Feature";
      leaf mpls {
        description
          "Enable Segment Routing Feature using MPLS encapsulation";
        must '/ios:native/ios:segment-routing/mpls and ../../ios-isis:net' {
          error-message
            "Global segment-routing and net-id must be configured before
             configuring segment-routing on router isis";
        }
        type empty;
      }
      container prefix-sid-map {
        description
          "Enable prefix-sid-map";
        leaf advertise-local {
          description
            "Advertise active local prefix-SID mappings";
          type empty;
        }
        container receive {
          description
            "Enable prefix-SID mapping client";
          presence "true";
          leaf disable {
            description
              "Disable prefix-SID mapping";
            type empty;
          }
        }
      }
    }
  }

  grouping config-segment-routing-grouping {
    container mpls {
      description
        "Segment Routing MPLS Mode";
      presence "true";
      container connected-prefix-sid-map {
        description
          "Enter Connected Prefix Sid Map  Mode";
        uses mcfg-srmpls-sidmap;
      }
      container global-block {
        description
          "SR Global Block Config";
        leaf range-start {
          description
            "SR GB Label Range Start";
          default "16000";
          type uint32 {
            range "16..1048575";
          }
        }
        leaf range-end {
          description
            "SR GB Label Range End";
          must '. >= ../range-start' {
            error-message "range-end must be greater than or equal to range-start";
          }
          default "23999";
          type uint32 {
            range "16..1048575";
          }
        }
      }
      container local-block {
        description
          "SR Local Block Config";
        leaf range-start {
          description
            "SR LB Label Range Start";
          default "15000";
          type uint32 {
            range "16..1048575";
          }
        }
        leaf range-end {
          description
            "SR LB Label Range End";
          must '. >= ../range-start' {
            error-message "range-end must be greater than or equal to range-start";
          }
          default "15999";
          type uint32 {
            range "16..1048575";
          }
        }
      }
      container mapping-server {
        description
          "Enter Segment Routing Mapping Server Mode";
        container prefix-sid-map {
          description
            "Enter Mapping Server Sidmap Mode";
          uses mcfg-srmpls-sidmap-attach;
        }
      }
      container set-attributes {
        description
          "Enter SR Set Attributes  Mode";
        container address-family {
          description
            "Enter Address Family command mode";
          container ipv4 {
            description
              "Address Family";
            uses srcfg-srmpls-attr-af;
          }
        }
      }
      leaf shutdown {
        description
          "SR Shutdown";
        type empty;
      }
    }
    container traffic-eng {
      description
        "Segment Routing traffic-eng mode";
      presence "true";
      container affinity-map {
        description
          "Affinity-map command mode";
        uses affinity-map-config-grouping;
      }
      list interface {
        description
          "Interface command mode";
        key "name";
        leaf name {
          description
            "Interface name";
          must '/ios:native/ios:interface/*[concat(local-name(.), ios:name) = current()]' {
            error-message
              "Interface must be configured before
               configuring it under segment-routing traffic-eng and
               deleted before deleting it under segment-routing traffic-eng";
          }
          type string;
        }
        uses interface-config-grouping;
      }
      container path {
        description
          "Path calculation configuration";
        container disable-algo-check {
          description
            "Disable algorithm check";
          leaf strict-spf {
            description
              "Strict Short Path First";
            type empty;
          }
        }
      }
      container logging {
        description
          "Logging configuration";
        container policy {
          description
            "Configure policy logging parameters";
          leaf status {
            description
              "Enable policy status logging";
            type empty;
          }
        }
      }
      list on-demand {
        description
          "On demand color mode";
        key "color";
        leaf color {
          description
            "Permitted colour";
          type uint32 {
            range "1..4294967295";
          }
        }
        uses on-demand-color-config-grouping;
      }
      container pcc {
        description
          "Path computation client mode";
        uses pcc-config-grouping;
      }
      list policy {
        description
          "Policy command mode";
        key "name";
        leaf name {
          description
            "Policy name";
          type string;
        }
        uses policy-config-grouping;
      }
      list segment-list {
        description
          "Segment-list configuration";
        key "name";
        leaf name {
          description
            "Identifying name for segment-list";
          type string;
        }
        uses segment-list-config-grouping;
      }
    }
    container srv6 {
      description
        "Segment Routing SRv6";
      presence "true";
      container sid {
        description
          "SID parameters";
        leaf holdtime {
          description
            "SID holdtime for a released SID";
          type uint32 {
            range "0..60";
          }
          default "10";
        }
      }
      leaf transit-node-ptb-relay {
        description
          "Transit node behavior for PTB relay";
        type empty;
      }
      container locators {
        description
          "Locators configuration";
        list locator {
          description
            "Locator configuration";
          key "name";
          leaf name {
            description
              "Locator name";
            type string;
          }
          leaf prefix {
            description
              "Locator prefix configuration";
            type inet:ipv6-prefix;
          }
          container format {
            description
              "Locator format";
            choice locator-format {
              case usid-f3216 {
                leaf usid-f3216 {
                  description
                    "usid-f3216 format";
                  type empty;
                }
              }
            }
          }
          leaf algorithm {
            description
              "Specify algorithm";
            type uint32 {
              range "128..255";
            }
          }
        }
      }
      container encapsulation {
        description
          "Encapsulation parameters";
        container hop-limit {
          description
            "Control Hop-limit field setting on IPv6 header";
          leaf count {
            description
              "Specify the count for hop-limit";
            type uint32 {
              range "1..255";
            }
          }
          leaf propagate {
            description
              "Propagate IP TTL/Hop-limit";
            type empty;
          }
        }
        leaf source-address {
          description
            "Specify Source address";
          type inet:ipv6-address;
        }
        container traffic-class {
          description
            "Control traffic-class field setting on IPv6 header";
          leaf count {
            description
              "Specify the value (as 2 hexadecimal nibbles) for traffic class";
            type string;
          }
          leaf propagate {
            description
              "Propagate IP TTL/Hop-limit";
            type empty;
          }
        }
        container mtu {
          description
            "MTU configuration";
          leaf value {
            description
              "Specify MTU value";
            type uint32 {
              range "1280..9960";
            }
          }
        }
      }
      container explicit-sids {
        description
          "Explicit SIDs configuration";
        list sid {
          description
            "Explicit SID configuration";
          key "address";
          leaf address {
            description
              "IPv6 address";
            type inet:ipv6-address;
          }
          container behavior {
            description
              "Behavior parameters";
            leaf behavior-type {
              mandatory true;
              type enumeration {
                enum end-dt4 {
                  description
                    "DT4";
                }
                enum end-dt46 {
                  description
                    "DT46";
                }
                enum end-dt6 {
                  description
                    "DT6";
                }
                enum end-x-usid-psp-usd {
                  description
                    "END.X USID with PSP/USD";
                }
              }
            }
            container forwarding {
              description
                "Forwarding configurations";
              when "../behavior-type = 'end-dt4' or ../behavior-type = 'end-dt46' or ../behavior-type = 'end-dt6'";
              list path {
                description
                  "Path configurations";
                key "path-id";
                leaf path-id {
                  description
                    "Path ID";
                  type uint32 {
                    range "1..2147483647";
                  }
                }
                container decap-and-lookup {
                  description
                    "Decapsulate and Lookup";
                  leaf vrf-name {
                    description
                      "VRF name";
                    type string;
                  }
                }
              }
            }
            container identification {
              description
                "Identification configurations";
              when "../behavior-type = 'end-x-usid-psp-usd'";
              container nexthop {
                description
                  "Nexthop configurations";
                presence "true";
                leaf interface {
                  description
                    "Interface name";
                  mandatory true;
                  must '/ios:native/ios:interface/*[concat(local-name(.), ios:name) = current()]' {
                    error-message
                      "Interface must be configured before
                       configuring it under segment-routing srv6 for explicit SID and
                       deleted before deleting it under segment-routing srv6 for explicit SID";
                  }
                  type string;
                }
                leaf address {
                  description
                    "IPv6 address";
                  type inet:ipv6-address;
                }
                leaf protected {
                  description
                    "Protected";
                  type empty;
                }
              }
            }
          }
        }
      }
    }
  }

  augment "/ios:native/ios:segment-routing" {
    uses config-segment-routing-grouping;
  }

  augment "/ios:native/ios:router/ios-isis:isis" {
    uses config-segment-routing-isis-grouping;
  }

  augment "/ios:native/ios:router/ios-isis:isis/ios-isis:address-family/ios-isis:ipv6" {
    uses config-segment-routing-isis-srv6-grouping;
  }

  augment "/ios:native/ios:router/ios-isis:isis-container/ios-isis:isis" {
    uses config-segment-routing-isis-grouping;
  }

  augment "/ios:native/ios:router/ios-isis:isis-container/ios-isis:isis/ios-isis:address-family/ios-isis:ipv6" {
    uses config-segment-routing-isis-srv6-grouping;
  }
}
