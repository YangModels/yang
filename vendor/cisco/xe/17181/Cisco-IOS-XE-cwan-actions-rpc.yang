module Cisco-IOS-XE-cwan-actions-rpc {
  yang-version 1.1;
  namespace "http://cisco.com/ns/yang/Cisco-IOS-XE-cwan-actions-rpc";
  prefix ios-xe-cwan-actions-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Copyright (c) 2025 by Cisco Systems, Inc.
     All rights reserved.";

  revision 2025-07-01 {
    description
      "Initial revision";
    reference
      "1.0.0";
    cisco-semver:module-version "1.0.0";
  }

  typedef cwan-resp-status {
    type enumeration {
      enum cwan-success {
        value 0;
        description
          "Success";
      }
      enum cwan-failed {
        value 1;
        description
          "Failed";
      }
      enum cwan-in-prog {
        value 2;
        description
          "In-progress";
      }
    }
    description
      "CWAN action response status";
  }

  grouping cwan-start-dmlog {
    description
      "This module defines the actions on the cellular modem to start modem DM log collection";
    leaf dm-tid {
      type string {
        length "1..255";
        pattern "[\\] A-Za-z0-9!\"#%&()*+,\\-./:;<=>^?@\\\\$_`{|}\\[']+";
      }
      mandatory true;
      description
        "The DM log transaction identifier is used to uniquely identify
         the modem DM log collection action invoked via RPC";
    }
    leaf if-name {
      type string {
        length "1..64";
        pattern '[0-9a-zA-Z\-_/]*';
      }
      mandatory true;
      description
        "Interface name to start modem DM log";
    }
    leaf radio-reset-enable {
      type empty;
      description
        "Radio reset option for DM log collection";
    }
    leaf rotation {
      type empty;
      description
        "Log rotation option for DM log collection";
    }
    leaf autostop-enable {
      type boolean;
      description
        "Enable DM log auto stop timer";
    }
    leaf autostop-timer {
      when "(../autostop-enable = 'true')";
      type uint8 {
        range "1..120";
      }
      description
        "DM log auto stop timer range 1-120 Minutes";
    }
  }

  grouping cwan-start-dmlog-resp {
    description
      "Response to cellular start DM log action command";
    leaf dm-tid {
      type string;
      description
        "The DM log transaction identifier is used to uniquely identify
         the modem DM log collection action invoked via RPC";
    }
    leaf status {
      type ios-xe-cwan-actions-rpc:cwan-resp-status;
      description
        "Start DM log response status";
    }
    leaf file-path {
      type string;
      description
        "DM log file path generated on the device";
    }
  }

  grouping cwan-stop-dmlog {
    description
      "This module defines the actions on the
       cellular modem to stop modem DM log collection";
    leaf dm-tid {
      type string {
        length "1..255";
        pattern "[\\] A-Za-z0-9!\"#%&()*+,\\-./:;<=>^?@\\\\$_`{|}\\[']+";
      }
      mandatory true;
      description
        "The DM log transaction identifier is used to uniquely identify
         the modem DM log collection action invoked via RPC";
    }
    leaf if-name {
      type string {
        length "1..64";
        pattern '[0-9a-zA-Z\-_/]*';
      }
      mandatory true;
      description
        "Interface name to stop modem DM log";
    }
  }

  grouping cwan-stop-dmlog-resp {
    description
      "Response to cellular stop DM log action command";
    leaf dm-tid {
      type string;
      description
        "The DM log transaction identifier is used to uniquely identify
         the modem DM log collection action invoked via RPC";
    }
    leaf status {
      type ios-xe-cwan-actions-rpc:cwan-resp-status;
      description
        "Stop DM log response status";
    }
    leaf file-path {
      type string;
      description
        "DM log file path generated on the device";
    }
  }

  grouping cwan-remove-dmlog {
    description
      "This module defines the actions on the
       cellular modem to remove modem DM log";
    leaf dm-tid {
      type string {
        length "1..255";
        pattern "[\\] A-Za-z0-9!\"#%&()*+,\\-./:;<=>^?@\\\\$_`{|}\\[']+";
      }
      mandatory true;
      description
        "The DM log transaction identifier is used to uniquely identify
         the modem DM log collection action invoked via RPC";
    }
    leaf if-name {
      type string {
        length "1..64";
        pattern '[0-9a-zA-Z\-_/]*';
      }
      mandatory true;
      description
        "Interface name to remove modem DM log file";
    }
  }

  grouping cwan-remove-dmlog-resp {
    description
      "Response to cellular remove DM log action command";
    leaf status {
      type ios-xe-cwan-actions-rpc:cwan-resp-status;
      description
        "Remove DM log response status";
    }
  }

  rpc cwan-start-dmlog {
    description
      "Start cellular modem DM log collection command";
    input {
      uses ios-xe-cwan-actions-rpc:cwan-start-dmlog;
    }
    output {
      uses ios-xe-cwan-actions-rpc:cwan-start-dmlog-resp;
    }
  }

  rpc cwan-stop-dmlog {
    description
      "Stop cellular modem DM log collection command";
    input {
      uses ios-xe-cwan-actions-rpc:cwan-stop-dmlog;
    }
    output {
      uses ios-xe-cwan-actions-rpc:cwan-stop-dmlog-resp;
    }
  }

  rpc cwan-remove-dmlog {
    description
      "Remove cellular modem DM log command";
    input {
      uses ios-xe-cwan-actions-rpc:cwan-remove-dmlog;
    }
    output {
      uses ios-xe-cwan-actions-rpc:cwan-remove-dmlog-resp;
    }
  }
}
