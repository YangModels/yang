module Cisco-IOS-XE-lte450-oper {
  yang-version 1.1;
  namespace "http://cisco.com/ns/yang/Cisco-IOS-XE-lte450-oper";
  prefix lte450-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for LTE450 device operational data.
     Copyright (c) 2025 by Cisco Systems, Inc.
     All rights reserved.";

  revision 2025-07-01 {
    description
      "Initial revision";
    reference
      "1.0.0";
    cisco-semver:module-version "1.0.0";
  }

  typedef lte450-conn-status {
    type enumeration {
      enum conn-status-init {
        value 0;
        description
          "The connection is in initializing state";
      }
      enum conn-status-offline {
        value 1;
        description
          "The connection is in offline state";
      }
      enum conn-status-online {
        value 2;
        description
          "The connection is in online state";
      }
      enum conn-status-unknown {
        value 3;
        description
          "The connection is in unknown state";
      }
    }
    description
      "Indicates the current connection status of the LTE450 module";
  }

  typedef lte450-sys-mode {
    type enumeration {
      enum sys-mode-unknown {
        value 0;
        description
          "The LTE450 system mode is unknown";
      }
      enum sys-mode-lte {
        value 1;
        description
          "The LTE450 system mode is LTE";
      }
    }
    description
      "LTE450 module system mode";
  }

  typedef lte450-eps-state {
    type enumeration {
      enum eps-state-unknown {
        value 0;
        description
          "The LTE450 EPS state is unknown";
      }
      enum eps-state-attached {
        value 1;
        description
          "The LTE450 EPS state is attached";
      }
      enum eps-state-detached {
        value 2;
        description
          "The LTE450 EPS state is detached";
      }
      enum eps-state-plmn-searched {
        value 3;
        description
          "The LTE450 EPS state is PLMN searched";
      }
    }
    description
      "LTE450 module EPS state";
  }

  typedef lte450-rrc-state {
    type enumeration {
      enum rrc-state-unknown {
        value 0;
        description
          "The LTE450 RRC state is unknown";
      }
      enum rrc-state-idle {
        value 1;
        description
          "The LTE450 RRC state is idle";
      }
      enum rrc-state-connected {
        value 2;
        description
          "The LTE450 RRC state is connected";
      }
    }
    description
      "LTE450 module RRC state";
  }

  typedef lte450-bw {
    type enumeration {
      enum bw-unknown {
        value 0;
        description
          "The LTE450 module bandwidth is unknown";
      }
      enum bw-1dot4-mhz {
        value 1;
        description
          "The LTE450 module bandwidth is 1.4 Mhz";
      }
      enum bw-3-mhz {
        value 2;
        description
          "The LTE450 module bandwidth is 3 Mhz";
      }
      enum bw-5-mhz {
        value 3;
        description
          "The LTE450 module bandwidth is 5 Mhz";
      }
    }
    description
      "LTE450 module bandwidth";
  }

  typedef lte450-band {
    type enumeration {
      enum band-unknown {
        value 0;
        description
          "The LTE450 module band is unknown";
      }
      enum band-31-mhz {
        value 1;
        description
          "The LTE450 module band is 31 Mhz";
      }
      enum band-72-mhz {
        value 2;
        description
          "The LTE450 module band is 72 Mhz";
      }
    }
    description
      "LTE450 band in MHz";
  }

  grouping lte450-hw-entry {
    description
      "LTE450 module hardware information";
    leaf if-name {
      type string;
      description
        "LTE450 interface name";
    }
    leaf sys-time {
      type yang:date-and-time;
      description
        "The LTE450 modem current date and time";
    }
    leaf boot-time {
      type yang:date-and-time;
      description
        "The absolute time from boot event of the modem";
    }
    leaf free-disk {
      type uint64;
      units "kilobytes";
      description
        "Available free disk space in kilobytes";
    }
    leaf free-ram {
      type uint64;
      units "kilobytes";
      description
        "Available free RAM in kilobytes";
    }
    leaf modem-mac {
      type yang:mac-address;
      description
        "The MAC address of the LTE450 modem";
    }
    leaf modem-hw-ver {
      type string;
      description
        "The modem hardware version";
    }
    leaf modem-fw-ver {
      type string;
      description
        "The LTE450 Modem firmware version";
    }
    leaf modem-temp {
      type decimal64 {
        fraction-digits 2;
      }
      units "celsius";
      description
        "The LTE450 modem temperature in celsius";
    }
    leaf pim-mac {
      type yang:mac-address;
      description
        "The MAC address of the PIM";
    }
    leaf pim-hw-ver {
      type string;
      description
        "The hardware version of the PIM";
    }
    leaf pim-fw-ver {
      type string;
      description
        "The firmware version of the PIM";
    }
    leaf pim-sn {
      type string;
      description
        "The serial number of the PIM";
    }
    leaf mgmt-ipv4-addr {
      type inet:ip-address;
      description
        "The IPv4 address of the management interface";
    }
    leaf mgmt-ipv6-addr {
      type inet:ipv6-address;
      description
        "The IPv6 address of the management interface";
    }
    leaf pim-temp {
      type decimal64 {
        fraction-digits 2;
      }
      units "celsius";
      description
        "The temperature of the PIM in celsius";
    }
    leaf hw-wd-ctr {
      type uint32;
      description
        "The hardware watchdog counter";
    }
    leaf modem-wd-ctr {
      type uint32;
      description
        "The Modem watchdog counter";
    }
  }

  grouping lte450-net-entry {
    description
      "LTE450 module network information";
    leaf if-name {
      type string;
      description
        "LTE450 interface name";
    }
    leaf conn-status {
      type lte450-ios-xe-oper:lte450-conn-status;
      description
        "The LTE450 modem connection status";
    }
    leaf conn-time {
      type yang:date-and-time;
      description
        "The date and time of the connection establishment";
    }
    leaf imsi {
      type string;
      description
        "The IMSI (International Mobile Subscriber Identity) of the SIM";
    }
    leaf iccid {
      type string;
      description
        "The ICCID (Integrated Circuit Card Identification) of the SIM";
    }
    leaf msisdn {
      type string;
      description
        "The MSISDN (Mobile Station International Subscriber Directory Number) of the SIM";
    }
    leaf apn1-ipv4-addr {
      type inet:ip-address;
      description
        "The IPv4 address of the APN-1 (Access Point Name 1)";
    }
    leaf apn1-ipv6-addr {
      type inet:ipv6-address;
      description
        "The IPv6 address of the APN-1 (Access Point Name 1)";
    }
    leaf apn2-ipv4-addr {
      type inet:ip-address;
      description
        "The IPv4 address of the APN-2 (Access Point Name 2)";
    }
    leaf apn2-ipv6-addr {
      type inet:ipv6-address;
      description
        "The IPv6 address of the APN-2 (Access Point Name 2)";
    }
    leaf apn3-ipv4-addr {
      type inet:ip-address;
      description
        "The IPv4 address of the APN-3 (Access Point Name 3)";
    }
    leaf apn3-ipv6-addr {
      type inet:ipv6-address;
      description
        "The IPv6 address of the APN-3 (Access Point Name 3)";
    }
    leaf imei {
      type string;
      description
        "The IMEI (International Mobile Equipment Identity) of the LTE450 modem";
    }
    leaf sys-mode {
      type lte450-ios-xe-oper:lte450-sys-mode;
      description
        "The wireless data transmission standard currently in use";
    }
    leaf eps-state {
      type lte450-ios-xe-oper:lte450-eps-state;
      description
        "The EPS (Evolved Packet System) connection state";
    }
    leaf rrc-state {
      type lte450-ios-xe-oper:lte450-rrc-state;
      description
        "The RRC (Radio Resource Control) operational state of the LTE450 Modem";
    }
    leaf cereg {
      type int16;
      description
        "The CEREG (Cellular Registration) status";
    }
    leaf apn1-name {
      type string;
      description
        "The name of the APN-1";
    }
    leaf apn2-name {
      type string;
      description
        "The name of the APN-2";
    }
    leaf apn3-name {
      type string;
      description
        "The name of the APN-3";
    }
    leaf band {
      type lte450-ios-xe-oper:lte450-band;
      description
        "The band currently in use";
    }
    leaf plmn {
      type string;
      description
        "The PLMN (Public Land Mobile Network) of the cellular network";
    }
    leaf cell-id {
      type uint64;
      description
        "The ID of the connected cell tower";
    }
    leaf tac {
      type string;
      description
        "The TAC (Tracking Area Code) of the LTE450 modem";
    }
    leaf pci {
      type uint16;
      description
        "The PCI (Physical Cell Identity) of the cell tower";
    }
    leaf tx-power {
      type int16;
      units "dBm";
      description
        "The transmission power measured in dBm";
    }
    leaf bw {
      type lte450-ios-xe-oper:lte450-bw;
      description
        "The bandwidth currently in use measured in MHz";
    }
    leaf lte-rx-chan {
      type uint32;
      units "RB";
      description
        "LTE reception channel of the LTE450 modem";
    }
    leaf lte-tx-chan {
      type uint32;
      units "RB";
      description
        "LTE transmission channel of the LTE450 modem";
    }
    leaf current-up {
      type decimal64 {
        fraction-digits 2;
      }
      units "kbps";
      description
        "The current upload speed in Kbps";
    }
    leaf current-dl {
      type decimal64 {
        fraction-digits 2;
      }
      units "kbps";
      description
        "The current download speed in Kbps";
    }
  }

  grouping lte450-radio-entry {
    description
      "LTE450 modem radio status entry details";
    leaf if-name {
      type string;
      description
        "LTE450 interface";
    }
    leaf rssi {
      type int16;
      units "dBm";
      description
        "The RSSI (Received Signal Strength Indicator) of the cellular network measured in dBm";
    }
    leaf rsrp {
      type int16;
      units "dBm";
      description
        "The RSRP (Reference Signal Received Power) of the cellular network measured in dBm";
    }
    leaf rsrq {
      type int16;
      units "dB";
      description
        "The RSRQ (Reference Signal Received Quality) of the cellular network measured in dBm";
    }
    leaf sinr {
      type int16;
      units "dB";
      description
        "The SINR (Signal-to-Interference-plus-Noise Ratio) of the cellular network measured in dBm";
    }
    leaf main-rssi {
      type int16;
      units "dBm";
      description
        "Antenna Main RSSI (Received Signal Strength Indicator) of the cellular network measured in dBm";
    }
    leaf main-rsrp {
      type int16;
      units "dBm";
      description
        "Antenna Main RSRP (Reference Signal Received Power) of the cellular network measured in dBm";
    }
    leaf aux-rssi {
      type int16;
      units "dBm";
      description
        "Antenna AUX RSSI (Received Signal Strength Indicator) of the cellular network measured in dBm";
    }
    leaf aux-rsrp {
      type int16;
      units "dBm";
      description
        "Antenna AUX RSRP (Reference Signal Received Power) of the cellular network measured in dBm";
    }
  }

  container lte450-oper-data {
    config false;
    description
      "LTE450 operational data";
    list lte450-hw {
      key "if-name";
      description
        "LTE450 hardware data";
      uses lte450-ios-xe-oper:lte450-hw-entry;
    }
    list lte450-net {
      key "if-name";
      description
        "LTE450 network data";
      uses lte450-ios-xe-oper:lte450-net-entry;
    }
    list lte450-radio {
      key "if-name";
      description
        "LTE450 radio data";
      uses lte450-ios-xe-oper:lte450-radio-entry;
    }
  }
}
