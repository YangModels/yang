module tailf-key-rotation {
  namespace "http://tail-f.com/ns/key-rotation";
  prefix keyrotation;

  yang-version 1.1;

  import ietf-yang-types {
    prefix yang;
  }
  import tailf-common {
    prefix tailf;
  }

  organization "Tail-f Systems";
  description
    "This module defines a data model for key-rotation action.

     Copyright 2024-2025 Cisco Systems, Inc.
     All rights reserved.
     Permission is hereby granted to redistribute this file without
     modification.";

  revision 2025-01-23 {
    description
     "Released as part of ConfD-8.4.2 / NCS-6.4.2.

      Added extension 'tailf:cli-operational-mode'
      to /key-rotation/apply-new-keys.

      Added action /key-rotation/show-active-generation.
     ";
  }

  revision 2024-11-14 {
   description
     "Released as part of ConfD-8.4 / NCS-6.4.
     ";
  }

  container key-rotation {
    tailf:info "Re-encryption of CDB";

    action apply-new-keys {

      tailf:cli-operational-mode;
      tailf:info "Re-encrypt all encrypted values with a new set of keys";

      description
        "Re-encrypt all encrypted string values with a new set of keys.
        ";

      tailf:actionpoint keyrotation {
        tailf:internal;
      }

      input {
        leaf new-key-generation {
          description
            "The new key generation to rotate to must be provided and loaded.";
          type int16 {
            range "-1..max";
          }
          mandatory true;
        }
      }

      output {
        leaf result {
          description
            "Indication of successful or unsuccessful key rotation.";
          type boolean;
        }

        choice return {
          case ok {
            leaf new-active-key-generation {
              description
                "The new active key generation after key rotation.";
              type int16;
            }
          }
          case error {
            leaf reason {
              description
                "Indication of what did not succeed during key rotation";
              type string;
            }
          }
        }
      }
    }

    action get-active-generation {
      tailf:cli-operational-mode;
      tailf:info "Display the currently active generation.";

      tailf:actionpoint keyrotation-get-active-generation {
        tailf:internal;
      }

      output {
        leaf active-generation {
          description
            "Currently active generation.";
          type int16;
        }
      }
    }
  }
}
