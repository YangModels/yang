module Cisco-IOS-XE-cwan-fw-rpc {
  yang-version 1.1;
  namespace "http://cisco.com/ns/yang/Cisco-IOS-XE-cwan-fw-rpc";
  prefix ios-xe-cwan-fw-rpc;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Copyright (c) 2024-2025 by Cisco Systems, Inc.
     All rights reserved.";

  revision 2025-07-01 {
    description
      "- Added firmware type and image name.
       - Added a new firmware type LTE450.";
    reference
      "1.1.0";
    cisco-semver:module-version "1.1.0";
  }
  revision 2024-03-01 {
    description
      "Initial revision";
    reference
      "1.0.0";
    cisco-semver:module-version "1.0.0";
  }

  typedef fw-type {
    type enumeration {
      enum default-fw {
        value 0;
        description
          "Firmware type to indicate upgrade of all modules on the device.";
      }
      enum cwan-fw {
        value 1;
        description
          "Firmware type of the cellular modem.";
      }
      enum wim-wgb-fw {
        value 2;
        description
          "Firmware type of embedded AP in WGB (WorkGroup Bridge) mode.";
      }
      enum lte450-fw {
        value 3;
        description
          "Firmware type of the LTE450 module.";
      }
    }
    description
      "Firmware type of the module.";
  }

  grouping trigger-upgrade {
    description
      "This module defines the actions that can be.
       performed on the cellular modem for firmware upgrade.";
    leaf fw-tid {
      type string {
        length "1..255";
        pattern "[\\] A-Za-z0-9!\"#%&()*+,\\-./:;<=>^?@\\\\$_`{|}\\[']+";
      }
      mandatory true;
      description
        "The firmware transaction identifier is used to uniquely identify
         the modem firmware upgrade action invoked via RPC.";
    }
    leaf src-path {
      type string {
        length "1..4095";
        pattern "[\\] A-Za-z0-9!\"#%&()*+,\\-./:;<=>^?@\\\\$_`{|}\\[']+";
      }
      mandatory true;
      description
        "Source path:
         for download to device: scp://user:password@ipv4 address:/path/to/file
         or https://ipv4 address/path/to/file
         or http://ipv4 address/path/to/file
         or ftp://user:password@ipv4 address:/path/to/file";
    }
    leaf uname {
      type string {
        length "1..63";
      }
      description
        "Username to be used for remote device";
    }
    leaf passwd {
      type string {
        length "1..63";
      }
      description
        "Password to be used for remote device";
    }
    leaf vpn {
      type string {
        length "0..32";
      }
      description
        "VPN name instance to reach remote device.";
    }
    leaf dnld-timeout {
      type uint32;
      units "minutes";
      description
        "Timeout period guarding modem firmware upgrade operation.
         If operation not completed, download will be aborted after this time.";
    }
    leaf schd-start {
      type yang:date-and-time;
      must 'current() and (../schd-end)' {
        error-message "Scheduled start time must be specified along with scheduled end time.";
        error-app-tag "must-violation";
      }
      description
        "Scheduled modem firmware upgrade start time";
    }
    leaf schd-end {
      type yang:date-and-time;
      description
        "Scheduled modem firmware upgrade end time and end time has to be minimum 10 min in future.";
    }
    leaf fwtype {
      type ios-xe-cwan-fw-rpc:fw-type;
      description
        "Firmware type of the embedded AP.";
    }
    leaf img-name {
      type string {
        length "1..63";
        pattern '[0-9a-zA-Z\-._]*';
      }
      description
        "Specific image to be picked from source path folder.
         This is used to upgrade or downgrade the firmware to a specific version.";
    }
  }

  grouping trigger-upgrade-response {
    description
      "Response to cellular modem firmware action command";
    leaf fw-tid {
      type string;
      description
        "The firmware transaction identifier is used to uniquely identify
         the modem firmware upgrade action invoked via RPC.";
    }
  }

  grouping cancel-upgrade {
    description
      "This module defines the actions that will cancel the
        scheduled modem firmware upgrade.";
    leaf fw-tid {
      type string {
        length "1..255";
        pattern "[\\] A-Za-z0-9!\"#%&()*+,\\-./:;<=>^?@\\\\$_`{|}\\[']+";
      }
      mandatory true;
      description
        "The firmware transaction identifier is used to uniquely identify
         the cancel scheduled modem firmware upgrade action invoked via RPC.";
    }
  }

  grouping cancel-upgrade-response {
    description
      "Response to cancel scheduled cellular modem firmware action command";
    leaf fw-tid {
      type string;
      description
        "The firmware transaction identifier is used to uniquely identify
         the cancel scheduled modem firmware upgrade action invoked via RPC.";
    }
  }

  rpc trigger-upgrade {
    description
      "Cellular modem firmware action command";
    input {
      uses ios-xe-cwan-fw-rpc:trigger-upgrade;
    }
    output {
      uses ios-xe-cwan-fw-rpc:trigger-upgrade-response;
    }
  }

  rpc cancel-upgrade {
    description
      "Cancel scheduled cellular modem firmware action command";
    input {
      uses ios-xe-cwan-fw-rpc:cancel-upgrade;
    }
    output {
      uses ios-xe-cwan-fw-rpc:cancel-upgrade-response;
    }
  }
}
