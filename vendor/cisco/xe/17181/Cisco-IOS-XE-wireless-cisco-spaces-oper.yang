module Cisco-IOS-XE-wireless-cisco-spaces-oper {
  yang-version 1.1;
  namespace "http://cisco.com/ns/yang/Cisco-IOS-XE-wireless-cisco-spaces-oper";
  prefix wireless-cisco-spaces-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Cisco wireless controller and spaces.
     Copyright (c) 2023-2024 by Cisco Systems, Inc.
     All rights reserved.";

  revision 2024-07-01 {
    description
      "Initial revision";
    reference
      "1.0.0";
    cisco-semver:module-version "1.0.0";
  }

  typedef spaces-onb-ws-state {
    type enumeration {
      enum enm-spaces-ws-not-connected {
        value 0;
        description
          "Web-socket connection not UP";
      }
      enum enm-spaces-ws-connected {
        value 1;
        description
          "Web-socket connection is UP";
      }
      enum enm-spaces-ws-in-progress {
        value 2;
        description
          "Web-socket connection is in progress";
      }
      enum enm-spaces-ws-disconnecting {
        value 3;
        description
          "Web-socket connection is disconnecting";
      }
    }
    description
      "Cisco spaces onboarding web-socket connection state";
  }

  typedef spaces-onb-ws-dis-reason {
    type enumeration {
      enum enm-spaces-dis-unknown {
        value 0;
        description
          "Connection error unknown";
      }
      enum enm-spaces-dis-dns-res-fail {
        value 1;
        description
          "Connection error DNS resolution failed";
      }
      enum enm-spaces-dis-unauthorized {
        value 2;
        description
          "Connection error unauthorized from server";
      }
      enum enm-spaces-dis-server-cert-ver-fail {
        value 3;
        description
          "Connection error server certificate verification failed";
      }
      enum enm-spaces-dis-network-error {
        value 4;
        description
          "Connection error network unreachable";
      }
      enum enm-spaces-dis-heartbeat-ack-miss {
        value 5;
        description
          "Disconnect heartbeat ACK miss from server";
      }
      enum enm-spaces-dis-user-triggered {
        value 6;
        description
          "Disconnect triggered by the user";
      }
    }
    description
      "Cisco spaces onboarding web-socket last disconnect reason";
  }

  grouping st-spaces-onb-ws-con-stats {
    description
      "Cisco spaces onboarding web-socket connection statistics";
    leaf total-con-attempts {
      type uint64;
      description
        "Total number of connection attempts";
    }
    leaf con-attempts-success {
      type uint64;
      description
        "Total number of attempts that succeeded";
    }
    leaf con-attempts-failure {
      type uint64;
      description
        "Total number of attempts that failed";
    }
    leaf total-discon {
      type uint64;
      description
        "Total number of disconnections";
    }
  }

  grouping st-spaces-onb-ws-tenant-detail {
    description
      "Cisco spaces onboarding web-socket tenant details";
    leaf tenant-id {
      type string;
      description
        "Tenant Identifier";
    }
    leaf tenant-name {
      type string;
      description
        "Tenant Name";
    }
  }

  grouping spaces-connection-detail {
    description
      "Cisco wireless controller to spaces connection details";
    leaf spaces-health-url {
      type string;
      description
        "Cisco spaces health check URL";
    }
    leaf con-state {
      type wireless-cisco-spaces-oper:spaces-onb-ws-state;
      description
        "Cisco spaces onboarding web-socket connection state";
    }
    leaf last-conn-err {
      type wireless-cisco-spaces-oper:spaces-onb-ws-dis-reason;
      description
        "Cisco spaces onboarding web-socket last connection error";
    }
    leaf conn-estb-time {
      type yang:date-and-time;
      description
        "Absolute time at which the onboarding web-socket connected";
    }
    container stats {
      description
        "Cisco spaces onboarding web-socket connection statistics";
      uses wireless-cisco-spaces-oper:st-spaces-onb-ws-con-stats;
    }
    container tenant {
      description
        "Cisco spaces onboarding web-socket tenant details";
      uses wireless-cisco-spaces-oper:st-spaces-onb-ws-tenant-detail;
    }
  }

  container cisco-spaces-oper-data {
    config false;
    description
      "Cisco spaces operational data";
    container spaces-connection-detail {
      presence "spaces-connection-detail";
      description
        "Statistics and connection details to Cisco spaces";
      uses wireless-cisco-spaces-oper:spaces-connection-detail;
    }
  }
}
