module Cisco-IOS-XE-cli-preview-rpc {
  yang-version 1.1;
  namespace "http://cisco.com/ns/yang/Cisco-IOS-XE-cli-preview-rpc";
  prefix ios-xe-cli-preview;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for the Configuration CLI Preview RPC.
     Copyright (c) 2023 by Cisco Systems, Inc.
     All rights reserved.";

  revision 2023-11-01 {
    description
      "Initial revision";
    reference
      "1.0.0";
    cisco-semver:module-version "1.0.0";
  }

  grouping cli-preview-netconf-xml-input {
    description
      "NETCONF XML encoded configuration input arguments";
    leaf config-xml {
      type string;
      mandatory true;
      description
        "This leaf accepts a NETCONF XML <config> tag holding configuration
         data corresponding to the device's YANG models similar to the
         <edit-config> RPC.

         For example:
         <config>
         ...
         </config>

         The target datastore is the 'running' datastore. The 'candidate'
         datastore is not supported.

         This leaf is defined to be of type 'string' and the input XML will
         need to be escaped when this RPC is executed using NETCONF.";
    }
  }

  grouping cli-preview {
    description
      "Config CLI Preview RPC input arguments";
    leaf custom-timeout {
      type uint32 {
        range "1..600";
      }
      units "seconds";
      default "60";
      description
        "The time required to generate a configuration CLI preview will
         vary with the input configuration. This leaf allows the client
         to specify how long it is willing to wait for a preview operation
         to complete up to a maximum of 600 seconds. If this leaf is not
         explicitly set the default value of 60 seconds will apply.";
    }
    choice input-choice {
      mandatory true;
      description
        "Input format options";
      case cli-preview-input-netconf-xml {
        container netconf-xml {
          description
            "NETCONF XML encoded configuration input";
          uses ios-xe-cli-preview:cli-preview-netconf-xml-input;
        }
      }
    }
  }

  grouping cli-preview-output {
    description
      "Configuration CLI Preview output data";
    leaf config-cli {
      type string;
      description
        "A preview of the IOS-XE command-line interface (CLI) configuration
         commands needed to apply the input configuration. The returned
         commands depend on the device's current configuration state and will
         vary if the device's configuration changes.";
    }
  }

  rpc cli-preview {
    description
      "The configuration CLI preview RPC accepts NETCONF XML encoded
       configuration based on YANG model schemas. It will return a
       preview of the IOS-XE command-line interface (CLI) configuration
       commands needed to apply the configuration. The returned commands
       depend on the device's current configuration state and will vary
       if the device's configuration changes. The configuration will not
       be applied to the device.";
    input {
      uses ios-xe-cli-preview:cli-preview;
    }
    output {
      uses ios-xe-cli-preview:cli-preview-output;
    }
  }
}
