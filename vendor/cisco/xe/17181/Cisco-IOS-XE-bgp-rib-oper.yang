module Cisco-IOS-XE-bgp-rib-oper {
  yang-version 1.1;
  namespace "http://cisco.com/ns/yang/Cisco-IOS-XE-bgp-rib-oper";
  prefix bgp-ios-rib-xe-oper;

  import Cisco-IOS-XE-common-types {
    prefix common-types-ios-xe;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for BGP RIB operational data.It provides detailed
     information about BGP paths, attributes, and their status
     within the BGP RIB.
     Copyright (c) 2020, 2024-2025 by Cisco Systems, Inc.
     All rights reserved.";

  revision 2025-07-01 {
    description
      "Initial revision";
    reference
      "1.0.0";
    cisco-semver:module-version "1.0.0";
  }

  typedef bgp-afisafi {
    type enumeration {
      enum baf-v4-mdt {
        value 0;
        description
          "IPv4 MDT address family";
      }
      enum baf-v4-mc {
        value 1;
        description
          "BGP IPv4 Multicast address family";
      }
      enum baf-v4-uc {
        value 2;
        description
          "BGP IPv4 Unicast address family";
      }
      enum baf-v4-mv {
        value 3;
        description
          "BGP IPV4 MVPN address family";
      }
      enum baf-v4-fs {
        value 4;
        description
          "BGP IPv4 Flowspec address family";
      }
      enum baf-v6-mc {
        value 5;
        description
          "BGP IPv6 Multicast address family";
      }
      enum baf-v6-uc {
        value 6;
        description
          "BGP IPv6 Unicast address family";
      }
      enum baf-v6-mv {
        value 7;
        description
          "BGP IPv6 MVPN address family";
      }
      enum baf-v6-fs {
        value 8;
        description
          "BGP IPv6 Flowspec address family";
      }
      enum baf-vpls {
        value 9;
        description
          "BGP L2VPN VPLS address family";
      }
      enum baf-evpn {
        value 10;
        description
          "BGP L2VPN EVPN address family";
      }
      enum baf-ns-uc {
        value 11;
        description
          "BGP NSAP Unicast address family";
      }
      enum baf-rtf-uc {
        value 12;
        description
          "BGP RT Filter Unicast address family";
      }
      enum baf-vn4-mc {
        value 13;
        description
          "BGP VPNv4 Multicast address family";
      }
      enum baf-vn4-uc {
        value 14;
        description
          "BGP VPNv4 Unicast address family";
      }
      enum baf-vn6-uc {
        value 15;
        description
          "BGP VPNv6 Unicast address family";
      }
      enum baf-vn6-mc {
        value 16;
        description
          "BGP VPNv6 Multicast address family";
      }
      enum baf-vn4-fs {
        value 17;
        description
          "BGP VPNv4 Flowspec address family";
      }
      enum baf-vn6-fs {
        value 18;
        description
          "BGP VPNv6 Flowspec address family";
      }
    }
    description
      "Address family and Subsequent Address Family Identifier for BGP";
  }

  typedef bgp-path-origin-code {
    type enumeration {
      enum bo-igp {
        value 0;
        description
          "BGP origin code IGP (Interior Gateway Protocol). Indicates that the route was learned from an IGP.";
      }
      enum bo-egp {
        value 1;
        description
          "BGP origin code EGP (Exterior Gateway Protocol). Indicates that the route was learned from an EGP.";
      }
      enum bo-inc {
        value 2;
        description
          "BGP origin code INCOMPLETE. Indicates that the origin of the route is unknown or learned in a different way.";
      }
    }
    description
      "BGP attribute defining the origin of the path information.The origin code indicates how BGP learned about the route.";
  }

  typedef bgp-path-rpki-status {
    type enumeration {
      enum br-val {
        value 0;
        description
          "The BGP route is valid according to RPKI validation.";
      }
      enum br-inv {
        value 1;
        description
          "The BGP route is invalid according to RPKI validation.";
      }
      enum br-nf {
        value 2;
        description
          "The BGP route does not have a corresponding RPKI record.";
      }
      enum br-ne {
        value 3;
        description
          "RPKI validation is not enabled for the BGP route.";
      }
      enum br-ill {
        value 4;
        description
          "The BGP route has an illegal RPKI status.";
      }
    }
    description
      "The RPKI (Resource Public Key Infrastructure) status of the BGP path, indicating the validity of the route based on cryptographic validation.";
  }

  typedef bgp-as-path-type {
    type enumeration {
      enum bas-sq {
        value 0;
        description
          "A sequence of AS numbers that the route has passed through, in the order they were traversed.";
      }
      enum bas-set {
        value 1;
        description
          "A set of AS numbers that the route has passed through, without any specific order.";
      }
      enum bas-csq {
        value 2;
        description
          "A sequence of AS numbers within a BGP confederation, in the order they were traversed.";
      }
      enum bas-cset {
        value 3;
        description
          "A set of AS numbers within a BGP confederation, without any specific order.";
      }
    }
    description
      "Defines the type of AS (Autonomous System) path used in BGP routing. This can include sequences or sets of AS numbers that the route has traversed.";
  }

  typedef bgp-path-source {
    type enumeration {
      enum bps-bgp {
        value 0;
        description
          "The path was learned from BGP (Border Gateway Protocol).";
      }
      enum bps-co {
        value 1;
        description
          "The path was learned from a directly connected network.";
      }
      enum bps-isis {
        value 2;
        description
          "The path was learned from IS-IS (Intermediate System to Intermediate System).";
      }
      enum bps-ospf {
        value 3;
        description
          "The path was learned from OSPF (Open Shortest Path First).";
      }
      enum bps-ospfv3 {
        value 4;
        description
          "The path was learned from OSPFv3 (Open Shortest Path First version 3).";
      }
      enum bps-st {
        value 5;
        description
          "The path was learned from a static route.";
      }
      enum bps-ri {
        value 6;
        description
          "The path was learned from the internal RIB (Routing Information Base).";
      }
      enum bps-rt {
        value 7;
        description
          "The path was received from another router.";
      }
    }
    description
      "The source of the BGP path, indicating the protocol or method by which the path was learned.";
  }

  typedef bgp-well-known-comm {
    type enumeration {
      enum bwc-ex {
        value 0;
        description
          "Do not export the route to other BGP peers.";
      }
      enum bwc-na {
        value 1;
        description
          "Do not advertise the route to any BGP peer.";
      }
      enum bwc-la {
        value 2;
        description
          "Do not export the route to external BGP peers outside the confederation.";
      }
      enum bwc-in {
        value 3;
        description
          "Advertise the route to the Internet.";
      }
      enum bwc-gs {
        value 4;
        description
          "Graceful shutdown community, indicating the route is being withdrawn.";
      }
    }
    description
      "Well-known BGP community values recognized by all BGP implementations, providing standard tags for routing policies.";
  }

  typedef bgp-extcomm-type {
    type enumeration {
      enum bext-soo {
        value 0;
        description
          "BGP site of origin extended community.";
      }
      enum bext-rt {
        value 1;
        description
          "BGP route target extended community.";
      }
      enum bext-ort {
        value 2;
        description
          "BGP OSPF route target extended community.";
      }
      enum bext-od {
        value 3;
        description
          "BGP OSPF domain id extended community.";
      }
      enum bext-lb {
        value 4;
        description
          "BGP load balancing extended community.";
      }
      enum bext-nlb {
        value 5;
        description
          "BGP link bandwidth extended community.";
      }
      enum bext-or {
        value 6;
        description
          "BGP ospf router id extended community.";
      }
      enum bext-maf {
        value 7;
        description
          "BGP mvpn address format extended community.";
      }
      enum bext-masf {
        value 8;
        description
          "BGP mvpn as format extended community.";
      }
      enum bext-mas4f {
        value 9;
        description
          "BGP mvpn as4 format extended community.";
      }
      enum bext-mc {
        value 10;
        description
          "BGP multicast extended community.";
      }
      enum bext-cost {
        value 11;
        description
          "BGP cost extended community.";
      }
      enum bext-vpn {
        value 12;
        description
          "BGP vpn id extended community.";
      }
      enum bext-fltr {
        value 13;
        description
          "BGP flowspec traffic rate extended community.";
      }
      enum bext-flrr {
        value 14;
        description
          "BGP flowspec redirect route target extended community.";
      }
      enum bext-fltm {
        value 15;
        description
          "BGP flowspec traffic mark extended community.";
      }
      enum bext-flrn {
        value 16;
        description
          "BGP flowspec redirect ip nexthop extended community.";
      }
      enum bext-flta {
        value 17;
        description
          "BGP flowspec traffic action extended community.";
      }
      enum bext-flis {
        value 18;
        description
          "BGP flowspec interface set extended community.";
      }
      enum bext-flet {
        value 19;
        description
          "BGP encap tunnel extended community.";
      }
      enum bext-clr {
        value 20;
        description
          "BGP color extended community.";
      }
    }
    description
      "Different types of BGP extended communities.";
  }

  typedef bgp-path-status {
    type bits {
      bit bp-su {
        position 0;
        description
          "The path is suppressed and not advertised.";
      }
      bit bp-dp {
        position 1;
        description
          "The path is damped due to route flapping.";
      }
      bit bp-hs {
        position 2;
        description
          "The path is in the history state.";
      }
      bit bp-vl {
        position 3;
        description
          "The path is valid.";
      }
      bit bp-sr {
        position 4;
        description
          "The path is sourced locally.";
      }
      bit bp-bp {
        position 5;
        description
          "The path is selected as the best path.";
      }
      bit bp-in {
        position 6;
        description
          "The path is internal to the AS.";
      }
      bit bp-rf {
        position 7;
        description
          "The path failed to be installed in the RIB.";
      }
      bit bp-st {
        position 8;
        description
          "The path is stale.";
      }
      bit bp-mp {
        position 9;
        description
          "The path is part of a multipath group.";
      }
      bit bp-bk {
        position 10;
        description
          "The path is a backup path.";
      }
      bit bp-rft {
        position 11;
        description
          "The path is used for RT filtering.";
      }
      bit bp-be {
        position 12;
        description
          "The path is the best external path.";
      }
      bit bp-ap {
        position 13;
        description
          "The path is an additional path.";
      }
      bit bp-rc {
        position 14;
        description
          "The path is compressed in the RIB.";
      }
    }
    description
      "Flags indicating the status of the BGP path, providing detailed information about the path's state and characteristics.";
  }

  typedef bgp-path-unknown-attr-flag {
    type bits {
      bit bu-tr {
        position 0;
        description
          "BGP Path Unknown Attribute Transitive.";
      }
      bit bu-op {
        position 1;
        description
          "BGP Path Unknown Attribute Optional.";
      }
      bit bu-pa {
        position 2;
        description
          "BGP Path Unknown Attribute Partial.";
      }
      bit bu-ex {
        position 3;
        description
          "BGP Path Unknown Attribute Extended.";
      }
    }
    description
      "Flag indicating the presence of unknown BGP path attributes.";
  }

  grouping bgp-num-comm-info {
    description
      "BGP numbered community information.";
    leaf num-comm {
      type uint32;
      description
        "BGP numbered community value.";
    }
  }

  grouping bgp-ext-comm-info {
    description
      "BGP extended community information.";
    leaf ext-comm-type {
      type bgp-ios-rib-xe-oper:bgp-extcomm-type;
      description
        "Types of BGP extended communities.";
    }
    leaf comm {
      type string;
      description
        "BGP community value.";
    }
  }

  grouping bgp-lrg-comm-info {
    description
      "BGP large community information.";
    leaf comm {
      type string;
      description
        "BGP community value.";
    }
  }

  grouping bgp-comm-info {
    description
      "Detailed standard community information attribute for BGP paths, providing specific community identifiers and their associated strings.";
    leaf id {
      type uint32;
      description
        "Unique identifier for the BGP standard community.";
    }
    list bgp-num-comm {
      key "num-comm";
      description
        "BGP standard community table.";
      uses bgp-ios-rib-xe-oper:bgp-num-comm-info;
    }
    leaf-list well-kn-comm {
      type bgp-ios-rib-xe-oper:bgp-well-known-comm;
      ordered-by user;
      description
        "BGP well known community.";
    }
  }

  grouping bgp-lrgcomm-info {
    description
      "Detailed large community information attribute for BGP paths, providing specific community identifiers and their associated strings.";
    leaf id {
      type uint32;
      description
        "Unique identifier for the BGP large community.";
    }
    list bgp-lrg-comm {
      key "comm";
      description
        "BGP large community table.";
      uses bgp-ios-rib-xe-oper:bgp-lrg-comm-info;
    }
  }

  grouping bgp-extcomm-info {
    description
      "Detailed extended community information attribute for BGP paths, providing specific community identifiers and their associated strings.";
    leaf id {
      type uint32;
      description
        "Unique identifier for the BGP extended community.";
    }
    list bgp-ext-comm {
      key "ext-comm-type comm";
      description
        "BGP extended community table.";
      uses bgp-ios-rib-xe-oper:bgp-ext-comm-info;
    }
  }

  grouping bgp-as-value {
    description
      "The AS value attribute for BGP paths, representing the specific AS number associated with the path.";
    leaf as-value {
      type string;
      description
        "The Autonomous System (AS) number value associated with the BGP path.";
    }
  }

  grouping bgp-as-path {
    description
      "The AS path attribute, which lists the AS numbers that the route has traversed.";
    leaf as-type {
      type bgp-ios-rib-xe-oper:bgp-as-path-type;
      description
        "BGP AS Path Type.";
    }
    list as-value {
      description
        "BGP AS Path Value.";
      uses bgp-ios-rib-xe-oper:bgp-as-value;
    }
  }

  grouping bgp-path-attr {
    description
      "Detailed attributes associated with a BGP path, providing comprehensive information about the path's characteristics and metrics.";
    leaf nh {
      type inet:ip-address;
      description
        "The next-hop IP address for the BGP route, indicating the immediate next router to which packets should be forwarded.";
    }
    leaf if-name {
      type string;
      description
        "Contains interface name if the next-hop is a link-local address, empty otherwise.";
    }
    leaf metric {
      type uint32;
      description
        "Metric associated with the path, used for determining the best path among multiple available paths.";
    }
    leaf lp {
      type uint32;
      description
        "Local preference for this path, used to prefer one path over another within the same AS.";
    }
    leaf weight {
      type uint32;
      description
        "Path weight, a Cisco-specific attribute used to select the best path when multiple paths are available.";
    }
    list as-path {
      description
        "AS path, listing the sequence of AS numbers that the route has traversed.";
      uses bgp-ios-rib-xe-oper:bgp-as-path;
    }
    leaf origin {
      type bgp-ios-rib-xe-oper:bgp-path-origin-code;
      description
        "Path origin, indicating how BGP learned about the route (IGP, EGP, or INCOMPLETE).";
    }
    list as4-path {
      description
        "AS path using 4-octet AS numbers, providing support for larger AS numbers.";
      uses bgp-ios-rib-xe-oper:bgp-as-path;
    }
    leaf aa {
      type boolean;
      description
        "Attribute indicating whether or not the prefix is an atomic aggregate, meaning it has been summarized.";
    }
    leaf aggr-as-num {
      type uint32;
      description
        "AS number of the autonomous system that performed the aggregation of the route.";
    }
    leaf aggr-as4-num {
      type uint32;
      description
        "AS4 number of the autonomous system that performed the aggregation of the route.";
    }
    leaf aggr-addr {
      type inet:ip-address;
      description
        "IP address of the router that performed the aggregation of the route.";
    }
    leaf orig-id {
      type inet:ip-address;
      description
        "The router ID of the originator of the route in the local AS, used in route reflection.";
    }
    leaf-list cl-id {
      type inet:ip-address;
      ordered-by user;
      description
        "The reflection path the route has passed, listing the cluster IDs of route reflectors.";
    }
    leaf ext-aigp-metric {
      type uint64;
      description
        "The accumulated IGP metric for the path, used for comparing paths based on IGP metrics.";
    }
    leaf path-cnt {
      type uint32;
      description
        "Path count, indicating the number of paths available for the route.";
    }
  }

  grouping bgp-attr-key {
    description
      "BGP attribute key.";
    leaf attr-id {
      type uint32;
      description
        "Attribute Index.";
    }
  }

  grouping bgp-path-unknown-attr {
    description
      "BGP path unknown attributes.";
    leaf type {
      type uint8;
      description
        "BGP path unknown attribute type.";
    }
    leaf len {
      type uint16;
      description
        "BGP path unknown attribute length.";
    }
    leaf val {
      type yang:hex-string;
      description
        "BGP path unknown attribute value.";
    }
    leaf fg {
      type bgp-ios-rib-xe-oper:bgp-path-unknown-attr-flag;
      description
        "BGP path unknown attribute flags.";
    }
  }

  grouping bgp-path-info {
    description
      "Detailed information about the BGP path, including various attributes and statuses.";
    leaf path-st {
      type bgp-ios-rib-xe-oper:bgp-path-status;
      description
        "The current status of the BGP path.";
    }
    leaf rpki-st {
      type bgp-ios-rib-xe-oper:bgp-path-rpki-status;
      description
        "The RPKI (Resource Public Key Infrastructure) status of the BGP path.";
    }
    leaf mpls-in {
      type string;
      description
        "The MPLS (Multiprotocol Label Switching) label for incoming traffic on the path.";
    }
    leaf mpls-out {
      type string;
      description
        "The MPLS (Multiprotocol Label Switching) label for outgoing traffic on the path.";
    }
    leaf sr-prof-name {
      type string;
      description
        "The Segment Routing (SR) profile name associated with the path.";
    }
    leaf sr-bg-sid {
      type string;
      description
        "The Segment Routing (SR) binding SID (Segment Identifier) for the path.";
    }
    leaf sr-lbl-indx {
      type uint32;
      description
        "The Segment Routing (SR) label index for the path.";
    }
    leaf attr-idx {
      type uint32;
      description
        "Index to the BGP attribute associated with the path.";
    }
    leaf comm-idx {
      type uint32;
      description
        "Index to the BGP community associated with the path.";
    }
    leaf extcomm-idx {
      type uint32;
      description
        "Index to the BGP extended community associated with the path.";
    }
    leaf lrgcomm-idx {
      type uint32;
      description
        "Index to the BGP large community associated with the path.";
    }
    list un-attr {
      description
        "Unknown BGP path attribute.";
      uses bgp-ios-rib-xe-oper:bgp-path-unknown-attr;
    }
  }

  grouping bgp-path-key {
    description
      "Unique key identifying a specific BGP path, used to distinguish between different paths for the same prefix.";
    leaf src-orig {
      type bgp-ios-rib-xe-oper:bgp-path-source;
      description
        "The origin of the BGP path, indicating how the path was learned.It is either the source protocol or the neighbor address.";
    }
    leaf nbr-addr {
      type inet:ip-address;
      description
        "The neighbor address from which the BGP path was learned.";
    }
    leaf if-name {
      type string;
      description
        "Contains interface name if this neighbor is a link-local address, empty otherwise.";
    }
    leaf src-rd {
      type string;
      description
        "The source route distinguisher associated with this path if this path was imported from another vrf, empty otherwise.";
    }
    leaf src-ni-name {
      type string;
      description
        "The name of the network instance associated with this path if this path was imported from another vrf, empty otherwise.";
    }
    leaf path-id {
      type uint32;
      description
        "A unique identifier for the BGP path, used to differentiate between multiple paths for the same prefix.";
    }
  }

  grouping bgp-route-entry-key {
    description
      "Key attributes for identifying a specific BGP prefix entry, including the prefix itself, network instance type and name, and address family.";
    leaf prefix {
      type inet:ip-prefix;
      description
        "The BGP prefix associated with the route entry.";
    }
    leaf ni-type {
      type common-types-ios-xe:net-inst-type;
      description
        "The type of network instance (e.g., VRF, global) associated with the route entry.";
    }
    leaf ni-name {
      type string;
      description
        "The name of the network instance associated with the route entry.";
    }
    leaf afi-safi {
      type bgp-ios-rib-xe-oper:bgp-afisafi;
      description
        "The address family identifier (AFI) and subsequent address family identifier (SAFI) for the route entry.";
    }
  }

  grouping bgp-route-info {
    description
      "BGP prefix information";
    leaf version {
      type uint32;
      description
        "BGP Prefix update version.";
    }
    leaf avail-paths {
      type uint32;
      description
        "The number of available BGP paths for the prefix, indicating the different routes that can be used to reach the destination.";
    }
    list bgp-path {
      key "src-orig nbr-addr if-name src-rd src-ni-name path-id";
      description
        "List of BGP paths associated with the prefix.";
      uses bgp-ios-rib-xe-oper:bgp-path-key;
      uses bgp-ios-rib-xe-oper:bgp-path-info;
    }
  }

  container bgp-rib-oper-data {
    config false;
    description
      "BGP RIB Operational Data.";
    list bgp-route {
      key "prefix ni-type ni-name afi-safi";
      description
        "List of BGP prefixes and their associated information.";
      uses bgp-ios-rib-xe-oper:bgp-route-entry-key;
      uses bgp-ios-rib-xe-oper:bgp-route-info;
    }
    list bgp-attr {
      key "attr-id";
      description
        "List of BGP attributes and their associated information.";
      uses bgp-ios-rib-xe-oper:bgp-attr-key;
      uses bgp-ios-rib-xe-oper:bgp-path-attr;
    }
    list bgp-comm {
      key "id";
      description
        "List of BGP communities and their associated information.";
      uses bgp-ios-rib-xe-oper:bgp-comm-info;
    }
    list bgp-extcomm {
      key "id";
      description
        "List of BGP extended communities and their associated information.";
      uses bgp-ios-rib-xe-oper:bgp-extcomm-info;
    }
    list bgp-lrgcomm {
      key "id";
      description
        "List of BGP large communities and their associated information.";
      uses bgp-ios-rib-xe-oper:bgp-lrgcomm-info;
    }
  }
}
