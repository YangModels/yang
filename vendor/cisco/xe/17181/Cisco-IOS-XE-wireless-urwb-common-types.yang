module Cisco-IOS-XE-wireless-urwb-common-types {
  yang-version 1.1;
  namespace "http://cisco.com/ns/yang/Cisco-IOS-XE-wireless-urwb-common-types";
  prefix wireless-urwb-common-types;

  import Cisco-IOS-XE-wireless-enum-types {
    prefix wireless-enum-types;
  }
  import Cisco-IOS-XE-wireless-types {
    prefix wireless-types;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Ultra Reliable Wireless Backhaul (URWB) configuration data.
     Copyright (c) 2025 by Cisco Systems, Inc.
     All rights reserved.";

  revision 2025-07-01 {
    description
      "Initial revision";
    reference
      "1.0.0";
    cisco-semver:module-version "1.0.0";
  }

  grouping st-urwb-mob {
    description
      "Attributes of URWB mobility config";
    leaf role {
      type wireless-enum-types:urwb-mob-mode;
      default "urwb-mob-base";
      description
        "This value indicates role of backhaul device";
    }
    leaf scan-idle {
      type uint32 {
        range "0 .. 65535";
      }
      units "seconds";
      default "0";
      description
        "This value indicated the time of the periodic background channel scanning";
    }
    leaf scan-after {
      type uint32 {
        range "0 .. 65535";
      }
      units "milliseconds";
      default "0";
      description
        "This value indicates the timeout for running an active scanning when the device is isolated from the infrastructure";
    }
    leaf scan-rssi-th {
      type uint32 {
        range "0 .. 96";
      }
      units "dBm";
      default "0";
      description
        "This value depicts RSSI threshold for active scanning";
    }
    leaf warmup {
      type uint32 {
        range "0 .. 300000";
      }
      units "milliseconds";
      default "30000";
      description
        "This value depicts warm up time before accepting/initiating handoff";
    }
    leaf timeout {
      type uint16;
      units "milliseconds";
      default "800";
      description
        "This value depicts timeout for candidate infrastructure units";
    }
    leaf rssi-dhi {
      type uint16 {
        range "0 .. 96";
      }
      units "dBm";
      default "6";
      description
        "This value indicates mobility handoff hysteresis high threshold value";
    }
    leaf rssi-dlo {
      type uint16 {
        range "0 .. 96";
      }
      default "3";
      description
        "This value indicates mobility handoff hysteresis low threshold value";
    }
    leaf rssi-dth {
      type uint16 {
        range "0 .. 96";
      }
      units "dBm";
      default "35";
      description
        "This value indicates low or high threshold value";
    }
    leaf ra-red {
      type uint8 {
        range "1 .. 5";
      }
      default "1";
      description
        "This value indicates level of redundancy for route advertisement signalling";
    }
    leaf bc-eth {
      type wireless-enum-types:urwb-mob-bce;
      default "urwb-mbce-dis";
      description
        "Configure handoff when all ethernet ports are disconnected";
    }
    leaf bc-crd {
      type wireless-enum-types:urwb-mob-bcc;
      default "urwb-mbcc-dis";
      description
        "Configure handoff when coordinator is unreachable";
    }
  }

  grouping st-urwb-mpls {
    description
      "Attributes of URWB MPLS config";
    leaf ha-en {
      type boolean;
      default "false";
      description
        "This value indicates whether high availability is enabled on the backhaul radio";
    }
    leaf ha-timeout {
      type uint16;
      default "100";
      description
        "This value indicates MPLS high availability timeout";
    }
    leaf uni-fl {
      type boolean;
      default "false";
      description
        "This value indicates MPLS unicast flood is enabled";
    }
    leaf uni-fl-l {
      type boolean;
      default "false";
      description
        "This value indicates MPLS unicast flood limits";
    }
    leaf eth-1 {
      type boolean;
      default "false";
      description
        "This value indicates ethernet I frames forwarding";
    }
    leaf eth-fm {
      type wireless-enum-types:urwb-efm;
      default "urwb-efm-none";
      description
        "This value indicates the method of configuration for the ethernet filter";
    }
  }

  grouping st-urwb-mpo {
    description
      "Attributes of URWB mobility config";
    leaf status {
      type wireless-enum-types:urwb-mpo-st;
      default "urwb-mpo-dis";
      description
        "This value indicates whether MPO is enabled on the backhaul radio";
    }
    leaf max-links {
      type uint8 {
        range "1 .. 4";
      }
      default "2";
      description
        "This value indicated the maximum number of MPO links on the backhaul radio";
    }
    leaf min-rssi {
      type int8 {
        range "0 .. 96";
      }
      units "dBm";
      default "20";
      description
        "This value indicates minimum RSSI to establish MPO redundant links";
    }
    leaf class-cs {
      type uint8 {
        range "0 .. 7";
      }
      default "6";
      description
        "This value indicates class-of-service of traffic to protect with MPO redundancy";
    }
    leaf tlmtry {
      type boolean;
      default "false";
      description
        "This value indicates MPO telemetry is enabled";
    }
  }

  grouping st-urwb-radio {
    description
      "Attributes of URWB radio";
    leaf role {
      type wireless-enum-types:enm-radio-urwb-role;
      default "urwb-rad-role-none";
      description
        "This value indicates URWB radio role";
    }
    leaf band {
      type wireless-types:enm-ewlc-dot11-radio-band;
      default "dot11-invalid-band";
      description
        "This value indicates URWB radio band";
    }
    leaf chan {
      type uint16 {
        range "1 .. 233";
      }
      default "1";
      description
        "This value indicates URWB channel";
    }
    leaf c-width {
      type wireless-enum-types:rrm-chan-width;
      units "MHz";
      default "rrm-channel-width-20-mhz";
      description
        "This value indicates URWB channel width";
    }
    leaf crypto {
      type wireless-enum-types:enm-radio-urwb-crypto;
      default "urwb-rad-crypt-fxkey";
      description
        "This value indicates AES key type";
    }
    leaf kc-rt {
      type uint16;
      units "seconds";
      default "15";
      description
        "This value indicates key control rotation timeout";
    }
    leaf rssi-th {
      type uint8;
      units "dBm";
      default "0";
      description
        "This value indicates RSSI threshold  for PTMP scanning";
    }
    leaf autoscan {
      type boolean;
      default "false";
      description
        "This value indicates whether autoscan is enabled for PTMP";
    }
    leaf cl-id {
      type string;
      default "CiscoURWB";
      description
        "This value indicates cluster id for PTMP";
    }
    leaf tw-id {
      type string;
      default "";
      description
        "This value indicates tower id for PTMP";
    }
  }

  grouping st-urwb-chan-list-entry {
    description
      "Attributes of URWB channel list";
    leaf chan {
      type uint16;
      description
        "This value indicates URWB channel number";
    }
    leaf c-width {
      type uint16;
      units "MHz";
      description
        "This value indicates URWB channel width";
    }
  }
}
