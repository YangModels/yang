module Cisco-IOS-XE-utd-actions-rpc {
  yang-version 1.1;
  namespace "http://cisco.com/ns/yang/Cisco-IOS-XE-utd-actions-rpc";
  prefix utd-actions-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     Unified Threat Defense (UTD) RPC.
     Copyright (c) 2022, 2025 by Cisco Systems, Inc.
     All rights reserved.";

  revision 2025-07-01 {
    description
      "Added support for custom-signature global actions";
    reference
      "1.1.0";
    cisco-semver:module-version "1.1.0";
  }
  revision 2022-11-01 {
    description
      "Initial revision";
    reference
      "1.0.0";
    cisco-semver:module-version "1.0.0";
  }

  grouping utd-custom-signature-profile-type {
    description
      "Custom-signature profile related grouping";
    leaf profile-name {
      type string {
        length "1..127";
      }
      mandatory true;
      description
        "Custom-signature profile name";
    }
    leaf filename {
      type string {
        length "1..127";
      }
      description
        "Custom-signature file name";
    }
  }

  grouping utd-custom-signature-file-type {
    description
      "Custom-signature file related grouping";
    leaf filename {
      type string {
        length "1..127";
      }
      mandatory true;
      description
        "Custom-signature file name";
    }
  }

  rpc utd-custom-signature-apply {
    description
      "Custom-signature apply action RPC.";
    input {
      uses utd-actions-rpc:utd-custom-signature-profile-type;
    }
  }

  rpc utd-custom-sig-glbl-apply {
    description
      "Custom-signature global apply action RPC.";
    input {
      uses utd-actions-rpc:utd-custom-signature-file-type;
    }
  }

  rpc utd-custom-signature-load {
    description
      "Custom-signature load action RPC.";
    input {
      uses utd-actions-rpc:utd-custom-signature-profile-type;
    }
  }

  rpc utd-custom-sig-glbl-load {
    description
      "Custom-signature global load action RPC.";
    input {
      uses utd-actions-rpc:utd-custom-signature-file-type;
    }
  }

  rpc utd-custom-signature-validate {
    description
      "Custom-signature validate action RPC.";
    input {
      uses utd-actions-rpc:utd-custom-signature-file-type;
    }
  }
}
