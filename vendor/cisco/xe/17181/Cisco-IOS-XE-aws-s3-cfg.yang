module Cisco-IOS-XE-aws-s3-cfg {
  yang-version 1.1;
  namespace "http://cisco.com/ns/yang/Cisco-IOS-XE-aws-s3-cfg";
  prefix aws-s3-cfg;

  import Cisco-IOS-XE-aws-common-cfg {
    prefix aws-common-cfg;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for AWS S3 configurational data.
     Copyright (c) 2023-2025 by Cisco Systems, Inc.
     All rights reserved.";

  revision 2025-07-01 {
    description
      "Initial revision";
    reference
      "1.0.0";
    cisco-semver:module-version "1.0.0";
  }

  grouping aws-s3-mount-config {
    description
      "S3 bucket mount configuration data";
    leaf bucket-name {
      type string {
        length "0|3..63";
        pattern '([a-z0-9][a-z0-9.-]*[a-z0-9])*';
      }
      default "";
      description
        "S3 bucket name";
    }
    leaf mount-point {
      type string {
        length "0..32";
        pattern '[0-9a-zA-Z_.-]*';
      }
      default "";
      description
        "S3 mount point";
    }
    leaf region {
      type string {
        length "0..16";
        pattern '[0-9a-zA-Z-]*';
      }
      default "";
      description
        "AWS S3 region";
    }
    leaf read-write {
      type boolean;
      default "true";
      description
        "read-write permissions for S3 config data";
    }
  }

  grouping aws-s3-config {
    description
      "S3 configuration data";
    leaf aws-s3-profile-name {
      type string {
        length "0..32";
        pattern '[0-9a-zA-Z_]*';
      }
      description
        "S3 profile name";
    }
    leaf aws-s3-profile-descr {
      type string {
        length "0..200";
        pattern '([^	 ].*[^	 ])*';
      }
      default "";
      description
        "S3 profile description";
    }
    container aws-s3-access-creds {
      description
        "AWS access credentials for S3";
      uses aws-common-cfg:aws-access-config;
    }
    container aws-s3-mount-config {
      description
        "S3 bucket mount configuration data";
      uses aws-s3-cfg:aws-s3-mount-config;
    }
    container aws-s3-proxy-config {
      description
        "AWS proxy config";
      uses aws-common-cfg:st-aws-proxy-config;
    }
    leaf aws-s3-shutdown {
      type boolean;
      must "(((current() = 'false') and (../aws-s3-mount-config/mount-point != '') and (../aws-s3-mount-config/bucket-name != '') and (../aws-s3-access-creds/access-key-id != '') and (../aws-s3-access-creds/secret-access-key != '')) or
            (current() = 'true'))" {
        error-message "must set bucket-name, mount-point, region, access-key-id and secret-access-key";
      }
      default "true";
      description
        "Shutdown variable for S3 profile";
    }
    leaf aws-s3-vrf {
      type aws-common-cfg:aws-vrf-name;
      default "aws-global-vrf";
      description
        "AWS S3 VRF";
    }
  }

  container aws-s3-cfg-data {
    description
      "AWS S3 configuration data";
    container aws-s3fs-profiles {
      description
        "AWS S3 Profile configuration data";
      list aws-s3fs {
        key "aws-s3-profile-name";
        description
          "AWS S3 Profile configuration data";
        uses aws-s3-cfg:aws-s3-config;
      }
    }
  }
}
