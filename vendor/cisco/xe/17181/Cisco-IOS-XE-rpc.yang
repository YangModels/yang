module Cisco-IOS-XE-rpc {
  yang-version 1.1;
  namespace "http://cisco.com/ns/yang/Cisco-IOS-XE-rpc";
  prefix ios-xe-rpc;

  import cisco-semver {
    prefix cisco-semver;
  }
  import ietf-inet-types {
    prefix inet;
  }
  import Cisco-IOS-XE-types {
    prefix ios-types;
  }
  include Cisco-IOS-XE-aaa-rpc;
  include Cisco-IOS-XE-arp-rpc;
  include Cisco-IOS-XE-bgp-rpc;
  include Cisco-IOS-XE-crypto-rpc;
  include Cisco-IOS-XE-multicast-rpc;
  include Cisco-IOS-XE-dhcp-rpc;
  include Cisco-IOS-XE-ospf-rpc;
  include Cisco-IOS-XE-platform-rpc;

  organization
    "Cisco Systems";
  contact
    "<mailto:cs-yang@cisco.com>";
  description
    "NED RPC YANG module for IOS
     Copyright (c) 2016-2020 by Cisco Systems, Inc.
     All rights reserved.";

  revision 2024-11-01 {
    description
      "- Added exec module for hw-module
       - Added crashinfo option in pattern for delete exec command
       - Added hw-module support for all Catalyst 9000 platforms";
    cisco-semver:module-version "3.7.0";
  }
  revision 2024-07-01 {
    description
      "- Added monitor support";
    cisco-semver:module-version "3.6.0";
  }
  revision 2024-03-01 {
    description
      "- Added monitor pcm-trace support";
    cisco-semver:module-version "3.5.0";
  }
  revision 2022-11-01 {
    description
      "- Update yang-version to 1.1";
    cisco-semver:module-version "3.4.0";
  }
  revision 2021-07-01 {
    description
      "- Added Null string support in count leaf";
    cisco-semver:module-version "3.3.0";
  }
  revision 2021-03-01 {
    description
      "- Added factory reset support";
    cisco-semver:module-version "3.2.0";
  }
  revision 2020-11-01 {
    description
      "Added clear iox feature
       corrected new keyword addition";
    cisco-semver:module-version "3.1.0";
  }
  revision 2020-07-01 {
    description
      "Added multicast feature RPC";
    cisco-semver:module-version "3.0.0";
  }
  revision 2020-03-01 {
    description
      "Added a container in monitor capture";
    cisco-semver:module-version "2.1.0";
  }
  revision 2019-11-01 {
    description
      "Added new test RPC";
    cisco-semver:module-version "2.0.0";
  }
  revision 2019-07-01 {
    description
      "Establish semantic version baseline";
    cisco-semver:module-version "1.0.0";
  }
  revision 2018-11-25 {
    description
      "Exec command to send AMP file analysis apikey";
  }
  revision 2018-11-07 {
    description
      "Cleanup spelling errors in description statements";
  }
  revision 2018-11-06 {
    description
      "Add UTD database update EXEC command";
  }
  revision 2018-10-29 {
    description
      "Added range-string for debug ipsec command";
  }
  revision 2018-10-12 {
    description
      "Added crypto pki debug and exec commands";
  }
  revision 2018-10-02 {
    description
      "Add unmount command in existing hw-module chain";
  }
  revision 2018-10-01 {
    description
      "Add IPSEC no debug exec commands";
  }
  revision 2018-09-20 {
    description
      "Add IPSEC debug exec commands";
  }
  revision 2018-08-17 {
    description
      "Added cts credential * and clear cts * commands";
  }
  revision 2018-08-05 {
    description
      "Add License Install Commands";
  }
  revision 2018-08-01 {
    description
      "Add UTD clear commands";
  }
  revision 2018-07-30 {
    description
      "Add hw-module commands";
  }
  revision 2018-06-18 {
    description
      "Update UTD signature update EXEC command to include local file support";
  }
  revision 2018-05-21 {
    description
      "Add Umbrella clear commands";
  }
  revision 2018-04-18 {
    description
      "Add ZBFW clear commands";
  }
  revision 2018-03-14 {
    description
      "Add UTD signature update EXEC command";
  }
  revision 2017-12-18 {
    description
      "Add GIR start maintenance and stop maintenance EXEC commands";
  }
  revision 2017-12-06 {
    description
      "Add Viptela clear aaa local user lockout username <> command";
  }
  revision 2017-11-27 {
    description
      "Add Viptela clear and release commands";
  }
  revision 2017-11-21 {
    description
      "Clear flow commands";
  }
  revision 2017-11-14 {
    description
      "Add app-hosting and guestshell EXEC commands";
  }
  revision 2017-11-04 {
    description
      "Add reason to reload";
  }
  revision 2017-10-12 {
    description
      "Added more nodes to the license RPC";
  }
  revision 2017-10-10 {
    description
      "Add copy and delete EXEC commands";
  }
  revision 2017-09-21 {
    description
      "Add virtual-service EXEC commands";
  }
  revision 2017-08-28 {
    description
      "Added the force option to the reload RPC";
  }
  revision 2017-07-13 {
    description
      "Added service sd-avc CLI";
  }
  revision 2017-02-07 {
    description
      "Initial revision";
  }

  grouping cisco-xe-rpc-output {
    description
      "Used to return output from RPCs";
    leaf result {
      type string;
      description
        "Output returned by the network element";
    }
  }

  rpc default {
    description
      "Set a command to its defaults";
    input {
      choice default-choice {
        mandatory true;
        case interface-case {
          leaf interface {
            description
              "Select an interface to configure";
            type string {
              pattern '[A-Za-z]([\w/.-]+)';
            }
          }
        }
      }
    }
    output {
      uses cisco-xe-rpc-output;
    }
  }

  rpc clear {
    description
      "Clear";
    input {
      choice clear-choice {
        mandatory true;
        case interface-case {
          leaf interface {
            description
              "Select an interface to clear";
            type string {
              pattern '[A-Za-z]([\w/.-]+)';
            }
          }
        }
        case count-case {
          leaf count {
            description
              "Select an interface to clear";
            type string {
              pattern '(([A-Za-z]([\w/.-]+))|\w{0})';
            }
          }
        }
        case ip-case {
          container ip {
            choice ip-protocol {
              case bgp-case {
                uses clear-choice-ip-case-ip-protocol-bgp-case-grouping;
              }
              case dhcp-case {
                uses clear-choice-ip-case-ip-protocol-dhcp-case-grouping;
              }
              case ospf-case {
                uses clear-choice-ip-case-ip-protocol-ospf-case-grouping;
              }
            }
          }
        }
        case arp-cache-case {
          uses clear-choice-arp-cache-case-grouping;
        }
        case aaa-case {
          uses clear-choice-aaa-case-grouping;
        }
        case platform-case {
          uses clear-choice-platform-case-grouping;
        }
        case iox-case {
          leaf iox {
            description
              "Clear all IOX data to the default, initial IOX state";
            type empty;
          }
        }
      }
    }
    output {
      uses cisco-xe-rpc-output;
    }
  }

  rpc crypto {
    description
      "Encryption related commands";
    input {
      uses crypto-input-grouping;
    }
    output {
      uses cisco-xe-rpc-output;
    }
  }

  rpc release {
    description
      "Release a resource";
    input {
      leaf dhcp {
        description
          "Release a dhcp lease (an interface)";
        type string;
      }
    }
    output {
      uses cisco-xe-rpc-output;
    }
  }

  rpc reload {
    description
      "Halt and perform a cold restart";
    input {
      leaf force {
        description
          "Force a restart even if there is unsaved config";
        type boolean;
      }
      leaf reason {
        description
          "Reload reason";
        type string;
      }
    }
    output {
      uses cisco-xe-rpc-output;
    }
  }

  rpc factory-reset {
    description
      "Perform a factory reset of the device";
    input {
      container all {
        description
          "Perform a factory reset of the device. This will
           restore the device to the factory setting and is an
           irreversible operation";
        presence "true";
      }
      leaf keep-licensing-info {
        description
          "Perform a factory reset of the device. This will
           keep some licensing specific information";
        type empty;
      }
    }
    output {
      uses cisco-xe-rpc-output;
    }
  }

  rpc license {
    input {
      choice license-command-choice {
        case licese-smart {
          container smart {
            choice smart-choice {
              case smart-save-case {
                container save {
                  choice save-case {
                    case save-usage-case {
                      container usage {
                        choice usage-case {
                          case usage-all {
                            container all {
                              leaf file {
                                description
                                  "The local or network file path to write the RUM
                                   reports to.";
                                type string {
                                  pattern '(((bootflash:)|(flash:)|(ftp:)|(http:)|(https:)|(nvram:)|(param:)|(scp:)|(syslog)|(system:)|(tftp:)|(tmpsys:)).*)';
                                }
                              }
                            }
                          }
                          case usage-unreported {
                            container unreported {
                              leaf file {
                                description
                                  "The local or network file path to write the RUM
                                   reports to.";
                                type string {
                                  pattern '(((bootflash:)|(flash:)|(ftp:)|(http:)|(https:)|(nvram:)|(param:)|(scp:)|(syslog)|(system:)|(tftp:)|(tmpsys:)).*)';
                                }
                              }
                            }
                          }
                        }
                        leaf days {
                          description
                            "Save RUM reports that include measurements in the
                             specified number of days";
                          type uint32 {
                            range "1..1000000";
                          }
                        }
                        leaf file {
                          description
                            "The local or network file path to write the RUM
                             reports to.";
                          type string {
                            pattern '(((bootflash:)|(flash:)|(ftp:)|(http:)|(https:)|(nvram:)|(param:)|(scp:)|(syslog)|(system:)|(tftp:)|(tmpsys:)).*)';
                          }
                        }
                      }
                    }
                    case save-trust-request-case {
                      leaf trust-request {
                        description
                          "The local or network file path to write
                           the trust request to.";
                        type string {
                          pattern '(((bootflash:)|(flash:)|(ftp:)|(http:)|(https:)|(nvram:)|(param:)|(scp:)|(syslog)|(system:)|(tftp:)|(tmpsys:)).*)';
                        }
                      }
                    }
                  }
                }
              }
              case smart-authorization-case {
                container authorization {
                  choice authorization-choice {
                    case authorization-request-case {
                      container request {
                        leaf add {
                          description
                            "The feature name to get the authorization code for
                             The smart agent will look this up in it's mapping
                             table and get the proper entitlement tag for it.";
                          type string;
                        }
                        leaf replace {
                          description
                            "The feature name to get the authorization code for
                             The smart agent will look this up in it's mapping
                             table and get the proper entitlement tag for it.";
                          type string;
                        }
                        leaf all {
                          description
                            "Applies to an HA configuration.";
                          type empty;
                        }
                        leaf local {
                          description
                            "The authorization request will only be for
                             the active device.";
                          type empty;
                        }
                      }
                    }
                    case authorization-return-case {
                      container return {
                        leaf all {
                          description
                            "Applies to an HA configuration.";
                          type empty;
                        }
                        leaf local {
                          description
                            "The authorization request will only be for
                             the active device.";
                          type empty;
                        }
                        leaf offline {
                          description
                            "Returns a currently installed authorization
                             code offline.";
                          type string;
                        }
                        leaf online {
                          description
                            "Returns a currently installed authorization
                             code online.";
                          type empty;
                        }
                      }
                    }
                  }
                }
              }
              case import-case {
                leaf import {
                  description
                    "The local or network file path to read from";
                  mandatory true;
                  type string;
                }
              }
              case trust-case {
                container trust {
                  leaf idtoken {
                    description
                      "The ID token used to establish trust.";
                    mandatory true;
                    type string;
                  }
                  leaf all {
                    description
                      "If true perform the operation for all devices
                       in an HA configuration.";
                    type empty;
                  }
                  leaf local {
                    description
                      "If false then only establish
                       trust for the active device.";
                    type empty;
                  }
                  leaf force {
                    description
                      "Force the trust establishment even if the product
                       instance has already establish trust with the Cisco
                       Smart Software Management.";
                    type empty;
                  }
                }
              }
              case register-case {
                container register {
                  leaf idtoken {
                    mandatory true;
                    type string;
                  }
                  leaf force {
                    description
                      "Forcefully register";
                    type empty;
                  }
                }
              }
              case deregister-case {
                leaf deregister {
                  type empty;
                }
              }
              case renew-case {
                container renew {
                  choice renew-choice {
                    mandatory true;
                    leaf ID {
                      type empty;
                    }
                    leaf auth {
                      type empty;
                    }
                  }
                }
              }
            }
          }
        }
        case license-install {
          leaf install {
            description
              "Install license information";
            type string {
              pattern '(((bootflash:)|(flash:)|(ftp:)|(http:)|(https:)|(nvram:)|(param:)|(scp:)|(syslog)|(system:)|(tftp:)|(tmpsys:)).*)';
            }
          }
        }
        case license-clear {
          leaf clear {
            description
              "Clear license information. Feature name to clear";
            type string;
          }
        }
      }
    }
    output {
      uses cisco-xe-rpc-output;
    }
  }

  rpc service {
    description
      "IOS integrated service enablement";
    input {
      choice services-choice {
        case wass-case {
          container waas {
            description
              "WAAS service";
            container wcm {
              description
                "Configure WAAS Central Manager (WCM)";
              choice wcm-choices {
                case ip-case {
                  container ip {
                    description
                      "ipv4";
                    leaf address {
                      type inet:ipv4-address;
                    }
                  }
                }
                case ipv6-case {
                  container ipv6 {
                    description
                      "ipv6 address";
                    leaf address {
                      type inet:ipv6-address;
                    }
                  }
                }
              }
            }
          }
        }
        case sd-avc-case {
          container sd-avc {
            description
              "SD-AVC service management";
            choice sd-avc-choice {
              mandatory true;
              case activate-case {
                leaf activate {
                  type empty;
                }
              }
              case configure-case {
                container configure {
                  container gateway {
                    leaf interface {
                      type string;
                    }
                    leaf service-ip {
                      type inet:ipv4-address;
                    }
                    leaf activate {
                      type empty;
                    }
                  }
                }
              }
              case connect-case {
                leaf connect {
                  type empty;
                }
              }
              case help-case {
                leaf help {
                  type empty;
                }
              }
              case deactivate-case {
                leaf deactivate {
                  type empty;
                }
              }
              case install-case {
                container install {
                  leaf package {
                    type string;
                  }
                }
              }
              case status-case {
                leaf status {
                  type empty;
                }
              }
              case unconfigure-case {
                leaf unconfigure {
                  type empty;
                }
              }
              case uninstall-case {
                leaf uninstall {
                  type empty;
                }
              }
              case upgrade-case {
                container upgrade {
                  leaf package {
                    type string;
                  }
                }
              }
            }
          }
        }
      }
    }
    output {
      uses cisco-xe-rpc-output;
    }
  }

  rpc virtual-service {
    description
      "Virtual-service management";
    input {
      choice operation {
        mandatory true;
        container install {
          leaf name {
            type string;
          }
          leaf package {
            type string;
          }
          leaf media {
            type string;
          }
        }
        container uninstall {
          leaf name {
            type string;
          }
        }
        container upgrade {
          leaf name {
            type string;
          }
          leaf package {
            type string;
          }
        }
        container move {
          leaf name {
            mandatory true;
            type string;
          }
          choice file-choice {
            mandatory true;
            container core {
              leaf to {
                type string {
                  pattern '(((bootflash:)|(flash:)|(harddisk:)).*)';
                }
              }
            }
            container log {
              leaf to {
                type string {
                  pattern '(((bootflash:)|(flash:)|(harddisk:)).*)';
                }
              }
            }
          }
        }
      }
    }
    output {
      uses cisco-xe-rpc-output;
    }
  }

  rpc copy {
    description
      "Copy from one file to another";
    input {
      leaf source-drop-node-name {
        mandatory true;
        type string {
          pattern '((((bootflash:)|(harddisk:)|(flash:)|(nvram:)|(ftp:)|(http:)|(https:)|(scp:)|(tftp:)).*)|((running-config)|(startup-config)))';
        }
      }
      leaf destination-drop-node-name {
        mandatory true;
        type string {
          pattern '((((bootflash:)|(harddisk:)|(flash:)|(nvram:)|(ftp:)|(http:)|(https:)|(scp:)|(tftp:)).*)|((running-config)|(startup-config)))';
        }
      }
    }
    output {
      uses cisco-xe-rpc-output;
    }
  }

  rpc delete {
    description
      "Delete a file";
    input {
      leaf filename-drop-node-name {
        mandatory true;
        type string {
          pattern '(((bootflash:)|(harddisk:)|(crashinfo:)|(flash:)|(nvram:)).*)';
        }
      }
    }
    output {
      uses cisco-xe-rpc-output;
    }
  }

  rpc app-hosting {
    description
      "App-hosting management";
    input {
      choice lifecycle {
        mandatory true;
        container install {
          leaf appid {
            type string;
          }
          leaf package {
            type string;
          }
        }
        container uninstall {
          leaf appid {
            type string;
          }
        }
        container activate {
          leaf appid {
            type string;
          }
        }
        container deactivate {
          leaf appid {
            type string;
          }
        }
        container start {
          leaf appid {
            type string;
          }
        }
        container stop {
          leaf appid {
            type string;
          }
        }
        container upgrade {
          leaf appid {
            type string;
          }
          leaf package {
            type string;
          }
        }
        container verification {
          leaf enable {
            type empty;
          }
          leaf disable {
            type empty;
          }
        }
        container move {
          choice type-choice {
            mandatory true;
            case appid-case {
              leaf appid {
                mandatory true;
                type string;
              }
              choice file-choice {
                mandatory true;
                container core {
                  leaf to {
                    type string {
                      pattern '(((bootflash:)|(flash:)|(harddisk:)).*)';
                    }
                  }
                }
                container log {
                  leaf to {
                    type string {
                      pattern '(((bootflash:)|(flash:)|(harddisk:)).*)';
                    }
                  }
                }
              }
            }
            case system-case {
              container system {
                container techsupport {
                  leaf to {
                    type string {
                      pattern '(((bootflash:)|(flash:)|(harddisk:)).*)';
                    }
                  }
                }
              }
            }
          }
        }
      }
    }
    output {
      uses cisco-xe-rpc-output;
    }
  }

  rpc guestshell {
    description
      "guestshell managementshell";
    input {
      choice action {
        mandatory true;
        case destroy-case {
          leaf destroy {
            description
              "Destroy guestshell";
            type empty;
          }
        }
        case disable-case {
          leaf disable {
            description
              "Disable guestshell";
            type empty;
          }
        }
        case enable-case {
          leaf enable {
            description
              "Enable guestshell";
            type empty;
          }
        }
      }
    }
    output {
      uses cisco-xe-rpc-output;
    }
  }

  rpc start {
    description
      "Start system operations";
    input {
      leaf maintenance {
        description
          "GIR start maintenance mode";
        type empty;
      }
    }
    output {
      uses cisco-xe-rpc-output;
    }
  }

  rpc stop {
    description
      "Stop system operations";
    input {
      leaf maintenance {
        description
          "GIR stop maintenance mode";
        type empty;
      }
    }
    output {
      uses cisco-xe-rpc-output;
    }
  }

  rpc hw-module {
    description
      "Control of individual components in the system";
    input {
      container switch {
        description
          "Switch in the system";
        leaf switch-number-drop-node-name {
          description
            "Switch number in the Stack (Refer to show switch CLI)";
          type uint8 {
            range "1..16";
          }
        }
        container subslot {
          description
            "<0-10>/<0-0>; Enter card slot/subslot number";
          leaf subslot-drop-node-name {
            type string {
              pattern '[0-10/0]*';
            }
          }
          choice oir-reload-start-stop {
            case oir-case {
              container oir {
                description
                  "Spa OIR";
                container power-cycle {
                  description
                    "Power cycle the target subslot";
                  presence "true";
                  leaf force {
                    description
                      "Proceed without prompting for confirmation";
                    type empty;
                  }
                }
              }
            }
            case reload-case {
              container reload {
                description
                  "Reload the target subslot";
                presence "true";
                leaf force {
                  description
                    "Proceed without prompting for confirmation";
                  type empty;
                }
              }
            }
            case start-case {
              leaf start {
                description
                  "Activate the target subslot";
                type empty;
              }
            }
            case stop-case {
              container stop {
                description
                  "Deactivate the target subslot";
                presence "true";
                leaf force {
                  description
                    "Proceed without prompting for confirmation";
                  type empty;
                }
              }
            }
          }
        }
        container usbflash1 {
          description
            "USB SSD";
          choice umount-sec {
            case unmount-case {
              leaf unmount {
                description
                  "unmount on usbflash1";
                type empty;
              }
            }
            case security-case {
              container security {
                description
                  "Security on usbflash1";
                choice security-choice {
                  case enable-case {
                    container enable {
                      description
                        "Enable security on usbflash1";
                      presence "true";
                      leaf password {
                        description
                          "Enter password for enabling security on usbflash1";
                        type string;
                      }
                    }
                  }
                  case disable-case {
                    container disable {
                      description
                        "Disable security on usbflash1";
                      presence "true";
                      leaf password {
                        description
                          "Enter password for Disabling security on usbflash1";
                        type string;
                      }
                    }
                  }
                  case unlock-case {
                    container unlock {
                      description
                        "Unlock security on usbflash1";
                      presence "true";
                      leaf password {
                        description
                          "Enter password for unlock security on usbflash1";
                        type string;
                      }
                    }
                  }
                }
              }
            }
          }
        }
      }
      container beacon {
        description
          "Control Blue Beacon LED in a FRU";
        choice slot-sw-rp-ssd-ps-ft {
          case slot-case {
            container slot {
              description
                "Switch in the system";
              leaf slot-number-drop-node-name {
                description
                  "Switch number 1..16 in the Stack or word active or standby (Refer to show switch CLI)";
                type string {
                  pattern '(([0-9]|1[0-6])|(active)|(standby))';
                }
              }
              choice on-off-status-port {
                case on-case {
                  leaf on {
                    description
                      "Turn on";
                    type empty;
                  }
                }
                case off-case {
                  leaf off {
                    description
                      "Turn off";
                    type empty;
                  }
                }
                case status-case {
                  leaf status {
                    type empty;
                  }
                }
                case fast-case {
                  leaf blink-fast {
                    type empty;
                  }
                }
                case slow-case {
                  leaf blink-slow {
                    type empty;
                  }
                }
                case port-case {
                  container port {
                    leaf port-number-drop-node-name {
                      type uint8 {
                        range "1..255";
                      }
                    }
                    choice fast-off-slow-status {
                      case fast-case {
                        leaf blink-fast {
                          type empty;
                        }
                      }
                      case off-case {
                        leaf blink-off {
                          type empty;
                        }
                      }
                      case slow-case {
                        leaf blink-slow {
                          type empty;
                        }
                      }
                      case status-case {
                        leaf status {
                          type empty;
                        }
                      }
                    }
                  }
                }
              }
            }
          }
          case switch-case {
            container switch {
              description
                "Switch Number";
              leaf switch-drop-node-name {
                description
                  "Switch number in the Stack (Refer to show switch CLI)";
                type string {
                  pattern '(([1-2])|(active)|(standby))';
                }
              }
              choice RP-fan-ps-slot {
                case RP-case {
                  container RP {
                    choice active-standby {
                      case active-case {
                        container active {
                          choice on-off-status {
                            case on-case {
                              leaf on {
                                type empty;
                              }
                            }
                            case off-case {
                              leaf off {
                                type empty;
                              }
                            }
                            case status-case {
                              leaf status {
                                type empty;
                              }
                            }
                          }
                        }
                      }
                      case standby-case {
                        container standby {
                          choice on-off-status {
                            case on-case {
                              leaf on {
                                type empty;
                              }
                            }
                            case off-case {
                              leaf off {
                                type empty;
                              }
                            }
                            case status-case {
                              leaf status {
                                type empty;
                              }
                            }
                          }
                        }
                      }
                    }
                  }
                }
                case fan-case {
                  container fan-tray {
                    choice on-off-status {
                      case on-case {
                        leaf on {
                          type empty;
                        }
                      }
                      case off-case {
                        leaf off {
                          type empty;
                        }
                      }
                      case status-case {
                        leaf status {
                          type empty;
                        }
                      }
                    }
                  }
                }
                case ps-case {
                  container power-supply {
                    leaf ps-drop-node-name {
                      description
                        "Power Supply slot number";
                      type uint8 {
                        range "1..16";
                      }
                    }
                    choice on-off-status {
                      case on-case {
                        leaf on {
                          type empty;
                        }
                      }
                      case off-case {
                        leaf off {
                          type empty;
                        }
                      }
                      case status-case {
                        leaf status {
                          type empty;
                        }
                      }
                    }
                  }
                }
                case slot-case {
                  container slot {
                    leaf slot-drop-node-name {
                      description
                        "slot number";
                      type uint8 {
                        range "1..10";
                      }
                    }
                    choice on-off-status {
                      case on-case {
                        leaf on {
                          type empty;
                        }
                      }
                      case off-case {
                        leaf off {
                          type empty;
                        }
                      }
                      case status-case {
                        leaf status {
                          type empty;
                        }
                      }
                    }
                  }
                }
              }
            }
          }
          case RP-case {
            container rp {
              container active {
                choice on-off-status {
                  case on-case {
                    leaf on {
                      type empty;
                    }
                  }
                  case off-case {
                    leaf off {
                      type empty;
                    }
                  }
                  case status-case {
                    leaf status {
                      type empty;
                    }
                  }
                }
              }
              container standby {
                choice on-off-status {
                  case on-case {
                    leaf on {
                      type empty;
                    }
                  }
                  case off-case {
                    leaf off {
                      type empty;
                    }
                  }
                  case status-case {
                    leaf status {
                      type empty;
                    }
                  }
                }
              }
            }
          }
          case ssd-case {
            container ssd {
              choice on-off-status {
                case on-case {
                  leaf on {
                    type empty;
                  }
                }
                case off-case {
                  leaf off {
                    type empty;
                  }
                }
                case status-case {
                  leaf status {
                    type empty;
                  }
                }
              }
            }
          }
          case ps-case {
            container power-supply {
              description
                "Power Supply in the system";
              leaf ps-number-drop-node-name {
                type uint8 {
                  range "1..2";
                }
              }
              choice on-off-status {
                case on-case {
                  leaf on {
                    description
                      "Turn on";
                    type empty;
                  }
                }
                case off-case {
                  leaf off {
                    description
                      "Turn off";
                    type empty;
                  }
                }
                case status-case {
                  leaf status {
                    type empty;
                  }
                }
              }
            }
          }
          case fantray-case {
            container fan-tray {
              choice on-off-status {
                case on-case {
                  leaf on {
                    type empty;
                  }
                }
                case off-case {
                  leaf off {
                    type empty;
                  }
                }
                case status-case {
                  leaf status {
                    type empty;
                  }
                }
              }
            }
          }
        }
      }
      container mcu {
        description
          "multipoint control units firmware updates";
        leaf rollback {
          description
            "roll back to previous multipoint control units version";
          type empty;
        }
      }
      container led {
        container switch {
          description
            "Switch number";
          leaf switch-number-drop-node-name {
            type uint8 {
              range "1..2";
            }
          }
          container slot {
            leaf slot-drop-node-name {
              description
                "slot number";
              type uint8 {
                range "1..10";
              }
            }
            leaf status {
              type empty;
            }
          }
        }
        container slot {
          leaf slot-drop-node-name {
            description
              "slot number";
            type uint8 {
              range "1..10";
            }
          }
          leaf status {
            type empty;
          }
        }
      }
      container usbflash1 {
        description
          "USB SSD";
        choice umount-sec {
          case unmount-case {
            leaf unmount {
              description
                "unmount on usbflash1";
              type empty;
            }
          }
          case security-case {
            container security {
              description
                "Security on usbflash1";
              choice security-choice {
                case enable-case {
                  container enable {
                    description
                      "Enable security on usbflash1";
                    presence "true";
                    leaf password {
                      description
                        "Enter password for enabling security on usbflash1";
                      type string;
                    }
                  }
                }
                case disable-case {
                  container disable {
                    description
                      "Disable security on usbflash1";
                    presence "true";
                    leaf password {
                      description
                        "Enter password for Disabling security on usbflash1";
                      type string;
                    }
                  }
                }
                case unlock-case {
                  container unlock {
                    description
                      "Unlock security on usbflash1";
                    presence "true";
                    leaf password {
                      description
                        "Enter password for unlock security on usbflash1";
                      type string;
                    }
                  }
                }
              }
            }
          }
        }
      }
      container subslot {
        description
          "<0-10>/<0-0>; Enter card slot/subslot number";
        leaf subslot-drop-node-name {
          type string {
            pattern '[0-10/0]*';
          }
        }
        choice oir-reload-start-stop {
          case oir-case {
            container oir {
              description
                "Spa OIR";
              container power-cycle {
                description
                  "Power cycle the target subslot";
                presence "true";
                leaf force {
                  description
                    "Proceed without prompting for confirmation";
                  type empty;
                }
              }
            }
          }
          case reload-case {
            container reload {
              description
                "Reload the target subslot";
              presence "true";
              leaf force {
                description
                  "Proceed without prompting for confirmation";
                type empty;
              }
            }
          }
          case start-case {
            leaf start {
              description
                "Activate the target subslot";
              type empty;
            }
          }
          case stop-case {
            container stop {
              description
                "Deactivate the target subslot";
              presence "true";
              leaf force {
                description
                  "Proceed without prompting for confirmation";
                type empty;
              }
            }
          }
        }
      }
    }
    output {
      uses cisco-xe-rpc-output;
    }
  }

  rpc debug {
    description
      "Debug";
    input {
      choice debug-choice {
        mandatory true;
        case crypto-case {
          uses debug-input-crypto-grouping;
        }
        case platform-case {
          uses debug-choice-platform-case-grouping;
        }
      }
    }
    output {
      uses cisco-xe-rpc-output;
    }
  }

  rpc monitor {
    description
      "monitor";
    input {
      leaf capture {
        description
          "Capture session";
        type string;
      }
      leaf access-list {
        description
          "access-list to be attached";
        type string;
      }
      container control-plane {
        description
          "Control Plane";
        choice capture-direction-choice {
          case both-case {
            leaf both {
              description
                "Inbound and outbound packets";
              type empty;
            }
          }
          case in-case {
            leaf in {
              description
                "Inbound packets";
              type empty;
            }
          }
          case out-case {
            leaf out {
              description
                "Outbound packets";
              type empty;
            }
          }
        }
      }
      leaf match {
        description
          "Describe filters inline";
        type string;
      }
      container inner {
        description
          "Inner filter options";
        leaf-list mac {
          description
            "Inner filter mac";
          max-elements 5;
          type ios-types:cisco-mac-address-type;
        }
        container protocol {
          description
            "Inner filter protocol";
          leaf DHCP {
            description
              "DHCP protocol";
            type empty;
          }
        }
      }
      leaf interface {
        description
          "Interface";
        type string;
      }
      choice capture-direction-choice {
        case both-case {
          leaf both {
            type empty;
          }
        }
        case in-case {
          leaf in {
            type empty;
          }
        }
        case out-case {
          leaf out {
            type empty;
          }
        }
      }
      container pcm-tracer {
        description
          "PCM tracer";
        choice pcm-tracer-choice {
          case start-case {
            container start {
              description
                "start PCM Capture";
              leaf profile {
                description
                  "PCM tracer profile";
                type uint8 {
                  range "1..10";
                }
              }
            }
          }
          case stop-case {
            container stop {
              description
                "stop PCM Capture";
              leaf profile {
                description
                  "PCM tracer profile";
                type uint8 {
                  range "1..10";
                }
              }
            }
          }
        }
      }
      container buffer {
        description
          "Buffer options";
        leaf size {
          description
            "Size of buffer in MB";
          type uint8 {
            range "1..100";
          }
        }
        leaf circular {
          description
            "circular buffer";
          type empty;
        }
      }
      container limit {
        description
          "Limit Packets Captured";
        leaf duration {
          description
            "Limit total duration of capture in seconds";
          type uint32 {
            range "1..1000000";
          }
        }
        leaf every {
          description
            "Limit capture to one in every nth packet";
          type uint32 {
            range "2..100000";
          }
        }
        leaf packet-len {
          description
            "Limit the packet length to capture";
          type uint16 {
            range "64..9500";
          }
        }
        leaf packets {
          description
            "Limit number of packets to capture";
          type uint32 {
            range "1..100000";
          }
        }
        leaf pps {
          description
            "Limit number of packets per second to capture";
          type uint32 {
            range "1..1000000";
          }
        }
      }
      choice capture-command-choice {
        case start-case {
          leaf start {
            description
              "Enable session capture points";
            type empty;
          }
        }
        case stop-case {
          leaf stop {
            description
              "Disable session capture points";
            type empty;
          }
        }
        case stop-export-case {
          leaf stop_export {
            description
              "Export session capture buffer";
            type empty;
          }
        }
        case export-case {
          leaf export {
            description
              "Export Buffer";
            type string;
          }
        }
      }
    }
    output {
      uses cisco-xe-rpc-output;
    }
  }

  rpc no {
    description
      "no";
    input {
      choice no-command-choice {
        case monitor-case {
          container monitor {
            description
              "Monitor capture";
            leaf capture {
              description
                "Capture session";
              type string;
            }
            leaf access-list {
              description
                "access-list to be attached";
              type empty;
            }
            container control-plane {
              description
                "Control Plane";
              choice capture-direction-choice {
                case both-case {
                  leaf both {
                    description
                      "Inbound and outbound packets";
                    type empty;
                  }
                }
                case in-case {
                  leaf in {
                    description
                      "Inbound packets";
                    type empty;
                  }
                }
                case out-case {
                  leaf out {
                    description
                      "Outbound packets";
                    type empty;
                  }
                }
              }
            }
            leaf match {
              description
                "Describe filters inline";
              type empty;
            }
            container inner {
              description
                "Inner filter options";
              leaf-list mac {
                description
                  "Inner filter mac";
                max-elements 5;
                type ios-types:cisco-mac-address-type;
              }
              container protocol {
                description
                  "Inner filter protocol";
                leaf dhcp {
                  description
                    "DHCP protocol";
                  type empty;
                }
              }
            }
            leaf interface {
              description
                "Interface name";
              type string;
            }
            choice capture-direction-choice {
              case both-case {
                leaf both {
                  description
                    "Inbound and outbound packets";
                  type empty;
                }
              }
              case in-case {
                leaf in {
                  description
                    "Inbound packets";
                  type empty;
                }
              }
              case out-case {
                leaf out {
                  description
                    "Outbound packets";
                  type empty;
                }
              }
            }
            container buffer {
              description
                "Buffer options";
              leaf size {
                description
                  "Size of buffer in MB";
                type empty;
              }
              leaf circular {
                description
                  "circular buffer";
                type empty;
              }
            }
            container limit {
              description
                "Limit Packets Captured";
              leaf duration {
                description
                  "Limit total duration of capture in seconds";
                type empty;
              }
              leaf every {
                description
                  "Limit capture to one in every nth packet";
                type empty;
              }
              leaf packet-len {
                description
                  "Limit the packet length to capture";
                type empty;
              }
              leaf packets {
                description
                  "Limit number of packets to capture";
                type empty;
              }
              leaf pps {
                description
                  "Limit number of packets per second to capture";
                type empty;
              }
            }
          }
        }
      }
    }
    output {
      uses cisco-xe-rpc-output;
    }
  }

  rpc pnpa {
    description
      "Plug and play command";
    input {
      container service {
        description
          "Service Name";
        choice service-choice {
          case wakeup-case {
            container wakeup {
              description
                "Wake up Profile";
              leaf profile-drop-node-name {
                description
                  "Profile name";
                type string;
              }
            }
          }
          case reset-case {
            leaf reset {
              description
                "Reset PnP config";
              type empty;
            }
          }
        }
      }
    }
    output {
      uses cisco-xe-rpc-output;
    }
  }

  rpc test {
    description
      "test exec command";
    input {
      choice test-feature;
    }
    output {
      uses cisco-xe-rpc-output;
    }
  }
}
