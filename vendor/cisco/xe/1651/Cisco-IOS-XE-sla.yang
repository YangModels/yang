module Cisco-IOS-XE-sla {
  namespace "http://cisco.com/ns/yang/Cisco-IOS-XE-sla";
  prefix ios-sla;


  import ietf-inet-types {
    prefix inet;
  }

  import Cisco-IOS-XE-native {
    prefix ios;
  }

  organization
    "Cisco Systems, Inc.";

  contact
    "Cisco Systems, Inc.
     Customer Service
     Postal: 170 W Tasman Drive
     San Jose, CA 95134
     Tel: +1 1800 553-NETS
     E-mail: cs-yang@cisco.com";

  description
    "Cisco XE Native Service Level Agreements (SLA) Yang model.
     Copyright (c) 2016 by Cisco Systems, Inc.
     All rights reserved."; 

  // =========================================================================
  // REVISION 
  // =========================================================================

  revision 2017-02-07 {
    description
      "Initial revision";
  }

  grouping ip-sla-path-echo-grouping {
    leaf paths-of-statistics-kept {
      description
              "Maximum number of statistics paths to capture";
      type uint8 {
    	  range "1..128";
      }
    }
    leaf samples-of-history-kept {
      description
        "Maximum number of history samples to collect";
      type uint8 {
        range "1..30";
      }
    }
    leaf hops-of-statistics-kept {
      description
        "Maximum number of statistics hops to capture";
      type uint8 {
        range "1..30";
      }
    }
  }

  grouping ip-sla-path-jitter-grouping {
    leaf frequency {
      description
        "Frequency of an operation";
      type uint32 {
        range "1..604800";
      }
    }
    leaf-list lsr-path {
      description
        "Loose Source Routing Path";
      type union {
        type string;
        type inet:ipv4-address;
      }
    }
    leaf owner {
      description
        "Owner of Entry";
      type string;
    }
    leaf request-data-size {
      description
        "Request data size";
      type uint32 {
        range "0..16384";
      }
    }
    leaf tag {
      description
        "User defined tag";
      type string;
    }
    leaf threshold {
      description
        "Operation threshold in milliseconds";
      type uint32 {
        range "0..60000";
      }
    }
    leaf timeout {
      description
        "Timeout of an operation";
      type uint32 {
        range "0..604800000";
      }
    }
    leaf tos {
      description
        "Type Of Service";
      type uint8;
    }
    leaf verify-data {
      description
        "Verify data";
      type empty;
    }
    leaf vrf {
      description
        "Configure IP SLAs for a VPN Routing/Forwarding instance";
      type string;
    }
  }

  grouping ip-sla-default-path-jitter-grouping {
    leaf frequency {
      description
        "Frequency of an operation";
      type empty;
    }
    leaf lsr-path {
      description
        "Loose Source Routing Path";
      type empty;
    }
    leaf owner {
      description
        "Owner of Entry";
      type empty;
    }
    leaf request-data-size {
      description
        "Request data size";
      type empty;
    }
    leaf tag {
      description
        "User defined tag";
      type empty;
    }
    leaf threshold {
      description
        "Operation threshold in milliseconds";
      type empty;
    }
    leaf timeout {
      description
        "Timeout of an operation";
      type empty;
    }
    leaf tos {
      description
        "Type Of Service";
      type empty;
    }
    leaf verify-data {
      description
        "Verify data";
      type empty;
    }
    leaf vrf {
      description
        "Configure IP SLAs for a VPN Routing/Forwarding instance";
      type empty;
    }
  }

  grouping ip-sla-udp-jitter-grouping {
    container history {
      description
        "History and Distribution Data";
      leaf distributions-of-statistics-kept {
        description
          "Maximum number of statistics distribution buckets to capture";
        type uint8 {
          range "1..20";
        }
      }
      container enhanced {
        description
          "Enable enhanced history collection";
        leaf interval {
          description
            "Aggregation interval";
          type uint16 {
            range "1..3600";
          }
        }
        leaf buckets {
          description
            "Number of buckets to collect data";
          type uint8 {
            range "1..100";
          }
        }
      }
      leaf hours-of-statistics-kept {
        description "Maximum number of statistics hour groups to capture";
        type uint8 {
          range "0..25";
        }
      }
      leaf statistics-distribution-interval {
        description "Statistics distribution interval size";
        type uint8 {
          range "1..100";
        }
      }
    }
    leaf owner {
      description
        "Owner of Entry";
      type string;
    }
    leaf request-data-size {
      description
      "Number of bytes in payload";
      type uint16 {
        range "16..17512";
      }
    }
    leaf tag {
      description
        "User defined tag";
      type string;
    }
    leaf threshold {
      description
        "Operation threshold in milliseconds";
      type uint16 {
        range "0..60000";
      }
    }
    leaf timeout {
      description
        "Timeout of an operation";
      type uint32 {
        range "0..604800000";
      }
    }
    leaf tos {
      description
        "Type Of Service";
      type uint8 {
        range "0..255";
      }
    }
    leaf traffic-class {
      description
        "Traffic class";
     type uint8 {
        range "0..255";
      }
    }
    leaf vrf {
      description
        "Configure IP SLAs for a VPN Routing/Forwarding instance";
      type string;
    }
  }

  grouping config-ip-sla-grouping {
    container sla {
      description
        "IP Service Level Agreement";
      list entry {
        key "number";
        leaf number {
          type uint32;
        }
        choice sla-param {
          case icmp-echo-case {
	        container icmp-echo {
	          description
	            "ICMP Echo Operation";
	          leaf destination {
	            type union {
	              type string;
	              type inet:ipv4-address;
	            }
	          }
	          leaf source-interface {
	            description
	              "Source Interface (ingress icmp packet interface)";
	            type string;
	          }
	          leaf source-ip {
	            description
	              "Source Address";
	            type union {
	              type string;
	              type inet:ipv4-address;
	            }
	          }
	          leaf data-pattern {
	            description
	              "Data Pattern";
	            type string;
	          }
	          leaf frequency {
	            description
	              "Frequency of an operation";
	            type uint32 {
	              range "1..604800";
	            }
	          }
	          container history {
	            description
	              "History and Distribution Data";
	            leaf buckets-kept {
                  description
                    "Maximum number of history buckets to collect";
                  type uint8;
	            }
	            leaf distributions-of-statistics-kept {
	              description
	                "Maximum number of statistics distribution buckets to capture";
	              type uint8;
	            }
	            container enhanced {
	              description
	                "Enable enhanced history collection";
	              leaf interval {
	                description
	                  "Aggregation interval";
	                type uint32 {
	                  range "1..3600";
	                }
	              }
	              leaf buckets {
	                description
	                  "Number of buckets to collect data";
	                type uint8 {
	                  range "1..100";
	                }
	              }
	            }
	            leaf filter {
	              description
	                "Add operation to History when...";
	              type enumeration {
	                enum "all";
	                enum "failures";
	                enum "none";
	                enum "overThreshold";
	              }
	            }
	            leaf hours-of-statistics-kept {
	              description
	                "Maximum number of statistics hour groups to capture";
	              type uint8 {
	                range "0..25";
	              }
	            }
	            leaf lives-kept {
	              description
	                "Maximum number of history lives to collect";
	              type uint8 {
	                range "0..2";
	              }
	            }
	            leaf statistics-distribution-interval {
	              description
	                "Statistics distribution interval size";
	              type uint8 {
	                range "1..100";
	              }
	            }
	          }
	          leaf owner {
	            description
	              "Owner of Entry";
	            type string;
	          }
	          leaf request-data-size {
	            description
	              "Request data size";
	            type uint32 {
	              range "0..16384";
	            }
	          }
	          leaf tag {
	            description
	              "User defined tag";
	            type string;
	          }
	          leaf threshold {
	            description
	              "Operation threshold in milliseconds";
	            type uint32 {
	              range "0..60000";
	            }
	          } 
	          leaf timeout {
	            description
	              "Timeout of an operation";
	            type uint64 {
	              range "0..604800000";
	            }
	          }
	          leaf tos {
	            description
	              "Type Of Service";
	            type uint8;
	          }
	          leaf verify-data {
	            description
	              "Verify data";
	            type empty;
	          }
	          leaf vrf {
	            description
	              "Configure IP SLAs for a VPN Routing/Forwarding instance";
	            type string;
	          }
	        }
          } // end icmp-echo-case
          case path-echo-case {
            container path-echo {
              description
                "Path Discovered ICMP Echo Operation";
              leaf dst-ip {
                description
                  "Destination IP address or hostname, broadcast disallowed";
                type union {
                  type string;
                  type inet:ipv4-address;
                }
              }
              leaf source-ip {
                description
                  "IP address or hostname, broadcast disallowed";
                type union {
                  type string;
                  type inet:ipv4-address;
                }
              }
              uses ip-sla-path-echo-grouping;
            }
          } // end path-echo-case
          case path-jitter-case {
            container path-jitter {
              description
                "Path Discovered ICMP Jitter Operation";
              leaf dst-ip {
                type union {
                  type string;
                  type inet:ipv4-address;
                  type inet:ipv6-address;
                }
              }
              leaf source-ip {
                description
                  "Source IP Address";
                type union {
                  type string;
                  type inet:ipv4-address;
                }
              }
              container default {
                description
                  "Set a command to its defaults";
                uses ip-sla-default-path-jitter-grouping;
              }
              uses ip-sla-path-jitter-grouping;
            }
          } // end path-jitter-case
          case udp-echo-case {
            // ip sla * /udp-echo
            container udp-echo {
              description
                              "UDP echo operation";
              leaf dest-addr {
                description
                                  "Hostname or A.B.C.D  Destination IP address or hostname, broadcast disallowed";
                type union {
                  type inet:ip-address;
                  type string;
                }
              }
              leaf dest-port {
                description
                                  "Port Number (Recommended ports greater than 1023)";
                type uint16 {
                  range "1..65535";
                }
              }
              leaf source-ip {
                description
                                  "Source address: Hostname or A.B.C.D IP address or hostname, broadcast disallowed";
                type union {
                  type inet:ip-address;
                  type string;
                }
              }
              leaf source-port {
                description
                                  "Source Port: Port Number (Recommended ports greater than 1023)";
                type uint16 {
                  range "1..65535";
                }
              }
            }
          } // end udp-echo-case
          case udp-jitter-case {
            // ip sla * /udp-jitter
            container udp-jitter {
              description 
                "UDP jitter operation";
              leaf dest-addr {
                description 
                  "Hostname or A.B.C.D  Destination IP address or hostname";
                type union {
                  type inet:ip-address;
                  type string;
                }
              }
              leaf portno {
                description
                  "Port Number";
                type uint16 {
                  range "1..65535";
                }
              }
              leaf source-ip {
                description
                  "Hostname or A.B.C.D  IP address or hostname, broadcast disallowed";
                type union {
                  type inet:ip-address;
                  type string;
                }
              }
              leaf num-packets {
                description "Number of Packets (default 10)";
                type uint16 {
                  range "1..60000";
                }
              }
              leaf interval {
                description "Delay (default 20)";
                type uint16 {
                  range "4..60000";
                }
              }
              uses ip-sla-udp-jitter-grouping;
            }
          } //end udp-jitter-case
          case http-case {
            //ip sla * / http
            container http {
              description
               "HTTP Operation";
  
              choice http-choice {
               case http-get {
                  container get {
                    description
                      "HTTP get operation";
  
                    leaf url {
                      description 
                        "URL";
                      type string;
                    }
                    leaf source-ip {
                      description
                        "Source Address";
                      type union {
                        type inet:ip-address;
                       type string;
                     }
                    }
                    leaf source-port {
                      description
                        "Source port";
                      type uint16 {
                        range "1..65535";
                      }
                    }
                    leaf name-server {
                      description
                        "Name server";
                      type union {
                        type string;
                        type inet:ip-address;
                      }
                    }
                  }
                }
                case http-raw {
                  container raw {
                    description
                      "HTTP raw operation";
                    leaf url {
                      type string;
                    }
                    leaf source-ip {
                      description
                        "Source Address";
                      type union {
                        type inet:ip-address;
                        type string;
                      }
                    }
                    leaf source-port {
                      description
                        "Source port";
                      type uint16 {
                        range "1..65535";
                      }
                    }
                    leaf name-server {
                      description
                        "Name server";
                      type union {
                        type string;
                        type inet:ip-address;
                      }
                    }
                  }
                }
              }
              //http submode CMDs:
              leaf owner {
                description
                  "Owner of Entry";
                type string;
              }
              leaf tag {
                description
                  "User defined tag";
                type string;
              }
              leaf vrf {
                description
                  "Configure IP SLAs for a new VPN Routing/Forwarding instance";
                type string;
              }
            } // end ip sla http
          } // end http-case
          case dhcp-case {
            container dhcp {
              description
                              "DHCP Operation";
              leaf dst-ip {
                description
                                  "Destination IP address or hostname, broadcast disallowed";
                type union {
                  type string;
                  type inet:ipv4-address;
                }
              }
              leaf source-ip {
                description
                  "IP address or hostname, broadcast disallowed";
                type union {
                  type string;
                  type inet:ipv4-address;
                }
              }
            } //end ip sla dhcp            
          }//end dhcp-case
        } // end choice sla-param 
      } // end ip sla entry

      // ip sla enable
      container enable {
        leaf reaction-alerts {
          type empty;
        }
      }
      // ip sla responder
      container responder {
        description "Enable IP SLAs Responder";
        presence true;
        container udp-echo {
          description "Setup udp-echo responder";
          leaf port {
            description "Permanent port";
            type uint16 {
              range "1..65535";
            }
          }
          list ipaddress {
            description "Permanent address";
            key "host";
            leaf host {
              type union {
                type inet:ipv4-address;
                type inet:ipv6-address;
              }
            }
            leaf port {
              description "Permanent port";
              type uint16 {
                range "1..65535";
              }
            }
          }
        }
        container tcp-connect {
          description "Setup tcp-connect responder";
          leaf port {
            description "Permanent port";
            type uint16 {
              range "1..65535";
            }
          }
          list ipaddress {
            description "Permanent address";
            key "host";
            leaf host {
              type union {
                type inet:ipv4-address;
                type inet:ipv6-address;
              }
            }
            leaf port {
              description "Permanent port";
              type uint16 {
                range "1..65535";
              }
            }
          }
        }
      }
      // ip sla logging
      container logging {
        description "low-memory";
        leaf traps {
          description "Enable syslog traps";
          type empty;
        }
      }
      // ip sla group
      container group {
        description "Group Configuration or Group Scheduling";
        list schedule {
          description "Group scheduling";
          key "entry-number";
          leaf entry-number {
            description "Group schedule entry number";
            type uint32 {
              range "1..2147483647";
            }
          }
          list probe-ids {
            key "word";
            leaf word {
              type string;
            }
            container schedule-period {
              description "Group schedule period range";
              leaf seconds {
                description "seconds";
                type uint32;
              }
              container frequency {
                description 
                  "Group operation frequency";
                choice frequency-choice {
                  case frequency-value {
                    leaf frequency-val {
                      description
                        "Specify frequency in seconds";
                      type uint32;
                    }
                  }
                  case frequency-range {
                      leaf range {
                        description 
                          "Group operation frequency-range for random scheduling";
                      type string;
                    }
                  }
                }
              }

              container start-time {
                description
                  "When to start this entry";
                leaf now {
                  description
                    "Start now";
                  type empty;
                }
              }
              
              leaf life {
                description
                  "Length of time to execute in seconds";
                type union {
                  type uint32;
                  type enumeration {
                    enum "forever";
                  }
                }
              }

            }// end container schedule-period

          }
        }
      }
      // ip sla schedule
      list schedule {
        description
          "Entry Scheduling";
        key "entry-number";
        leaf entry-number {
          type uint32;
        }
        leaf ageout {
          description
            "How long to keep this Entry when inactive";
          type uint32 {
            range "0..2073600";
          }
        }
        leaf life {
          description
            "Length of time to execute in seconds";
          type union {
            type uint32;
            type enumeration {
              enum "forever";
            }
          }
        }
        leaf recurring {
          description
            "Probe to be scheduled automatically every day";
          type empty;
        }
        container start-time {
          description
            "When to start this entry";
          leaf after {
            description
              "Start after a certain amount of time from now";
            type string;
          }
          leaf hour-min {
            type string;
          }
          leaf hour-min-sec {
            type string;
          }
          leaf now {
            description
              "Start now";
            type empty;
          }
          leaf pending {
            description
              "Start pending";
            type empty;
          }
          leaf random {
            description
              "Start after random time (range)";
            type uint32 {
              range "500..10000";
            }
          }
        }
      }

      // ip sla reaction-configuration
      list reaction-configuration {
        description
          "IP SLA's reaction configuration";

        key "entry-number";
        leaf entry-number {
          description
            "Entry number";
          type uint64 {
            range "1..2147483647";
          }
        }

        // ip sla reaction-configuration * react
        container react {
          container connectionLoss {
            presence true;
            container threshold-type {
              container xOfy {
                leaf x-val {
                  description
                    "X value";
                  type uint8 {
                    range "1..16";
                  }
                }
                leaf y-val {
                  description
                    "Y value";
                  type uint8 {
                    range "1..16";
                  }
                }
                leaf action-type {
                  type enumeration {
                    enum "none";
                    enum "trapAndTrigger";
                    enum "trapOnly";
                    enum "triggerOnly";
                  }
                }
              }
            }
          }

          container rtt {
            presence true;
            container threshold-value {
              leaf upper-limit-val {
                description
                  "Upper limit";
                type uint32 {
                  range "1..60000";
                }
              }
              leaf lower-limit-val {
                description
                  "Lower limit";
                type uint32 {
                  range "1..60000";
                }
              }
              leaf threshold-type {
                description
                  "Threshold type";
                type enumeration {
                  enum "immediate";
                }
              }
              leaf action-type {
                type enumeration {
                  enum "none";
                  enum "trapAndTrigger";
                  enum "trapOnly";
                  enum "triggerOnly";
                }
              }
            }
          } //end rtt
        } //end react
      } //end reaction-configuration

      // ip sla server
      container server {
        description "IPPM server configuration";
        container twamp {
          description "IPPM TWAMP server configuration";
          presence "true";
        }
      }
    }
  }

  /////////////////////////////////////////////////////////
  // native / ip / sla
  /////////////////////////////////////////////////////////
  augment "/ios:native/ios:ip" {
    uses config-ip-sla-grouping;
  } //augment

}
