/*
 * Generated by confdc --mib2yang-std
 * Source: mgmt/dmi/model/common/mib-source/hand-processed/CISCO-CDP-MIB.mib
 */
/*
 * This YANG module has been generated by smidump 0.5.0:
 *
 *      smidump -f yang CISCO-CDP-MIB
 *
 * Do not edit. Edit the source file instead!
 */

module CISCO-CDP-MIB {

  namespace "urn:ietf:params:xml:ns:yang:smiv2:CISCO-CDP-MIB";
  prefix CISCO-CDP-MIB;

  import CISCO-TC {
    prefix "cisco-tc";
  }

  import CISCO-VTP-MIB {
    prefix "cisco-vtp";
  }

  import IF-MIB {
    prefix "if-mib";
  }

  import SNMPv2-TC {
    prefix "snmpv2-tc";
  }

  import ietf-yang-smiv2 {
    prefix "smiv2";
  }

  import ietf-yang-types {
    prefix "yang";
  }

  organization
   "Cisco System Inc.";

  contact
   "       Cisco Systems
    Customer Service
    
    Postal: 170 West Tasman Drive,
    San Jose CA 95134-1706.
    USA
    
    Tel: +1 800 553-NETS
    
    E-mail: cs-snmp@cisco.com";

  description
   "The MIB module for management of the Cisco Discovery
    Protocol in Cisco devices.";

  revision 2005-03-21 {
    description
     "Added the following object:
      cdpInterfaceName.";
  }

  revision 2005-03-14 {
    description
     "Added cdpCtAddressTable which contains the following
      objects:
      cdpCtAddressIndex,
      cdpCtAddressType, 
      cdpCtAddress.";
  }

  revision 2001-11-23 {
    description
     "Added cdpInterfaceExtTable which contains the following
      objects:
      cdpInterfaceExtendedTrust, 
      cdpInterfaceCosForUntrustedPort.";
  }

  revision 2001-04-23 {
    description
     "Added the following objects:
      cdpGlobalDeviceIdFormatCpb, 
      cdpGlobalDeviceIdFormat.";
  }

  revision 2000-11-22 {
    description
     "Added the following objects: 
      cdpCacheApplianceID,
      cdpCacheVlanID, 
      cdpCachePowerConsumption,
      cdpCacheMTU,
      cdpCachePrimaryMgmtAddrType,
      cdpCachePrimaryMgmtAddr,
      cdpCacheSecondaryMgmtAddrType,
      cdpCacheSecondaryMgmtAddr,
      cdpCacheLastChange,
      cdpCachePhysLocation,
      cdpCacheSysName, 
      cdpCacheSysObjectID,
      cdpGlobalLastChange";
  }

  revision 1998-12-10 {
    description
     "Added cdpGlobalDeviceId object.";
  }

  revision 1998-09-16 {
    description
     "added these objects to cdpCacheTable:  
      cdpCacheVTPMgmtDomain, 
      cdpCacheNativeVLAN, 
      cdpCacheDuplex.";
  }

  revision 1996-07-08 {
    description
     "Obsolete cdpInterfaceMessageInterval and newly
      define cdpGlobal object.";
  }

  revision 1995-08-15 {
    description
     "Specify a correct (non-negative) range for several
      index objects.";
  }

  revision 1995-07-27 {
    description
     "Correct range of cdpInterfaceMessageInterval.";
  }

  revision 1995-01-25 {
    description
     "Move from ciscoExperiment to ciscoMgmt oid subtree.";
  }


  container CISCO-CDP-MIB {
    config false;

    container cdpGlobal {
      smiv2:oid "1.3.6.1.4.1.9.9.23.1.3";

      leaf cdpGlobalRun {
        type boolean;
        description
         "An indication of whether the Cisco Discovery Protocol
          is currently running.  Entries in cdpCacheTable are
          deleted when CDP is disabled.";
        smiv2:defval "true";
        smiv2:max-access "read-write";
        smiv2:oid "1.3.6.1.4.1.9.9.23.1.3.1";
      }

      leaf cdpGlobalMessageInterval {
        type int32 {
          range "5..254";
        }
        units "seconds";
        description
         "The interval at which CDP messages are to be generated.
          The default value is 60 seconds.";
        smiv2:defval "60";
        smiv2:max-access "read-write";
        smiv2:oid "1.3.6.1.4.1.9.9.23.1.3.2";
      }

      leaf cdpGlobalHoldTime {
        type int32 {
          range "10..255";
        }
        units "seconds";
        description
         "The time for the receiving device holds CDP message.
          The default value is 180 seconds.";
        smiv2:defval "180";
        smiv2:max-access "read-write";
        smiv2:oid "1.3.6.1.4.1.9.9.23.1.3.3";
      }

      leaf cdpGlobalDeviceId {
        type snmpv2-tc:DisplayString;
        description
         "The device ID advertised by this device. The format of this
          device id is characterized by the value of 
          cdpGlobalDeviceIdFormat object.";
        smiv2:max-access "read-only";
        smiv2:oid "1.3.6.1.4.1.9.9.23.1.3.4";
      }

      leaf cdpGlobalLastChange {
        type yang:timestamp;
        description
         "Indicates the time when the cache table was last changed. It
          is the most recent time at which any row was last created,
          modified or deleted.";
        smiv2:max-access "read-only";
        smiv2:oid "1.3.6.1.4.1.9.9.23.1.3.5";
      }

      leaf cdpGlobalDeviceIdFormatCpb {
        type bits {
          bit serialNumber {
            position "0";
          }
          bit macAddress {
            position "1";
          }
          bit other {
            position "2";
          }
        }
        description
         "Indicate the Device-Id format capability of the device.
          
          serialNumber(0) indicates that the device supports using
          serial number as the format for its DeviceId.
          
          macAddress(1) indicates that the device supports using
          layer 2 MAC address as the format for its DeviceId.
          
          other(2) indicates that the device supports using its
          platform specific format as the format for its DeviceId.";
        smiv2:max-access "read-only";
        smiv2:oid "1.3.6.1.4.1.9.9.23.1.3.6";
      }

      leaf cdpGlobalDeviceIdFormat {
        type enumeration {
          enum "serialNumber" {
            value "1";
          }
          enum "macAddress" {
            value "2";
          }
          enum "other" {
            value "3";
          }
        }
        description
         "An indication of the format of Device-Id contained in the
          corresponding instance of cdpGlobalDeviceId. User can only
          specify the formats that the device is capable of as
          denoted in cdpGlobalDeviceIdFormatCpb object.
          
          serialNumber(1) indicates that the value of cdpGlobalDeviceId 
          object is in the form of an ASCII string contain the device
          serial number. 
          
          macAddress(2) indicates that the value of cdpGlobalDeviceId 
          object is in the form of Layer 2 MAC address.
          
          other(3) indicates that the value of cdpGlobalDeviceId object
          is in the form of a platform specific ASCII string contain
          info that identifies the device. For example: ASCII string
          contains serialNumber appended/prepened with system name.";
        smiv2:max-access "read-write";
        smiv2:oid "1.3.6.1.4.1.9.9.23.1.3.7";
      }
    }

    container cdpInterfaceTable {
      description
       "The (conceptual) table containing the status of CDP on
        the device's interfaces.";
      smiv2:oid "1.3.6.1.4.1.9.9.23.1.1.1";

      list cdpInterfaceEntry {
        key "cdpInterfaceIfIndex";
        description
         "An entry (conceptual row) in the cdpInterfaceTable,
          containing the status of CDP on an interface.";
        smiv2:oid "1.3.6.1.4.1.9.9.23.1.1.1.1";

        leaf cdpInterfaceIfIndex {
          type int32 {
            range "0..2147483647";
          }
          description
           "The ifIndex value of the local interface.
            
            For 802.3 Repeaters on which the repeater ports do not
            have ifIndex values assigned, this value is a unique
            value for the port, and greater than any ifIndex value
            supported by the repeater; in this case, the specific
            port is indicated by corresponding values of
            cdpInterfaceGroup and cdpInterfacePort, where these
            values correspond to the group number and port number
            values of RFC 1516.";
          smiv2:max-access "not-accessible";
          smiv2:oid "1.3.6.1.4.1.9.9.23.1.1.1.1.1";
        }

        leaf cdpInterfaceEnable {
          type boolean;
          description
           "An indication of whether the Cisco Discovery Protocol
            is currently running on this interface.  This variable
            has no effect when CDP is disabled (cdpGlobalRun = FALSE).";
          smiv2:max-access "read-write";
          smiv2:oid "1.3.6.1.4.1.9.9.23.1.1.1.1.2";
        }

        leaf cdpInterfaceMessageInterval {
          type int32 {
            range "0..254";
          }
          units "seconds";
          status obsolete;
          description
           "The interval at which CDP messages are to be generated
            on this interface.  The default value is 60 seconds.";
          smiv2:max-access "read-write";
          smiv2:oid "1.3.6.1.4.1.9.9.23.1.1.1.1.3";
        }

        leaf cdpInterfaceGroup {
          type int32;
          description
           "This object is only relevant to interfaces which are
            repeater ports on 802.3 repeaters.  In this situation,
            it indicates the RFC1516 group number of the repeater
            port which corresponds to this interface.";
          smiv2:max-access "read-only";
          smiv2:oid "1.3.6.1.4.1.9.9.23.1.1.1.1.4";
        }

        leaf cdpInterfacePort {
          type int32;
          description
           "This object is only relevant to interfaces which are
            repeater ports on 802.3 repeaters.  In this situation,
            it indicates the RFC1516 port number of the repeater
            port which corresponds to this interface.";
          smiv2:max-access "read-only";
          smiv2:oid "1.3.6.1.4.1.9.9.23.1.1.1.1.5";
        }

        leaf cdpInterfaceName {
          type snmpv2-tc:DisplayString;
          description
           "The name of the local interface as advertised by
            CDP in the Port-ID TLV";
          smiv2:max-access "read-only";
          smiv2:oid "1.3.6.1.4.1.9.9.23.1.1.1.1.6";
        }
      }
    }

    container cdpInterfaceExtTable {
      description
       "This table contains the additional CDP configuration on
        the device's interfaces.";
      smiv2:oid "1.3.6.1.4.1.9.9.23.1.1.2";

      list cdpInterfaceExtEntry {
        key "ifIndex";
        description
         "An entry in the cdpInterfaceExtTable contains the values
          configured for Extented Trust TLV and COS (Class of Service)
          for Untrusted Ports TLV on an interface which supports the
          sending of these TLVs.";
        smiv2:oid "1.3.6.1.4.1.9.9.23.1.1.2.1";

        leaf ifIndex {
          type leafref {
            path "/if-mib:IF-MIB/if-mib:ifTable/if-mib:ifEntry/if-mib:ifIndex";
          }
        }

        leaf cdpInterfaceExtendedTrust {
          type enumeration {
            enum "trusted" {
              value "1";
            }
            enum "noTrust" {
              value "2";
            }
          }
          description
           "Indicates the value to be sent by Extended Trust TLV.
            
            If trusted(1) is configured, the value of Extended Trust TLV
            is one byte in length with its least significant bit equal to
            1 to indicate extended trust. All other bits are 0.
            
            If noTrust(2) is configured, the value of Extended Trust TLV
            is one byte in length with its least significant bit equal to
            0 to indicate no extended trust. All other bits are 0.";
          smiv2:max-access "read-write";
          smiv2:oid "1.3.6.1.4.1.9.9.23.1.1.2.1.1";
        }

        leaf cdpInterfaceCosForUntrustedPort {
          type uint32 {
            range "0..7";
          }
          description
           "Indicates the value to be sent by COS for Untrusted Ports TLV.";
          smiv2:max-access "read-write";
          smiv2:oid "1.3.6.1.4.1.9.9.23.1.1.2.1.2";
        }
      }
    }

    container cdpCacheTable {
      description
       "The (conceptual) table containing the cached
        information obtained via receiving CDP messages.";
      smiv2:oid "1.3.6.1.4.1.9.9.23.1.2.1";

      list cdpCacheEntry {
        key "cdpCacheIfIndex cdpCacheDeviceIndex";
        description
         "An entry (conceptual row) in the cdpCacheTable,
          containing the information received via CDP on one
          interface from one device.  Entries appear when
          a CDP advertisement is received from a neighbor
          device.  Entries disappear when CDP is disabled
          on the interface, or globally.";
        smiv2:oid "1.3.6.1.4.1.9.9.23.1.2.1.1";

        leaf cdpCacheIfIndex {
          type int32 {
            range "0..2147483647";
          }
          description
           "Normally, the ifIndex value of the local interface.
            For 802.3 Repeaters for which the repeater ports do not
            have ifIndex values assigned, this value is a unique
            value for the port, and greater than any ifIndex value
            supported by the repeater; the specific port number in
            this case, is given by the corresponding value of
            cdpInterfacePort.";
          smiv2:max-access "not-accessible";
          smiv2:oid "1.3.6.1.4.1.9.9.23.1.2.1.1.1";
        }

        leaf cdpCacheDeviceIndex {
          type int32 {
            range "0..2147483647";
          }
          description
           "A unique value for each device from which CDP messages
            are being received.";
          smiv2:max-access "not-accessible";
          smiv2:oid "1.3.6.1.4.1.9.9.23.1.2.1.1.2";
        }

        leaf cdpCacheAddressType {
          type cisco-tc:CiscoNetworkProtocol;
          description
           "An indication of the type of address contained in the
            corresponding instance of cdpCacheAddress.";
          smiv2:max-access "read-only";
          smiv2:oid "1.3.6.1.4.1.9.9.23.1.2.1.1.3";
        }

        leaf cdpCacheAddress {
          type cisco-tc:CiscoNetworkAddress;
          description
           "The (first) network-layer address of the device
            as reported in the Address TLV of the most recently received
            CDP message.  For example, if the corresponding instance of
            cacheAddressType had the value 'ip(1)', then this object 
            would be an IPv4-address.  If the neighbor device is 
            SNMP-manageable, it is supposed to generate its CDP messages
            such that this address is one at which it will receive SNMP
            messages. Use cdpCtAddressTable to extract the remaining
            addresses from the Address TLV received most recently.";
          smiv2:max-access "read-only";
          smiv2:oid "1.3.6.1.4.1.9.9.23.1.2.1.1.4";
        }

        leaf cdpCacheVersion {
          type snmpv2-tc:DisplayString;
          description
           "The Version string as reported in the most recent CDP
            message.  The zero-length string indicates no Version
            field (TLV) was reported in the most recent CDP
            message.";
          smiv2:max-access "read-only";
          smiv2:oid "1.3.6.1.4.1.9.9.23.1.2.1.1.5";
        }

        leaf cdpCacheDeviceId {
          type snmpv2-tc:DisplayString;
          description
           "The Device-ID string as reported in the most recent CDP
            message.  The zero-length string indicates no Device-ID
            field (TLV) was reported in the most recent CDP
            message.";
          smiv2:max-access "read-only";
          smiv2:oid "1.3.6.1.4.1.9.9.23.1.2.1.1.6";
        }

        leaf cdpCacheDevicePort {
          type snmpv2-tc:DisplayString;
          description
           "The Port-ID string as reported in the most recent CDP
            message.  This will typically be the value of the ifName
            object (e.g., 'Ethernet0').  The zero-length string
            indicates no Port-ID field (TLV) was reported in the
            most recent CDP message.";
          smiv2:max-access "read-only";
          smiv2:oid "1.3.6.1.4.1.9.9.23.1.2.1.1.7";
        }

        leaf cdpCachePlatform {
          type snmpv2-tc:DisplayString;
          description
           "The Device's Hardware Platform as reported in the most
            recent CDP message.  The zero-length string indicates
            that no Platform field (TLV) was reported in the most
            recent CDP message.";
          smiv2:max-access "read-only";
          smiv2:oid "1.3.6.1.4.1.9.9.23.1.2.1.1.8";
        }

        leaf cdpCacheCapabilities {
          type binary {
            length "0..4";
          }
          description
           "The Device's Functional Capabilities as reported in the
            most recent CDP message.  For latest set of specific
            values, see the latest version of the CDP specification.
            The zero-length string indicates no Capabilities field
            (TLV) was reported in the most recent CDP message.";
          reference
           "Cisco Discovery Protocol Specification, 10/19/94.";
          smiv2:max-access "read-only";
          smiv2:oid "1.3.6.1.4.1.9.9.23.1.2.1.1.9";
        }

        leaf cdpCacheVTPMgmtDomain {
          type snmpv2-tc:DisplayString {
            length "0..32";
          }
          description
           "The VTP Management Domain for the remote device's interface, 
            as reported in the most recently received CDP message.
            This object is not instantiated if no VTP Management Domain field
            (TLV) was reported in the most recently received CDP message.";
          reference
           "managementDomainName in CISCO-VTP-MIB";
          smiv2:max-access "read-only";
          smiv2:oid "1.3.6.1.4.1.9.9.23.1.2.1.1.10";
        }

        leaf cdpCacheNativeVLAN {
          type cisco-vtp:VlanIndex;
          description
           "The remote device's interface's native VLAN, as reported in the 
            most recent CDP message.  The value 0 indicates
            no native VLAN field (TLV) was reported in the most
            recent CDP message.";
          smiv2:max-access "read-only";
          smiv2:oid "1.3.6.1.4.1.9.9.23.1.2.1.1.11";
        }

        leaf cdpCacheDuplex {
          type enumeration {
            enum "unknown" {
              value "1";
            }
            enum "halfduplex" {
              value "2";
            }
            enum "fullduplex" {
              value "3";
            }
          }
          description
           "The remote device's interface's duplex mode, as reported in the 
            most recent CDP message.  The value unknown(1) indicates
            no duplex mode field (TLV) was reported in the most
            recent CDP message.";
          smiv2:max-access "read-only";
          smiv2:oid "1.3.6.1.4.1.9.9.23.1.2.1.1.12";
        }

        leaf cdpCacheApplianceID {
          type uint32 {
            range "0..255";
          }
          description
           "The remote device's Appliance ID, as reported in the 
            most recent CDP message. This object is not instantiated if
            no Appliance VLAN-ID field (TLV) was reported in the most
            recently received CDP message.";
          smiv2:max-access "read-only";
          smiv2:oid "1.3.6.1.4.1.9.9.23.1.2.1.1.13";
        }

        leaf cdpCacheVlanID {
          type uint32 {
            range "0..4095";
          }
          description
           "The remote device's VoIP VLAN ID, as reported in the 
            most recent CDP message. This object is not instantiated if
            no Appliance VLAN-ID field (TLV) was reported in the most
            recently received CDP message.";
          smiv2:max-access "read-only";
          smiv2:oid "1.3.6.1.4.1.9.9.23.1.2.1.1.14";
        }

        leaf cdpCachePowerConsumption {
          type uint32;
          units "milliwatts";
          description
           "The amount of power consumed by remote device, as reported
            in the most recent CDP message. This object is not instantiated
            if no Power Consumption field (TLV) was reported in the most
            recently received CDP message.";
          smiv2:max-access "read-only";
          smiv2:oid "1.3.6.1.4.1.9.9.23.1.2.1.1.15";
        }

        leaf cdpCacheMTU {
          type uint32;
          description
           "Indicates the size of the largest datagram that can be
            sent/received by remote device, as reported in the most recent
            CDP message. This object is not instantiated if no MTU field
            (TLV) was reported in the most recently received CDP message.";
          smiv2:max-access "read-only";
          smiv2:oid "1.3.6.1.4.1.9.9.23.1.2.1.1.16";
        }

        leaf cdpCacheSysName {
          type snmpv2-tc:DisplayString {
            length "0..255";
          }
          description
           "Indicates the value of the remote device's sysName MIB object.
            By convention, it is the device's fully qualified domain name.
            This object is not instantiated if no sysName field (TLV) was
            reported in the most recently received CDP message.";
          smiv2:max-access "read-only";
          smiv2:oid "1.3.6.1.4.1.9.9.23.1.2.1.1.17";
        }

        leaf cdpCacheSysObjectID {
          type yang:object-identifier-128;
          description
           "Indicates the value of the remote device's sysObjectID MIB
            object. This object is not instantiated if no sysObjectID field
            (TLV) was reported in the most recently received CDP message.";
          smiv2:max-access "read-only";
          smiv2:oid "1.3.6.1.4.1.9.9.23.1.2.1.1.18";
        }

        leaf cdpCachePrimaryMgmtAddrType {
          type cisco-tc:CiscoNetworkProtocol;
          description
           "An indication of the type of address contained in the
            corresponding instance of cdpCachePrimaryMgmtAddress.";
          smiv2:max-access "read-only";
          smiv2:oid "1.3.6.1.4.1.9.9.23.1.2.1.1.19";
        }

        leaf cdpCachePrimaryMgmtAddr {
          type cisco-tc:CiscoNetworkAddress;
          description
           "This object indicates the (first) network layer
            address at which the device will accept SNMP messages
            as reported in the first address in the 
            Management-Address TLV of the most recently received
            CDP message.  If the corresponding instance of 
            cdpCachePrimaryMgmtAddrType has the value 'ip(1)',
            then this object would be an IP-address. If the 
            remote device is not currently manageable via any 
            network protocol, then it reports the special value 
            of the IPv4 address 0.0.0.0, and that address is 
            recorded in this object.  If the most recently received
            CDP message did not contain the Management-Address
            TLV, then this object is not instanstiated.";
          smiv2:max-access "read-only";
          smiv2:oid "1.3.6.1.4.1.9.9.23.1.2.1.1.20";
        }

        leaf cdpCacheSecondaryMgmtAddrType {
          type cisco-tc:CiscoNetworkProtocol;
          description
           "An indication of the type of address contained in the
            corresponding instance of cdpCacheSecondaryMgmtAddress.";
          smiv2:max-access "read-only";
          smiv2:oid "1.3.6.1.4.1.9.9.23.1.2.1.1.21";
        }

        leaf cdpCacheSecondaryMgmtAddr {
          type cisco-tc:CiscoNetworkAddress;
          description
           "This object indicates the alternate network layer
            address at which the device will accept SNMP messages
            as reported in the second address in the 
            Management-Address TLV of the most recently received
            CDP message.  If the corresponding instance of
            cdpCacheSecondaryMgmtAddrType has the value 'ip(1)',
            then this object would be an IP-address. If the 
            remote device reports the special value of the 
            IPv4 address 0.0.0.0, that address is recorded in 
            this object.  If the most recently received CDP
            message did not contain the Management-Address
            TLV, or if that TLV contained only one address, then
            this object is not instanstiated.";
          smiv2:max-access "read-only";
          smiv2:oid "1.3.6.1.4.1.9.9.23.1.2.1.1.22";
        }

        leaf cdpCachePhysLocation {
          type snmpv2-tc:DisplayString;
          description
           "Indicates the physical location, as reported by the most recent
            CDP message, of a connector which is on, or physically connected
            to, the remote device's interface over which the CDP packet is
            sent. This object is not instantiated if no Physical Location
            field (TLV) was reported by the most recently received CDP
            message.";
          smiv2:max-access "read-only";
          smiv2:oid "1.3.6.1.4.1.9.9.23.1.2.1.1.23";
        }

        leaf cdpCacheLastChange {
          type yang:timestamp;
          description
           "Indicates the time when this cache entry was last changed.
            This object is initialised to the current time when the entry
            gets created and updated to the current time whenever the value
            of any (other) object instance in the corresponding row is
            modified.";
          smiv2:max-access "read-only";
          smiv2:oid "1.3.6.1.4.1.9.9.23.1.2.1.1.24";
        }
      }
    }

    container cdpCtAddressTable {
      description
       "The (conceptual) table containing the list of 
        network-layer addresses of a neighbor interface,
        as reported in the Address TLV of the most recently
        received CDP message. The first address included in
        the Address TLV is saved in cdpCacheAddress.  This
        table contains the remainder of the addresses in the
        Address TLV.";
      smiv2:oid "1.3.6.1.4.1.9.9.23.1.2.2";

      list cdpCtAddressEntry {
        key "cdpCacheIfIndex cdpCacheDeviceIndex cdpCtAddressIndex";
        description
         "An entry (conceptual row) in the cdpCtAddressTable,
          containing the information on one address received via CDP 
          on one interface from one device.  Entries appear 
          when a CDP advertisement is received from a neighbor
          device, with an Address TLV.  Entries disappear when
          CDP is disabled on the interface, or globally. An entry 
          or entries would also disappear if the most recently
          received CDP packet contain fewer address entries in the
          Address TLV, than are currently present in the CDP cache.";
        smiv2:oid "1.3.6.1.4.1.9.9.23.1.2.2.1";

        leaf cdpCacheIfIndex {
          type leafref {
            path "/CISCO-CDP-MIB:CISCO-CDP-MIB/CISCO-CDP-MIB:cdpCacheTable/CISCO-CDP-MIB:cdpCacheEntry/CISCO-CDP-MIB:cdpCacheIfIndex";
          }
        }

        leaf cdpCacheDeviceIndex {
          type leafref {
            path "/CISCO-CDP-MIB:CISCO-CDP-MIB/CISCO-CDP-MIB:cdpCacheTable/CISCO-CDP-MIB:cdpCacheEntry/CISCO-CDP-MIB:cdpCacheDeviceIndex";
          }
        }

        leaf cdpCtAddressIndex {
          type int32 {
            range "1..2147483647";
          }
          description
           "The index of the address entry for a given 
            cdpCacheIfIndex,cdpCacheDeviceIndex pair. It
            has the value N-1 for the N-th address in the
            Address TLV";
          smiv2:max-access "not-accessible";
          smiv2:oid "1.3.6.1.4.1.9.9.23.1.2.2.1.3";
        }

        leaf cdpCtAddressType {
          type cisco-tc:CiscoNetworkProtocol;
          description
           "An indication of the type of address contained in the
            corresponding instance of cdpCtAddress.";
          smiv2:max-access "read-only";
          smiv2:oid "1.3.6.1.4.1.9.9.23.1.2.2.1.4";
        }

        leaf cdpCtAddress {
          type cisco-tc:CiscoNetworkAddress;
          description
           "The N-th network-layer address of the device as reported
            in the most recent CDP message's Address TLV, where N-1 is
            given by the value of cdpCtAddressIndex. For example, if
            the the corresponding instance of cdpCtAddressType had the
            value 'ip(1)', then this object would be an IPv4-address.
            NOTE - The 1st address received in the Address TLV is
                   available using cdpCacheAddress";
          smiv2:max-access "read-only";
          smiv2:oid "1.3.6.1.4.1.9.9.23.1.2.2.1.5";
        }
      }
    }
  }

  smiv2:alias "ciscoCdpMIB" {
    smiv2:oid "1.3.6.1.4.1.9.9.23";
  }

  smiv2:alias "ciscoCdpMIBObjects" {
    smiv2:oid "1.3.6.1.4.1.9.9.23.1";
  }

  smiv2:alias "cdpInterface" {
    smiv2:oid "1.3.6.1.4.1.9.9.23.1.1";
  }

  smiv2:alias "cdpCache" {
    smiv2:oid "1.3.6.1.4.1.9.9.23.1.2";
  }

  smiv2:alias "cdpGlobal" {
    smiv2:oid "1.3.6.1.4.1.9.9.23.1.3";
  }

  smiv2:alias "ciscoCdpMIBConformance" {
    smiv2:oid "1.3.6.1.4.1.9.9.23.2";
  }

  smiv2:alias "ciscoCdpMIBCompliances" {
    smiv2:oid "1.3.6.1.4.1.9.9.23.2.1";
  }

  smiv2:alias "ciscoCdpMIBGroups" {
    smiv2:oid "1.3.6.1.4.1.9.9.23.2.2";
  }

}
