/*
 * Generated by confdc --mib2yang-std
 * Source: mgmt/dmi/model/common/mib-source/TUNNEL-MIB.mib
 */
/*
 * This YANG module has been generated by smidump 0.5.0:
 *
 *      smidump -f yang TUNNEL-MIB
 *
 * Do not edit. Edit the source file instead!
 */

module TUNNEL-MIB {

  namespace "urn:ietf:params:xml:ns:yang:smiv2:TUNNEL-MIB";
  prefix TUNNEL-MIB;

  import IANAifType-MIB {
    prefix "ianaiftype-mib";
  }

  import IF-MIB {
    prefix "if-mib";
  }

  import INET-ADDRESS-MIB {
    prefix "inet-address";
  }

  import SNMPv2-TC {
    prefix "snmpv2-tc";
  }

  import ietf-inet-types {
    prefix "inet";
  }

  import ietf-yang-smiv2 {
    prefix "smiv2";
  }

  organization
   "IETF IP Version 6 (IPv6) Working Group";

  contact
   " Dave Thaler
    Microsoft Corporation
    One Microsoft Way
    Redmond, WA  98052-6399
    EMail: dthaler@microsoft.com";

  description
   "The MIB module for management of IP Tunnels,
    independent of the specific encapsulation scheme in
    use.
    
    Copyright (C) The Internet Society (2005).  This
    version of this MIB module is part of RFC 4087;  see
    the RFC itself for full legal notices.";

  revision 2005-05-16 {
    description
     "IPv4-specific objects were deprecated, including
      tunnelIfLocalAddress, tunnelIfRemoteAddress, the
      tunnelConfigTable, and the tunnelMIBBasicGroup.
      
      Added IP version-agnostic objects that should be used
      instead, including tunnelIfAddressType,
      tunnelIfLocalInetAddress, tunnelIfRemoteInetAddress,
      the tunnelInetConfigTable, and the
      tunnelIMIBInetGroup.
      
      The new tunnelIfLocalInetAddress and
      tunnelIfRemoteInetAddress objects are read-write,
      rather than read-only.
      
      Updated DESCRIPTION clauses of existing version-
      agnostic objects (e.g., tunnelIfTOS) that contained
      IPv4-specific text to cover IPv6 as well.
      
      Added tunnelIfFlowLabel for tunnels over IPv6.
      
      The encapsulation method was previously an INTEGER
      type, and is now an IANA-maintained textual
      convention.
      
      Published as RFC 4087.";
  }

  revision 1999-08-24 {
    description
     "Initial version, published as RFC 2667.";
  }


  container TUNNEL-MIB {
    config false;

    container tunnelIfTable {
      description
       "The (conceptual) table containing information on
        configured tunnels.";
      smiv2:oid "1.3.6.1.2.1.10.131.1.1.1";

      list tunnelIfEntry {
        key "ifIndex";
        description
         "An entry (conceptual row) containing the information
          on a particular configured tunnel.";
        smiv2:oid "1.3.6.1.2.1.10.131.1.1.1.1";

        leaf ifIndex {
          type leafref {
            path "/if-mib:IF-MIB/if-mib:ifTable/if-mib:ifEntry/if-mib:ifIndex";
          }
        }

        leaf tunnelIfLocalAddress {
          type inet:ipv4-address;
          status deprecated;
          description
           "The address of the local endpoint of the tunnel
            (i.e., the source address used in the outer IP
            header), or 0.0.0.0 if unknown or if the tunnel is
            over IPv6.
            
            Since this object does not support IPv6, it is
            deprecated in favor of tunnelIfLocalInetAddress.";
          smiv2:max-access "read-only";
          smiv2:oid "1.3.6.1.2.1.10.131.1.1.1.1.1";
        }

        leaf tunnelIfRemoteAddress {
          type inet:ipv4-address;
          status deprecated;
          description
           "The address of the remote endpoint of the tunnel
            (i.e., the destination address used in the outer IP
            header), or 0.0.0.0 if unknown, or an IPv6 address, or
            
            the tunnel is not a point-to-point link (e.g., if it
            is a 6to4 tunnel).
            
            Since this object does not support IPv6, it is
            deprecated in favor of tunnelIfRemoteInetAddress.";
          smiv2:max-access "read-only";
          smiv2:oid "1.3.6.1.2.1.10.131.1.1.1.1.2";
        }

        leaf tunnelIfEncapsMethod {
          type ianaiftype-mib:IANAtunnelType;
          description
           "The encapsulation method used by the tunnel.";
          smiv2:max-access "read-only";
          smiv2:oid "1.3.6.1.2.1.10.131.1.1.1.1.3";
        }

        leaf tunnelIfHopLimit {
          type int32 {
            range "0..255";
          }
          description
           "The IPv4 TTL or IPv6 Hop Limit to use in the outer IP
            header.  A value of 0 indicates that the value is
            copied from the payload's header.";
          smiv2:max-access "read-write";
          smiv2:oid "1.3.6.1.2.1.10.131.1.1.1.1.4";
        }

        leaf tunnelIfSecurity {
          type enumeration {
            enum "none" {
              value "1";
            }
            enum "ipsec" {
              value "2";
            }
            enum "other" {
              value "3";
            }
          }
          description
           "The method used by the tunnel to secure the outer IP
            header.  The value ipsec indicates that IPsec is used
            between the tunnel endpoints for authentication or
            encryption or both.  More specific security-related
            information may be available in a MIB module for the
            security protocol in use.";
          smiv2:max-access "read-only";
          smiv2:oid "1.3.6.1.2.1.10.131.1.1.1.1.5";
        }

        leaf tunnelIfTOS {
          type int32 {
            range "-2..63";
          }
          description
           "The method used to set the high 6 bits (the
            
            differentiated services codepoint) of the IPv4 TOS or
            IPv6 Traffic Class in the outer IP header.  A value of
            -1 indicates that the bits are copied from the
            payload's header.  A value of -2 indicates that a
            traffic conditioner is invoked and more information
            may be available in a traffic conditioner MIB module.
            A value between 0 and 63 inclusive indicates that the
            bit field is set to the indicated value.
            
            Note: instead of the name tunnelIfTOS, a better name
            would have been tunnelIfDSCPMethod, but the existing
            name appeared in RFC 2667 and existing objects cannot
            be renamed.";
          smiv2:max-access "read-write";
          smiv2:oid "1.3.6.1.2.1.10.131.1.1.1.1.6";
        }

        leaf tunnelIfFlowLabel {
          type int32 {
            range "-1..100";
          }
          description
           "The method used to set the IPv6 Flow Label value.
            This object need not be present in rows where
            tunnelIfAddressType indicates the tunnel is not over
            IPv6.  A value of -1 indicates that a traffic
            conditioner is invoked and more information may be
            available in a traffic conditioner MIB.  Any other
            value indicates that the Flow Label field is set to
            the indicated value.";
          smiv2:max-access "read-write";
          smiv2:oid "1.3.6.1.2.1.10.131.1.1.1.1.7";
        }

        leaf tunnelIfAddressType {
          type inet-address:InetAddressType;
          description
           "The type of address in the corresponding
            tunnelIfLocalInetAddress and tunnelIfRemoteInetAddress
            objects.";
          smiv2:max-access "read-write";
          smiv2:oid "1.3.6.1.2.1.10.131.1.1.1.1.8";
        }

        leaf tunnelIfLocalInetAddress {
          type inet-address:InetAddress;
          description
           "The address of the local endpoint of the tunnel
            (i.e., the source address used in the outer IP
            header).  If the address is unknown, the value is
            
            0.0.0.0 for IPv4 or :: for IPv6.  The type of this
            object is given by tunnelIfAddressType.";
          smiv2:max-access "read-write";
          smiv2:oid "1.3.6.1.2.1.10.131.1.1.1.1.9";
        }

        leaf tunnelIfRemoteInetAddress {
          type inet-address:InetAddress;
          description
           "The address of the remote endpoint of the tunnel
            (i.e., the destination address used in the outer IP
            header).  If the address is unknown or the tunnel is
            not a point-to-point link (e.g., if it is a 6to4
            tunnel), the value is 0.0.0.0 for tunnels over IPv4 or
            :: for tunnels over IPv6.  The type of this object is
            given by tunnelIfAddressType.";
          smiv2:max-access "read-write";
          smiv2:oid "1.3.6.1.2.1.10.131.1.1.1.1.10";
        }

        leaf tunnelIfEncapsLimit {
          type int32 {
            range "-1..255";
          }
          description
           "The maximum number of additional encapsulations
            permitted for packets undergoing encapsulation at this
            node.  A value of -1 indicates that no limit is
            present (except as a result of the packet size).";
          reference
           "RFC 2473, section 4.1.1";
          smiv2:max-access "read-write";
          smiv2:oid "1.3.6.1.2.1.10.131.1.1.1.1.11";
        }
      }
    }

    container tunnelConfigTable {
      status deprecated;
      description
       "The (conceptual) table containing information on
        configured tunnels.  This table can be used to map a
        set of tunnel endpoints to the associated ifIndex
        value.  It can also be used for row creation.  Note
        that every row in the tunnelIfTable with a fixed IPv4
        destination address should have a corresponding row in
        the tunnelConfigTable, regardless of whether it was
        created via SNMP.
        
        Since this table does not support IPv6, it is
        deprecated in favor of tunnelInetConfigTable.";
      smiv2:oid "1.3.6.1.2.1.10.131.1.1.2";

      list tunnelConfigEntry {
        key "tunnelConfigLocalAddress tunnelConfigRemoteAddress tunnelConfigEncapsMethod tunnelConfigID";
        status deprecated;
        description
         "An entry (conceptual row) containing the information
          on a particular configured tunnel.
          
          Since this entry does not support IPv6, it is
          deprecated in favor of tunnelInetConfigEntry.";
        smiv2:oid "1.3.6.1.2.1.10.131.1.1.2.1";

        leaf tunnelConfigLocalAddress {
          type inet:ipv4-address;
          status deprecated;
          description
           "The address of the local endpoint of the tunnel, or
            0.0.0.0 if the device is free to choose any of its
            addresses at tunnel establishment time.
            
            Since this object does not support IPv6, it is
            deprecated in favor of tunnelInetConfigLocalAddress.";
          smiv2:max-access "not-accessible";
          smiv2:oid "1.3.6.1.2.1.10.131.1.1.2.1.1";
        }

        leaf tunnelConfigRemoteAddress {
          type inet:ipv4-address;
          status deprecated;
          description
           "The address of the remote endpoint of the tunnel.
            
            Since this object does not support IPv6, it is
            deprecated in favor of tunnelInetConfigRemoteAddress.";
          smiv2:max-access "not-accessible";
          smiv2:oid "1.3.6.1.2.1.10.131.1.1.2.1.2";
        }

        leaf tunnelConfigEncapsMethod {
          type ianaiftype-mib:IANAtunnelType;
          status deprecated;
          description
           "The encapsulation method used by the tunnel.
            
            Since this object does not support IPv6, it is
            deprecated in favor of tunnelInetConfigEncapsMethod.";
          smiv2:max-access "not-accessible";
          smiv2:oid "1.3.6.1.2.1.10.131.1.1.2.1.3";
        }

        leaf tunnelConfigID {
          type int32 {
            range "1..2147483647";
          }
          status deprecated;
          description
           "An identifier used to distinguish between multiple
            tunnels of the same encapsulation method, with the
            same endpoints.  If the encapsulation protocol only
            allows one tunnel per set of endpoint addresses (such
            as for GRE or IP-in-IP), the value of this object is
            1.  For encapsulation methods (such as L2F) which
            allow multiple parallel tunnels, the manager is
            responsible for choosing any ID which does not
            conflict with an existing row, such as choosing a
            random number.
            
            Since this object does not support IPv6, it is
            deprecated in favor of tunnelInetConfigID.";
          smiv2:max-access "not-accessible";
          smiv2:oid "1.3.6.1.2.1.10.131.1.1.2.1.4";
        }

        leaf tunnelConfigIfIndex {
          type if-mib:InterfaceIndexOrZero;
          status deprecated;
          description
           "If the value of tunnelConfigStatus for this row is
            active, then this object contains the value of ifIndex
            corresponding to the tunnel interface.  A value of 0
            is not legal in the active state, and means that the
            interface index has not yet been assigned.
            
            Since this object does not support IPv6, it is
            deprecated in favor of tunnelInetConfigIfIndex.";
          smiv2:max-access "read-only";
          smiv2:oid "1.3.6.1.2.1.10.131.1.1.2.1.5";
        }

        leaf tunnelConfigStatus {
          type snmpv2-tc:RowStatus;
          status deprecated;
          description
           "The status of this row, by which new entries may be
            created, or old entries deleted from this table.  The
            agent need not support setting this object to
            createAndWait or notInService since there are no other
            writable objects in this table, and writable objects
            in rows of corresponding tables such as the
            tunnelIfTable may be modified while this row is
            active.
            
            To create a row in this table for an encapsulation
            method which does not support multiple parallel
            tunnels with the same endpoints, the management
            station should simply use a tunnelConfigID of 1, and
            set tunnelConfigStatus to createAndGo.  For
            encapsulation methods such as L2F which allow multiple
            parallel tunnels, the management station may select a
            pseudo-random number to use as the tunnelConfigID and
            set tunnelConfigStatus to createAndGo.  In the event
            that this ID is already in use and an
            inconsistentValue is returned in response to the set
            operation, the management station should simply select
            a new pseudo-random number and retry the operation.
            
            Creating a row in this table will cause an interface
            index to be assigned by the agent in an
            implementation-dependent manner, and corresponding
            rows will be instantiated in the ifTable and the
            tunnelIfTable.  The status of this row will become
            active as soon as the agent assigns the interface
            index, regardless of whether the interface is
            operationally up.
            
            Deleting a row in this table will likewise delete the
            corresponding row in the ifTable and in the
            tunnelIfTable.
            
            Since this object does not support IPv6, it is
            deprecated in favor of tunnelInetConfigStatus.";
          smiv2:max-access "read-write";
          smiv2:oid "1.3.6.1.2.1.10.131.1.1.2.1.6";
        }
      }
    }

    container tunnelInetConfigTable {
      description
       "The (conceptual) table containing information on
        configured tunnels.  This table can be used to map a
        set of tunnel endpoints to the associated ifIndex
        value.  It can also be used for row creation.  Note
        that every row in the tunnelIfTable with a fixed
        destination address should have a corresponding row in
        the tunnelInetConfigTable, regardless of whether it
        was created via SNMP.";
      smiv2:oid "1.3.6.1.2.1.10.131.1.1.3";

      list tunnelInetConfigEntry {
        key "tunnelInetConfigAddressType tunnelInetConfigLocalAddress tunnelInetConfigRemoteAddress tunnelInetConfigEncapsMethod tunnelInetConfigID";
        description
         "An entry (conceptual row) containing the information
          on a particular configured tunnel.  Note that there is
          a 128 subid maximum for object OIDs.  Implementers
          need to be aware that if the total number of octets in
          tunnelInetConfigLocalAddress and
          tunnelInetConfigRemoteAddress exceeds 110 then OIDs of
          column instances in this table will have more than 128
          sub-identifiers and cannot be accessed using SNMPv1,
          SNMPv2c, or SNMPv3.  In practice this is not expected
          to be a problem since IPv4 and IPv6 addresses will not
          cause the limit to be reached, but if other types are
          supported by an agent, care must be taken to ensure
          that the sum of the lengths do not cause the limit to
          be exceeded.";
        smiv2:oid "1.3.6.1.2.1.10.131.1.1.3.1";

        leaf tunnelInetConfigAddressType {
          type inet-address:InetAddressType;
          description
           "The address type over which the tunnel encapsulates
            packets.";
          smiv2:max-access "not-accessible";
          smiv2:oid "1.3.6.1.2.1.10.131.1.1.3.1.1";
        }

        leaf tunnelInetConfigLocalAddress {
          type inet-address:InetAddress;
          description
           "The address of the local endpoint of the tunnel, or
            0.0.0.0 (for IPv4) or :: (for IPv6) if the device is
            free to choose any of its addresses at tunnel
            establishment time.";
          smiv2:max-access "not-accessible";
          smiv2:oid "1.3.6.1.2.1.10.131.1.1.3.1.2";
        }

        leaf tunnelInetConfigRemoteAddress {
          type inet-address:InetAddress;
          description
           "The address of the remote endpoint of the tunnel.";
          smiv2:max-access "not-accessible";
          smiv2:oid "1.3.6.1.2.1.10.131.1.1.3.1.3";
        }

        leaf tunnelInetConfigEncapsMethod {
          type ianaiftype-mib:IANAtunnelType;
          description
           "The encapsulation method used by the tunnel.";
          smiv2:max-access "not-accessible";
          smiv2:oid "1.3.6.1.2.1.10.131.1.1.3.1.4";
        }

        leaf tunnelInetConfigID {
          type int32 {
            range "1..2147483647";
          }
          description
           "An identifier used to distinguish between multiple
            tunnels of the same encapsulation method, with the
            same endpoints.  If the encapsulation protocol only
            allows one tunnel per set of endpoint addresses (such
            as for GRE or IP-in-IP), the value of this object is
            1.  For encapsulation methods (such as L2F) which
            allow multiple parallel tunnels, the manager is
            responsible for choosing any ID which does not
            
            conflict with an existing row, such as choosing a
            random number.";
          smiv2:max-access "not-accessible";
          smiv2:oid "1.3.6.1.2.1.10.131.1.1.3.1.5";
        }

        leaf tunnelInetConfigIfIndex {
          type if-mib:InterfaceIndexOrZero;
          description
           "If the value of tunnelInetConfigStatus for this row
            is active, then this object contains the value of
            ifIndex corresponding to the tunnel interface.  A
            value of 0 is not legal in the active state, and means
            that the interface index has not yet been assigned.";
          smiv2:max-access "read-only";
          smiv2:oid "1.3.6.1.2.1.10.131.1.1.3.1.6";
        }

        leaf tunnelInetConfigStatus {
          type snmpv2-tc:RowStatus;
          description
           "The status of this row, by which new entries may be
            created, or old entries deleted from this table.  The
            agent need not support setting this object to
            createAndWait or notInService since there are no other
            writable objects in this table, and writable objects
            in rows of corresponding tables such as the
            tunnelIfTable may be modified while this row is
            active.
            
            To create a row in this table for an encapsulation
            method which does not support multiple parallel
            tunnels with the same endpoints, the management
            station should simply use a tunnelInetConfigID of 1,
            and set tunnelInetConfigStatus to createAndGo.  For
            encapsulation methods such as L2F which allow multiple
            parallel tunnels, the management station may select a
            pseudo-random number to use as the tunnelInetConfigID
            and set tunnelInetConfigStatus to createAndGo.  In the
            event that this ID is already in use and an
            inconsistentValue is returned in response to the set
            operation, the management station should simply select
            a new pseudo-random number and retry the operation.
            
            Creating a row in this table will cause an interface
            index to be assigned by the agent in an
            implementation-dependent manner, and corresponding
            rows will be instantiated in the ifTable and the
            
            tunnelIfTable.  The status of this row will become
            active as soon as the agent assigns the interface
            index, regardless of whether the interface is
            operationally up.
            
            Deleting a row in this table will likewise delete the
            corresponding row in the ifTable and in the
            tunnelIfTable.";
          smiv2:max-access "read-write";
          smiv2:oid "1.3.6.1.2.1.10.131.1.1.3.1.7";
        }

        leaf tunnelInetConfigStorageType {
          type snmpv2-tc:StorageType;
          description
           "The storage type of this row.  If the row is
            permanent(4), no objects in the row need be writable.";
          smiv2:max-access "read-write";
          smiv2:oid "1.3.6.1.2.1.10.131.1.1.3.1.8";
        }
      }
    }
  }

  smiv2:alias "tunnelMIB" {
    smiv2:oid "1.3.6.1.2.1.10.131";
  }

  smiv2:alias "tunnelMIBObjects" {
    smiv2:oid "1.3.6.1.2.1.10.131.1";
  }

  smiv2:alias "tunnel" {
    smiv2:oid "1.3.6.1.2.1.10.131.1.1";
  }

  smiv2:alias "tunnelMIBConformance" {
    smiv2:oid "1.3.6.1.2.1.10.131.2";
  }

  smiv2:alias "tunnelMIBCompliances" {
    smiv2:oid "1.3.6.1.2.1.10.131.2.1";
  }

  smiv2:alias "tunnelMIBGroups" {
    smiv2:oid "1.3.6.1.2.1.10.131.2.2";
  }

}
