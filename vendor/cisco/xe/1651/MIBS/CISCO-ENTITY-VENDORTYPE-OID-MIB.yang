/*
 * Generated by confdc --mib2yang-std
 * Source: mgmt/dmi/model/common/mib-source/CISCO-ENTITY-VENDORTYPE-OID-MIB.mib
 */
/*
 * This YANG module has been generated by smidump 0.5.0:
 *
 *      smidump -f yang CISCO-ENTITY-VENDORTYPE-OID-MIB
 *
 * Do not edit. Edit the source file instead!
 */

module CISCO-ENTITY-VENDORTYPE-OID-MIB {

  namespace "urn:ietf:params:xml:ns:yang:smiv2:CISCO-ENTITY-VENDORTYPE-OID-MIB";
  prefix CISCO-ENTITY-VENDORTYPE-OID-MIB;

  import ietf-yang-smiv2 {
    prefix "smiv2";
  }

  organization
   "Cisco Systems, Inc.";

  contact
   "       Cisco Systems
    Customer Service
    
    Postal: 170 W Tasman Drive
    San Jose, CA  95134
    USA
    
    Tel: +1 800 553-NETS
    
    E-mail: cs-snmp@cisco.com";

  description
   "This module defines the object identifiers that are
    assigned to various components on cisco products,
    which are used by the entPhysicalTable of the ENTITY-MIB
    to uniquely identify the type of each physical entry.";

  revision 2014-12-09 {
    description
     "Added following OIDs:
      cevChassisME6340ACA, cevChassisME6340DCA,
      cevChassisME6340DCB, cevChassisCat296024TT,
      cevChassisCat296048TT, cevContainerFabric13Slot,
      cevPowerSupply6340PWRDC, cevPowerSupply6340PWRAC,
      cevFanTrayUbr10012, cevPowerSupplyUbr10012AC,
      cevPowerSupplyUbr10012DC, cevVwic2T1E1Ran,
      cevModuleCat296024TT,cevModuleCat296048TT
      cevCat6kMsfc2a, cevCat6kWs6340Sup,
      cevCat6kWs6340LcA, cevCat6kWs6340LcB,
      cevPortAdslAnnexA, cevPortAdslAnnexB";
  }

  revision 2005-04-28 {
    description
     "Added following OIDs:
      cevUbrTccPlus";
  }

  revision 2005-04-18 {
    description
     "Added following OIDs:
      cevChassisCat6kMsfc2a, cevChassisCe611K9
      cevContainer9513RearFanBay, cevNme16Es1GeNoPwr,
      cevNmeX24Es1GeNoPwr, cevNmeXd24Es2StNoPwr,
      cevNmeXd48Es2GeNoPwr, cevCpuCat6kMsfc2a,
      cevGsrCsc12404B, cevGsrCsc12406B,
      cevGsrCsc12410B, cevGsrCsc12416B,
      cevONS1553010G4ChASp, cevONS1553010G4ChBSp,
      cevONS1553010G4ChCSp, cevONS1553010G4ChDSp,
      cevONS1553010G4ChESp, cevONS1553010G4ChFSp,
      cevONS1553010G4ChGSp, cevONS1553010G4ChHSp,
      cevONS1553010G4ChA, cevONS1553010G4ChB,
      cevONS1553010G4ChC, cevONS1553010G4ChD,
      cevONS1553010G4ChE, cevONS1553010G4ChF,
      cevONS1553010G4ChG, cevONS1553010G4ChH,
      cevONS1553010G32ChSp, cevONS1553010G32Ch,
      cevSFPOc3smsr, cevSFPOc12smsr, cevSFPOc48mm.";
  }

  revision 2002-04-05 {
    description
     "CANA Assignments.";
  }

  revision 1997-08-05 {
    description
     "Miscellaneous updates.";
  }

  smiv2:alias "ciscoEntityVendortypeOIDMIB" {
    smiv2:oid "1.3.6.1.4.1.9.12.3";
  }

  smiv2:alias "cevMIBObjects" {
    smiv2:oid "1.3.6.1.4.1.9.12.3.1";
  }

  smiv2:alias "cevOther" {
    smiv2:oid "1.3.6.1.4.1.9.12.3.1.1";
  }

  smiv2:alias "cevOtherUnknownCard" {
    smiv2:oid "1.3.6.1.4.1.9.12.3.1.1.1";
  }

  smiv2:alias "cevOtherMoH" {
    smiv2:oid "1.3.6.1.4.1.9.12.3.1.1.2";
  }

  smiv2:alias "cevNmeApaLink" {
    smiv2:oid "1.3.6.1.4.1.9.12.3.1.1.3";
  }

  smiv2:alias "cevOtherSce8000Scm" {
    smiv2:oid "1.3.6.1.4.1.9.12.3.1.1.5";
  }

  smiv2:alias "cevOtherSce8000Sip" {
    smiv2:oid "1.3.6.1.4.1.9.12.3.1.1.6";
  }

  smiv2:alias "cevOtherCscLink" {
    smiv2:oid "1.3.6.1.4.1.9.12.3.1.1.8";
  }

  smiv2:alias "cevOtherPHY" {
    smiv2:oid "1.3.6.1.4.1.9.12.3.1.1.9";
  }

  smiv2:alias "cevUnknown" {
    smiv2:oid "1.3.6.1.4.1.9.12.3.1.2";
  }

  smiv2:alias "cevChassis" {
    smiv2:oid "1.3.6.1.4.1.9.12.3.1.3";
  }

  smiv2:alias "cevChassisUnknown" {
    smiv2:oid "1.3.6.1.4.1.9.12.3.1.3.1";
  }

  smiv2:alias "cevChassis2000" {
    smiv2:oid "1.3.6.1.4.1.9.12.3.1.3.2";
  }

  smiv2:alias "cevChassis2500" {
    smiv2:oid "1.3.6.1.4.1.9.12.3.1.3.3";
  }

  smiv2:alias "cevChassis2501" {
    smiv2:oid "1.3.6.1.4.1.9.12.3.1.3.4";
  }

  smiv2:alias "cevChassis2502" {
    smiv2:oid "1.3.6.1.4.1.9.12.3.1.3.5";
  }

  smiv2:alias "cevChassis2503" {
    smiv2:oid "1.3.6.1.4.1.9.12.3.1.3.6";
  }

  smiv2:alias "cevChassis2504" {
    smiv2:oid "1.3.6.1.4.1.9.12.3.1.3.7";
  }

  smiv2:alias "cevChassis2505" {
    smiv2:oid "1.3.6.1.4.1.9.12.3.1.3.8";
  }

  smiv2:alias "cevChassis2506" {
    smiv2:oid "1.3.6.1.4.1.9.12.3.1.3.9";
  }

  smiv2:alias "cevChassis2507" {
    smiv2:oid "1.3.6.1.4.1.9.12.3.1.3.10";
  }

  smiv2:alias "cevChassis2508" {
    smiv2:oid "1.3.6.1.4.1.9.12.3.1.3.11";
  }

  smiv2:alias "cevChassis2509" {
    smiv2:oid "1.3.6.1.4.1.9.12.3.1.3.12";
  }

  smiv2:alias "cevChassis2510" {
    smiv2:oid "1.3.6.1.4.1.9.12.3.1.3.13";
  }

  smiv2:alias "cevChassis2511" {
    smiv2:oid "1.3.6.1.4.1.9.12.3.1.3.14";
  }

  smiv2:alias "cevChassis2512" {
    smiv2:oid "1.3.6.1.4.1.9.12.3.1.3.15";
  }

  smiv2:alias "cevChassis2513" {
    smiv2:oid "1.3.6.1.4.1.9.12.3.1.3.16";
  }

  smiv2:alias "cevChassis2514" {
    smiv2:oid "1.3.6.1.4.1.9.12.3.1.3.17";
  }

  smiv2:alias "cevChassis2515" {
    smiv2:oid "1.3.6.1.4.1.9.12.3.1.3.18";
  }

  smiv2:alias "cevChassis2516" {
    smiv2:oid "1.3.6.1.4.1.9.12.3.1.3.19";
  }

  smiv2:alias "cevChassis2517" {
    smiv2:oid "1.3.6.1.4.1.9.12.3.1.3.20";
  }

  smiv2:alias "cevChassis2518" {
    smiv2:oid "1.3.6.1.4.1.9.12.3.1.3.21";
  }

  smiv2:alias "cevChassis2519" {
    smiv2:oid "1.3.6.1.4.1.9.12.3.1.3.22";
  }

  smiv2:alias "cevChassis2520" {
    smiv2:oid "1.3.6.1.4.1.9.12.3.1.3.23";
  }

  smiv2:alias "cevChassis2521" {
    smiv2:oid "1.3.6.1.4.1.9.12.3.1.3.24";
  }

  smiv2:alias "cevChassis2522" {
    smiv2:oid "1.3.6.1.4.1.9.12.3.1.3.25";
  }

  smiv2:alias "cevChassis2523" {
    smiv2:oid "1.3.6.1.4.1.9.12.3.1.3.26";
  }

  smiv2:alias "cevChassis2524" {
    smiv2:oid "1.3.6.1.4.1.9.12.3.1.3.27";
  }

  smiv2:alias "cevChassis2525" {
    smiv2:oid "1.3.6.1.4.1.9.12.3.1.3.28";
  }

  smiv2:alias "cevChassis3000" {
    smiv2:oid "1.3.6.1.4.1.9.12.3.1.3.29";
  }

  smiv2:alias "cevChassis3104" {
    smiv2:oid "1.3.6.1.4.1.9.12.3.1.3.30";
  }

  smiv2:alias "cevChassis3204" {
    smiv2:oid "1.3.6.1.4.1.9.12.3.1.3.31";
  }

  smiv2:alias "cevChassisIGS" {
    smiv2:oid "1.3.6.1.4.1.9.12.3.1.3.32";
  }

  smiv2:alias "cevChassis2501LANFRADFX" {
    smiv2:oid "1.3.6.1.4.1.9.12.3.1.3.33";
  }

  smiv2:alias "cevChassis2501FRADFX" {
    smiv2:oid "1.3.6.1.4.1.9.12.3.1.3.34";
  }

  smiv2:alias "cevChassis2502LANFRADFX" {
    smiv2:oid "1.3.6.1.4.1.9.12.3.1.3.35";
  }

  smiv2:alias "cevChassisWSX3011" {
    smiv2:oid "1.3.6.1.4.1.9.12.3.1.3.36";
  }

  smiv2:alias "cevChassisAccessProEC" {
    smiv2:oid "1.3.6.1.4.1.9.12.3.1.3.37";
  }

  smiv2:alias "cevChassisAccessProRC" {
    smiv2:oid "1.3.6.1.4.1.9.12.3.1.3.38";
  }

  smiv2:alias "cevChassisWSX5301" {
    smiv2:oid "1.3.6.1.4.1.9.12.3.1.3.39";
  }

  smiv2:alias "cevChassisAS2509RJ" {
    smiv2:oid "1.3.6.1.4.1.9.12.3.1.3.40";
  }

  smiv2:alias "cevChassisAS2511RJ" {
    smiv2:oid "1.3.6.1.4.1.9.12.3.1.3.41";
  }

  smiv2:alias "cevChassis3800" {
    smiv2:oid "1.3.6.1.4.1.9.12.3.1.3.42";
  }

  smiv2:alias "cevChassis3620" {
    smiv2:oid "1.3.6.1.4.1.9.12.3.1.3.43";
  }

  smiv2:alias "cevChassis3640" {
    smiv2:oid "1.3.6.1.4.1.9.12.3.1.3.44";
  }

  smiv2:alias "cevChassis7204" {
    smiv2:oid "1.3.6.1.4.1.9.12.3.1.3.45";
  }

  smiv2:alias "cevChassis7206" {
    smiv2:oid "1.3.6.1.4.1.9.12.3.1.3.46";
  }

  smiv2:alias "cevChassisAS5300" {
    smiv2:oid "1.3.6.1.4.1.9.12.3.1.3.47";
  }

  smiv2:alias "cevChassisAs5800RS" {
    smiv2:oid "1.3.6.1.4.1.9.12.3.1.3.49";
  }

  smiv2:alias "cevChassisAs5800DS" {
    smiv2:oid "1.3.6.1.4.1.9.12.3.1.3.50";
  }

  smiv2:alias "cevChassis7202" {
    smiv2:oid "1.3.6.1.4.1.9.12.3.1.3.51";
  }

  smiv2:alias "cevChassisRpm" {
    smiv2:oid "1.3.6.1.4.1.9.12.3.1.3.52";
  }

  smiv2:alias "cevChassis1710" {
    smiv2:oid "1.3.6.1.4.1.9.12.3.1.3.53";
  }

  smiv2:alias "cevChassis1720" {
    smiv2:oid "1.3.6.1.4.1.9.12.3.1.3.54";
  }

  smiv2:alias "cevChassisCat8540Msr" {
    smiv2:oid "1.3.6.1.4.1.9.12.3.1.3.55";
  }

  smiv2:alias "cevChassisCat8540Csr" {
    smiv2:oid "1.3.6.1.4.1.9.12.3.1.3.56";
  }

  smiv2:alias "cevChassisUbr7246" {
    smiv2:oid "1.3.6.1.4.1.9.12.3.1.3.57";
  }

  smiv2:alias "cevChassis7576" {
    smiv2:oid "1.3.6.1.4.1.9.12.3.1.3.58";
  }

  smiv2:alias "cevChassis3660" {
    smiv2:oid "1.3.6.1.4.1.9.12.3.1.3.59";
  }

  smiv2:alias "cevChassis1401" {
    smiv2:oid "1.3.6.1.4.1.9.12.3.1.3.60";
  }

  smiv2:alias "cevChassis2613" {
    smiv2:oid "1.3.6.1.4.1.9.12.3.1.3.61";
  }

  smiv2:alias "cevChassis2610" {
    smiv2:oid "1.3.6.1.4.1.9.12.3.1.3.62";
  }

  smiv2:alias "cevChassis2612" {
    smiv2:oid "1.3.6.1.4.1.9.12.3.1.3.63";
  }

  smiv2:alias "cevChassis2611" {
    smiv2:oid "1.3.6.1.4.1.9.12.3.1.3.64";
  }

  smiv2:alias "cevChassis2620" {
    smiv2:oid "1.3.6.1.4.1.9.12.3.1.3.65";
  }

  smiv2:alias "cevChassis2621" {
    smiv2:oid "1.3.6.1.4.1.9.12.3.1.3.66";
  }

  smiv2:alias "cevChassisCat8510Csr" {
    smiv2:oid "1.3.6.1.4.1.9.12.3.1.3.67";
  }

  smiv2:alias "cevChassisUbr7223" {
    smiv2:oid "1.3.6.1.4.1.9.12.3.1.3.68";
  }

  smiv2:alias "cevChassis6400Nrp" {
    smiv2:oid "1.3.6.1.4.1.9.12.3.1.3.69";
  }

  smiv2:alias "cevChassis801" {
    smiv2:oid "1.3.6.1.4.1.9.12.3.1.3.70";
  }

  smiv2:alias "cevChassis802" {
    smiv2:oid "1.3.6.1.4.1.9.12.3.1.3.71";
  }

  smiv2:alias "cevChassis803" {
    smiv2:oid "1.3.6.1.4.1.9.12.3.1.3.72";
  }

  smiv2:alias "cevChassis804" {
    smiv2:oid "1.3.6.1.4.1.9.12.3.1.3.73";
  }

  smiv2:alias "cevChassis7206Vxr" {
    smiv2:oid "1.3.6.1.4.1.9.12.3.1.3.74";
  }

  smiv2:alias "cevChassis7204Vxr" {
    smiv2:oid "1.3.6.1.4.1.9.12.3.1.3.75";
  }

  smiv2:alias "cevChassis1750" {
    smiv2:oid "1.3.6.1.4.1.9.12.3.1.3.76";
  }

  smiv2:alias "cevChassisCat2924XLv" {
    smiv2:oid "1.3.6.1.4.1.9.12.3.1.3.77";
  }

  smiv2:alias "cevChassisCat2924CXLv" {
    smiv2:oid "1.3.6.1.4.1.9.12.3.1.3.78";
  }

  smiv2:alias "cevChassisCat2912XL" {
    smiv2:oid "1.3.6.1.4.1.9.12.3.1.3.79";
  }

  smiv2:alias "cevChassisCat2924MXL" {
    smiv2:oid "1.3.6.1.4.1.9.12.3.1.3.80";
  }

  smiv2:alias "cevChassisCat2912MfXL" {
    smiv2:oid "1.3.6.1.4.1.9.12.3.1.3.81";
  }

  smiv2:alias "cevChassis1538M" {
    smiv2:oid "1.3.6.1.4.1.9.12.3.1.3.82";
  }

  smiv2:alias "cevChassis1548M" {
    smiv2:oid "1.3.6.1.4.1.9.12.3.1.3.83";
  }

  smiv2:alias "cevChassisFasthub100" {
    smiv2:oid "1.3.6.1.4.1.9.12.3.1.3.84";
  }

  smiv2:alias "cevChassisPIXFirewall" {
    smiv2:oid "1.3.6.1.4.1.9.12.3.1.3.85";
  }

  smiv2:alias "cevChassisMGX8850" {
    smiv2:oid "1.3.6.1.4.1.9.12.3.1.3.86";
  }

  smiv2:alias "cevChassisMGX8820" {
    smiv2:oid "1.3.6.1.4.1.9.12.3.1.3.87";
  }

  smiv2:alias "cevChassisCat8510Msr" {
    smiv2:oid "1.3.6.1.4.1.9.12.3.1.3.88";
  }

  smiv2:alias "cevChassisCat8515Msr" {
    smiv2:oid "1.3.6.1.4.1.9.12.3.1.3.89";
  }

  smiv2:alias "cevChassisIGX8410" {
    smiv2:oid "1.3.6.1.4.1.9.12.3.1.3.90";
  }

  smiv2:alias "cevChassisIGX8420" {
    smiv2:oid "1.3.6.1.4.1.9.12.3.1.3.91";
  }

  smiv2:alias "cevChassisIGX8430" {
    smiv2:oid "1.3.6.1.4.1.9.12.3.1.3.92";
  }

  smiv2:alias "cevChassisIGX8450" {
    smiv2:oid "1.3.6.1.4.1.9.12.3.1.3.93";
  }

  smiv2:alias "cevChassisBPX8620" {
    smiv2:oid "1.3.6.1.4.1.9.12.3.1.3.95";
  }

  smiv2:alias "cevChassisBPX8650" {
    smiv2:oid "1.3.6.1.4.1.9.12.3.1.3.96";
  }

  smiv2:alias "cevChassisBPX8680" {
    smiv2:oid "1.3.6.1.4.1.9.12.3.1.3.97";
  }

  smiv2:alias "cevChassisCacheEngine" {
    smiv2:oid "1.3.6.1.4.1.9.12.3.1.3.98";
  }

  smiv2:alias "cevChassisCat6000" {
    smiv2:oid "1.3.6.1.4.1.9.12.3.1.3.99";
  }

  smiv2:alias "cevChassisMC3810" {
    smiv2:oid "1.3.6.1.4.1.9.12.3.1.3.100";
  }

  smiv2:alias "cevChassisIGXSes" {
    smiv2:oid "1.3.6.1.4.1.9.12.3.1.3.102";
  }

  smiv2:alias "cevChassisLocalDirector" {
    smiv2:oid "1.3.6.1.4.1.9.12.3.1.3.103";
  }

  smiv2:alias "cevChassis805" {
    smiv2:oid "1.3.6.1.4.1.9.12.3.1.3.104";
  }

  smiv2:alias "cevChassisCat3508GXL" {
    smiv2:oid "1.3.6.1.4.1.9.12.3.1.3.105";
  }

  smiv2:alias "cevChassisCat3512XL" {
    smiv2:oid "1.3.6.1.4.1.9.12.3.1.3.106";
  }

  smiv2:alias "cevChassisCat3524XL" {
    smiv2:oid "1.3.6.1.4.1.9.12.3.1.3.107";
  }

  smiv2:alias "cevChassisCat2908XL" {
    smiv2:oid "1.3.6.1.4.1.9.12.3.1.3.108";
  }

  smiv2:alias "cevChassisCat2916MXL" {
    smiv2:oid "1.3.6.1.4.1.9.12.3.1.3.109";
  }

  smiv2:alias "cevChassis1417" {
    smiv2:oid "1.3.6.1.4.1.9.12.3.1.3.111";
  }

  smiv2:alias "cevChassisOpticalRegenerator" {
    smiv2:oid "1.3.6.1.4.1.9.12.3.1.3.112";
  }

  smiv2:alias "cevChassis6100" {
    smiv2:oid "1.3.6.1.4.1.9.12.3.1.3.113";
  }

  smiv2:alias "cevChassis6130" {
    smiv2:oid "1.3.6.1.4.1.9.12.3.1.3.114";
  }

  smiv2:alias "cevChassis6260" {
    smiv2:oid "1.3.6.1.4.1.9.12.3.1.3.115";
  }

  smiv2:alias "cevChassisCat2924XL" {
    smiv2:oid "1.3.6.1.4.1.9.12.3.1.3.116";
  }

  smiv2:alias "cevChassisCat2924CXL" {
    smiv2:oid "1.3.6.1.4.1.9.12.3.1.3.117";
  }

  smiv2:alias "cevChassisUbr924" {
    smiv2:oid "1.3.6.1.4.1.9.12.3.1.3.118";
  }

  smiv2:alias "cevChassisWsX6302Msm" {
    smiv2:oid "1.3.6.1.4.1.9.12.3.1.3.119";
  }

  smiv2:alias "cevChassisCat5kRsfc" {
    smiv2:oid "1.3.6.1.4.1.9.12.3.1.3.120";
  }

  smiv2:alias "cevChassis7120Quadt1" {
    smiv2:oid "1.3.6.1.4.1.9.12.3.1.3.122";
  }

  smiv2:alias "cevChassis7120T3" {
    smiv2:oid "1.3.6.1.4.1.9.12.3.1.3.123";
  }

  smiv2:alias "cevChassis7120E3" {
    smiv2:oid "1.3.6.1.4.1.9.12.3.1.3.124";
  }

  smiv2:alias "cevChassis7120At3" {
    smiv2:oid "1.3.6.1.4.1.9.12.3.1.3.125";
  }

  smiv2:alias "cevChassis7120Ae3" {
    smiv2:oid "1.3.6.1.4.1.9.12.3.1.3.126";
  }

  smiv2:alias "cevChassis7120Smi3" {
    smiv2:oid "1.3.6.1.4.1.9.12.3.1.3.127";
  }

  smiv2:alias "cevChassis7140Dualt3" {
    smiv2:oid "1.3.6.1.4.1.9.12.3.1.3.128";
  }

  smiv2:alias "cevChassis7140Duale3" {
    smiv2:oid "1.3.6.1.4.1.9.12.3.1.3.129";
  }

  smiv2:alias "cevChassis7140Dualat3" {
    smiv2:oid "1.3.6.1.4.1.9.12.3.1.3.130";
  }

  smiv2:alias "cevChassis7140Dualae3" {
    smiv2:oid "1.3.6.1.4.1.9.12.3.1.3.131";
  }

  smiv2:alias "cevChassis7140Dualmm3" {
    smiv2:oid "1.3.6.1.4.1.9.12.3.1.3.132";
  }

  smiv2:alias "cevChassis827QuadV" {
    smiv2:oid "1.3.6.1.4.1.9.12.3.1.3.133";
  }

  smiv2:alias "cevChassisUbr7246Vxr" {
    smiv2:oid "1.3.6.1.4.1.9.12.3.1.3.134";
  }

  smiv2:alias "cevChassis12016" {
    smiv2:oid "1.3.6.1.4.1.9.12.3.1.3.136";
  }

  smiv2:alias "cevChassisAs5400" {
    smiv2:oid "1.3.6.1.4.1.9.12.3.1.3.137";
  }

  smiv2:alias "cevChassis7140Octt1" {
    smiv2:oid "1.3.6.1.4.1.9.12.3.1.3.138";
  }

  smiv2:alias "cevChassis7140Dualfe" {
    smiv2:oid "1.3.6.1.4.1.9.12.3.1.3.139";
  }

  smiv2:alias "cevChassisCat3548XL" {
    smiv2:oid "1.3.6.1.4.1.9.12.3.1.3.140";
  }

  smiv2:alias "cevChassisCat6006" {
    smiv2:oid "1.3.6.1.4.1.9.12.3.1.3.141";
  }

  smiv2:alias "cevChassisCat6009" {
    smiv2:oid "1.3.6.1.4.1.9.12.3.1.3.142";
  }

  smiv2:alias "cevChassisCat6506" {
    smiv2:oid "1.3.6.1.4.1.9.12.3.1.3.143";
  }

  smiv2:alias "cevChassisCat6509" {
    smiv2:oid "1.3.6.1.4.1.9.12.3.1.3.144";
  }

  smiv2:alias "cevChassis827" {
    smiv2:oid "1.3.6.1.4.1.9.12.3.1.3.145";
  }

  smiv2:alias "cevChassisAS5200" {
    smiv2:oid "1.3.6.1.4.1.9.12.3.1.3.146";
  }

  smiv2:alias "cevChassis12008" {
    smiv2:oid "1.3.6.1.4.1.9.12.3.1.3.147";
  }

  smiv2:alias "cevChassis12012" {
    smiv2:oid "1.3.6.1.4.1.9.12.3.1.3.148";
  }

  smiv2:alias "cevChassisMc3810V3" {
    smiv2:oid "1.3.6.1.4.1.9.12.3.1.3.149";
  }

  smiv2:alias "cevChassis7507z" {
    smiv2:oid "1.3.6.1.4.1.9.12.3.1.3.151";
  }

  smiv2:alias "cevChassis7513z" {
    smiv2:oid "1.3.6.1.4.1.9.12.3.1.3.152";
  }

  smiv2:alias "cevChassis7507mx" {
    smiv2:oid "1.3.6.1.4.1.9.12.3.1.3.153";
  }

  smiv2:alias "cevChassis7513mx" {
    smiv2:oid "1.3.6.1.4.1.9.12.3.1.3.154";
  }

  smiv2:alias "cevChassisUbr912C" {
    smiv2:oid "1.3.6.1.4.1.9.12.3.1.3.155";
  }

  smiv2:alias "cevChassisUbr912S" {
    smiv2:oid "1.3.6.1.4.1.9.12.3.1.3.156";
  }

  smiv2:alias "cevChassisUbr914" {
    smiv2:oid "1.3.6.1.4.1.9.12.3.1.3.157";
  }

  smiv2:alias "cevChassis6160" {
    smiv2:oid "1.3.6.1.4.1.9.12.3.1.3.160";
  }

  smiv2:alias "cevChassisCat2948gL3" {
    smiv2:oid "1.3.6.1.4.1.9.12.3.1.3.161";
  }

  smiv2:alias "cevChassisCat4232L3" {
    smiv2:oid "1.3.6.1.4.1.9.12.3.1.3.164";
  }

  smiv2:alias "cevChassisOpticalRegeneratorDCPower" {
    smiv2:oid "1.3.6.1.4.1.9.12.3.1.3.165";
  }

  smiv2:alias "cevChassisCVA122" {
    smiv2:oid "1.3.6.1.4.1.9.12.3.1.3.171";
  }

  smiv2:alias "cevChassisCVA124" {
    smiv2:oid "1.3.6.1.4.1.9.12.3.1.3.172";
  }

  smiv2:alias "cevChassisAs5850" {
    smiv2:oid "1.3.6.1.4.1.9.12.3.1.3.173";
  }

  smiv2:alias "cevChassisMGX8240" {
    smiv2:oid "1.3.6.1.4.1.9.12.3.1.3.176";
  }

  smiv2:alias "cevChassisAs5350" {
    smiv2:oid "1.3.6.1.4.1.9.12.3.1.3.178";
  }

  smiv2:alias "cevChassisMGX8950" {
    smiv2:oid "1.3.6.1.4.1.9.12.3.1.3.181";
  }

  smiv2:alias "cevChassisUbr925" {
    smiv2:oid "1.3.6.1.4.1.9.12.3.1.3.182";
  }

  smiv2:alias "cevChassisUbr10012" {
    smiv2:oid "1.3.6.1.4.1.9.12.3.1.3.183";
  }

  smiv2:alias "cevChassisCat4kGateway" {
    smiv2:oid "1.3.6.1.4.1.9.12.3.1.3.184";
  }

  smiv2:alias "cevChassis120168r" {
    smiv2:oid "1.3.6.1.4.1.9.12.3.1.3.185";
  }

  smiv2:alias "cevChassis2650" {
    smiv2:oid "1.3.6.1.4.1.9.12.3.1.3.186";
  }

  smiv2:alias "cevChassis2651" {
    smiv2:oid "1.3.6.1.4.1.9.12.3.1.3.187";
  }

  smiv2:alias "cevChassis826" {
    smiv2:oid "1.3.6.1.4.1.9.12.3.1.3.189";
  }

  smiv2:alias "cevChassisCat295012" {
    smiv2:oid "1.3.6.1.4.1.9.12.3.1.3.190";
  }

  smiv2:alias "cevChassisCat295024" {
    smiv2:oid "1.3.6.1.4.1.9.12.3.1.3.191";
  }

  smiv2:alias "cevChassis1751" {
    smiv2:oid "1.3.6.1.4.1.9.12.3.1.3.193";
  }

  smiv2:alias "cevChassis1730Iad8Fxs" {
    smiv2:oid "1.3.6.1.4.1.9.12.3.1.3.194";
  }

  smiv2:alias "cevChassis1730Iad16Fxs" {
    smiv2:oid "1.3.6.1.4.1.9.12.3.1.3.195";
  }

  smiv2:alias "cevChassis626" {
    smiv2:oid "1.3.6.1.4.1.9.12.3.1.3.196";
  }

  smiv2:alias "cevChassis627" {
    smiv2:oid "1.3.6.1.4.1.9.12.3.1.3.197";
  }

  smiv2:alias "cevChassis633" {
    smiv2:oid "1.3.6.1.4.1.9.12.3.1.3.198";
  }

  smiv2:alias "cevChassis673" {
    smiv2:oid "1.3.6.1.4.1.9.12.3.1.3.199";
  }

  smiv2:alias "cevChassis675" {
    smiv2:oid "1.3.6.1.4.1.9.12.3.1.3.200";
  }

  smiv2:alias "cevChassis675e" {
    smiv2:oid "1.3.6.1.4.1.9.12.3.1.3.201";
  }

  smiv2:alias "cevChassis676" {
    smiv2:oid "1.3.6.1.4.1.9.12.3.1.3.202";
  }

  smiv2:alias "cevChassis677" {
    smiv2:oid "1.3.6.1.4.1.9.12.3.1.3.203";
  }

  smiv2:alias "cevChassis678" {
    smiv2:oid "1.3.6.1.4.1.9.12.3.1.3.204";
  }

  smiv2:alias "cevChassis3661Ac" {
    smiv2:oid "1.3.6.1.4.1.9.12.3.1.3.205";
  }

  smiv2:alias "cevChassis3661Dc" {
    smiv2:oid "1.3.6.1.4.1.9.12.3.1.3.206";
  }

  smiv2:alias "cevChassis3662Ac" {
    smiv2:oid "1.3.6.1.4.1.9.12.3.1.3.207";
  }

  smiv2:alias "cevChassis3662Dc" {
    smiv2:oid "1.3.6.1.4.1.9.12.3.1.3.208";
  }

  smiv2:alias "cevChassis3662AcCo" {
    smiv2:oid "1.3.6.1.4.1.9.12.3.1.3.209";
  }

  smiv2:alias "cevChassis3662DcCo" {
    smiv2:oid "1.3.6.1.4.1.9.12.3.1.3.210";
  }

  smiv2:alias "cevChassisUbr7111" {
    smiv2:oid "1.3.6.1.4.1.9.12.3.1.3.211";
  }

  smiv2:alias "cevChassisUbr7114" {
    smiv2:oid "1.3.6.1.4.1.9.12.3.1.3.213";
  }

  smiv2:alias "cevChassis12010" {
    smiv2:oid "1.3.6.1.4.1.9.12.3.1.3.215";
  }

  smiv2:alias "cevChassis8110" {
    smiv2:oid "1.3.6.1.4.1.9.12.3.1.3.216";
  }

  smiv2:alias "cevChassisSOHO77" {
    smiv2:oid "1.3.6.1.4.1.9.12.3.1.3.220";
  }

  smiv2:alias "cevChassisSOHO76" {
    smiv2:oid "1.3.6.1.4.1.9.12.3.1.3.221";
  }

  smiv2:alias "cevChassis7150Dualfe" {
    smiv2:oid "1.3.6.1.4.1.9.12.3.1.3.222";
  }

  smiv2:alias "cevChassis7150Octt1" {
    smiv2:oid "1.3.6.1.4.1.9.12.3.1.3.223";
  }

  smiv2:alias "cevChassis7150Dualt3" {
    smiv2:oid "1.3.6.1.4.1.9.12.3.1.3.224";
  }

  smiv2:alias "cevChassisCat2950t24" {
    smiv2:oid "1.3.6.1.4.1.9.12.3.1.3.226";
  }

  smiv2:alias "cevChassisVPS1110" {
    smiv2:oid "1.3.6.1.4.1.9.12.3.1.3.227";
  }

  smiv2:alias "cevChassisContentEngine" {
    smiv2:oid "1.3.6.1.4.1.9.12.3.1.3.228";
  }

  smiv2:alias "cevChassisIAD2420" {
    smiv2:oid "1.3.6.1.4.1.9.12.3.1.3.229";
  }

  smiv2:alias "cevChassis677i" {
    smiv2:oid "1.3.6.1.4.1.9.12.3.1.3.230";
  }

  smiv2:alias "cevChassis674" {
    smiv2:oid "1.3.6.1.4.1.9.12.3.1.3.231";
  }

  smiv2:alias "cevChassisDPA7630" {
    smiv2:oid "1.3.6.1.4.1.9.12.3.1.3.232";
  }

  smiv2:alias "cevChassisCat355024" {
    smiv2:oid "1.3.6.1.4.1.9.12.3.1.3.233";
  }

  smiv2:alias "cevChassisCat355048" {
    smiv2:oid "1.3.6.1.4.1.9.12.3.1.3.234";
  }

  smiv2:alias "cevChassisCat355012T" {
    smiv2:oid "1.3.6.1.4.1.9.12.3.1.3.235";
  }

  smiv2:alias "cevChassisCVA122E" {
    smiv2:oid "1.3.6.1.4.1.9.12.3.1.3.238";
  }

  smiv2:alias "cevChassisCVA124E" {
    smiv2:oid "1.3.6.1.4.1.9.12.3.1.3.239";
  }

  smiv2:alias "cevChassisURM" {
    smiv2:oid "1.3.6.1.4.1.9.12.3.1.3.240";
  }

  smiv2:alias "cevChassisURM2FE" {
    smiv2:oid "1.3.6.1.4.1.9.12.3.1.3.241";
  }

  smiv2:alias "cevChassisURM2FE2V" {
    smiv2:oid "1.3.6.1.4.1.9.12.3.1.3.242";
  }

  smiv2:alias "cevChassisCAP340" {
    smiv2:oid "1.3.6.1.4.1.9.12.3.1.3.245";
  }

  smiv2:alias "cevChassisDPA7610" {
    smiv2:oid "1.3.6.1.4.1.9.12.3.1.3.247";
  }

  smiv2:alias "cevChassis828" {
    smiv2:oid "1.3.6.1.4.1.9.12.3.1.3.248";
  }

  smiv2:alias "cevChassisSOHO78" {
    smiv2:oid "1.3.6.1.4.1.9.12.3.1.3.249";
  }

  smiv2:alias "cevChassis806" {
    smiv2:oid "1.3.6.1.4.1.9.12.3.1.3.250";
  }

  smiv2:alias "cevChassis12416" {
    smiv2:oid "1.3.6.1.4.1.9.12.3.1.3.251";
  }

  smiv2:alias "cevChassisCat2948gL3Dc" {
    smiv2:oid "1.3.6.1.4.1.9.12.3.1.3.252";
  }

  smiv2:alias "cevChassisCat4908gL3Dc" {
    smiv2:oid "1.3.6.1.4.1.9.12.3.1.3.253";
  }

  smiv2:alias "cevChassis12406" {
    smiv2:oid "1.3.6.1.4.1.9.12.3.1.3.254";
  }

  smiv2:alias "cevChassisPIXFirewall506" {
    smiv2:oid "1.3.6.1.4.1.9.12.3.1.3.255";
  }

  smiv2:alias "cevChassisPIXFirewall515" {
    smiv2:oid "1.3.6.1.4.1.9.12.3.1.3.256";
  }

  smiv2:alias "cevChassisPIXFirewall520" {
    smiv2:oid "1.3.6.1.4.1.9.12.3.1.3.257";
  }

  smiv2:alias "cevChassisPIXFirewall525" {
    smiv2:oid "1.3.6.1.4.1.9.12.3.1.3.258";
  }

  smiv2:alias "cevChassisPIXFirewall535" {
    smiv2:oid "1.3.6.1.4.1.9.12.3.1.3.259";
  }

  smiv2:alias "cevChassis12410" {
    smiv2:oid "1.3.6.1.4.1.9.12.3.1.3.260";
  }

  smiv2:alias "cevChassis811" {
    smiv2:oid "1.3.6.1.4.1.9.12.3.1.3.261";
  }

  smiv2:alias "cevChassis813" {
    smiv2:oid "1.3.6.1.4.1.9.12.3.1.3.262";
  }

  smiv2:alias "cevChassis10720" {
    smiv2:oid "1.3.6.1.4.1.9.12.3.1.3.263";
  }

  smiv2:alias "cevChassisMWR1900" {
    smiv2:oid "1.3.6.1.4.1.9.12.3.1.3.264";
  }

  smiv2:alias "cevChassis4224" {
    smiv2:oid "1.3.6.1.4.1.9.12.3.1.3.265";
  }

  smiv2:alias "cevChassisWSC6513" {
    smiv2:oid "1.3.6.1.4.1.9.12.3.1.3.266";
  }

  smiv2:alias "cevChassisCisco7603" {
    smiv2:oid "1.3.6.1.4.1.9.12.3.1.3.267";
  }

  smiv2:alias "cevChassisCisco7606" {
    smiv2:oid "1.3.6.1.4.1.9.12.3.1.3.268";
  }

  smiv2:alias "cevChassis7401ASR" {
    smiv2:oid "1.3.6.1.4.1.9.12.3.1.3.269";
  }

  smiv2:alias "cevChassis1105" {
    smiv2:oid "1.3.6.1.4.1.9.12.3.1.3.271";
  }

  smiv2:alias "cevChassisONS15540ESP" {
    smiv2:oid "1.3.6.1.4.1.9.12.3.1.3.272";
  }

  smiv2:alias "cevChassisCe507" {
    smiv2:oid "1.3.6.1.4.1.9.12.3.1.3.275";
  }

  smiv2:alias "cevChassisCe560" {
    smiv2:oid "1.3.6.1.4.1.9.12.3.1.3.276";
  }

  smiv2:alias "cevChassisCe590" {
    smiv2:oid "1.3.6.1.4.1.9.12.3.1.3.277";
  }

  smiv2:alias "cevChassisCe7320" {
    smiv2:oid "1.3.6.1.4.1.9.12.3.1.3.278";
  }

  smiv2:alias "cevChassis2691" {
    smiv2:oid "1.3.6.1.4.1.9.12.3.1.3.279";
  }

  smiv2:alias "cevChassis3725" {
    smiv2:oid "1.3.6.1.4.1.9.12.3.1.3.280";
  }

  smiv2:alias "cevChassis1760" {
    smiv2:oid "1.3.6.1.4.1.9.12.3.1.3.282";
  }

  smiv2:alias "cevChassisPIXFirewall501" {
    smiv2:oid "1.3.6.1.4.1.9.12.3.1.3.283";
  }

  smiv2:alias "cevChassis2610M" {
    smiv2:oid "1.3.6.1.4.1.9.12.3.1.3.284";
  }

  smiv2:alias "cevChassis2611M" {
    smiv2:oid "1.3.6.1.4.1.9.12.3.1.3.285";
  }

  smiv2:alias "cevChassis12404" {
    smiv2:oid "1.3.6.1.4.1.9.12.3.1.3.289";
  }

  smiv2:alias "cevChassis9004" {
    smiv2:oid "1.3.6.1.4.1.9.12.3.1.3.290";
  }

  smiv2:alias "cevChassisCat295012G" {
    smiv2:oid "1.3.6.1.4.1.9.12.3.1.3.293";
  }

  smiv2:alias "cevChassisCat295024G" {
    smiv2:oid "1.3.6.1.4.1.9.12.3.1.3.294";
  }

  smiv2:alias "cevChassisCat295048G" {
    smiv2:oid "1.3.6.1.4.1.9.12.3.1.3.295";
  }

  smiv2:alias "cevChassisCat355012G" {
    smiv2:oid "1.3.6.1.4.1.9.12.3.1.3.297";
  }

  smiv2:alias "cevChassisCE507AV" {
    smiv2:oid "1.3.6.1.4.1.9.12.3.1.3.298";
  }

  smiv2:alias "cevChassisCE560AV" {
    smiv2:oid "1.3.6.1.4.1.9.12.3.1.3.299";
  }

  smiv2:alias "cevChassisIE2105" {
    smiv2:oid "1.3.6.1.4.1.9.12.3.1.3.300";
  }

  smiv2:alias "cevChassis3745" {
    smiv2:oid "1.3.6.1.4.1.9.12.3.1.3.301";
  }

  smiv2:alias "cevChassis10005" {
    smiv2:oid "1.3.6.1.4.1.9.12.3.1.3.302";
  }

  smiv2:alias "cevChassis10008" {
    smiv2:oid "1.3.6.1.4.1.9.12.3.1.3.303";
  }

  smiv2:alias "cevChassis7304" {
    smiv2:oid "1.3.6.1.4.1.9.12.3.1.3.304";
  }

  smiv2:alias "cevChassis7505" {
    smiv2:oid "1.3.6.1.4.1.9.12.3.1.3.305";
  }

  smiv2:alias "cevChassis1721" {
    smiv2:oid "1.3.6.1.4.1.9.12.3.1.3.310";
  }

  smiv2:alias "cevChassisCat4000Sup3" {
    smiv2:oid "1.3.6.1.4.1.9.12.3.1.3.311";
  }

  smiv2:alias "cevChassis827H" {
    smiv2:oid "1.3.6.1.4.1.9.12.3.1.3.312";
  }

  smiv2:alias "cevChassisSOHO77H" {
    smiv2:oid "1.3.6.1.4.1.9.12.3.1.3.313";
  }

  smiv2:alias "cevChassisCat4006" {
    smiv2:oid "1.3.6.1.4.1.9.12.3.1.3.314";
  }

  smiv2:alias "cevChassisCat355024Mmf" {
    smiv2:oid "1.3.6.1.4.1.9.12.3.1.3.315";
  }

  smiv2:alias "cevChassisWSC6503" {
    smiv2:oid "1.3.6.1.4.1.9.12.3.1.3.316";
  }

  smiv2:alias "cevChassisPIXFirewall506E" {
    smiv2:oid "1.3.6.1.4.1.9.12.3.1.3.317";
  }

  smiv2:alias "cevChassisPIXFirewall515E" {
    smiv2:oid "1.3.6.1.4.1.9.12.3.1.3.318";
  }

  smiv2:alias "cevChassisCat355024Dc" {
    smiv2:oid "1.3.6.1.4.1.9.12.3.1.3.319";
  }

  smiv2:alias "cevChassisCe2636" {
    smiv2:oid "1.3.6.1.4.1.9.12.3.1.3.320";
  }

  smiv2:alias "cevChassisCeDw2636" {
    smiv2:oid "1.3.6.1.4.1.9.12.3.1.3.321";
  }

  smiv2:alias "cevChassis14MGX8830" {
    smiv2:oid "1.3.6.1.4.1.9.12.3.1.3.323";
  }

  smiv2:alias "cevChassisONS15530NEBS" {
    smiv2:oid "1.3.6.1.4.1.9.12.3.1.3.325";
  }

  smiv2:alias "cevChassisONS15530ETSI" {
    smiv2:oid "1.3.6.1.4.1.9.12.3.1.3.326";
  }

  smiv2:alias "cevChassisSOHO71" {
    smiv2:oid "1.3.6.1.4.1.9.12.3.1.3.327";
  }

  smiv2:alias "cevChassis6400UAC" {
    smiv2:oid "1.3.6.1.4.1.9.12.3.1.3.328";
  }

  smiv2:alias "cevChassisRPMPR" {
    smiv2:oid "1.3.6.1.4.1.9.12.3.1.3.329";
  }

  smiv2:alias "cevChassis2610XM" {
    smiv2:oid "1.3.6.1.4.1.9.12.3.1.3.330";
  }

  smiv2:alias "cevChassis2611XM" {
    smiv2:oid "1.3.6.1.4.1.9.12.3.1.3.331";
  }

  smiv2:alias "cevChassis2620XM" {
    smiv2:oid "1.3.6.1.4.1.9.12.3.1.3.332";
  }

  smiv2:alias "cevChassis2621XM" {
    smiv2:oid "1.3.6.1.4.1.9.12.3.1.3.333";
  }

  smiv2:alias "cevChassis2650XM" {
    smiv2:oid "1.3.6.1.4.1.9.12.3.1.3.334";
  }

  smiv2:alias "cevChassis2651XM" {
    smiv2:oid "1.3.6.1.4.1.9.12.3.1.3.335";
  }

  smiv2:alias "cevChassisCat295024GDc" {
    smiv2:oid "1.3.6.1.4.1.9.12.3.1.3.336";
  }

  smiv2:alias "cevChassisONS15540ESPx" {
    smiv2:oid "1.3.6.1.4.1.9.12.3.1.3.337";
  }

  smiv2:alias "cevChassisC7301" {
    smiv2:oid "1.3.6.1.4.1.9.12.3.1.3.340";
  }

  smiv2:alias "cevChassis12816" {
    smiv2:oid "1.3.6.1.4.1.9.12.3.1.3.341";
  }

  smiv2:alias "cevChassis12810" {
    smiv2:oid "1.3.6.1.4.1.9.12.3.1.3.342";
  }

  smiv2:alias "cevChassisCat295024sx" {
    smiv2:oid "1.3.6.1.4.1.9.12.3.1.3.347";
  }

  smiv2:alias "cevChassisAs5400HPX" {
    smiv2:oid "1.3.6.1.4.1.9.12.3.1.3.348";
  }

  smiv2:alias "cevChassisAs5350HPX" {
    smiv2:oid "1.3.6.1.4.1.9.12.3.1.3.349";
  }

  smiv2:alias "cevChassisCat2955T12" {
    smiv2:oid "1.3.6.1.4.1.9.12.3.1.3.350";
  }

  smiv2:alias "cevChassisCat2955C12" {
    smiv2:oid "1.3.6.1.4.1.9.12.3.1.3.351";
  }

  smiv2:alias "cevChassis837" {
    smiv2:oid "1.3.6.1.4.1.9.12.3.1.3.354";
  }

  smiv2:alias "cevChassisSOHO97" {
    smiv2:oid "1.3.6.1.4.1.9.12.3.1.3.355";
  }

  smiv2:alias "cevChassis831" {
    smiv2:oid "1.3.6.1.4.1.9.12.3.1.3.356";
  }

  smiv2:alias "cevChassisSOHO91" {
    smiv2:oid "1.3.6.1.4.1.9.12.3.1.3.357";
  }

  smiv2:alias "cevChassis836" {
    smiv2:oid "1.3.6.1.4.1.9.12.3.1.3.358";
  }

  smiv2:alias "cevChassisSOHO96" {
    smiv2:oid "1.3.6.1.4.1.9.12.3.1.3.359";
  }

  smiv2:alias "cevChassisCat4507" {
    smiv2:oid "1.3.6.1.4.1.9.12.3.1.3.360";
  }

  smiv2:alias "cevChassisCat4506" {
    smiv2:oid "1.3.6.1.4.1.9.12.3.1.3.361";
  }

  smiv2:alias "cevChassisCat4503" {
    smiv2:oid "1.3.6.1.4.1.9.12.3.1.3.362";
  }

  smiv2:alias "cevChassis7507" {
    smiv2:oid "1.3.6.1.4.1.9.12.3.1.3.363";
  }

  smiv2:alias "cevChassis7513" {
    smiv2:oid "1.3.6.1.4.1.9.12.3.1.3.364";
  }

  smiv2:alias "cevChassisAIRAP1100" {
    smiv2:oid "1.3.6.1.4.1.9.12.3.1.3.365";
  }

  smiv2:alias "cevChassisCat2955S12" {
    smiv2:oid "1.3.6.1.4.1.9.12.3.1.3.367";
  }

  smiv2:alias "cevChassisCisco7609" {
    smiv2:oid "1.3.6.1.4.1.9.12.3.1.3.368";
  }

  smiv2:alias "cevChassisWSC65509" {
    smiv2:oid "1.3.6.1.4.1.9.12.3.1.3.369";
  }

  smiv2:alias "cevChassisCat375024" {
    smiv2:oid "1.3.6.1.4.1.9.12.3.1.3.370";
  }

  smiv2:alias "cevChassisCat375048" {
    smiv2:oid "1.3.6.1.4.1.9.12.3.1.3.371";
  }

  smiv2:alias "cevChassisCat375024TS" {
    smiv2:oid "1.3.6.1.4.1.9.12.3.1.3.372";
  }

  smiv2:alias "cevChassisCat375024T" {
    smiv2:oid "1.3.6.1.4.1.9.12.3.1.3.373";
  }

  smiv2:alias "cevChassisMWR1941DC" {
    smiv2:oid "1.3.6.1.4.1.9.12.3.1.3.374";
  }

  smiv2:alias "cevChassisDSC9506" {
    smiv2:oid "1.3.6.1.4.1.9.12.3.1.3.375";
  }

  smiv2:alias "cevChassisDSC9509" {
    smiv2:oid "1.3.6.1.4.1.9.12.3.1.3.376";
  }

  smiv2:alias "cevChassisDSC9513" {
    smiv2:oid "1.3.6.1.4.1.9.12.3.1.3.377";
  }

  smiv2:alias "cevChassisONS15201" {
    smiv2:oid "1.3.6.1.4.1.9.12.3.1.3.378";
  }

  smiv2:alias "cevChassisONS15252" {
    smiv2:oid "1.3.6.1.4.1.9.12.3.1.3.379";
  }

  smiv2:alias "cevChassisMdsDSX9216" {
    smiv2:oid "1.3.6.1.4.1.9.12.3.1.3.380";
  }

  smiv2:alias "cevChassisVG200" {
    smiv2:oid "1.3.6.1.4.1.9.12.3.1.3.381";
  }

  smiv2:alias "cevChassisAIRAP1210" {
    smiv2:oid "1.3.6.1.4.1.9.12.3.1.3.382";
  }

  smiv2:alias "cevChassisCat375048PS" {
    smiv2:oid "1.3.6.1.4.1.9.12.3.1.3.383";
  }

  smiv2:alias "cevChassisCat375024PS" {
    smiv2:oid "1.3.6.1.4.1.9.12.3.1.3.384";
  }

  smiv2:alias "cevChassisCe510" {
    smiv2:oid "1.3.6.1.4.1.9.12.3.1.3.385";
  }

  smiv2:alias "cevChassisCe565" {
    smiv2:oid "1.3.6.1.4.1.9.12.3.1.3.386";
  }

  smiv2:alias "cevChassisCe7305" {
    smiv2:oid "1.3.6.1.4.1.9.12.3.1.3.387";
  }

  smiv2:alias "cevChassisCe7325" {
    smiv2:oid "1.3.6.1.4.1.9.12.3.1.3.388";
  }

  smiv2:alias "cevChassisCe4630" {
    smiv2:oid "1.3.6.1.4.1.9.12.3.1.3.389";
  }

  smiv2:alias "cevChassisCe4650" {
    smiv2:oid "1.3.6.1.4.1.9.12.3.1.3.390";
  }

  smiv2:alias "cevChassisCat297024" {
    smiv2:oid "1.3.6.1.4.1.9.12.3.1.3.391";
  }

  smiv2:alias "cevChassisCisco7613" {
    smiv2:oid "1.3.6.1.4.1.9.12.3.1.3.392";
  }

  smiv2:alias "cevChassisCat3750Ge12Sfp" {
    smiv2:oid "1.3.6.1.4.1.9.12.3.1.3.394";
  }

  smiv2:alias "cevChassisCr4450" {
    smiv2:oid "1.3.6.1.4.1.9.12.3.1.3.395";
  }

  smiv2:alias "cevChassisAIRBR1410" {
    smiv2:oid "1.3.6.1.4.1.9.12.3.1.3.396";
  }

  smiv2:alias "cevChassisWSC6509neba" {
    smiv2:oid "1.3.6.1.4.1.9.12.3.1.3.397";
  }

  smiv2:alias "cevChassisCat4510" {
    smiv2:oid "1.3.6.1.4.1.9.12.3.1.3.398";
  }

  smiv2:alias "cevChassisCisco1711" {
    smiv2:oid "1.3.6.1.4.1.9.12.3.1.3.399";
  }

  smiv2:alias "cevChassisCisco1712" {
    smiv2:oid "1.3.6.1.4.1.9.12.3.1.3.400";
  }

  smiv2:alias "cevChassisCisco1701" {
    smiv2:oid "1.3.6.1.4.1.9.12.3.1.3.401";
  }

  smiv2:alias "cevChassis29408TT" {
    smiv2:oid "1.3.6.1.4.1.9.12.3.1.3.402";
  }

  smiv2:alias "cevChassis29408TF" {
    smiv2:oid "1.3.6.1.4.1.9.12.3.1.3.403";
  }

  smiv2:alias "cevChassis3825" {
    smiv2:oid "1.3.6.1.4.1.9.12.3.1.3.404";
  }

  smiv2:alias "cevChassis3845" {
    smiv2:oid "1.3.6.1.4.1.9.12.3.1.3.405";
  }

  smiv2:alias "cevChassis2430Iad24Fxs" {
    smiv2:oid "1.3.6.1.4.1.9.12.3.1.3.406";
  }

  smiv2:alias "cevChassis2431Iad8Fxs" {
    smiv2:oid "1.3.6.1.4.1.9.12.3.1.3.407";
  }

  smiv2:alias "cevChassis2431Iad16Fxs" {
    smiv2:oid "1.3.6.1.4.1.9.12.3.1.3.408";
  }

  smiv2:alias "cevChassis2431Iad1T1E1" {
    smiv2:oid "1.3.6.1.4.1.9.12.3.1.3.409";
  }

  smiv2:alias "cevChassis2432Iad24Fxs" {
    smiv2:oid "1.3.6.1.4.1.9.12.3.1.3.410";
  }

  smiv2:alias "cevChassisDSC9140K9" {
    smiv2:oid "1.3.6.1.4.1.9.12.3.1.3.411";
  }

  smiv2:alias "cevChassisAirAp350IOS" {
    smiv2:oid "1.3.6.1.4.1.9.12.3.1.3.412";
  }

  smiv2:alias "cevChassis3220" {
    smiv2:oid "1.3.6.1.4.1.9.12.3.1.3.413";
  }

  smiv2:alias "cevChassisDSC9120K9" {
    smiv2:oid "1.3.6.1.4.1.9.12.3.1.3.414";
  }

  smiv2:alias "cevChassisCat295024LreSt997" {
    smiv2:oid "1.3.6.1.4.1.9.12.3.1.3.415";
  }

  smiv2:alias "cevChassisCat6kSup720" {
    smiv2:oid "1.3.6.1.4.1.9.12.3.1.3.416";
  }

  smiv2:alias "cevChassisVG224" {
    smiv2:oid "1.3.6.1.4.1.9.12.3.1.3.417";
  }

  smiv2:alias "cevChassisCat295048T" {
    smiv2:oid "1.3.6.1.4.1.9.12.3.1.3.418";
  }

  smiv2:alias "cevChassisCat295048SX" {
    smiv2:oid "1.3.6.1.4.1.9.12.3.1.3.419";
  }

  smiv2:alias "cevChassisCat297024TS" {
    smiv2:oid "1.3.6.1.4.1.9.12.3.1.3.420";
  }

  smiv2:alias "cevChassisCrs116Fabric" {
    smiv2:oid "1.3.6.1.4.1.9.12.3.1.3.421";
  }

  smiv2:alias "cevChassisCrs116LineCard" {
    smiv2:oid "1.3.6.1.4.1.9.12.3.1.3.422";
  }

  smiv2:alias "cevChassisCrs18LineCard" {
    smiv2:oid "1.3.6.1.4.1.9.12.3.1.3.423";
  }

  smiv2:alias "cevChassisCat356048PS" {
    smiv2:oid "1.3.6.1.4.1.9.12.3.1.3.424";
  }

  smiv2:alias "cevChassisCat356024PS" {
    smiv2:oid "1.3.6.1.4.1.9.12.3.1.3.425";
  }

  smiv2:alias "cevChassisAIRBR1300" {
    smiv2:oid "1.3.6.1.4.1.9.12.3.1.3.426";
  }

  smiv2:alias "cevChassis12004" {
    smiv2:oid "1.3.6.1.4.1.9.12.3.1.3.427";
  }

  smiv2:alias "cevChassis12006" {
    smiv2:oid "1.3.6.1.4.1.9.12.3.1.3.428";
  }

  smiv2:alias "cevChassis851" {
    smiv2:oid "1.3.6.1.4.1.9.12.3.1.3.429";
  }

  smiv2:alias "cevChassis857" {
    smiv2:oid "1.3.6.1.4.1.9.12.3.1.3.430";
  }

  smiv2:alias "cevChassis876" {
    smiv2:oid "1.3.6.1.4.1.9.12.3.1.3.431";
  }

  smiv2:alias "cevChassis877" {
    smiv2:oid "1.3.6.1.4.1.9.12.3.1.3.432";
  }

  smiv2:alias "cevChassis878" {
    smiv2:oid "1.3.6.1.4.1.9.12.3.1.3.433";
  }

  smiv2:alias "cevChassis871" {
    smiv2:oid "1.3.6.1.4.1.9.12.3.1.3.434";
  }

  smiv2:alias "cevChassisUmg9820" {
    smiv2:oid "1.3.6.1.4.1.9.12.3.1.3.435";
  }

  smiv2:alias "cevChassis2811" {
    smiv2:oid "1.3.6.1.4.1.9.12.3.1.3.436";
  }

  smiv2:alias "cevChassis2821" {
    smiv2:oid "1.3.6.1.4.1.9.12.3.1.3.437";
  }

  smiv2:alias "cevChassis2851" {
    smiv2:oid "1.3.6.1.4.1.9.12.3.1.3.438";
  }

  smiv2:alias "cevChassisCat375024ME" {
    smiv2:oid "1.3.6.1.4.1.9.12.3.1.3.439";
  }

  smiv2:alias "cevChassisMdsDSC9216AK9" {
    smiv2:oid "1.3.6.1.4.1.9.12.3.1.3.442";
  }

  smiv2:alias "cevChassis3201WMIC" {
    smiv2:oid "1.3.6.1.4.1.9.12.3.1.3.443";
  }

  smiv2:alias "cevChassisCat3750G16TD" {
    smiv2:oid "1.3.6.1.4.1.9.12.3.1.3.444";
  }

  smiv2:alias "cevChassis1718" {
    smiv2:oid "1.3.6.1.4.1.9.12.3.1.3.445";
  }

  smiv2:alias "cevChassisIGESM" {
    smiv2:oid "1.3.6.1.4.1.9.12.3.1.3.446";
  }

  smiv2:alias "cevChassisASA5510" {
    smiv2:oid "1.3.6.1.4.1.9.12.3.1.3.447";
  }

  smiv2:alias "cevChassisASA5520" {
    smiv2:oid "1.3.6.1.4.1.9.12.3.1.3.448";
  }

  smiv2:alias "cevChassisASA5540" {
    smiv2:oid "1.3.6.1.4.1.9.12.3.1.3.449";
  }

  smiv2:alias "cevChassis1841" {
    smiv2:oid "1.3.6.1.4.1.9.12.3.1.3.450";
  }

  smiv2:alias "cevChassis2801" {
    smiv2:oid "1.3.6.1.4.1.9.12.3.1.3.451";
  }

  smiv2:alias "cevChassisCe511K9" {
    smiv2:oid "1.3.6.1.4.1.9.12.3.1.3.452";
  }

  smiv2:alias "cevChassisCe566K9" {
    smiv2:oid "1.3.6.1.4.1.9.12.3.1.3.453";
  }

  smiv2:alias "cevChassisASA5560" {
    smiv2:oid "1.3.6.1.4.1.9.12.3.1.3.454";
  }

  smiv2:alias "cevChassisMGX8880" {
    smiv2:oid "1.3.6.1.4.1.9.12.3.1.3.455";
  }

  smiv2:alias "cevChassisCe7306K9" {
    smiv2:oid "1.3.6.1.4.1.9.12.3.1.3.456";
  }

  smiv2:alias "cevChassisCe7326K9" {
    smiv2:oid "1.3.6.1.4.1.9.12.3.1.3.457";
  }

  smiv2:alias "cevChassisCat3750G24PS" {
    smiv2:oid "1.3.6.1.4.1.9.12.3.1.3.458";
  }

  smiv2:alias "cevChassisCat3750G48PS" {
    smiv2:oid "1.3.6.1.4.1.9.12.3.1.3.459";
  }

  smiv2:alias "cevChassisCat3750G48TS" {
    smiv2:oid "1.3.6.1.4.1.9.12.3.1.3.460";
  }

  smiv2:alias "cevChassisCat297048TS" {
    smiv2:oid "1.3.6.1.4.1.9.12.3.1.3.461";
  }

  smiv2:alias "cevChassisDSX9132K9" {
    smiv2:oid "1.3.6.1.4.1.9.12.3.1.3.462";
  }

  smiv2:alias "cevChassisDSX9116K9" {
    smiv2:oid "1.3.6.1.4.1.9.12.3.1.3.463";
  }

  smiv2:alias "cevChassisBMGX8830" {
    smiv2:oid "1.3.6.1.4.1.9.12.3.1.3.464";
  }

  smiv2:alias "cevChassisBMGX8850" {
    smiv2:oid "1.3.6.1.4.1.9.12.3.1.3.465";
  }

  smiv2:alias "cevChassisWsC4948" {
    smiv2:oid "1.3.6.1.4.1.9.12.3.1.3.466";
  }

  smiv2:alias "cevChassisCe501K9" {
    smiv2:oid "1.3.6.1.4.1.9.12.3.1.3.467";
  }

  smiv2:alias "cevChassisCat3560G24PS" {
    smiv2:oid "1.3.6.1.4.1.9.12.3.1.3.468";
  }

  smiv2:alias "cevChassisCat3560G24TS" {
    smiv2:oid "1.3.6.1.4.1.9.12.3.1.3.469";
  }

  smiv2:alias "cevChassisCat3560G48PS" {
    smiv2:oid "1.3.6.1.4.1.9.12.3.1.3.470";
  }

  smiv2:alias "cevChassisCat3560G48TS" {
    smiv2:oid "1.3.6.1.4.1.9.12.3.1.3.471";
  }

  smiv2:alias "cevChassisDSC9216iK9" {
    smiv2:oid "1.3.6.1.4.1.9.12.3.1.3.472";
  }

  smiv2:alias "cevChassisAs5400XM" {
    smiv2:oid "1.3.6.1.4.1.9.12.3.1.3.473";
  }

  smiv2:alias "cevChassisAs5350XM" {
    smiv2:oid "1.3.6.1.4.1.9.12.3.1.3.474";
  }

  smiv2:alias "cevChassisAIRAP1130" {
    smiv2:oid "1.3.6.1.4.1.9.12.3.1.3.475";
  }

  smiv2:alias "cevChassisCisco7604" {
    smiv2:oid "1.3.6.1.4.1.9.12.3.1.3.476";
  }

  smiv2:alias "cevChassisWsC494810GE" {
    smiv2:oid "1.3.6.1.4.1.9.12.3.1.3.477";
  }

  smiv2:alias "cevChassisCat3750G24TS1U" {
    smiv2:oid "1.3.6.1.4.1.9.12.3.1.3.478";
  }

  smiv2:alias "cevChassis371098HP001" {
    smiv2:oid "1.3.6.1.4.1.9.12.3.1.3.480";
  }

  smiv2:alias "cevChassisSB101" {
    smiv2:oid "1.3.6.1.4.1.9.12.3.1.3.481";
  }

  smiv2:alias "cevChassisSB106" {
    smiv2:oid "1.3.6.1.4.1.9.12.3.1.3.482";
  }

  smiv2:alias "cevChassisSB107" {
    smiv2:oid "1.3.6.1.4.1.9.12.3.1.3.483";
  }

  smiv2:alias "cevChassisCat356024TS" {
    smiv2:oid "1.3.6.1.4.1.9.12.3.1.3.484";
  }

  smiv2:alias "cevChassisCat356048TS" {
    smiv2:oid "1.3.6.1.4.1.9.12.3.1.3.485";
  }

  smiv2:alias "cevChassisONS15310" {
    smiv2:oid "1.3.6.1.4.1.9.12.3.1.3.486";
  }

  smiv2:alias "cevChassis1801" {
    smiv2:oid "1.3.6.1.4.1.9.12.3.1.3.487";
  }

  smiv2:alias "cevChassis1802" {
    smiv2:oid "1.3.6.1.4.1.9.12.3.1.3.488";
  }

  smiv2:alias "cevChassis1803" {
    smiv2:oid "1.3.6.1.4.1.9.12.3.1.3.489";
  }

  smiv2:alias "cevChassis1811" {
    smiv2:oid "1.3.6.1.4.1.9.12.3.1.3.490";
  }

  smiv2:alias "cevChassis1812" {
    smiv2:oid "1.3.6.1.4.1.9.12.3.1.3.491";
  }

  smiv2:alias "cevWLSEChassis1130" {
    smiv2:oid "1.3.6.1.4.1.9.12.3.1.3.492";
  }

  smiv2:alias "cevWLSEChassis1030" {
    smiv2:oid "1.3.6.1.4.1.9.12.3.1.3.493";
  }

  smiv2:alias "cevChassisIDS4210" {
    smiv2:oid "1.3.6.1.4.1.9.12.3.1.3.495";
  }

  smiv2:alias "cevChassisIDS4215" {
    smiv2:oid "1.3.6.1.4.1.9.12.3.1.3.496";
  }

  smiv2:alias "cevChassisIDS4235" {
    smiv2:oid "1.3.6.1.4.1.9.12.3.1.3.497";
  }

  smiv2:alias "cevChassisIDS4240" {
    smiv2:oid "1.3.6.1.4.1.9.12.3.1.3.498";
  }

  smiv2:alias "cevChassisIDS4250" {
    smiv2:oid "1.3.6.1.4.1.9.12.3.1.3.499";
  }

  smiv2:alias "cevChassisIDS4250SX" {
    smiv2:oid "1.3.6.1.4.1.9.12.3.1.3.500";
  }

  smiv2:alias "cevChassisIDS4250XL" {
    smiv2:oid "1.3.6.1.4.1.9.12.3.1.3.501";
  }

  smiv2:alias "cevChassisIDS4255" {
    smiv2:oid "1.3.6.1.4.1.9.12.3.1.3.502";
  }

  smiv2:alias "cevChassisCat375024FS" {
    smiv2:oid "1.3.6.1.4.1.9.12.3.1.3.503";
  }

  smiv2:alias "cevChassisWSC6504E" {
    smiv2:oid "1.3.6.1.4.1.9.12.3.1.3.504";
  }

  smiv2:alias "cevChassisIGESMSFP" {
    smiv2:oid "1.3.6.1.4.1.9.12.3.1.3.505";
  }

  smiv2:alias "cevChasisFe6326K9" {
    smiv2:oid "1.3.6.1.4.1.9.12.3.1.3.506";
  }

  smiv2:alias "cevChassisFe7326K9" {
    smiv2:oid "1.3.6.1.4.1.9.12.3.1.3.508";
  }

  smiv2:alias "cevChassisFe511K9" {
    smiv2:oid "1.3.6.1.4.1.9.12.3.1.3.509";
  }

  smiv2:alias "cevChassisSCEDispatcher" {
    smiv2:oid "1.3.6.1.4.1.9.12.3.1.3.510";
  }

  smiv2:alias "cevChassisSCE2000" {
    smiv2:oid "1.3.6.1.4.1.9.12.3.1.3.511";
  }

  smiv2:alias "cevChassisSCE1000" {
    smiv2:oid "1.3.6.1.4.1.9.12.3.1.3.512";
  }

  smiv2:alias "cevChassisAIRAP1240" {
    smiv2:oid "1.3.6.1.4.1.9.12.3.1.3.513";
  }

  smiv2:alias "cevChassisDSC902020K9" {
    smiv2:oid "1.3.6.1.4.1.9.12.3.1.3.514";
  }

  smiv2:alias "cevChassisFe611K9" {
    smiv2:oid "1.3.6.1.4.1.9.12.3.1.3.515";
  }

  smiv2:alias "cevChassisCat3750Ge12SfpDc" {
    smiv2:oid "1.3.6.1.4.1.9.12.3.1.3.520";
  }

  smiv2:alias "cevChassisCat296024" {
    smiv2:oid "1.3.6.1.4.1.9.12.3.1.3.521";
  }

  smiv2:alias "cevChassisCat296048" {
    smiv2:oid "1.3.6.1.4.1.9.12.3.1.3.522";
  }

  smiv2:alias "cevChassisCat2960G24" {
    smiv2:oid "1.3.6.1.4.1.9.12.3.1.3.523";
  }

  smiv2:alias "cevChassisCat2960G48" {
    smiv2:oid "1.3.6.1.4.1.9.12.3.1.3.524";
  }

  smiv2:alias "cevChassisCat6kMsfc2a" {
    smiv2:oid "1.3.6.1.4.1.9.12.3.1.3.529";
  }

  smiv2:alias "cevChassisCe611K9" {
    smiv2:oid "1.3.6.1.4.1.9.12.3.1.3.530";
  }

  smiv2:alias "cevChassisME6340ACA" {
    smiv2:oid "1.3.6.1.4.1.9.12.3.1.3.531";
  }

  smiv2:alias "cevChassisME6340DCA" {
    smiv2:oid "1.3.6.1.4.1.9.12.3.1.3.532";
  }

  smiv2:alias "cevChassisME6340DCB" {
    smiv2:oid "1.3.6.1.4.1.9.12.3.1.3.533";
  }

  smiv2:alias "cevChassisCat296024TT" {
    smiv2:oid "1.3.6.1.4.1.9.12.3.1.3.534";
  }

  smiv2:alias "cevChassisCat296048TT" {
    smiv2:oid "1.3.6.1.4.1.9.12.3.1.3.535";
  }

  smiv2:alias "cevChassisIGESMSFPT" {
    smiv2:oid "1.3.6.1.4.1.9.12.3.1.3.536";
  }

  smiv2:alias "cevChassisMec6524gs8s" {
    smiv2:oid "1.3.6.1.4.1.9.12.3.1.3.537";
  }

  smiv2:alias "cevChassisMec6524gt8s" {
    smiv2:oid "1.3.6.1.4.1.9.12.3.1.3.538";
  }

  smiv2:alias "cevChassisPaldron" {
    smiv2:oid "1.3.6.1.4.1.9.12.3.1.3.541";
  }

  smiv2:alias "cevChassisIGESMT" {
    smiv2:oid "1.3.6.1.4.1.9.12.3.1.3.542";
  }

  smiv2:alias "cevChassisCatCE50024TT" {
    smiv2:oid "1.3.6.1.4.1.9.12.3.1.3.543";
  }

  smiv2:alias "cevChassisCatCE50024LC" {
    smiv2:oid "1.3.6.1.4.1.9.12.3.1.3.544";
  }

  smiv2:alias "cevChassisCatCE50024PC" {
    smiv2:oid "1.3.6.1.4.1.9.12.3.1.3.545";
  }

  smiv2:alias "cevChassisCatCE50012TC" {
    smiv2:oid "1.3.6.1.4.1.9.12.3.1.3.546";
  }

  smiv2:alias "cevChassis5750" {
    smiv2:oid "1.3.6.1.4.1.9.12.3.1.3.547";
  }

  smiv2:alias "cevChassisMWR1941DCA" {
    smiv2:oid "1.3.6.1.4.1.9.12.3.1.3.548";
  }

  smiv2:alias "cevChassis815" {
    smiv2:oid "1.3.6.1.4.1.9.12.3.1.3.549";
  }

  smiv2:alias "cevChassis240024TSA" {
    smiv2:oid "1.3.6.1.4.1.9.12.3.1.3.550";
  }

  smiv2:alias "cevChassis240024TSD" {
    smiv2:oid "1.3.6.1.4.1.9.12.3.1.3.551";
  }

  smiv2:alias "cevChassis340024TSA" {
    smiv2:oid "1.3.6.1.4.1.9.12.3.1.3.552";
  }

  smiv2:alias "cevChassis340024TSD" {
    smiv2:oid "1.3.6.1.4.1.9.12.3.1.3.553";
  }

  smiv2:alias "cevChassisFe2636" {
    smiv2:oid "1.3.6.1.4.1.9.12.3.1.3.556";
  }

  smiv2:alias "cevChassisIDS4220" {
    smiv2:oid "1.3.6.1.4.1.9.12.3.1.3.557";
  }

  smiv2:alias "cevChassisIDS4230" {
    smiv2:oid "1.3.6.1.4.1.9.12.3.1.3.558";
  }

  smiv2:alias "cevChassisASA5505" {
    smiv2:oid "1.3.6.1.4.1.9.12.3.1.3.560";
  }

  smiv2:alias "cevChassisWS3020HPQ" {
    smiv2:oid "1.3.6.1.4.1.9.12.3.1.3.561";
  }

  smiv2:alias "cevChassisWS3030DEL" {
    smiv2:oid "1.3.6.1.4.1.9.12.3.1.3.562";
  }

  smiv2:alias "cevChassisWLSE1133" {
    smiv2:oid "1.3.6.1.4.1.9.12.3.1.3.563";
  }

  smiv2:alias "cevChassisASA5550" {
    smiv2:oid "1.3.6.1.4.1.9.12.3.1.3.564";
  }

  smiv2:alias "cevChassisWae612K9" {
    smiv2:oid "1.3.6.1.4.1.9.12.3.1.3.565";
  }

  smiv2:alias "cevChassisAirap1250" {
    smiv2:oid "1.3.6.1.4.1.9.12.3.1.3.567";
  }

  smiv2:alias "cevChassisCe512K9" {
    smiv2:oid "1.3.6.1.4.1.9.12.3.1.3.568";
  }

  smiv2:alias "cevChassisFe512K9" {
    smiv2:oid "1.3.6.1.4.1.9.12.3.1.3.569";
  }

  smiv2:alias "cevChassisCe612K9" {
    smiv2:oid "1.3.6.1.4.1.9.12.3.1.3.570";
  }

  smiv2:alias "cevChassisFe612K9" {
    smiv2:oid "1.3.6.1.4.1.9.12.3.1.3.571";
  }

  smiv2:alias "cevChassisOe512K9" {
    smiv2:oid "1.3.6.1.4.1.9.12.3.1.3.573";
  }

  smiv2:alias "cevChassisOe612K9" {
    smiv2:oid "1.3.6.1.4.1.9.12.3.1.3.574";
  }

  smiv2:alias "cevChassisCat3750G24WS" {
    smiv2:oid "1.3.6.1.4.1.9.12.3.1.3.575";
  }

  smiv2:alias "cevChassisCrs14LineCard" {
    smiv2:oid "1.3.6.1.4.1.9.12.3.1.3.576";
  }

  smiv2:alias "cevChassisMe3400g12CsA" {
    smiv2:oid "1.3.6.1.4.1.9.12.3.1.3.577";
  }

  smiv2:alias "cevChassisMe3400g12CsD" {
    smiv2:oid "1.3.6.1.4.1.9.12.3.1.3.578";
  }

  smiv2:alias "cevChassis877M" {
    smiv2:oid "1.3.6.1.4.1.9.12.3.1.3.579";
  }

  smiv2:alias "cevChassis1801M" {
    smiv2:oid "1.3.6.1.4.1.9.12.3.1.3.580";
  }

  smiv2:alias "cevChassisWsCbs3040Fsc" {
    smiv2:oid "1.3.6.1.4.1.9.12.3.1.3.581";
  }

  smiv2:alias "cevChassisSpaIPSEC2g2" {
    smiv2:oid "1.3.6.1.4.1.9.12.3.1.3.582";
  }

  smiv2:alias "cevChassisOe511K9" {
    smiv2:oid "1.3.6.1.4.1.9.12.3.1.3.583";
  }

  smiv2:alias "cevChassisOe611K9" {
    smiv2:oid "1.3.6.1.4.1.9.12.3.1.3.584";
  }

  smiv2:alias "cevChassisOe7326K9" {
    smiv2:oid "1.3.6.1.4.1.9.12.3.1.3.585";
  }

  smiv2:alias "cevChassisMe492410GE" {
    smiv2:oid "1.3.6.1.4.1.9.12.3.1.3.586";
  }

  smiv2:alias "cevChassisDSC9124" {
    smiv2:oid "1.3.6.1.4.1.9.12.3.1.3.587";
  }

  smiv2:alias "cevChassisCat3750E48TD" {
    smiv2:oid "1.3.6.1.4.1.9.12.3.1.3.588";
  }

  smiv2:alias "cevChassisCat3750E24TD" {
    smiv2:oid "1.3.6.1.4.1.9.12.3.1.3.589";
  }

  smiv2:alias "cevChassisCat3750E24PD" {
    smiv2:oid "1.3.6.1.4.1.9.12.3.1.3.590";
  }

  smiv2:alias "cevChassisCat3750E48PD" {
    smiv2:oid "1.3.6.1.4.1.9.12.3.1.3.591";
  }

  smiv2:alias "cevChassisCat3560E24TD" {
    smiv2:oid "1.3.6.1.4.1.9.12.3.1.3.592";
  }

  smiv2:alias "cevChassisCat3560E48TD" {
    smiv2:oid "1.3.6.1.4.1.9.12.3.1.3.593";
  }

  smiv2:alias "cevChassisCat3560E24PD" {
    smiv2:oid "1.3.6.1.4.1.9.12.3.1.3.594";
  }

  smiv2:alias "cevChassisCat3560E48PD" {
    smiv2:oid "1.3.6.1.4.1.9.12.3.1.3.595";
  }

  smiv2:alias "cevChassisCat35608PC" {
    smiv2:oid "1.3.6.1.4.1.9.12.3.1.3.596";
  }

  smiv2:alias "cevChassisCat29608TC" {
    smiv2:oid "1.3.6.1.4.1.9.12.3.1.3.597";
  }

  smiv2:alias "cevChassisCat2960G8TC" {
    smiv2:oid "1.3.6.1.4.1.9.12.3.1.3.598";
  }

  smiv2:alias "cevChassisCisco7606S" {
    smiv2:oid "1.3.6.1.4.1.9.12.3.1.3.599";
  }

  smiv2:alias "cevChassisCisco7609S" {
    smiv2:oid "1.3.6.1.4.1.9.12.3.1.3.600";
  }

  smiv2:alias "cevChassisDSIBMFC" {
    smiv2:oid "1.3.6.1.4.1.9.12.3.1.3.601";
  }

  smiv2:alias "cevChassisIPSVirtual" {
    smiv2:oid "1.3.6.1.4.1.9.12.3.1.3.602";
  }

  smiv2:alias "cevChassis3250" {
    smiv2:oid "1.3.6.1.4.1.9.12.3.1.3.603";
  }

  smiv2:alias "cevChassis3205WMIC" {
    smiv2:oid "1.3.6.1.4.1.9.12.3.1.3.604";
  }

  smiv2:alias "cevChassisCisco5720" {
    smiv2:oid "1.3.6.1.4.1.9.12.3.1.3.605";
  }

  smiv2:alias "cevChassisMe3400g2csA" {
    smiv2:oid "1.3.6.1.4.1.9.12.3.1.3.607";
  }

  smiv2:alias "cevChassis7201" {
    smiv2:oid "1.3.6.1.4.1.9.12.3.1.3.608";
  }

  smiv2:alias "cevChassisNmWae" {
    smiv2:oid "1.3.6.1.4.1.9.12.3.1.3.609";
  }

  smiv2:alias "cevChassisACE4710K9" {
    smiv2:oid "1.3.6.1.4.1.9.12.3.1.3.610";
  }

  smiv2:alias "cevChassisN7Kc7010" {
    smiv2:oid "1.3.6.1.4.1.9.12.3.1.3.612";
  }

  smiv2:alias "cevChassisUbr7225Vxr" {
    smiv2:oid "1.3.6.1.4.1.9.12.3.1.3.613";
  }

  smiv2:alias "cevChassisWSC6509ve" {
    smiv2:oid "1.3.6.1.4.1.9.12.3.1.3.615";
  }

  smiv2:alias "cevChassisDSC9134" {
    smiv2:oid "1.3.6.1.4.1.9.12.3.1.3.616";
  }

  smiv2:alias "cevChassisCisco7603S" {
    smiv2:oid "1.3.6.1.4.1.9.12.3.1.3.617";
  }

  smiv2:alias "cevChassis5740" {
    smiv2:oid "1.3.6.1.4.1.9.12.3.1.3.620";
  }

  smiv2:alias "cevChassis867" {
    smiv2:oid "1.3.6.1.4.1.9.12.3.1.3.623";
  }

  smiv2:alias "cevChassis881" {
    smiv2:oid "1.3.6.1.4.1.9.12.3.1.3.624";
  }

  smiv2:alias "cevChassis881G" {
    smiv2:oid "1.3.6.1.4.1.9.12.3.1.3.625";
  }

  smiv2:alias "cevChassisIad881F" {
    smiv2:oid "1.3.6.1.4.1.9.12.3.1.3.626";
  }

  smiv2:alias "cevChassisIad881B" {
    smiv2:oid "1.3.6.1.4.1.9.12.3.1.3.627";
  }

  smiv2:alias "cevChassis881Srst" {
    smiv2:oid "1.3.6.1.4.1.9.12.3.1.3.628";
  }

  smiv2:alias "cevChassis886" {
    smiv2:oid "1.3.6.1.4.1.9.12.3.1.3.629";
  }

  smiv2:alias "cevChassis886G" {
    smiv2:oid "1.3.6.1.4.1.9.12.3.1.3.630";
  }

  smiv2:alias "cevChassisIad886F" {
    smiv2:oid "1.3.6.1.4.1.9.12.3.1.3.631";
  }

  smiv2:alias "cevChassisIad886B" {
    smiv2:oid "1.3.6.1.4.1.9.12.3.1.3.632";
  }

  smiv2:alias "cevChassis886Srst" {
    smiv2:oid "1.3.6.1.4.1.9.12.3.1.3.633";
  }

  smiv2:alias "cevChassis887" {
    smiv2:oid "1.3.6.1.4.1.9.12.3.1.3.634";
  }

  smiv2:alias "cevChassis887G" {
    smiv2:oid "1.3.6.1.4.1.9.12.3.1.3.635";
  }

  smiv2:alias "cevChassisIad887F" {
    smiv2:oid "1.3.6.1.4.1.9.12.3.1.3.636";
  }

  smiv2:alias "cevChassisIad887B" {
    smiv2:oid "1.3.6.1.4.1.9.12.3.1.3.637";
  }

  smiv2:alias "cevChassis887Srst" {
    smiv2:oid "1.3.6.1.4.1.9.12.3.1.3.638";
  }

  smiv2:alias "cevChassis888G" {
    smiv2:oid "1.3.6.1.4.1.9.12.3.1.3.640";
  }

  smiv2:alias "cevChassisIad888F" {
    smiv2:oid "1.3.6.1.4.1.9.12.3.1.3.641";
  }

  smiv2:alias "cevChassisIad888B" {
    smiv2:oid "1.3.6.1.4.1.9.12.3.1.3.642";
  }

  smiv2:alias "cevChassis888Srst" {
    smiv2:oid "1.3.6.1.4.1.9.12.3.1.3.643";
  }

  smiv2:alias "cevChassis891" {
    smiv2:oid "1.3.6.1.4.1.9.12.3.1.3.644";
  }

  smiv2:alias "cevChassis892" {
    smiv2:oid "1.3.6.1.4.1.9.12.3.1.3.645";
  }

  smiv2:alias "cevChassis885D3" {
    smiv2:oid "1.3.6.1.4.1.9.12.3.1.3.646";
  }

  smiv2:alias "cevChassisIad885FD3" {
    smiv2:oid "1.3.6.1.4.1.9.12.3.1.3.647";
  }

  smiv2:alias "cevChassis885EJ3" {
    smiv2:oid "1.3.6.1.4.1.9.12.3.1.3.648";
  }

  smiv2:alias "cevChassis7816H" {
    smiv2:oid "1.3.6.1.4.1.9.12.3.1.3.649";
  }

  smiv2:alias "cevChassisSce8000" {
    smiv2:oid "1.3.6.1.4.1.9.12.3.1.3.650";
  }

  smiv2:alias "cevChassisMdsDSC9222i" {
    smiv2:oid "1.3.6.1.4.1.9.12.3.1.3.651";
  }

  smiv2:alias "cevChassis860Ap" {
    smiv2:oid "1.3.6.1.4.1.9.12.3.1.3.653";
  }

  smiv2:alias "cevChassis880Ap" {
    smiv2:oid "1.3.6.1.4.1.9.12.3.1.3.654";
  }

  smiv2:alias "cevChassis890Ap" {
    smiv2:oid "1.3.6.1.4.1.9.12.3.1.3.655";
  }

  smiv2:alias "cevChassis1900Ap" {
    smiv2:oid "1.3.6.1.4.1.9.12.3.1.3.656";
  }

  smiv2:alias "cevChassis340024FSA" {
    smiv2:oid "1.3.6.1.4.1.9.12.3.1.3.657";
  }

  smiv2:alias "cevChassisCat4503e" {
    smiv2:oid "1.3.6.1.4.1.9.12.3.1.3.658";
  }

  smiv2:alias "cevChassisCat4506e" {
    smiv2:oid "1.3.6.1.4.1.9.12.3.1.3.659";
  }

  smiv2:alias "cevChassisCat4507re" {
    smiv2:oid "1.3.6.1.4.1.9.12.3.1.3.660";
  }

  smiv2:alias "cevChassisCat4510re" {
    smiv2:oid "1.3.6.1.4.1.9.12.3.1.3.661";
  }

  smiv2:alias "cevChassisUc520s8U4FxoK9" {
    smiv2:oid "1.3.6.1.4.1.9.12.3.1.3.662";
  }

  smiv2:alias "cevChassisUc520s8U4FxoWK9" {
    smiv2:oid "1.3.6.1.4.1.9.12.3.1.3.663";
  }

  smiv2:alias "cevChassisUc520s8U2BriK9" {
    smiv2:oid "1.3.6.1.4.1.9.12.3.1.3.664";
  }

  smiv2:alias "cevChassisUc520s8U2BriWK9" {
    smiv2:oid "1.3.6.1.4.1.9.12.3.1.3.665";
  }

  smiv2:alias "cevChassisUc520s16U4FxoK9" {
    smiv2:oid "1.3.6.1.4.1.9.12.3.1.3.666";
  }

  smiv2:alias "cevChassisUc520s16U4FxoWK9" {
    smiv2:oid "1.3.6.1.4.1.9.12.3.1.3.667";
  }

  smiv2:alias "cevChassisUc520s16U2BriK9" {
    smiv2:oid "1.3.6.1.4.1.9.12.3.1.3.668";
  }

  smiv2:alias "cevChassisUc520s16U2BriWK9" {
    smiv2:oid "1.3.6.1.4.1.9.12.3.1.3.669";
  }

  smiv2:alias "cevChassisUc520m32U8FxoK9" {
    smiv2:oid "1.3.6.1.4.1.9.12.3.1.3.670";
  }

  smiv2:alias "cevChassisUc520m32U8FxoW" {
    smiv2:oid "1.3.6.1.4.1.9.12.3.1.3.671";
  }

  smiv2:alias "cevChassisUc520m32U4BriK9" {
    smiv2:oid "1.3.6.1.4.1.9.12.3.1.3.672";
  }

  smiv2:alias "cevChassisUc520m32U4BriW" {
    smiv2:oid "1.3.6.1.4.1.9.12.3.1.3.673";
  }

  smiv2:alias "cevChassisUc520m48U12FxoK9" {
    smiv2:oid "1.3.6.1.4.1.9.12.3.1.3.674";
  }

  smiv2:alias "cevChassisUc520m48U12FxoW" {
    smiv2:oid "1.3.6.1.4.1.9.12.3.1.3.675";
  }

  smiv2:alias "cevChassisUc520m48U6BriK9" {
    smiv2:oid "1.3.6.1.4.1.9.12.3.1.3.676";
  }

  smiv2:alias "cevChassisUc520m48U6BriW" {
    smiv2:oid "1.3.6.1.4.1.9.12.3.1.3.677";
  }

  smiv2:alias "cevChassisUc520m48U1T1E1FK9" {
    smiv2:oid "1.3.6.1.4.1.9.12.3.1.3.678";
  }

  smiv2:alias "cevChassisUc520m48U1T1E1BK9" {
    smiv2:oid "1.3.6.1.4.1.9.12.3.1.3.679";
  }

  smiv2:alias "cevChassisCE5208PC" {
    smiv2:oid "1.3.6.1.4.1.9.12.3.1.3.680";
  }

  smiv2:alias "cevChassis7828H" {
    smiv2:oid "1.3.6.1.4.1.9.12.3.1.3.681";
  }

  smiv2:alias "cevChassis7816I" {
    smiv2:oid "1.3.6.1.4.1.9.12.3.1.3.682";
  }

  smiv2:alias "cevChassis7828I" {
    smiv2:oid "1.3.6.1.4.1.9.12.3.1.3.683";
  }

  smiv2:alias "cevChassis1861Uc2BK9" {
    smiv2:oid "1.3.6.1.4.1.9.12.3.1.3.684";
  }

  smiv2:alias "cevChassis1861Uc4FK9" {
    smiv2:oid "1.3.6.1.4.1.9.12.3.1.3.685";
  }

  smiv2:alias "cevChassis1861Srst2BK9" {
    smiv2:oid "1.3.6.1.4.1.9.12.3.1.3.686";
  }

  smiv2:alias "cevChassis1861Srst4FK9" {
    smiv2:oid "1.3.6.1.4.1.9.12.3.1.3.687";
  }

  smiv2:alias "cevChassisOe7330K9" {
    smiv2:oid "1.3.6.1.4.1.9.12.3.1.3.688";
  }

  smiv2:alias "cevChassisOe7350K9" {
    smiv2:oid "1.3.6.1.4.1.9.12.3.1.3.689";
  }

  smiv2:alias "cevChassisCat296048TCS" {
    smiv2:oid "1.3.6.1.4.1.9.12.3.1.3.694";
  }

  smiv2:alias "cevChassisCat296024TCS" {
    smiv2:oid "1.3.6.1.4.1.9.12.3.1.3.695";
  }

  smiv2:alias "cevChassisCat296024S" {
    smiv2:oid "1.3.6.1.4.1.9.12.3.1.3.696";
  }

  smiv2:alias "cevChassisCat296024PC" {
    smiv2:oid "1.3.6.1.4.1.9.12.3.1.3.697";
  }

  smiv2:alias "cevChassisCat296024LT" {
    smiv2:oid "1.3.6.1.4.1.9.12.3.1.3.698";
  }

  smiv2:alias "cevChassisCat2960PD8TT" {
    smiv2:oid "1.3.6.1.4.1.9.12.3.1.3.699";
  }

  smiv2:alias "cevChassisASR1002" {
    smiv2:oid "1.3.6.1.4.1.9.12.3.1.3.700";
  }

  smiv2:alias "cevChassisASR1004" {
    smiv2:oid "1.3.6.1.4.1.9.12.3.1.3.701";
  }

  smiv2:alias "cevChassisASR1006" {
    smiv2:oid "1.3.6.1.4.1.9.12.3.1.3.702";
  }

  smiv2:alias "cevChassisWsC4900M" {
    smiv2:oid "1.3.6.1.4.1.9.12.3.1.3.703";
  }

  smiv2:alias "cevChassisASA5580" {
    smiv2:oid "1.3.6.1.4.1.9.12.3.1.3.704";
  }

  smiv2:alias "cevChassisCatRfgw" {
    smiv2:oid "1.3.6.1.4.1.9.12.3.1.3.705";
  }

  smiv2:alias "cevChassisCE52024PC" {
    smiv2:oid "1.3.6.1.4.1.9.12.3.1.3.706";
  }

  smiv2:alias "cevChassisCE52024LC" {
    smiv2:oid "1.3.6.1.4.1.9.12.3.1.3.707";
  }

  smiv2:alias "cevChassisCE52024TT" {
    smiv2:oid "1.3.6.1.4.1.9.12.3.1.3.708";
  }

  smiv2:alias "cevChassisCE520G24TC" {
    smiv2:oid "1.3.6.1.4.1.9.12.3.1.3.709";
  }

  smiv2:alias "cevChassis1861Srst2BCueK9" {
    smiv2:oid "1.3.6.1.4.1.9.12.3.1.3.710";
  }

  smiv2:alias "cevChassis1861Srst4FCueK9" {
    smiv2:oid "1.3.6.1.4.1.9.12.3.1.3.711";
  }

  smiv2:alias "cevChassisVgd1t3" {
    smiv2:oid "1.3.6.1.4.1.9.12.3.1.3.712";
  }

  smiv2:alias "cevChassisCat3560e12d" {
    smiv2:oid "1.3.6.1.4.1.9.12.3.1.3.718";
  }

  smiv2:alias "cevChassisN5kC5020pBf" {
    smiv2:oid "1.3.6.1.4.1.9.12.3.1.3.719";
  }

  smiv2:alias "cevChassisN5kC5020pBd" {
    smiv2:oid "1.3.6.1.4.1.9.12.3.1.3.720";
  }

  smiv2:alias "cevChassisCat3560E12SD" {
    smiv2:oid "1.3.6.1.4.1.9.12.3.1.3.721";
  }

  smiv2:alias "cevChassisOe674" {
    smiv2:oid "1.3.6.1.4.1.9.12.3.1.3.722";
  }

  smiv2:alias "cevChassisIE30004TC" {
    smiv2:oid "1.3.6.1.4.1.9.12.3.1.3.723";
  }

  smiv2:alias "cevChassisIE30008TC" {
    smiv2:oid "1.3.6.1.4.1.9.12.3.1.3.724";
  }

  smiv2:alias "cevChassisRAIE1783MS06" {
    smiv2:oid "1.3.6.1.4.1.9.12.3.1.3.725";
  }

  smiv2:alias "cevChassisRAIE1783MS10T" {
    smiv2:oid "1.3.6.1.4.1.9.12.3.1.3.726";
  }

  smiv2:alias "cevChassis2435Iad8Fxs" {
    smiv2:oid "1.3.6.1.4.1.9.12.3.1.3.727";
  }

  smiv2:alias "cevChassisVG204" {
    smiv2:oid "1.3.6.1.4.1.9.12.3.1.3.728";
  }

  smiv2:alias "cevChassisVG202" {
    smiv2:oid "1.3.6.1.4.1.9.12.3.1.3.729";
  }

  smiv2:alias "cevChassisCat291824TT" {
    smiv2:oid "1.3.6.1.4.1.9.12.3.1.3.730";
  }

  smiv2:alias "cevChassisCat291824TC" {
    smiv2:oid "1.3.6.1.4.1.9.12.3.1.3.731";
  }

  smiv2:alias "cevChassisCat291848TT" {
    smiv2:oid "1.3.6.1.4.1.9.12.3.1.3.732";
  }

  smiv2:alias "cevChassisCat291848TC" {
    smiv2:oid "1.3.6.1.4.1.9.12.3.1.3.733";
  }

  smiv2:alias "cevChassis1805" {
    smiv2:oid "1.3.6.1.4.1.9.12.3.1.3.734";
  }

  smiv2:alias "cevChassisUc52024u4briK9" {
    smiv2:oid "1.3.6.1.4.1.9.12.3.1.3.735";
  }

  smiv2:alias "cevChassisUc52024u8fxoK9" {
    smiv2:oid "1.3.6.1.4.1.9.12.3.1.3.736";
  }

  smiv2:alias "cevChassisUc520s8u2briWJK9" {
    smiv2:oid "1.3.6.1.4.1.9.12.3.1.3.737";
  }

  smiv2:alias "cevChassisUc520s16u2briWJK9" {
    smiv2:oid "1.3.6.1.4.1.9.12.3.1.3.738";
  }

  smiv2:alias "cevChassisVSIntSP" {
    smiv2:oid "1.3.6.1.4.1.9.12.3.1.3.739";
  }

  smiv2:alias "cevChassisVSSP" {
    smiv2:oid "1.3.6.1.4.1.9.12.3.1.3.740";
  }

  smiv2:alias "cevChassisVSHydecoder" {
    smiv2:oid "1.3.6.1.4.1.9.12.3.1.3.741";
  }

  smiv2:alias "cevChassisVSDecoder" {
    smiv2:oid "1.3.6.1.4.1.9.12.3.1.3.742";
  }

  smiv2:alias "cevChassisVSEncoder1P" {
    smiv2:oid "1.3.6.1.4.1.9.12.3.1.3.743";
  }

  smiv2:alias "cevChassisCiscoMwr2941Dc" {
    smiv2:oid "1.3.6.1.4.1.9.12.3.1.3.745";
  }

  smiv2:alias "cevChassisOe574" {
    smiv2:oid "1.3.6.1.4.1.9.12.3.1.3.746";
  }

  smiv2:alias "cevChassisOe474" {
    smiv2:oid "1.3.6.1.4.1.9.12.3.1.3.747";
  }

  smiv2:alias "cevChassisOe274" {
    smiv2:oid "1.3.6.1.4.1.9.12.3.1.3.748";
  }

  smiv2:alias "cevChassis7816c" {
    smiv2:oid "1.3.6.1.4.1.9.12.3.1.3.749";
  }

  smiv2:alias "cevChassisAp801agn" {
    smiv2:oid "1.3.6.1.4.1.9.12.3.1.3.750";
  }

  smiv2:alias "cevChassisAp801gn" {
    smiv2:oid "1.3.6.1.4.1.9.12.3.1.3.751";
  }

  smiv2:alias "cevChassisC1861WSrst4FCueK9" {
    smiv2:oid "1.3.6.1.4.1.9.12.3.1.3.752";
  }

  smiv2:alias "cevChassisC1861WSrst2BCueK9" {
    smiv2:oid "1.3.6.1.4.1.9.12.3.1.3.753";
  }

  smiv2:alias "cevChassisC1861WSrst4FK9" {
    smiv2:oid "1.3.6.1.4.1.9.12.3.1.3.754";
  }

  smiv2:alias "cevChassisC1861WSrst2BK9" {
    smiv2:oid "1.3.6.1.4.1.9.12.3.1.3.755";
  }

  smiv2:alias "cevChassisC1861WUc4FK9" {
    smiv2:oid "1.3.6.1.4.1.9.12.3.1.3.756";
  }

  smiv2:alias "cevChassisC1861WUc2BK9" {
    smiv2:oid "1.3.6.1.4.1.9.12.3.1.3.757";
  }

  smiv2:alias "cevChassisMe3400e24tsM" {
    smiv2:oid "1.3.6.1.4.1.9.12.3.1.3.758";
  }

  smiv2:alias "cevChassisMe3400eg12csM" {
    smiv2:oid "1.3.6.1.4.1.9.12.3.1.3.759";
  }

  smiv2:alias "cevChassisMe3400eg2csA" {
    smiv2:oid "1.3.6.1.4.1.9.12.3.1.3.760";
  }

  smiv2:alias "cevChassisCe674" {
    smiv2:oid "1.3.6.1.4.1.9.12.3.1.3.761";
  }

  smiv2:alias "cevChassisCAM35" {
    smiv2:oid "1.3.6.1.4.1.9.12.3.1.3.762";
  }

  smiv2:alias "cevChassisCe7341" {
    smiv2:oid "1.3.6.1.4.1.9.12.3.1.3.763";
  }

  smiv2:alias "cevChassisCe7371" {
    smiv2:oid "1.3.6.1.4.1.9.12.3.1.3.764";
  }

  smiv2:alias "cevChassisWsCbs3125gS" {
    smiv2:oid "1.3.6.1.4.1.9.12.3.1.3.768";
  }

  smiv2:alias "cevChassisWsC492810GE" {
    smiv2:oid "1.3.6.1.4.1.9.12.3.1.3.770";
  }

  smiv2:alias "cevChassisCat296048TTS" {
    smiv2:oid "1.3.6.1.4.1.9.12.3.1.3.771";
  }

  smiv2:alias "cevChassisCat29608TCS" {
    smiv2:oid "1.3.6.1.4.1.9.12.3.1.3.772";
  }

  smiv2:alias "cevChassisSr520FE" {
    smiv2:oid "1.3.6.1.4.1.9.12.3.1.3.774";
  }

  smiv2:alias "cevChassisSr520ADSL" {
    smiv2:oid "1.3.6.1.4.1.9.12.3.1.3.775";
  }

  smiv2:alias "cevChassisSr520ADSLi" {
    smiv2:oid "1.3.6.1.4.1.9.12.3.1.3.776";
  }

  smiv2:alias "cevChassisN7Kc7018" {
    smiv2:oid "1.3.6.1.4.1.9.12.3.1.3.777";
  }

  smiv2:alias "cevChassisCat356012PCS" {
    smiv2:oid "1.3.6.1.4.1.9.12.3.1.3.778";
  }

  smiv2:alias "cevChassisCat296048PSTL" {
    smiv2:oid "1.3.6.1.4.1.9.12.3.1.3.779";
  }

  smiv2:alias "cevChassisASR9010" {
    smiv2:oid "1.3.6.1.4.1.9.12.3.1.3.780";
  }

  smiv2:alias "cevChassisASR9006" {
    smiv2:oid "1.3.6.1.4.1.9.12.3.1.3.781";
  }

  smiv2:alias "cevChassisASR14K4" {
    smiv2:oid "1.3.6.1.4.1.9.12.3.1.3.782";
  }

  smiv2:alias "cevChassisASR14K8" {
    smiv2:oid "1.3.6.1.4.1.9.12.3.1.3.783";
  }

  smiv2:alias "cevChassisCat3560v224tsD" {
    smiv2:oid "1.3.6.1.4.1.9.12.3.1.3.784";
  }

  smiv2:alias "cevChassisCat3560v224ts" {
    smiv2:oid "1.3.6.1.4.1.9.12.3.1.3.785";
  }

  smiv2:alias "cevChassisCat3560v224ps" {
    smiv2:oid "1.3.6.1.4.1.9.12.3.1.3.786";
  }

  smiv2:alias "cevChassisCat3750v224ts" {
    smiv2:oid "1.3.6.1.4.1.9.12.3.1.3.787";
  }

  smiv2:alias "cevChassisCat3750v224ps" {
    smiv2:oid "1.3.6.1.4.1.9.12.3.1.3.788";
  }

  smiv2:alias "cevChassisCat3560v248ts" {
    smiv2:oid "1.3.6.1.4.1.9.12.3.1.3.789";
  }

  smiv2:alias "cevChassisCat3560v248ps" {
    smiv2:oid "1.3.6.1.4.1.9.12.3.1.3.790";
  }

  smiv2:alias "cevChassisCat3750v248ts" {
    smiv2:oid "1.3.6.1.4.1.9.12.3.1.3.791";
  }

  smiv2:alias "cevChassisCat3750v248ps" {
    smiv2:oid "1.3.6.1.4.1.9.12.3.1.3.792";
  }

  smiv2:alias "cevChassisAirbr1430" {
    smiv2:oid "1.3.6.1.4.1.9.12.3.1.3.793";
  }

  smiv2:alias "cevChassisNamApp2204rj45" {
    smiv2:oid "1.3.6.1.4.1.9.12.3.1.3.794";
  }

  smiv2:alias "cevChassisNamApp2220" {
    smiv2:oid "1.3.6.1.4.1.9.12.3.1.3.795";
  }

  smiv2:alias "cevChassisAIRAP1141" {
    smiv2:oid "1.3.6.1.4.1.9.12.3.1.3.796";
  }

  smiv2:alias "cevChassisAIRAP1142" {
    smiv2:oid "1.3.6.1.4.1.9.12.3.1.3.797";
  }

  smiv2:alias "cevChassisN5kC5010pBf" {
    smiv2:oid "1.3.6.1.4.1.9.12.3.1.3.798";
  }

  smiv2:alias "cevChassisASR9010DC" {
    smiv2:oid "1.3.6.1.4.1.9.12.3.1.3.799";
  }

  smiv2:alias "cevChassisASR9006DC" {
    smiv2:oid "1.3.6.1.4.1.9.12.3.1.3.800";
  }

  smiv2:alias "cevChassis18xxx" {
    smiv2:oid "1.3.6.1.4.1.9.12.3.1.3.801";
  }

  smiv2:alias "cevChassisc887Vdsl2" {
    smiv2:oid "1.3.6.1.4.1.9.12.3.1.3.802";
  }

  smiv2:alias "cevChassisC1941" {
    smiv2:oid "1.3.6.1.4.1.9.12.3.1.3.803";
  }

  smiv2:alias "cevChassisC2901" {
    smiv2:oid "1.3.6.1.4.1.9.12.3.1.3.804";
  }

  smiv2:alias "cevChassisC2911" {
    smiv2:oid "1.3.6.1.4.1.9.12.3.1.3.805";
  }

  smiv2:alias "cevChassisC2921" {
    smiv2:oid "1.3.6.1.4.1.9.12.3.1.3.806";
  }

  smiv2:alias "cevChassisC2951" {
    smiv2:oid "1.3.6.1.4.1.9.12.3.1.3.807";
  }

  smiv2:alias "cevChassisC3925" {
    smiv2:oid "1.3.6.1.4.1.9.12.3.1.3.808";
  }

  smiv2:alias "cevChassisC3945" {
    smiv2:oid "1.3.6.1.4.1.9.12.3.1.3.809";
  }

  smiv2:alias "cevChassisEsw52024pK9" {
    smiv2:oid "1.3.6.1.4.1.9.12.3.1.3.810";
  }

  smiv2:alias "cevChassisEsw54024pK9" {
    smiv2:oid "1.3.6.1.4.1.9.12.3.1.3.811";
  }

  smiv2:alias "cevChassisEsw52048pK9" {
    smiv2:oid "1.3.6.1.4.1.9.12.3.1.3.812";
  }

  smiv2:alias "cevChassisEsw52024K9" {
    smiv2:oid "1.3.6.1.4.1.9.12.3.1.3.813";
  }

  smiv2:alias "cevChassisEsw54024K9" {
    smiv2:oid "1.3.6.1.4.1.9.12.3.1.3.814";
  }

  smiv2:alias "cevChassisEsw52048K9" {
    smiv2:oid "1.3.6.1.4.1.9.12.3.1.3.815";
  }

  smiv2:alias "cevChassisEsw54048K9" {
    smiv2:oid "1.3.6.1.4.1.9.12.3.1.3.816";
  }

  smiv2:alias "cevChassisNamApp2204sfp" {
    smiv2:oid "1.3.6.1.4.1.9.12.3.1.3.817";
  }

  smiv2:alias "cevChassisSR520T1" {
    smiv2:oid "1.3.6.1.4.1.9.12.3.1.3.818";
  }

  smiv2:alias "cevChassisN2kC2148T1GE" {
    smiv2:oid "1.3.6.1.4.1.9.12.3.1.3.820";
  }

  smiv2:alias "cevChassisC1941W" {
    smiv2:oid "1.3.6.1.4.1.9.12.3.1.3.827";
  }

  smiv2:alias "cevChassisC888E" {
    smiv2:oid "1.3.6.1.4.1.9.12.3.1.3.828";
  }

  smiv2:alias "cevChassisC888EG" {
    smiv2:oid "1.3.6.1.4.1.9.12.3.1.3.829";
  }

  smiv2:alias "cevChassisIad888EF" {
    smiv2:oid "1.3.6.1.4.1.9.12.3.1.3.830";
  }

  smiv2:alias "cevChassisIad888EB" {
    smiv2:oid "1.3.6.1.4.1.9.12.3.1.3.831";
  }

  smiv2:alias "cevChassisC888ESRST" {
    smiv2:oid "1.3.6.1.4.1.9.12.3.1.3.832";
  }

  smiv2:alias "cevChassis3845nv" {
    smiv2:oid "1.3.6.1.4.1.9.12.3.1.3.833";
  }

  smiv2:alias "cevChassis3825nv" {
    smiv2:oid "1.3.6.1.4.1.9.12.3.1.3.834";
  }

  smiv2:alias "cevChassisWSC235048TD" {
    smiv2:oid "1.3.6.1.4.1.9.12.3.1.3.836";
  }

  smiv2:alias "cevChassis887M" {
    smiv2:oid "1.3.6.1.4.1.9.12.3.1.3.837";
  }

  smiv2:alias "cevChassisASR9010AC" {
    smiv2:oid "1.3.6.1.4.1.9.12.3.1.3.838";
  }

  smiv2:alias "cevChassisASR9006AC" {
    smiv2:oid "1.3.6.1.4.1.9.12.3.1.3.839";
  }

  smiv2:alias "cevChassisN1KV" {
    smiv2:oid "1.3.6.1.4.1.9.12.3.1.3.840";
  }

  smiv2:alias "cevChassisUCSN10S6100" {
    smiv2:oid "1.3.6.1.4.1.9.12.3.1.3.847";
  }

  smiv2:alias "cevChassisCDScde420" {
    smiv2:oid "1.3.6.1.4.1.9.12.3.1.3.848";
  }

  smiv2:alias "cevChassisCDScde220" {
    smiv2:oid "1.3.6.1.4.1.9.12.3.1.3.849";
  }

  smiv2:alias "cevChassisCDScde110" {
    smiv2:oid "1.3.6.1.4.1.9.12.3.1.3.850";
  }

  smiv2:alias "cevChassisCiscoCeVirtualBlade" {
    smiv2:oid "1.3.6.1.4.1.9.12.3.1.3.851";
  }

  smiv2:alias "cevChassisASR1002F" {
    smiv2:oid "1.3.6.1.4.1.9.12.3.1.3.852";
  }

  smiv2:alias "cevChassisADE2120" {
    smiv2:oid "1.3.6.1.4.1.9.12.3.1.3.853";
  }

  smiv2:alias "cevChassisAIRAP3501" {
    smiv2:oid "1.3.6.1.4.1.9.12.3.1.3.860";
  }

  smiv2:alias "cevChassisAIRAP3502" {
    smiv2:oid "1.3.6.1.4.1.9.12.3.1.3.861";
  }

  smiv2:alias "cevChassisCDScde200" {
    smiv2:oid "1.3.6.1.4.1.9.12.3.1.3.862";
  }

  smiv2:alias "cevChassisCDScde100" {
    smiv2:oid "1.3.6.1.4.1.9.12.3.1.3.863";
  }

  smiv2:alias "cevChassisCDScde300" {
    smiv2:oid "1.3.6.1.4.1.9.12.3.1.3.864";
  }

  smiv2:alias "cevChassisCDScde400" {
    smiv2:oid "1.3.6.1.4.1.9.12.3.1.3.865";
  }

  smiv2:alias "cevChassisSps2004B" {
    smiv2:oid "1.3.6.1.4.1.9.12.3.1.3.869";
  }

  smiv2:alias "cevChassisSps204B" {
    smiv2:oid "1.3.6.1.4.1.9.12.3.1.3.870";
  }

  smiv2:alias "cevChassisAp541nAK9" {
    smiv2:oid "1.3.6.1.4.1.9.12.3.1.3.874";
  }

  smiv2:alias "cevChassisAp541nEK9" {
    smiv2:oid "1.3.6.1.4.1.9.12.3.1.3.875";
  }

  smiv2:alias "cevChassisAp541nNK9" {
    smiv2:oid "1.3.6.1.4.1.9.12.3.1.3.876";
  }

  smiv2:alias "cevChassisSRP521" {
    smiv2:oid "1.3.6.1.4.1.9.12.3.1.3.877";
  }

  smiv2:alias "cevChassisSRP526" {
    smiv2:oid "1.3.6.1.4.1.9.12.3.1.3.878";
  }

  smiv2:alias "cevChassisSRP527" {
    smiv2:oid "1.3.6.1.4.1.9.12.3.1.3.879";
  }

  smiv2:alias "cevChassisSRP541" {
    smiv2:oid "1.3.6.1.4.1.9.12.3.1.3.880";
  }

  smiv2:alias "cevChassisSRP546" {
    smiv2:oid "1.3.6.1.4.1.9.12.3.1.3.881";
  }

  smiv2:alias "cevChassisSRP547" {
    smiv2:oid "1.3.6.1.4.1.9.12.3.1.3.882";
  }

  smiv2:alias "cevChassisVS510FXO" {
    smiv2:oid "1.3.6.1.4.1.9.12.3.1.3.883";
  }

  smiv2:alias "cevChassis887GVdsl2" {
    smiv2:oid "1.3.6.1.4.1.9.12.3.1.3.884";
  }

  smiv2:alias "cevChassis887SrstVdsl2" {
    smiv2:oid "1.3.6.1.4.1.9.12.3.1.3.885";
  }

  smiv2:alias "cevChassis59xx" {
    smiv2:oid "1.3.6.1.4.1.9.12.3.1.3.895";
  }

  smiv2:alias "cevChassisCat296024LCS" {
    smiv2:oid "1.3.6.1.4.1.9.12.3.1.3.896";
  }

  smiv2:alias "cevChassisCat296024PCS" {
    smiv2:oid "1.3.6.1.4.1.9.12.3.1.3.897";
  }

  smiv2:alias "cevChassisCat296048PSTS" {
    smiv2:oid "1.3.6.1.4.1.9.12.3.1.3.898";
  }

  smiv2:alias "cevChassisCiscoNMWAE900" {
    smiv2:oid "1.3.6.1.4.1.9.12.3.1.3.900";
  }

  smiv2:alias "cevChassisCiscoNMWAE700" {
    smiv2:oid "1.3.6.1.4.1.9.12.3.1.3.901";
  }

  smiv2:alias "cevChassis5940" {
    smiv2:oid "1.3.6.1.4.1.9.12.3.1.3.902";
  }

  smiv2:alias "cevChassisN4KIBMEth" {
    smiv2:oid "1.3.6.1.4.1.9.12.3.1.3.903";
  }

  smiv2:alias "cevChassisASR1001" {
    smiv2:oid "1.3.6.1.4.1.9.12.3.1.3.904";
  }

  smiv2:alias "cevChassisASR1013" {
    smiv2:oid "1.3.6.1.4.1.9.12.3.1.3.905";
  }

  smiv2:alias "cevChassisCDScde205" {
    smiv2:oid "1.3.6.1.4.1.9.12.3.1.3.906";
  }

  smiv2:alias "cevChassisNexus1010" {
    smiv2:oid "1.3.6.1.4.1.9.12.3.1.3.907";
  }

  smiv2:alias "cevChassisRaie1783Rms06t" {
    smiv2:oid "1.3.6.1.4.1.9.12.3.1.3.908";
  }

  smiv2:alias "cevChassisRaie1783Rms10t" {
    smiv2:oid "1.3.6.1.4.1.9.12.3.1.3.909";
  }

  smiv2:alias "cevChassisMXE5600" {
    smiv2:oid "1.3.6.1.4.1.9.12.3.1.3.910";
  }

  smiv2:alias "cevChassisEsw5408pK9" {
    smiv2:oid "1.3.6.1.4.1.9.12.3.1.3.911";
  }

  smiv2:alias "cevChassisEsw5208pK9" {
    smiv2:oid "1.3.6.1.4.1.9.12.3.1.3.912";
  }

  smiv2:alias "cevChassisN2kC2232PP10GE" {
    smiv2:oid "1.3.6.1.4.1.9.12.3.1.3.913";
  }

  smiv2:alias "cevChassisN2kC2248TP1GE" {
    smiv2:oid "1.3.6.1.4.1.9.12.3.1.3.914";
  }

  smiv2:alias "cevChassisWsC4948e10GE" {
    smiv2:oid "1.3.6.1.4.1.9.12.3.1.3.915";
  }

  smiv2:alias "cevChassis1921k9" {
    smiv2:oid "1.3.6.1.4.1.9.12.3.1.3.928";
  }

  smiv2:alias "cevChassis1905k9" {
    smiv2:oid "1.3.6.1.4.1.9.12.3.1.3.929";
  }

  smiv2:alias "cevChassisN4KIBMCiscoEth" {
    smiv2:oid "1.3.6.1.4.1.9.12.3.1.3.930";
  }

  smiv2:alias "cevChassisASA5585" {
    smiv2:oid "1.3.6.1.4.1.9.12.3.1.3.931";
  }

  smiv2:alias "cevChassisN7Kc7009" {
    smiv2:oid "1.3.6.1.4.1.9.12.3.1.3.932";
  }

  smiv2:alias "cevChassisMwr2941DcA" {
    smiv2:oid "1.3.6.1.4.1.9.12.3.1.3.933";
  }

  smiv2:alias "cevChassisOeNm302" {
    smiv2:oid "1.3.6.1.4.1.9.12.3.1.3.937";
  }

  smiv2:alias "cevChassisOeNm502" {
    smiv2:oid "1.3.6.1.4.1.9.12.3.1.3.938";
  }

  smiv2:alias "cevChassisOeNm522" {
    smiv2:oid "1.3.6.1.4.1.9.12.3.1.3.939";
  }

  smiv2:alias "cevChassisOeSmSre700" {
    smiv2:oid "1.3.6.1.4.1.9.12.3.1.3.940";
  }

  smiv2:alias "cevChassisOeSmSre900" {
    smiv2:oid "1.3.6.1.4.1.9.12.3.1.3.941";
  }

  smiv2:alias "cevChassisCDScde2202s3" {
    smiv2:oid "1.3.6.1.4.1.9.12.3.1.3.944";
  }

  smiv2:alias "cevChassisWsC3750x24" {
    smiv2:oid "1.3.6.1.4.1.9.12.3.1.3.945";
  }

  smiv2:alias "cevChassisWsC3750x48" {
    smiv2:oid "1.3.6.1.4.1.9.12.3.1.3.946";
  }

  smiv2:alias "cevChassisWsC3750x24P" {
    smiv2:oid "1.3.6.1.4.1.9.12.3.1.3.947";
  }

  smiv2:alias "cevChassisWsC3750x48P" {
    smiv2:oid "1.3.6.1.4.1.9.12.3.1.3.948";
  }

  smiv2:alias "cevChassisWsC3560x24" {
    smiv2:oid "1.3.6.1.4.1.9.12.3.1.3.949";
  }

  smiv2:alias "cevChassisWsC3560x48" {
    smiv2:oid "1.3.6.1.4.1.9.12.3.1.3.950";
  }

  smiv2:alias "cevChassis1841Ck9" {
    smiv2:oid "1.3.6.1.4.1.9.12.3.1.3.957";
  }

  smiv2:alias "cevChassis2801Ck9" {
    smiv2:oid "1.3.6.1.4.1.9.12.3.1.3.958";
  }

  smiv2:alias "cevChassis2811Ck9" {
    smiv2:oid "1.3.6.1.4.1.9.12.3.1.3.959";
  }

  smiv2:alias "cevChassis2821Ck9" {
    smiv2:oid "1.3.6.1.4.1.9.12.3.1.3.960";
  }

  smiv2:alias "cevChassis3825Ck9" {
    smiv2:oid "1.3.6.1.4.1.9.12.3.1.3.962";
  }

  smiv2:alias "cevChassis3845Ck9" {
    smiv2:oid "1.3.6.1.4.1.9.12.3.1.3.963";
  }

  smiv2:alias "cevChassisAIRAP1262" {
    smiv2:oid "1.3.6.1.4.1.9.12.3.1.3.966";
  }

  smiv2:alias "cevChassisAIRAP1261" {
    smiv2:oid "1.3.6.1.4.1.9.12.3.1.3.967";
  }

  smiv2:alias "cevChassis892F" {
    smiv2:oid "1.3.6.1.4.1.9.12.3.1.3.968";
  }

  smiv2:alias "cevChassisMe3600x24fsM" {
    smiv2:oid "1.3.6.1.4.1.9.12.3.1.3.969";
  }

  smiv2:alias "cevChassisMe3600x24tsM" {
    smiv2:oid "1.3.6.1.4.1.9.12.3.1.3.970";
  }

  smiv2:alias "cevChassisMe3800x24fsM" {
    smiv2:oid "1.3.6.1.4.1.9.12.3.1.3.971";
  }

  smiv2:alias "cevChassisCGR2010" {
    smiv2:oid "1.3.6.1.4.1.9.12.3.1.3.972";
  }

  smiv2:alias "cevChassisWsC2960s48tsS" {
    smiv2:oid "1.3.6.1.4.1.9.12.3.1.3.973";
  }

  smiv2:alias "cevChassisWsC2960s24tsS" {
    smiv2:oid "1.3.6.1.4.1.9.12.3.1.3.974";
  }

  smiv2:alias "cevChassisWsC2960s48fpdL" {
    smiv2:oid "1.3.6.1.4.1.9.12.3.1.3.975";
  }

  smiv2:alias "cevChassisWsC2960s48lpdL" {
    smiv2:oid "1.3.6.1.4.1.9.12.3.1.3.976";
  }

  smiv2:alias "cevChassisWsC2960s48tdL" {
    smiv2:oid "1.3.6.1.4.1.9.12.3.1.3.977";
  }

  smiv2:alias "cevChassisWsC2960s24pdL" {
    smiv2:oid "1.3.6.1.4.1.9.12.3.1.3.978";
  }

  smiv2:alias "cevChassisWsC2960s24tdL" {
    smiv2:oid "1.3.6.1.4.1.9.12.3.1.3.979";
  }

  smiv2:alias "cevChassisWsC2960s48fpsL" {
    smiv2:oid "1.3.6.1.4.1.9.12.3.1.3.980";
  }

  smiv2:alias "cevChassisWsC2960s48lpsL" {
    smiv2:oid "1.3.6.1.4.1.9.12.3.1.3.981";
  }

  smiv2:alias "cevChassisWsC2960s24psL" {
    smiv2:oid "1.3.6.1.4.1.9.12.3.1.3.982";
  }

  smiv2:alias "cevChassisWsC2960s48tsL" {
    smiv2:oid "1.3.6.1.4.1.9.12.3.1.3.983";
  }

  smiv2:alias "cevChassisWsC2960S24tsL" {
    smiv2:oid "1.3.6.1.4.1.9.12.3.1.3.984";
  }

  smiv2:alias "cevChassis1906Ck9" {
    smiv2:oid "1.3.6.1.4.1.9.12.3.1.3.985";
  }

  smiv2:alias "cevChassisAIRAP1042" {
    smiv2:oid "1.3.6.1.4.1.9.12.3.1.3.986";
  }

  smiv2:alias "cevChassisAIRAP1041" {
    smiv2:oid "1.3.6.1.4.1.9.12.3.1.3.987";
  }

  smiv2:alias "cevChassis887Va" {
    smiv2:oid "1.3.6.1.4.1.9.12.3.1.3.988";
  }

  smiv2:alias "cevChassis886Va" {
    smiv2:oid "1.3.6.1.4.1.9.12.3.1.3.989";
  }

  smiv2:alias "cevChassis867Va" {
    smiv2:oid "1.3.6.1.4.1.9.12.3.1.3.990";
  }

  smiv2:alias "cevChassis887VaM" {
    smiv2:oid "1.3.6.1.4.1.9.12.3.1.3.991";
  }

  smiv2:alias "cevChassisASR1001IDC2pOc3Pos" {
    smiv2:oid "1.3.6.1.4.1.9.12.3.1.3.992";
  }

  smiv2:alias "cevChassisASR1001IDC4pT3" {
    smiv2:oid "1.3.6.1.4.1.9.12.3.1.3.993";
  }

  smiv2:alias "cevChassisASR1001IDC4pGE" {
    smiv2:oid "1.3.6.1.4.1.9.12.3.1.3.994";
  }

  smiv2:alias "cevChassisASR1001IDC8pCT1E1" {
    smiv2:oid "1.3.6.1.4.1.9.12.3.1.3.995";
  }

  smiv2:alias "cevChassisASR1001IDCHDD" {
    smiv2:oid "1.3.6.1.4.1.9.12.3.1.3.996";
  }

  smiv2:alias "cevChassisCat2960cPD8TT" {
    smiv2:oid "1.3.6.1.4.1.9.12.3.1.3.997";
  }

  smiv2:alias "cevChassisCGS252024TC" {
    smiv2:oid "1.3.6.1.4.1.9.12.3.1.3.998";
  }

  smiv2:alias "cevChassisCGS252016S8PC" {
    smiv2:oid "1.3.6.1.4.1.9.12.3.1.3.999";
  }

  smiv2:alias "cevChassisWsC236048TdS" {
    smiv2:oid "1.3.6.1.4.1.9.12.3.1.3.1002";
  }

  smiv2:alias "cevChassisN2kC2232TT10GE" {
    smiv2:oid "1.3.6.1.4.1.9.12.3.1.3.1003";
  }

  smiv2:alias "cevChassisN2kC2232TP10GE" {
    smiv2:oid "1.3.6.1.4.1.9.12.3.1.3.1004";
  }

  smiv2:alias "cevChassisN2kC2248TT1GE" {
    smiv2:oid "1.3.6.1.4.1.9.12.3.1.3.1005";
  }

  smiv2:alias "cevChassisN2kC2224TP1GE" {
    smiv2:oid "1.3.6.1.4.1.9.12.3.1.3.1006";
  }

  smiv2:alias "cevChassisCDScde250" {
    smiv2:oid "1.3.6.1.4.1.9.12.3.1.3.1007";
  }

  smiv2:alias "cevChassisN5kC5548p" {
    smiv2:oid "1.3.6.1.4.1.9.12.3.1.3.1008";
  }

  smiv2:alias "cevChassis881G2" {
    smiv2:oid "1.3.6.1.4.1.9.12.3.1.3.1009";
  }

  smiv2:alias "cevChassisWsC3750v224fsS" {
    smiv2:oid "1.3.6.1.4.1.9.12.3.1.3.1010";
  }

  smiv2:alias "cevChassisOeVWaas" {
    smiv2:oid "1.3.6.1.4.1.9.12.3.1.3.1011";
  }

  smiv2:alias "cevChassisCrs16SB" {
    smiv2:oid "1.3.6.1.4.1.9.12.3.1.3.1012";
  }

  smiv2:alias "cevChassisCat2960cG8TC" {
    smiv2:oid "1.3.6.1.4.1.9.12.3.1.3.1014";
  }

  smiv2:alias "cevChassisECDS1100" {
    smiv2:oid "1.3.6.1.4.1.9.12.3.1.3.1017";
  }

  smiv2:alias "cevChassisECDS3100" {
    smiv2:oid "1.3.6.1.4.1.9.12.3.1.3.1018";
  }

  smiv2:alias "cevChassisIE301016S8PC" {
    smiv2:oid "1.3.6.1.4.1.9.12.3.1.3.1019";
  }

  smiv2:alias "cevChassisIE301024TC" {
    smiv2:oid "1.3.6.1.4.1.9.12.3.1.3.1020";
  }

  smiv2:alias "cevChassisWsC4948ef10GE" {
    smiv2:oid "1.3.6.1.4.1.9.12.3.1.3.1023";
  }

  smiv2:alias "cevChassisWave284K9" {
    smiv2:oid "1.3.6.1.4.1.9.12.3.1.3.1024";
  }

  smiv2:alias "cevChassisWave584K9" {
    smiv2:oid "1.3.6.1.4.1.9.12.3.1.3.1025";
  }

  smiv2:alias "cevChassisWave684K9" {
    smiv2:oid "1.3.6.1.4.1.9.12.3.1.3.1026";
  }

  smiv2:alias "cevChassisWave7441K9" {
    smiv2:oid "1.3.6.1.4.1.9.12.3.1.3.1027";
  }

  smiv2:alias "cevChassisWave7471K9" {
    smiv2:oid "1.3.6.1.4.1.9.12.3.1.3.1028";
  }

  smiv2:alias "cevChassisWave7626K9" {
    smiv2:oid "1.3.6.1.4.1.9.12.3.1.3.1029";
  }

  smiv2:alias "cevChassisCat292848TCC" {
    smiv2:oid "1.3.6.1.4.1.9.12.3.1.3.1032";
  }

  smiv2:alias "cevChassisCat292824TCC" {
    smiv2:oid "1.3.6.1.4.1.9.12.3.1.3.1033";
  }

  smiv2:alias "cevChassisCat292824LTC" {
    smiv2:oid "1.3.6.1.4.1.9.12.3.1.3.1034";
  }

  smiv2:alias "cevChassisGrwicDes2s8pc" {
    smiv2:oid "1.3.6.1.4.1.9.12.3.1.3.1036";
  }

  smiv2:alias "cevChassisGrwicDes6s" {
    smiv2:oid "1.3.6.1.4.1.9.12.3.1.3.1037";
  }

  smiv2:alias "cevChassisN5kC5596Up" {
    smiv2:oid "1.3.6.1.4.1.9.12.3.1.3.1038";
  }

  smiv2:alias "cevChassisC1861eUc2BriK9" {
    smiv2:oid "1.3.6.1.4.1.9.12.3.1.3.1039";
  }

  smiv2:alias "cevChassisC1861eUc4FxoK9" {
    smiv2:oid "1.3.6.1.4.1.9.12.3.1.3.1040";
  }

  smiv2:alias "cevChassisC1861eSrstFK9" {
    smiv2:oid "1.3.6.1.4.1.9.12.3.1.3.1041";
  }

  smiv2:alias "cevChassisC1861eSrstBK9" {
    smiv2:oid "1.3.6.1.4.1.9.12.3.1.3.1042";
  }

  smiv2:alias "cevChassisC1861eSrstCFK9" {
    smiv2:oid "1.3.6.1.4.1.9.12.3.1.3.1043";
  }

  smiv2:alias "cevChassisC1861eSrstCBK9" {
    smiv2:oid "1.3.6.1.4.1.9.12.3.1.3.1044";
  }

  smiv2:alias "cevChassis88XG2DSL" {
    smiv2:oid "1.3.6.1.4.1.9.12.3.1.3.1045";
  }

  smiv2:alias "cevChassisN2kC2248TPE1GE" {
    smiv2:oid "1.3.6.1.4.1.9.12.3.1.3.1046";
  }

  smiv2:alias "cevChassisWave8541" {
    smiv2:oid "1.3.6.1.4.1.9.12.3.1.3.1047";
  }

  smiv2:alias "cevChassisWave7571" {
    smiv2:oid "1.3.6.1.4.1.9.12.3.1.3.1048";
  }

  smiv2:alias "cevChassisWave7541" {
    smiv2:oid "1.3.6.1.4.1.9.12.3.1.3.1049";
  }

  smiv2:alias "cevChassisWave694" {
    smiv2:oid "1.3.6.1.4.1.9.12.3.1.3.1050";
  }

  smiv2:alias "cevChassisWave594" {
    smiv2:oid "1.3.6.1.4.1.9.12.3.1.3.1051";
  }

  smiv2:alias "cevChassisWave294" {
    smiv2:oid "1.3.6.1.4.1.9.12.3.1.3.1052";
  }

  smiv2:alias "cevChassis5915" {
    smiv2:oid "1.3.6.1.4.1.9.12.3.1.3.1053";
  }

  smiv2:alias "cevChassis86xVAE" {
    smiv2:oid "1.3.6.1.4.1.9.12.3.1.3.1055";
  }

  smiv2:alias "cevChassisAp802gn" {
    smiv2:oid "1.3.6.1.4.1.9.12.3.1.3.1056";
  }

  smiv2:alias "cevChassisN2kB22HPP" {
    smiv2:oid "1.3.6.1.4.1.9.12.3.1.3.1058";
  }

  smiv2:alias "cevChassisN2kC2248GVP" {
    smiv2:oid "1.3.6.1.4.1.9.12.3.1.3.1059";
  }

  smiv2:alias "cevChassisN3kC3064PQ" {
    smiv2:oid "1.3.6.1.4.1.9.12.3.1.3.1060";
  }

  smiv2:alias "cevChassisN2kC2232TM10GE" {
    smiv2:oid "1.3.6.1.4.1.9.12.3.1.3.1061";
  }

  smiv2:alias "cevChassisUCSFI6248UP" {
    smiv2:oid "1.3.6.1.4.1.9.12.3.1.3.1062";
  }

  smiv2:alias "cevChassisUCSFI6296UP" {
    smiv2:oid "1.3.6.1.4.1.9.12.3.1.3.1063";
  }

  smiv2:alias "cevChassis2811ve" {
    smiv2:oid "1.3.6.1.4.1.9.12.3.1.3.1064";
  }

  smiv2:alias "cevChassis1841ve" {
    smiv2:oid "1.3.6.1.4.1.9.12.3.1.3.1065";
  }

  smiv2:alias "cevChassis2960c8tcS" {
    smiv2:oid "1.3.6.1.4.1.9.12.3.1.3.1066";
  }

  smiv2:alias "cevChassis2960c8tcL" {
    smiv2:oid "1.3.6.1.4.1.9.12.3.1.3.1067";
  }

  smiv2:alias "cevChassis2960c8pcL" {
    smiv2:oid "1.3.6.1.4.1.9.12.3.1.3.1068";
  }

  smiv2:alias "cevChassis2960c12pcL" {
    smiv2:oid "1.3.6.1.4.1.9.12.3.1.3.1069";
  }

  smiv2:alias "cevChassis3560cpd8ptS" {
    smiv2:oid "1.3.6.1.4.1.9.12.3.1.3.1070";
  }

  smiv2:alias "cevChassis886Vag7K9" {
    smiv2:oid "1.3.6.1.4.1.9.12.3.1.3.1071";
  }

  smiv2:alias "cevChassis887VagSK9" {
    smiv2:oid "1.3.6.1.4.1.9.12.3.1.3.1072";
  }

  smiv2:alias "cevChassis887Vag7K9" {
    smiv2:oid "1.3.6.1.4.1.9.12.3.1.3.1073";
  }

  smiv2:alias "cevChassis887Vamg7K9" {
    smiv2:oid "1.3.6.1.4.1.9.12.3.1.3.1074";
  }

  smiv2:alias "cevChassis888Eg7K9" {
    smiv2:oid "1.3.6.1.4.1.9.12.3.1.3.1075";
  }

  smiv2:alias "cevChassis881GUK9" {
    smiv2:oid "1.3.6.1.4.1.9.12.3.1.3.1076";
  }

  smiv2:alias "cevChassis881GSK9" {
    smiv2:oid "1.3.6.1.4.1.9.12.3.1.3.1077";
  }

  smiv2:alias "cevChassis881GVK9" {
    smiv2:oid "1.3.6.1.4.1.9.12.3.1.3.1078";
  }

  smiv2:alias "cevChassis881GBK9" {
    smiv2:oid "1.3.6.1.4.1.9.12.3.1.3.1079";
  }

  smiv2:alias "cevChassis881G7K9" {
    smiv2:oid "1.3.6.1.4.1.9.12.3.1.3.1080";
  }

  smiv2:alias "cevChassis881G7AK9" {
    smiv2:oid "1.3.6.1.4.1.9.12.3.1.3.1081";
  }

  smiv2:alias "cevChassisN5kC5548UP" {
    smiv2:oid "1.3.6.1.4.1.9.12.3.1.3.1084";
  }

  smiv2:alias "cevChassis881W" {
    smiv2:oid "1.3.6.1.4.1.9.12.3.1.3.1085";
  }

  smiv2:alias "cevChassis886VAW" {
    smiv2:oid "1.3.6.1.4.1.9.12.3.1.3.1086";
  }

  smiv2:alias "cevChassis887VAMW" {
    smiv2:oid "1.3.6.1.4.1.9.12.3.1.3.1087";
  }

  smiv2:alias "cevChassis887VAW" {
    smiv2:oid "1.3.6.1.4.1.9.12.3.1.3.1088";
  }

  smiv2:alias "cevChassis819G" {
    smiv2:oid "1.3.6.1.4.1.9.12.3.1.3.1089";
  }

  smiv2:alias "cevChassis819HG" {
    smiv2:oid "1.3.6.1.4.1.9.12.3.1.3.1090";
  }

  smiv2:alias "cevChassisIAD886VA" {
    smiv2:oid "1.3.6.1.4.1.9.12.3.1.3.1091";
  }

  smiv2:alias "cevChassisIAD886VAJ" {
    smiv2:oid "1.3.6.1.4.1.9.12.3.1.3.1092";
  }

  smiv2:alias "cevChassisIAD887VA" {
    smiv2:oid "1.3.6.1.4.1.9.12.3.1.3.1093";
  }

  smiv2:alias "cevChassisIAD887VAM" {
    smiv2:oid "1.3.6.1.4.1.9.12.3.1.3.1094";
  }

  smiv2:alias "cevChassisPCM" {
    smiv2:oid "1.3.6.1.4.1.9.12.3.1.3.1095";
  }

  smiv2:alias "cevChassisDSavsm" {
    smiv2:oid "1.3.6.1.4.1.9.12.3.1.3.1102";
  }

  smiv2:alias "cevChassisEcdsVB" {
    smiv2:oid "1.3.6.1.4.1.9.12.3.1.3.1104";
  }

  smiv2:alias "cevChassisN3kC3064PQ10GE" {
    smiv2:oid "1.3.6.1.4.1.9.12.3.1.3.1105";
  }

  smiv2:alias "cevChassisN3kC3048TP1GE" {
    smiv2:oid "1.3.6.1.4.1.9.12.3.1.3.1106";
  }

  smiv2:alias "cevChassisN3kC3016Q40GE" {
    smiv2:oid "1.3.6.1.4.1.9.12.3.1.3.1107";
  }

  smiv2:alias "cevChassisASR903" {
    smiv2:oid "1.3.6.1.4.1.9.12.3.1.3.1118";
  }

  smiv2:alias "cevChassis3560c12pcS" {
    smiv2:oid "1.3.6.1.4.1.9.12.3.1.3.1121";
  }

  smiv2:alias "cevChassis3560c8pcS" {
    smiv2:oid "1.3.6.1.4.1.9.12.3.1.3.1122";
  }

  smiv2:alias "cevChassisCrs8SB" {
    smiv2:oid "1.3.6.1.4.1.9.12.3.1.3.1123";
  }

  smiv2:alias "cevChassisRAIE1783BMS06S" {
    smiv2:oid "1.3.6.1.4.1.9.12.3.1.3.1124";
  }

  smiv2:alias "cevChassisRAIE1783BMS06T" {
    smiv2:oid "1.3.6.1.4.1.9.12.3.1.3.1125";
  }

  smiv2:alias "cevChassisRAIE1783BMS06SG" {
    smiv2:oid "1.3.6.1.4.1.9.12.3.1.3.1126";
  }

  smiv2:alias "cevChassisRAIE1783BMS10C" {
    smiv2:oid "1.3.6.1.4.1.9.12.3.1.3.1127";
  }

  smiv2:alias "cevChassisRAIE1783BMS06TG" {
    smiv2:oid "1.3.6.1.4.1.9.12.3.1.3.1128";
  }

  smiv2:alias "cevChassisRAIE1783BMS10CG" {
    smiv2:oid "1.3.6.1.4.1.9.12.3.1.3.1129";
  }

  smiv2:alias "cevChassisRAIE1783BMS20C" {
    smiv2:oid "1.3.6.1.4.1.9.12.3.1.3.1130";
  }

  smiv2:alias "cevChassisRAIE1783BMS20CG" {
    smiv2:oid "1.3.6.1.4.1.9.12.3.1.3.1131";
  }

  smiv2:alias "cevChassisRAIE1783BMS20CGPK" {
    smiv2:oid "1.3.6.1.4.1.9.12.3.1.3.1132";
  }

  smiv2:alias "cevChassisIE20004TS" {
    smiv2:oid "1.3.6.1.4.1.9.12.3.1.3.1133";
  }

  smiv2:alias "cevChassisIE20004T" {
    smiv2:oid "1.3.6.1.4.1.9.12.3.1.3.1134";
  }

  smiv2:alias "cevChassisIE20004TSG" {
    smiv2:oid "1.3.6.1.4.1.9.12.3.1.3.1135";
  }

  smiv2:alias "cevChassisIE20004TG" {
    smiv2:oid "1.3.6.1.4.1.9.12.3.1.3.1136";
  }

  smiv2:alias "cevChassisIE20008TC" {
    smiv2:oid "1.3.6.1.4.1.9.12.3.1.3.1137";
  }

  smiv2:alias "cevChassisIE20008TCG" {
    smiv2:oid "1.3.6.1.4.1.9.12.3.1.3.1138";
  }

  smiv2:alias "cevChassisIE200016TC" {
    smiv2:oid "1.3.6.1.4.1.9.12.3.1.3.1139";
  }

  smiv2:alias "cevChassisIE200016TCG" {
    smiv2:oid "1.3.6.1.4.1.9.12.3.1.3.1140";
  }

  smiv2:alias "cevChassisIE200016TCGX" {
    smiv2:oid "1.3.6.1.4.1.9.12.3.1.3.1141";
  }

  smiv2:alias "cevChassisASR5000CHSSYSK9" {
    smiv2:oid "1.3.6.1.4.1.9.12.3.1.3.1145";
  }

  smiv2:alias "cevChassisASR55CHSSYS" {
    smiv2:oid "1.3.6.1.4.1.9.12.3.1.3.1146";
  }

  smiv2:alias "cevChassisN7Kc7004" {
    smiv2:oid "1.3.6.1.4.1.9.12.3.1.3.1147";
  }

  smiv2:alias "cevChassisASR901" {
    smiv2:oid "1.3.6.1.4.1.9.12.3.1.3.1159";
  }

  smiv2:alias "cevChassisASR901E" {
    smiv2:oid "1.3.6.1.4.1.9.12.3.1.3.1160";
  }

  smiv2:alias "cevChassisOeSmSre710" {
    smiv2:oid "1.3.6.1.4.1.9.12.3.1.3.1161";
  }

  smiv2:alias "cevChassisOeSmSre910" {
    smiv2:oid "1.3.6.1.4.1.9.12.3.1.3.1162";
  }

  smiv2:alias "cevChassisN3kC3064PQ10GX" {
    smiv2:oid "1.3.6.1.4.1.9.12.3.1.3.1163";
  }

  smiv2:alias "cevChassisVSR1000" {
    smiv2:oid "1.3.6.1.4.1.9.12.3.1.3.1165";
  }

  smiv2:alias "cevChassisFlowAgent3000" {
    smiv2:oid "1.3.6.1.4.1.9.12.3.1.3.1166";
  }

  smiv2:alias "cevChassisASR1002X" {
    smiv2:oid "1.3.6.1.4.1.9.12.3.1.3.1167";
  }

  smiv2:alias "cevChassisNamApp2304" {
    smiv2:oid "1.3.6.1.4.1.9.12.3.1.3.1168";
  }

  smiv2:alias "cevChassisNamApp2320" {
    smiv2:oid "1.3.6.1.4.1.9.12.3.1.3.1169";
  }

  smiv2:alias "cevChassisECDS50IVB" {
    smiv2:oid "1.3.6.1.4.1.9.12.3.1.3.1173";
  }

  smiv2:alias "cevChassisN5kC5596TFA" {
    smiv2:oid "1.3.6.1.4.1.9.12.3.1.3.1175";
  }

  smiv2:alias "cevChassisASR9001" {
    smiv2:oid "1.3.6.1.4.1.9.12.3.1.3.1178";
  }

  smiv2:alias "cevChassis819GM" {
    smiv2:oid "1.3.6.1.4.1.9.12.3.1.3.1188";
  }

  smiv2:alias "cevChassis819HGM" {
    smiv2:oid "1.3.6.1.4.1.9.12.3.1.3.1189";
  }

  smiv2:alias "cevChassisN2kC2232TME10GE" {
    smiv2:oid "1.3.6.1.4.1.9.12.3.1.3.1190";
  }

  smiv2:alias "cevChassisCDScde2502s6" {
    smiv2:oid "1.3.6.1.4.1.9.12.3.1.3.1191";
  }

  smiv2:alias "cevChassisCDScde2502m0" {
    smiv2:oid "1.3.6.1.4.1.9.12.3.1.3.1192";
  }

  smiv2:alias "cevChassisCDScde2502s8" {
    smiv2:oid "1.3.6.1.4.1.9.12.3.1.3.1193";
  }

  smiv2:alias "cevChassisASA1000V" {
    smiv2:oid "1.3.6.1.4.1.9.12.3.1.3.1194";
  }

  smiv2:alias "cevChassisISR4400" {
    smiv2:oid "1.3.6.1.4.1.9.12.3.1.3.1195";
  }

  smiv2:alias "cevChassisMe3600x24CxM" {
    smiv2:oid "1.3.6.1.4.1.9.12.3.1.3.1196";
  }

  smiv2:alias "cevChassisA9014CFD" {
    smiv2:oid "1.3.6.1.4.1.9.12.3.1.3.1197";
  }

  smiv2:alias "cevChassisA9014CFtD" {
    smiv2:oid "1.3.6.1.4.1.9.12.3.1.3.1198";
  }

  smiv2:alias "cevChassisMDE10XVB" {
    smiv2:oid "1.3.6.1.4.1.9.12.3.1.3.1199";
  }

  smiv2:alias "cevChassisWsC4500x16" {
    smiv2:oid "1.3.6.1.4.1.9.12.3.1.3.1202";
  }

  smiv2:alias "cevChassisWsC4500x32" {
    smiv2:oid "1.3.6.1.4.1.9.12.3.1.3.1203";
  }

  smiv2:alias "cevChassisN2kC2248PQ10GE" {
    smiv2:oid "1.3.6.1.4.1.9.12.3.1.3.1205";
  }

  smiv2:alias "cevChassisCDScde2502s9" {
    smiv2:oid "1.3.6.1.4.1.9.12.3.1.3.1206";
  }

  smiv2:alias "cevChassisCDScde2502s10" {
    smiv2:oid "1.3.6.1.4.1.9.12.3.1.3.1207";
  }

  smiv2:alias "cevChassisCDScdeGeneric" {
    smiv2:oid "1.3.6.1.4.1.9.12.3.1.3.1208";
  }

  smiv2:alias "cevChassisN2kB22FTSP" {
    smiv2:oid "1.3.6.1.4.1.9.12.3.1.3.1210";
  }

  smiv2:alias "cevChassisN2kB22DELLP" {
    smiv2:oid "1.3.6.1.4.1.9.12.3.1.3.1211";
  }

  smiv2:alias "cevChassisASR9922Dc" {
    smiv2:oid "1.3.6.1.4.1.9.12.3.1.3.1225";
  }

  smiv2:alias "cevChassisASR9922Ac" {
    smiv2:oid "1.3.6.1.4.1.9.12.3.1.3.1226";
  }

  smiv2:alias "cevChassisN6kC600496Q" {
    smiv2:oid "1.3.6.1.4.1.9.12.3.1.3.1237";
  }

  smiv2:alias "cevChassisN3kC3548P10G" {
    smiv2:oid "1.3.6.1.4.1.9.12.3.1.3.1238";
  }

  smiv2:alias "cevChassisN3kC3064TQ10GT" {
    smiv2:oid "1.3.6.1.4.1.9.12.3.1.3.1239";
  }

  smiv2:alias "cevChassis86xVAEW" {
    smiv2:oid "1.3.6.1.4.1.9.12.3.1.3.1240";
  }

  smiv2:alias "cevChassisASR9912AC" {
    smiv2:oid "1.3.6.1.4.1.9.12.3.1.3.1241";
  }

  smiv2:alias "cevChassisASR9912DC" {
    smiv2:oid "1.3.6.1.4.1.9.12.3.1.3.1242";
  }

  smiv2:alias "cevChassisOeKWaas" {
    smiv2:oid "1.3.6.1.4.1.9.12.3.1.3.1243";
  }

  smiv2:alias "cevChassisasr1000" {
    smiv2:oid "1.3.6.1.4.1.9.12.3.1.3.1244";
  }

  smiv2:alias "cevChassisCDScde2202s4" {
    smiv2:oid "1.3.6.1.4.1.9.12.3.1.3.1245";
  }

  smiv2:alias "cevChassisISR4441" {
    smiv2:oid "1.3.6.1.4.1.9.12.3.1.3.1246";
  }

  smiv2:alias "cevChassisISR4442" {
    smiv2:oid "1.3.6.1.4.1.9.12.3.1.3.1247";
  }

  smiv2:alias "cevChassisISR4451" {
    smiv2:oid "1.3.6.1.4.1.9.12.3.1.3.1248";
  }

  smiv2:alias "cevChassisISR4452" {
    smiv2:oid "1.3.6.1.4.1.9.12.3.1.3.1249";
  }

  smiv2:alias "cevChassisAIRAP1553" {
    smiv2:oid "1.3.6.1.4.1.9.12.3.1.3.1251";
  }

  smiv2:alias "cevChassisAIRAP1552" {
    smiv2:oid "1.3.6.1.4.1.9.12.3.1.3.1252";
  }

  smiv2:alias "cevChassisAIRAP1602" {
    smiv2:oid "1.3.6.1.4.1.9.12.3.1.3.1253";
  }

  smiv2:alias "cevChassisAIRAP1601" {
    smiv2:oid "1.3.6.1.4.1.9.12.3.1.3.1254";
  }

  smiv2:alias "cevChassisAIRAP2602" {
    smiv2:oid "1.3.6.1.4.1.9.12.3.1.3.1255";
  }

  smiv2:alias "cevChassisAIRAP2601" {
    smiv2:oid "1.3.6.1.4.1.9.12.3.1.3.1256";
  }

  smiv2:alias "cevChassisAIRAP3602" {
    smiv2:oid "1.3.6.1.4.1.9.12.3.1.3.1257";
  }

  smiv2:alias "cevChassisAIRAP3601" {
    smiv2:oid "1.3.6.1.4.1.9.12.3.1.3.1258";
  }

  smiv2:alias "cevChassisWsC2960x48fpdL" {
    smiv2:oid "1.3.6.1.4.1.9.12.3.1.3.1259";
  }

  smiv2:alias "cevChassisWsC2960x48lpdL" {
    smiv2:oid "1.3.6.1.4.1.9.12.3.1.3.1260";
  }

  smiv2:alias "cevChassisWsC2960x48tdL" {
    smiv2:oid "1.3.6.1.4.1.9.12.3.1.3.1261";
  }

  smiv2:alias "cevChassisWsC2960x24pdL" {
    smiv2:oid "1.3.6.1.4.1.9.12.3.1.3.1262";
  }

  smiv2:alias "cevChassisWsC2960x24tdL" {
    smiv2:oid "1.3.6.1.4.1.9.12.3.1.3.1263";
  }

  smiv2:alias "cevChassisWsC2960x48fpsL" {
    smiv2:oid "1.3.6.1.4.1.9.12.3.1.3.1264";
  }

  smiv2:alias "cevChassisWsC2960x48lpsL" {
    smiv2:oid "1.3.6.1.4.1.9.12.3.1.3.1265";
  }

  smiv2:alias "cevChassisWsC2960x24psL" {
    smiv2:oid "1.3.6.1.4.1.9.12.3.1.3.1266";
  }

  smiv2:alias "cevChassisWsC2960x48tsL" {
    smiv2:oid "1.3.6.1.4.1.9.12.3.1.3.1267";
  }

  smiv2:alias "cevChassisWsC2960x24tsL" {
    smiv2:oid "1.3.6.1.4.1.9.12.3.1.3.1268";
  }

  smiv2:alias "cevChassisWsC2960x24psqL" {
    smiv2:oid "1.3.6.1.4.1.9.12.3.1.3.1269";
  }

  smiv2:alias "cevChassisWsC2960x48lpsS" {
    smiv2:oid "1.3.6.1.4.1.9.12.3.1.3.1270";
  }

  smiv2:alias "cevChassisWsC2960x24psS" {
    smiv2:oid "1.3.6.1.4.1.9.12.3.1.3.1271";
  }

  smiv2:alias "cevChassisWsC2960x48tsLL" {
    smiv2:oid "1.3.6.1.4.1.9.12.3.1.3.1272";
  }

  smiv2:alias "cevChassisWsC2960x24tsLL" {
    smiv2:oid "1.3.6.1.4.1.9.12.3.1.3.1273";
  }

  smiv2:alias "cevChassisIE200016TCGP" {
    smiv2:oid "1.3.6.1.4.1.9.12.3.1.3.1278";
  }

  smiv2:alias "cevChassisIE200016TCGEP" {
    smiv2:oid "1.3.6.1.4.1.9.12.3.1.3.1279";
  }

  smiv2:alias "cevChassisIE200016TCGNXP" {
    smiv2:oid "1.3.6.1.4.1.9.12.3.1.3.1280";
  }

  smiv2:alias "cevChassisRAIE1783BMS12T4E2CGL" {
    smiv2:oid "1.3.6.1.4.1.9.12.3.1.3.1281";
  }

  smiv2:alias "cevChassisRAIE1783BMS12T4E2CGP" {
    smiv2:oid "1.3.6.1.4.1.9.12.3.1.3.1282";
  }

  smiv2:alias "cevChassisRAIE1783BMS12T4E2CGNK" {
    smiv2:oid "1.3.6.1.4.1.9.12.3.1.3.1283";
  }

  smiv2:alias "cevChassisIE20008TCGN" {
    smiv2:oid "1.3.6.1.4.1.9.12.3.1.3.1284";
  }

  smiv2:alias "cevChassisIE200016TCGN" {
    smiv2:oid "1.3.6.1.4.1.9.12.3.1.3.1285";
  }

  smiv2:alias "cevChassisRAIE1783BMS10CGN" {
    smiv2:oid "1.3.6.1.4.1.9.12.3.1.3.1286";
  }

  smiv2:alias "cevChassisRAIE1783BMS20CGN" {
    smiv2:oid "1.3.6.1.4.1.9.12.3.1.3.1287";
  }

  smiv2:alias "cevChassisNexus1010X" {
    smiv2:oid "1.3.6.1.4.1.9.12.3.1.3.1288";
  }

  smiv2:alias "cevChassisNexus1110S" {
    smiv2:oid "1.3.6.1.4.1.9.12.3.1.3.1289";
  }

  smiv2:alias "cevChassisNexus1110XL" {
    smiv2:oid "1.3.6.1.4.1.9.12.3.1.3.1290";
  }

  smiv2:alias "cevChassisNexus1110X" {
    smiv2:oid "1.3.6.1.4.1.9.12.3.1.3.1291";
  }

  smiv2:alias "cevChassisNexus1000VKVM" {
    smiv2:oid "1.3.6.1.4.1.9.12.3.1.3.1292";
  }

  smiv2:alias "cevChassisNexus1000VMH" {
    smiv2:oid "1.3.6.1.4.1.9.12.3.1.3.1294";
  }

  smiv2:alias "cevChassisVG202XM" {
    smiv2:oid "1.3.6.1.4.1.9.12.3.1.3.1295";
  }

  smiv2:alias "cevChassisVG204XM" {
    smiv2:oid "1.3.6.1.4.1.9.12.3.1.3.1296";
  }

  smiv2:alias "cevChassisAsr9904AC" {
    smiv2:oid "1.3.6.1.4.1.9.12.3.1.3.1301";
  }

  smiv2:alias "cevChassisAsr9904DC" {
    smiv2:oid "1.3.6.1.4.1.9.12.3.1.3.1302";
  }

  smiv2:alias "cevChassisME2600X" {
    smiv2:oid "1.3.6.1.4.1.9.12.3.1.3.1303";
  }

  smiv2:alias "cevChassisNCSCHASSIS" {
    smiv2:oid "1.3.6.1.4.1.9.12.3.1.3.1304";
  }

  smiv2:alias "cevChassisC6807xl" {
    smiv2:oid "1.3.6.1.4.1.9.12.3.1.3.1305";
  }

  smiv2:alias "cevChassisN6kC600164P" {
    smiv2:oid "1.3.6.1.4.1.9.12.3.1.3.1308";
  }

  smiv2:alias "cevChassis131WsC385024U" {
    smiv2:oid "1.3.6.1.4.1.9.12.3.1.3.1309";
  }

  smiv2:alias "cevChassis131WsC385048U" {
    smiv2:oid "1.3.6.1.4.1.9.12.3.1.3.1310";
  }

  smiv2:alias "cevChassisDSC9250IK9" {
    smiv2:oid "1.3.6.1.4.1.9.12.3.1.3.1326";
  }

  smiv2:alias "cevChassisDSC9710" {
    smiv2:oid "1.3.6.1.4.1.9.12.3.1.3.1327";
  }

  smiv2:alias "cevChassisC6880xle" {
    smiv2:oid "1.3.6.1.4.1.9.12.3.1.3.1328";
  }

  smiv2:alias "cevChassisIE2000U16TCGP" {
    smiv2:oid "1.3.6.1.4.1.9.12.3.1.3.1338";
  }

  smiv2:alias "cevChassisN2kB22IBMP" {
    smiv2:oid "1.3.6.1.4.1.9.12.3.1.3.1339";
  }

  smiv2:alias "cevChassisN6kC600164T" {
    smiv2:oid "1.3.6.1.4.1.9.12.3.1.3.1340";
  }

  smiv2:alias "cevChassisWsC2960P48PstL" {
    smiv2:oid "1.3.6.1.4.1.9.12.3.1.3.1342";
  }

  smiv2:alias "cevChassisWsC2960P24PcL" {
    smiv2:oid "1.3.6.1.4.1.9.12.3.1.3.1343";
  }

  smiv2:alias "cevChassisWsC2960P24LcL" {
    smiv2:oid "1.3.6.1.4.1.9.12.3.1.3.1344";
  }

  smiv2:alias "cevChassisWsC2960P48TcL" {
    smiv2:oid "1.3.6.1.4.1.9.12.3.1.3.1345";
  }

  smiv2:alias "cevChassisWsC2960P24TcL" {
    smiv2:oid "1.3.6.1.4.1.9.12.3.1.3.1346";
  }

  smiv2:alias "cevChassisWsC2960P48PstS" {
    smiv2:oid "1.3.6.1.4.1.9.12.3.1.3.1347";
  }

  smiv2:alias "cevChassisWsC2960P24PcS" {
    smiv2:oid "1.3.6.1.4.1.9.12.3.1.3.1348";
  }

  smiv2:alias "cevChassisWsC2960P24LcS" {
    smiv2:oid "1.3.6.1.4.1.9.12.3.1.3.1349";
  }

  smiv2:alias "cevChassisWsC2960P48TcS" {
    smiv2:oid "1.3.6.1.4.1.9.12.3.1.3.1350";
  }

  smiv2:alias "cevChassisWsC2960P24TcS" {
    smiv2:oid "1.3.6.1.4.1.9.12.3.1.3.1351";
  }

  smiv2:alias "cevChassisN77c7718" {
    smiv2:oid "1.3.6.1.4.1.9.12.3.1.3.1352";
  }

  smiv2:alias "cevChassisN77c7710" {
    smiv2:oid "1.3.6.1.4.1.9.12.3.1.3.1353";
  }

  smiv2:alias "cevChassisN77c7706" {
    smiv2:oid "1.3.6.1.4.1.9.12.3.1.3.1354";
  }

  smiv2:alias "cevChassisA901S4SGFD" {
    smiv2:oid "1.3.6.1.4.1.9.12.3.1.3.1375";
  }

  smiv2:alias "cevChassisA901S3SGFD" {
    smiv2:oid "1.3.6.1.4.1.9.12.3.1.3.1376";
  }

  smiv2:alias "cevChassisA901S2SGFD" {
    smiv2:oid "1.3.6.1.4.1.9.12.3.1.3.1377";
  }

  smiv2:alias "cevChassisA901S3SGFAH" {
    smiv2:oid "1.3.6.1.4.1.9.12.3.1.3.1378";
  }

  smiv2:alias "cevChassisA901S2SGFAH" {
    smiv2:oid "1.3.6.1.4.1.9.12.3.1.3.1379";
  }

  smiv2:alias "cevChassisASR901AC10G" {
    smiv2:oid "1.3.6.1.4.1.9.12.3.1.3.1380";
  }

  smiv2:alias "cevChassisASR901DC10G" {
    smiv2:oid "1.3.6.1.4.1.9.12.3.1.3.1381";
  }

  smiv2:alias "cevChassisASR901eAC10G" {
    smiv2:oid "1.3.6.1.4.1.9.12.3.1.3.1382";
  }

  smiv2:alias "cevChassisASR901eDC10G" {
    smiv2:oid "1.3.6.1.4.1.9.12.3.1.3.1383";
  }

  smiv2:alias "cevChassisIE2000U4STSG" {
    smiv2:oid "1.3.6.1.4.1.9.12.3.1.3.1384";
  }

  smiv2:alias "cevChassisC881" {
    smiv2:oid "1.3.6.1.4.1.9.12.3.1.3.1385";
  }

  smiv2:alias "cevChassisC886VA" {
    smiv2:oid "1.3.6.1.4.1.9.12.3.1.3.1386";
  }

  smiv2:alias "cevChassisC887VA" {
    smiv2:oid "1.3.6.1.4.1.9.12.3.1.3.1387";
  }

  smiv2:alias "cevChassisN3KC3172PQ10GE" {
    smiv2:oid "1.3.6.1.4.1.9.12.3.1.3.1388";
  }

  smiv2:alias "cevChassisN3KC3172TQ10GT" {
    smiv2:oid "1.3.6.1.4.1.9.12.3.1.3.1389";
  }

  smiv2:alias "cevChassisN3KC3132Q40GE" {
    smiv2:oid "1.3.6.1.4.1.9.12.3.1.3.1390";
  }

  smiv2:alias "cevChassisN3KC3132Q40GS" {
    smiv2:oid "1.3.6.1.4.1.9.12.3.1.3.1391";
  }

  smiv2:alias "cevChassisASR9001S" {
    smiv2:oid "1.3.6.1.4.1.9.12.3.1.3.1392";
  }

  smiv2:alias "cevChassisIE20008T67B" {
    smiv2:oid "1.3.6.1.4.1.9.12.3.1.3.1393";
  }

  smiv2:alias "cevChassisIE200016T67B" {
    smiv2:oid "1.3.6.1.4.1.9.12.3.1.3.1394";
  }

  smiv2:alias "cevChassisIE200024T67B" {
    smiv2:oid "1.3.6.1.4.1.9.12.3.1.3.1395";
  }

  smiv2:alias "cevChassisIE20008T67PGE" {
    smiv2:oid "1.3.6.1.4.1.9.12.3.1.3.1396";
  }

  smiv2:alias "cevChassisIE200016T67PGE" {
    smiv2:oid "1.3.6.1.4.1.9.12.3.1.3.1397";
  }

  smiv2:alias "cevChassisRAIE1783ZMS8TA" {
    smiv2:oid "1.3.6.1.4.1.9.12.3.1.3.1398";
  }

  smiv2:alias "cevChassisRAIE1783ZMS16TA" {
    smiv2:oid "1.3.6.1.4.1.9.12.3.1.3.1399";
  }

  smiv2:alias "cevChassisRAIE1783ZMS24TA" {
    smiv2:oid "1.3.6.1.4.1.9.12.3.1.3.1400";
  }

  smiv2:alias "cevChassisRAIE1783ZMS4T4E2TGP" {
    smiv2:oid "1.3.6.1.4.1.9.12.3.1.3.1401";
  }

  smiv2:alias "cevChassisRAIE1783ZMS8T8E2TGP" {
    smiv2:oid "1.3.6.1.4.1.9.12.3.1.3.1402";
  }

  smiv2:alias "cevChassisC888" {
    smiv2:oid "1.3.6.1.4.1.9.12.3.1.3.1403";
  }

  smiv2:alias "cevChassisC891F" {
    smiv2:oid "1.3.6.1.4.1.9.12.3.1.3.1404";
  }

  smiv2:alias "cevChassisC891FW" {
    smiv2:oid "1.3.6.1.4.1.9.12.3.1.3.1405";
  }

  smiv2:alias "cevChassis1783WAP5100xK9" {
    smiv2:oid "1.3.6.1.4.1.9.12.3.1.3.1407";
  }

  smiv2:alias "cevChassisCDScde2502s5" {
    smiv2:oid "1.3.6.1.4.1.9.12.3.1.3.1408";
  }

  smiv2:alias "cevChassisN5KC56128P" {
    smiv2:oid "1.3.6.1.4.1.9.12.3.1.3.1409";
  }

  smiv2:alias "cevChassisN5KC5672UP" {
    smiv2:oid "1.3.6.1.4.1.9.12.3.1.3.1410";
  }

  smiv2:alias "cevChassisIE2000U4TG" {
    smiv2:oid "1.3.6.1.4.1.9.12.3.1.3.1412";
  }

  smiv2:alias "cevChassisIE2000U4TSG" {
    smiv2:oid "1.3.6.1.4.1.9.12.3.1.3.1413";
  }

  smiv2:alias "cevChassisIE2000U8TCG" {
    smiv2:oid "1.3.6.1.4.1.9.12.3.1.3.1414";
  }

  smiv2:alias "cevChassisIE2000U16TCG" {
    smiv2:oid "1.3.6.1.4.1.9.12.3.1.3.1415";
  }

  smiv2:alias "cevChassisIE2000U16TCGX" {
    smiv2:oid "1.3.6.1.4.1.9.12.3.1.3.1416";
  }

  smiv2:alias "cevChassisN3KC3132Q40GX" {
    smiv2:oid "1.3.6.1.4.1.9.12.3.1.3.1417";
  }

  smiv2:alias "cevChassisVG310" {
    smiv2:oid "1.3.6.1.4.1.9.12.3.1.3.1418";
  }

  smiv2:alias "cevChassisVG320" {
    smiv2:oid "1.3.6.1.4.1.9.12.3.1.3.1419";
  }

  smiv2:alias "cevChassisDSC9706" {
    smiv2:oid "1.3.6.1.4.1.9.12.3.1.3.1420";
  }

  smiv2:alias "cevChassisAIRAP702" {
    smiv2:oid "1.3.6.1.4.1.9.12.3.1.3.1422";
  }

  smiv2:alias "cevChassisAIRAP1532" {
    smiv2:oid "1.3.6.1.4.1.9.12.3.1.3.1423";
  }

  smiv2:alias "cevChassisC6800IA48FPD" {
    smiv2:oid "1.3.6.1.4.1.9.12.3.1.3.1424";
  }

  smiv2:alias "cevChassisC6800IA48TD" {
    smiv2:oid "1.3.6.1.4.1.9.12.3.1.3.1425";
  }

  smiv2:alias "cevChassis131WsC385024S" {
    smiv2:oid "1.3.6.1.4.1.9.12.3.1.3.1433";
  }

  smiv2:alias "cevChassis131WsC385012S" {
    smiv2:oid "1.3.6.1.4.1.9.12.3.1.3.1434";
  }

  smiv2:alias "cevChassisASR902" {
    smiv2:oid "1.3.6.1.4.1.9.12.3.1.3.1449";
  }

  smiv2:alias "cevChassisVASA" {
    smiv2:oid "1.3.6.1.4.1.9.12.3.1.3.1451";
  }

  smiv2:alias "cevChassisUCSFIM6324" {
    smiv2:oid "1.3.6.1.4.1.9.12.3.1.3.1454";
  }

  smiv2:alias "cevChassisN9Kc9508" {
    smiv2:oid "1.3.6.1.4.1.9.12.3.1.3.1467";
  }

  smiv2:alias "cevChassisME12006sAO" {
    smiv2:oid "1.3.6.1.4.1.9.12.3.1.3.1469";
  }

  smiv2:alias "cevChassisME12006sD" {
    smiv2:oid "1.3.6.1.4.1.9.12.3.1.3.1470";
  }

  smiv2:alias "cevChassisME12006sA" {
    smiv2:oid "1.3.6.1.4.1.9.12.3.1.3.1471";
  }

  smiv2:alias "cevChassis1783SR" {
    smiv2:oid "1.3.6.1.4.1.9.12.3.1.3.1472";
  }

  smiv2:alias "cevChassisWapAP702" {
    smiv2:oid "1.3.6.1.4.1.9.12.3.1.3.1475";
  }

  smiv2:alias "cevChassisWapAP2602" {
    smiv2:oid "1.3.6.1.4.1.9.12.3.1.3.1476";
  }

  smiv2:alias "cevChassisWapAP1602" {
    smiv2:oid "1.3.6.1.4.1.9.12.3.1.3.1477";
  }

  smiv2:alias "cevChassisC6880x" {
    smiv2:oid "1.3.6.1.4.1.9.12.3.1.3.1486";
  }

  smiv2:alias "cevChassisAIRAP2702" {
    smiv2:oid "1.3.6.1.4.1.9.12.3.1.3.1487";
  }

  smiv2:alias "cevChassisN6kC6004" {
    smiv2:oid "1.3.6.1.4.1.9.12.3.1.3.1489";
  }

  smiv2:alias "cevChassisAsr9000V24vDcA" {
    smiv2:oid "1.3.6.1.4.1.9.12.3.1.3.1490";
  }

  smiv2:alias "cevChassisDSC9148SK9" {
    smiv2:oid "1.3.6.1.4.1.9.12.3.1.3.1491";
  }

  smiv2:alias "cevChassisRT1081K9" {
    smiv2:oid "1.3.6.1.4.1.9.12.3.1.3.1494";
  }

  smiv2:alias "cevChassisRT1091FK9" {
    smiv2:oid "1.3.6.1.4.1.9.12.3.1.3.1495";
  }

  smiv2:alias "cevChassisRT2241K9" {
    smiv2:oid "1.3.6.1.4.1.9.12.3.1.3.1496";
  }

  smiv2:alias "cevChassisRT2221K9" {
    smiv2:oid "1.3.6.1.4.1.9.12.3.1.3.1497";
  }

  smiv2:alias "cevChassisRT2241WCK9" {
    smiv2:oid "1.3.6.1.4.1.9.12.3.1.3.1498";
  }

  smiv2:alias "cevChassisRT3211K9" {
    smiv2:oid "1.3.6.1.4.1.9.12.3.1.3.1499";
  }

  smiv2:alias "cevChassisRT3221K9" {
    smiv2:oid "1.3.6.1.4.1.9.12.3.1.3.1500";
  }

  smiv2:alias "cevChassisRT3201K9" {
    smiv2:oid "1.3.6.1.4.1.9.12.3.1.3.1501";
  }

  smiv2:alias "cevChassisN9Kc9516" {
    smiv2:oid "1.3.6.1.4.1.9.12.3.1.3.1506";
  }

  smiv2:alias "cevChassisN9Kc9504" {
    smiv2:oid "1.3.6.1.4.1.9.12.3.1.3.1507";
  }

  smiv2:alias "cevChassisN9KC9396PX" {
    smiv2:oid "1.3.6.1.4.1.9.12.3.1.3.1508";
  }

  smiv2:alias "cevChassisN9KC9396TX" {
    smiv2:oid "1.3.6.1.4.1.9.12.3.1.3.1509";
  }

  smiv2:alias "cevChassisN9KC93128TX" {
    smiv2:oid "1.3.6.1.4.1.9.12.3.1.3.1510";
  }

  smiv2:alias "cevChassisVSGateway" {
    smiv2:oid "1.3.6.1.4.1.9.12.3.1.3.1519";
  }

  smiv2:alias "cevChassisPrime" {
    smiv2:oid "1.3.6.1.4.1.9.12.3.1.3.1520";
  }

  smiv2:alias "cevChassis897VAB" {
    smiv2:oid "1.3.6.1.4.1.9.12.3.1.3.1521";
  }

  smiv2:alias "cevChassisN5kC5696Q" {
    smiv2:oid "1.3.6.1.4.1.9.12.3.1.3.1539";
  }

  smiv2:alias "cevChassisN2KC2348TQ" {
    smiv2:oid "1.3.6.1.4.1.9.12.3.1.3.1540";
  }

  smiv2:alias "cevChassisN2KC2348UPQ" {
    smiv2:oid "1.3.6.1.4.1.9.12.3.1.3.1541";
  }

  smiv2:alias "cevChassisIE40004TC4GE" {
    smiv2:oid "1.3.6.1.4.1.9.12.3.1.3.1546";
  }

  smiv2:alias "cevChassisIE40008T4GE" {
    smiv2:oid "1.3.6.1.4.1.9.12.3.1.3.1547";
  }

  smiv2:alias "cevChassisIE40008S4GE" {
    smiv2:oid "1.3.6.1.4.1.9.12.3.1.3.1548";
  }

  smiv2:alias "cevChassisIE40004T4P4GE" {
    smiv2:oid "1.3.6.1.4.1.9.12.3.1.3.1549";
  }

  smiv2:alias "cevChassisIE400016T4GE" {
    smiv2:oid "1.3.6.1.4.1.9.12.3.1.3.1550";
  }

  smiv2:alias "cevChassisIE40004S8P4GE" {
    smiv2:oid "1.3.6.1.4.1.9.12.3.1.3.1551";
  }

  smiv2:alias "cevChassisIE40008GT4GE" {
    smiv2:oid "1.3.6.1.4.1.9.12.3.1.3.1552";
  }

  smiv2:alias "cevChassisIE40008GS4GE" {
    smiv2:oid "1.3.6.1.4.1.9.12.3.1.3.1553";
  }

  smiv2:alias "cevChassisIE40004GC4GP4GE" {
    smiv2:oid "1.3.6.1.4.1.9.12.3.1.3.1554";
  }

  smiv2:alias "cevChassisIE400016GT4GE" {
    smiv2:oid "1.3.6.1.4.1.9.12.3.1.3.1555";
  }

  smiv2:alias "cevChassisIE40008GT8GP4GE" {
    smiv2:oid "1.3.6.1.4.1.9.12.3.1.3.1556";
  }

  smiv2:alias "cevChassisIE40004GS8GP4GE" {
    smiv2:oid "1.3.6.1.4.1.9.12.3.1.3.1557";
  }

  smiv2:alias "cevChassisRAIE1783HMS4C4CGN" {
    smiv2:oid "1.3.6.1.4.1.9.12.3.1.3.1558";
  }

  smiv2:alias "cevChassisRAIE1783HMS8T4CGN" {
    smiv2:oid "1.3.6.1.4.1.9.12.3.1.3.1559";
  }

  smiv2:alias "cevChassisRAIE1783HMS8S4CGN" {
    smiv2:oid "1.3.6.1.4.1.9.12.3.1.3.1560";
  }

  smiv2:alias "cevChassisRAIE1783HMS4T4E4CGN" {
    smiv2:oid "1.3.6.1.4.1.9.12.3.1.3.1561";
  }

  smiv2:alias "cevChassisRAIE1783HMS16T4CGN" {
    smiv2:oid "1.3.6.1.4.1.9.12.3.1.3.1562";
  }

  smiv2:alias "cevChassisRAIE1783HMS4S8E4CGN" {
    smiv2:oid "1.3.6.1.4.1.9.12.3.1.3.1563";
  }

  smiv2:alias "cevChassisRAIE1783HMS8TG4CGN" {
    smiv2:oid "1.3.6.1.4.1.9.12.3.1.3.1564";
  }

  smiv2:alias "cevChassisRAIE1783HMS8SG4CGN" {
    smiv2:oid "1.3.6.1.4.1.9.12.3.1.3.1565";
  }

  smiv2:alias "cevChassisRAIE1783HMS4EG8CGN" {
    smiv2:oid "1.3.6.1.4.1.9.12.3.1.3.1566";
  }

  smiv2:alias "cevChassisRAIE1783HMS16TG4CGN" {
    smiv2:oid "1.3.6.1.4.1.9.12.3.1.3.1567";
  }

  smiv2:alias "cevChassisRAIE1783HMS8TG8EG4CGN" {
    smiv2:oid "1.3.6.1.4.1.9.12.3.1.3.1568";
  }

  smiv2:alias "cevChassisRAIE1783HMS4SG8EG4CGN" {
    smiv2:oid "1.3.6.1.4.1.9.12.3.1.3.1569";
  }

  smiv2:alias "cevChassisN2KC2232TQ" {
    smiv2:oid "1.3.6.1.4.1.9.12.3.1.3.1571";
  }

  smiv2:alias "cevChassisASR901eDC10GS" {
    smiv2:oid "1.3.6.1.4.1.9.12.3.1.3.1577";
  }

  smiv2:alias "cevChassisASR901eAC10GS" {
    smiv2:oid "1.3.6.1.4.1.9.12.3.1.3.1578";
  }

  smiv2:alias "cevChassisCiscoQvPCDI" {
    smiv2:oid "1.3.6.1.4.1.9.12.3.1.3.1585";
  }

  smiv2:alias "cevChassisCiscoQvPC" {
    smiv2:oid "1.3.6.1.4.1.9.12.3.1.3.1586";
  }

  smiv2:alias "cevChassisIOG910GK9" {
    smiv2:oid "1.3.6.1.4.1.9.12.3.1.3.1595";
  }

  smiv2:alias "cevChassisIOG910WK9" {
    smiv2:oid "1.3.6.1.4.1.9.12.3.1.3.1596";
  }

  smiv2:alias "cevChassisIOG910K9" {
    smiv2:oid "1.3.6.1.4.1.9.12.3.1.3.1597";
  }

  smiv2:alias "cevChassisC3850E12XS" {
    smiv2:oid "1.3.6.1.4.1.9.12.3.1.3.1605";
  }

  smiv2:alias "cevChassisC3850E24XS" {
    smiv2:oid "1.3.6.1.4.1.9.12.3.1.3.1606";
  }

  smiv2:alias "cevChassisC3850E48XS" {
    smiv2:oid "1.3.6.1.4.1.9.12.3.1.3.1607";
  }

  smiv2:alias "cevChassisN3KC3164Q40GE" {
    smiv2:oid "1.3.6.1.4.1.9.12.3.1.3.1609";
  }

  smiv2:alias "cevChassisCCE8RU" {
    smiv2:oid "1.3.6.1.4.1.9.12.3.1.3.1610";
  }

  smiv2:alias "cevChassisCCE13RU" {
    smiv2:oid "1.3.6.1.4.1.9.12.3.1.3.1611";
  }

  smiv2:alias "cevChassisCCE18RU" {
    smiv2:oid "1.3.6.1.4.1.9.12.3.1.3.1612";
  }

  smiv2:alias "cevChassis891x24X" {
    smiv2:oid "1.3.6.1.4.1.9.12.3.1.3.1614";
  }

  smiv2:alias "cevChassisAsr9KvV2Ac" {
    smiv2:oid "1.3.6.1.4.1.9.12.3.1.3.1615";
  }

  smiv2:alias "cevChassisAsr9KvV2DcA" {
    smiv2:oid "1.3.6.1.4.1.9.12.3.1.3.1616";
  }

  smiv2:alias "cevChassisAsr9KvV2DcE" {
    smiv2:oid "1.3.6.1.4.1.9.12.3.1.3.1617";
  }

  smiv2:alias "cevChassisN9KC9332PQ" {
    smiv2:oid "1.3.6.1.4.1.9.12.3.1.3.1625";
  }

  smiv2:alias "cevChassisN9KC9372PX" {
    smiv2:oid "1.3.6.1.4.1.9.12.3.1.3.1626";
  }

  smiv2:alias "cevChassisN9KC9372TX" {
    smiv2:oid "1.3.6.1.4.1.9.12.3.1.3.1627";
  }

  smiv2:alias "cevChassis414R" {
    smiv2:oid "1.3.6.1.4.1.9.12.3.1.3.1628";
  }

  smiv2:alias "cevChassis418R" {
    smiv2:oid "1.3.6.1.4.1.9.12.3.1.3.1629";
  }

  smiv2:alias "cevChassisCiscoQvPCVSM" {
    smiv2:oid "1.3.6.1.4.1.9.12.3.1.3.1630";
  }

  smiv2:alias "cevChassisRAIE1783ZMS4T4E2TGN" {
    smiv2:oid "1.3.6.1.4.1.9.12.3.1.3.1632";
  }

  smiv2:alias "cevChassisRAIE1783ZMS8T8E2TGN" {
    smiv2:oid "1.3.6.1.4.1.9.12.3.1.3.1633";
  }

  smiv2:alias "cevChassisRAIE1783HMS8TG4CGR" {
    smiv2:oid "1.3.6.1.4.1.9.12.3.1.3.1636";
  }

  smiv2:alias "cevChassisRAIE1783HMS8SG4CGR" {
    smiv2:oid "1.3.6.1.4.1.9.12.3.1.3.1637";
  }

  smiv2:alias "cevChassisRAIE1783HMS4EG8CGR" {
    smiv2:oid "1.3.6.1.4.1.9.12.3.1.3.1638";
  }

  smiv2:alias "cevChassisRAIE1783HMS16TG4CGR" {
    smiv2:oid "1.3.6.1.4.1.9.12.3.1.3.1639";
  }

  smiv2:alias "cevChassisRAIE1783HMS8TG8EG4CGR" {
    smiv2:oid "1.3.6.1.4.1.9.12.3.1.3.1640";
  }

  smiv2:alias "cevChassisRAIE1783HMS4SG8EG4CGR" {
    smiv2:oid "1.3.6.1.4.1.9.12.3.1.3.1641";
  }

  smiv2:alias "cevChassisCDScde2802s5" {
    smiv2:oid "1.3.6.1.4.1.9.12.3.1.3.1642";
  }

  smiv2:alias "cevChassisCDScde2802s10" {
    smiv2:oid "1.3.6.1.4.1.9.12.3.1.3.1643";
  }

  smiv2:alias "cevChassisCDScde2802s21" {
    smiv2:oid "1.3.6.1.4.1.9.12.3.1.3.1644";
  }

  smiv2:alias "cevChassisCDScde2802h0" {
    smiv2:oid "1.3.6.1.4.1.9.12.3.1.3.1645";
  }

  smiv2:alias "cevChassisCDScde2802h13" {
    smiv2:oid "1.3.6.1.4.1.9.12.3.1.3.1646";
  }

  smiv2:alias "cevChassisCDScde2802h26" {
    smiv2:oid "1.3.6.1.4.1.9.12.3.1.3.1647";
  }

  smiv2:alias "cevChassis841Mx4X" {
    smiv2:oid "1.3.6.1.4.1.9.12.3.1.3.1650";
  }

  smiv2:alias "cevChassis841Mx8X" {
    smiv2:oid "1.3.6.1.4.1.9.12.3.1.3.1651";
  }

  smiv2:alias "cevChassisN2kC2332TQ10GE" {
    smiv2:oid "1.3.6.1.4.1.9.12.3.1.3.1652";
  }

  smiv2:alias "cevChassisSce10000" {
    smiv2:oid "1.3.6.1.4.1.9.12.3.1.3.1654";
  }

  smiv2:alias "cevChassisDSC9396SK9" {
    smiv2:oid "1.3.6.1.4.1.9.12.3.1.3.1660";
  }

  smiv2:alias "cevBackplane" {
    smiv2:oid "1.3.6.1.4.1.9.12.3.1.4";
  }

  smiv2:alias "cevBackplaneAtm" {
    smiv2:oid "1.3.6.1.4.1.9.12.3.1.4.4";
  }

  smiv2:alias "cevBackplaneCat5500" {
    smiv2:oid "1.3.6.1.4.1.9.12.3.1.4.5";
  }

  smiv2:alias "cevBackplaneCat6400" {
    smiv2:oid "1.3.6.1.4.1.9.12.3.1.4.6";
  }

  smiv2:alias "cevBackplaneCat8510" {
    smiv2:oid "1.3.6.1.4.1.9.12.3.1.4.7";
  }

  smiv2:alias "cevBackplaneCat8540" {
    smiv2:oid "1.3.6.1.4.1.9.12.3.1.4.8";
  }

  smiv2:alias "cevBackplaneMGX8850" {
    smiv2:oid "1.3.6.1.4.1.9.12.3.1.4.9";
  }

  smiv2:alias "cevBackplaneMGX8820" {
    smiv2:oid "1.3.6.1.4.1.9.12.3.1.4.10";
  }

  smiv2:alias "cevBackplaneBPXSes" {
    smiv2:oid "1.3.6.1.4.1.9.12.3.1.4.11";
  }

  smiv2:alias "cevBackplaneIGXSes" {
    smiv2:oid "1.3.6.1.4.1.9.12.3.1.4.12";
  }

  smiv2:alias "cevBackplaneCat6000" {
    smiv2:oid "1.3.6.1.4.1.9.12.3.1.4.13";
  }

  smiv2:alias "cevBackplaneCat6500" {
    smiv2:oid "1.3.6.1.4.1.9.12.3.1.4.14";
  }

  smiv2:alias "cevBackplaneMGX8950" {
    smiv2:oid "1.3.6.1.4.1.9.12.3.1.4.15";
  }

  smiv2:alias "cevBackplaneONS15540Fixed" {
    smiv2:oid "1.3.6.1.4.1.9.12.3.1.4.16";
  }

  smiv2:alias "cevBackplaneCat4006" {
    smiv2:oid "1.3.6.1.4.1.9.12.3.1.4.18";
  }

  smiv2:alias "cevBackplaneMGX8830" {
    smiv2:oid "1.3.6.1.4.1.9.12.3.1.4.19";
  }

  smiv2:alias "cevBackplaneONS15530" {
    smiv2:oid "1.3.6.1.4.1.9.12.3.1.4.20";
  }

  smiv2:alias "cevBackplaneCat4507" {
    smiv2:oid "1.3.6.1.4.1.9.12.3.1.4.23";
  }

  smiv2:alias "cevBackplaneCat4503" {
    smiv2:oid "1.3.6.1.4.1.9.12.3.1.4.24";
  }

  smiv2:alias "cevBackplaneCat4506" {
    smiv2:oid "1.3.6.1.4.1.9.12.3.1.4.25";
  }

  smiv2:alias "cevBackplaneDSC9506" {
    smiv2:oid "1.3.6.1.4.1.9.12.3.1.4.26";
  }

  smiv2:alias "cevBackplaneDSC9509" {
    smiv2:oid "1.3.6.1.4.1.9.12.3.1.4.27";
  }

  smiv2:alias "cevBackplaneDSC9513" {
    smiv2:oid "1.3.6.1.4.1.9.12.3.1.4.28";
  }

  smiv2:alias "cevBackplaneONS15540ESPx" {
    smiv2:oid "1.3.6.1.4.1.9.12.3.1.4.29";
  }

  smiv2:alias "cevBackplaneUnknown" {
    smiv2:oid "1.3.6.1.4.1.9.12.3.1.4.30";
  }

  smiv2:alias "cevBackplaneCat4510" {
    smiv2:oid "1.3.6.1.4.1.9.12.3.1.4.31";
  }

  smiv2:alias "cevBackplaneDSC9140K9" {
    smiv2:oid "1.3.6.1.4.1.9.12.3.1.4.32";
  }

  smiv2:alias "cevBackplaneBMGX8850" {
    smiv2:oid "1.3.6.1.4.1.9.12.3.1.4.33";
  }

  smiv2:alias "cevBackplaneBMGX8950" {
    smiv2:oid "1.3.6.1.4.1.9.12.3.1.4.34";
  }

  smiv2:alias "cevBackplaneCisco7600" {
    smiv2:oid "1.3.6.1.4.1.9.12.3.1.4.35";
  }

  smiv2:alias "cevBackplaneBMGX8830" {
    smiv2:oid "1.3.6.1.4.1.9.12.3.1.4.36";
  }

  smiv2:alias "cevBackplaneDSC9216AK9" {
    smiv2:oid "1.3.6.1.4.1.9.12.3.1.4.37";
  }

  smiv2:alias "cevBackplaneMGX8880" {
    smiv2:oid "1.3.6.1.4.1.9.12.3.1.4.38";
  }

  smiv2:alias "cevBackplane6SlotsRCON8850" {
    smiv2:oid "1.3.6.1.4.1.9.12.3.1.4.39";
  }

  smiv2:alias "cevBackplane4SlotsRCON8850" {
    smiv2:oid "1.3.6.1.4.1.9.12.3.1.4.40";
  }

  smiv2:alias "cevBackplane4SlotsRCON8830" {
    smiv2:oid "1.3.6.1.4.1.9.12.3.1.4.41";
  }

  smiv2:alias "cevBackplaneDSX9116K9" {
    smiv2:oid "1.3.6.1.4.1.9.12.3.1.4.42";
  }

  smiv2:alias "cevBackplaneONS15310" {
    smiv2:oid "1.3.6.1.4.1.9.12.3.1.4.43";
  }

  smiv2:alias "cevBackplaneCat4503e" {
    smiv2:oid "1.3.6.1.4.1.9.12.3.1.4.48";
  }

  smiv2:alias "cevBackplaneCat4506e" {
    smiv2:oid "1.3.6.1.4.1.9.12.3.1.4.49";
  }

  smiv2:alias "cevBackplaneCat4507re" {
    smiv2:oid "1.3.6.1.4.1.9.12.3.1.4.50";
  }

  smiv2:alias "cevBackplaneCat4510re" {
    smiv2:oid "1.3.6.1.4.1.9.12.3.1.4.51";
  }

  smiv2:alias "cevBackplaneN7Kc7010" {
    smiv2:oid "1.3.6.1.4.1.9.12.3.1.4.52";
  }

  smiv2:alias "cevBackplaneCatRfgw" {
    smiv2:oid "1.3.6.1.4.1.9.12.3.1.4.53";
  }

  smiv2:alias "cevBackplaneN7Kc7018" {
    smiv2:oid "1.3.6.1.4.1.9.12.3.1.4.55";
  }

  smiv2:alias "cevBackplaneMXE5600" {
    smiv2:oid "1.3.6.1.4.1.9.12.3.1.4.56";
  }

  smiv2:alias "cevBackplaneN7Kc7009" {
    smiv2:oid "1.3.6.1.4.1.9.12.3.1.4.57";
  }

  smiv2:alias "cevBackplaneN7Kc7004" {
    smiv2:oid "1.3.6.1.4.1.9.12.3.1.4.61";
  }

  smiv2:alias "cevBackplaneDSC9710" {
    smiv2:oid "1.3.6.1.4.1.9.12.3.1.4.63";
  }

  smiv2:alias "cevBackplaneN77c7718" {
    smiv2:oid "1.3.6.1.4.1.9.12.3.1.4.64";
  }

  smiv2:alias "cevBackplaneN77c7710" {
    smiv2:oid "1.3.6.1.4.1.9.12.3.1.4.65";
  }

  smiv2:alias "cevBackplaneN77c7706" {
    smiv2:oid "1.3.6.1.4.1.9.12.3.1.4.66";
  }

  smiv2:alias "cevBackplaneCat6800" {
    smiv2:oid "1.3.6.1.4.1.9.12.3.1.4.67";
  }

  smiv2:alias "cevBackplaneDSC9706" {
    smiv2:oid "1.3.6.1.4.1.9.12.3.1.4.68";
  }

  smiv2:alias "cevBackPlaneN2kC2332TQ" {
    smiv2:oid "1.3.6.1.4.1.9.12.3.1.4.71";
  }

  smiv2:alias "cevContainer" {
    smiv2:oid "1.3.6.1.4.1.9.12.3.1.5";
  }

  smiv2:alias "cevContainerSlot" {
    smiv2:oid "1.3.6.1.4.1.9.12.3.1.5.1";
  }

  smiv2:alias "cevContainerDaughterCard" {
    smiv2:oid "1.3.6.1.4.1.9.12.3.1.5.2";
  }

  smiv2:alias "cevContainerPCMCIA" {
    smiv2:oid "1.3.6.1.4.1.9.12.3.1.5.12";
  }

  smiv2:alias "cevContainerDSPModuleSlot" {
    smiv2:oid "1.3.6.1.4.1.9.12.3.1.5.16";
  }

  smiv2:alias "cevContainerCat8500Carrier" {
    smiv2:oid "1.3.6.1.4.1.9.12.3.1.5.17";
  }

  smiv2:alias "cevContainerCat8500CpuSwitchAndFeature" {
    smiv2:oid "1.3.6.1.4.1.9.12.3.1.5.18";
  }

  smiv2:alias "cevContainerCat8500CpuSwitchAndFeaturePFQ" {
    smiv2:oid "1.3.6.1.4.1.9.12.3.1.5.19";
  }

  smiv2:alias "cevContainerCat8500SuperCarrier" {
    smiv2:oid "1.3.6.1.4.1.9.12.3.1.5.20";
  }

  smiv2:alias "cevContainerCat8500CpuRoute" {
    smiv2:oid "1.3.6.1.4.1.9.12.3.1.5.21";
  }

  smiv2:alias "cevContainerCat8500Switch10GAndFC" {
    smiv2:oid "1.3.6.1.4.1.9.12.3.1.5.22";
  }

  smiv2:alias "cevContainerCat8500Switch10GNoFC" {
    smiv2:oid "1.3.6.1.4.1.9.12.3.1.5.23";
  }

  smiv2:alias "cevContainerDslamSlot" {
    smiv2:oid "1.3.6.1.4.1.9.12.3.1.5.24";
  }

  smiv2:alias "cevContainerC6260PsSlot" {
    smiv2:oid "1.3.6.1.4.1.9.12.3.1.5.25";
  }

  smiv2:alias "cevContainerC6260FanSlot" {
    smiv2:oid "1.3.6.1.4.1.9.12.3.1.5.26";
  }

  smiv2:alias "cevContainerDslamControllerSlot" {
    smiv2:oid "1.3.6.1.4.1.9.12.3.1.5.27";
  }

  smiv2:alias "cevContainerDslamNi2DcSlot" {
    smiv2:oid "1.3.6.1.4.1.9.12.3.1.5.28";
  }

  smiv2:alias "cevContainerPsmSlot" {
    smiv2:oid "1.3.6.1.4.1.9.12.3.1.5.31";
  }

  smiv2:alias "cevContainerSmSlot" {
    smiv2:oid "1.3.6.1.4.1.9.12.3.1.5.32";
  }

  smiv2:alias "cevContainerMGX8800FanTray" {
    smiv2:oid "1.3.6.1.4.1.9.12.3.1.5.33";
  }

  smiv2:alias "cevContainerSrmSlot" {
    smiv2:oid "1.3.6.1.4.1.9.12.3.1.5.34";
  }

  smiv2:alias "cevContainerMGX8800ACPSTray" {
    smiv2:oid "1.3.6.1.4.1.9.12.3.1.5.35";
  }

  smiv2:alias "cevContainerSESFanTray" {
    smiv2:oid "1.3.6.1.4.1.9.12.3.1.5.36";
  }

  smiv2:alias "cevContainer12012TopBlowerBay" {
    smiv2:oid "1.3.6.1.4.1.9.12.3.1.5.37";
  }

  smiv2:alias "cevContainer12012BottomBlowerBay" {
    smiv2:oid "1.3.6.1.4.1.9.12.3.1.5.38";
  }

  smiv2:alias "cevContainer12012ModuleBay" {
    smiv2:oid "1.3.6.1.4.1.9.12.3.1.5.39";
  }

  smiv2:alias "cevContainer12012SwitchFabricBay" {
    smiv2:oid "1.3.6.1.4.1.9.12.3.1.5.40";
  }

  smiv2:alias "cevContainer12012PowerSupplyBay" {
    smiv2:oid "1.3.6.1.4.1.9.12.3.1.5.41";
  }

  smiv2:alias "cevContainer12008PowerBlowerBay" {
    smiv2:oid "1.3.6.1.4.1.9.12.3.1.5.42";
  }

  smiv2:alias "cevContainer12008MainBlowerBay" {
    smiv2:oid "1.3.6.1.4.1.9.12.3.1.5.43";
  }

  smiv2:alias "cevContainer12008ModuleBay" {
    smiv2:oid "1.3.6.1.4.1.9.12.3.1.5.44";
  }

  smiv2:alias "cevContainer12008SwitchFabricBay" {
    smiv2:oid "1.3.6.1.4.1.9.12.3.1.5.45";
  }

  smiv2:alias "cevContainer12008PowerSupplyBay" {
    smiv2:oid "1.3.6.1.4.1.9.12.3.1.5.46";
  }

  smiv2:alias "cevContainerC6160PsSlot" {
    smiv2:oid "1.3.6.1.4.1.9.12.3.1.5.48";
  }

  smiv2:alias "cevContainerC6160FanSlot" {
    smiv2:oid "1.3.6.1.4.1.9.12.3.1.5.49";
  }

  smiv2:alias "cevContainerMGXXm60Slot" {
    smiv2:oid "1.3.6.1.4.1.9.12.3.1.5.52";
  }

  smiv2:alias "cevContainerCat8500CMPMCarrier" {
    smiv2:oid "1.3.6.1.4.1.9.12.3.1.5.55";
  }

  smiv2:alias "cevContainer12010TopBlowerBay" {
    smiv2:oid "1.3.6.1.4.1.9.12.3.1.5.56";
  }

  smiv2:alias "cevContainer12010BottomBlowerBay" {
    smiv2:oid "1.3.6.1.4.1.9.12.3.1.5.57";
  }

  smiv2:alias "cevContainer12010UpperModuleBay" {
    smiv2:oid "1.3.6.1.4.1.9.12.3.1.5.58";
  }

  smiv2:alias "cevContainer12010LowerModuleBay" {
    smiv2:oid "1.3.6.1.4.1.9.12.3.1.5.59";
  }

  smiv2:alias "cevContainer12010SwitchFabricBay" {
    smiv2:oid "1.3.6.1.4.1.9.12.3.1.5.60";
  }

  smiv2:alias "cevContainer12010PowerSupplyBay" {
    smiv2:oid "1.3.6.1.4.1.9.12.3.1.5.61";
  }

  smiv2:alias "cevContainer12010PowerBlowerBay" {
    smiv2:oid "1.3.6.1.4.1.9.12.3.1.5.62";
  }

  smiv2:alias "cevContainer12010MainBlowerBay" {
    smiv2:oid "1.3.6.1.4.1.9.12.3.1.5.63";
  }

  smiv2:alias "cevContainer12406ModuleBay" {
    smiv2:oid "1.3.6.1.4.1.9.12.3.1.5.64";
  }

  smiv2:alias "cevContainer12406FabricAlarmBay" {
    smiv2:oid "1.3.6.1.4.1.9.12.3.1.5.65";
  }

  smiv2:alias "cevContainer12406PowerSupplyBay" {
    smiv2:oid "1.3.6.1.4.1.9.12.3.1.5.66";
  }

  smiv2:alias "cevContainer12406MainBlowerBay" {
    smiv2:oid "1.3.6.1.4.1.9.12.3.1.5.67";
  }

  smiv2:alias "cevContainer12410TopBlowerBay" {
    smiv2:oid "1.3.6.1.4.1.9.12.3.1.5.68";
  }

  smiv2:alias "cevContainer12410BottomBlowerBay" {
    smiv2:oid "1.3.6.1.4.1.9.12.3.1.5.69";
  }

  smiv2:alias "cevContainer12410UpperModuleBay" {
    smiv2:oid "1.3.6.1.4.1.9.12.3.1.5.70";
  }

  smiv2:alias "cevContainer12410LowerModuleBay" {
    smiv2:oid "1.3.6.1.4.1.9.12.3.1.5.71";
  }

  smiv2:alias "cevContainer12410SwitchFabricBay" {
    smiv2:oid "1.3.6.1.4.1.9.12.3.1.5.72";
  }

  smiv2:alias "cevContainer12410PowerSupplyBay" {
    smiv2:oid "1.3.6.1.4.1.9.12.3.1.5.73";
  }

  smiv2:alias "cevContainer12410PowerBlowerBay" {
    smiv2:oid "1.3.6.1.4.1.9.12.3.1.5.74";
  }

  smiv2:alias "cevContainer12410MainBlowerBay" {
    smiv2:oid "1.3.6.1.4.1.9.12.3.1.5.75";
  }

  smiv2:alias "cevContainerONS15540CardSlot" {
    smiv2:oid "1.3.6.1.4.1.9.12.3.1.5.76";
  }

  smiv2:alias "cevContainerONS15540FanTraySlot" {
    smiv2:oid "1.3.6.1.4.1.9.12.3.1.5.77";
  }

  smiv2:alias "cevContainerONS15540TspSubslot" {
    smiv2:oid "1.3.6.1.4.1.9.12.3.1.5.78";
  }

  smiv2:alias "cevContainerONS15540MDXSubslot" {
    smiv2:oid "1.3.6.1.4.1.9.12.3.1.5.79";
  }

  smiv2:alias "cevContainerONS15540SubCardSlot" {
    smiv2:oid "1.3.6.1.4.1.9.12.3.1.5.80";
  }

  smiv2:alias "cevContainer12404ModuleBay" {
    smiv2:oid "1.3.6.1.4.1.9.12.3.1.5.81";
  }

  smiv2:alias "cevContainer12404FabricAlarmBay" {
    smiv2:oid "1.3.6.1.4.1.9.12.3.1.5.82";
  }

  smiv2:alias "cevContainer12404PowerSupplyBay" {
    smiv2:oid "1.3.6.1.4.1.9.12.3.1.5.83";
  }

  smiv2:alias "cevContainer12404MainBlowerBay" {
    smiv2:oid "1.3.6.1.4.1.9.12.3.1.5.84";
  }

  smiv2:alias "cevContainerC7304PowerSupplyBay" {
    smiv2:oid "1.3.6.1.4.1.9.12.3.1.5.85";
  }

  smiv2:alias "cevContainerC10KSlot" {
    smiv2:oid "1.3.6.1.4.1.9.12.3.1.5.86";
  }

  smiv2:alias "cevContainerC10KPowerSupplySlot" {
    smiv2:oid "1.3.6.1.4.1.9.12.3.1.5.87";
  }

  smiv2:alias "cevContainerC10KFanTraySlot" {
    smiv2:oid "1.3.6.1.4.1.9.12.3.1.5.88";
  }

  smiv2:alias "cevContainerC10KFlashCardSlot" {
    smiv2:oid "1.3.6.1.4.1.9.12.3.1.5.89";
  }

  smiv2:alias "cevContainerCat4kFanTrayBay" {
    smiv2:oid "1.3.6.1.4.1.9.12.3.1.5.90";
  }

  smiv2:alias "cevContainerCat4kPowerSupplyBay" {
    smiv2:oid "1.3.6.1.4.1.9.12.3.1.5.91";
  }

  smiv2:alias "cevContainerCat4kPEMBay" {
    smiv2:oid "1.3.6.1.4.1.9.12.3.1.5.92";
  }

  smiv2:alias "cevContainer12016PowerBlowerBay" {
    smiv2:oid "1.3.6.1.4.1.9.12.3.1.5.93";
  }

  smiv2:alias "cevContainer12016LowerModuleBay" {
    smiv2:oid "1.3.6.1.4.1.9.12.3.1.5.94";
  }

  smiv2:alias "cevContainer12016SwitchFabricBay" {
    smiv2:oid "1.3.6.1.4.1.9.12.3.1.5.95";
  }

  smiv2:alias "cevContainer12016PowerSupplyBay" {
    smiv2:oid "1.3.6.1.4.1.9.12.3.1.5.96";
  }

  smiv2:alias "cevContainer12016TopBlowerBay" {
    smiv2:oid "1.3.6.1.4.1.9.12.3.1.5.97";
  }

  smiv2:alias "cevContainer12016BottomBlowerBay" {
    smiv2:oid "1.3.6.1.4.1.9.12.3.1.5.98";
  }

  smiv2:alias "cevContainer12016UpperModuleBay" {
    smiv2:oid "1.3.6.1.4.1.9.12.3.1.5.99";
  }

  smiv2:alias "cevContainerONS15530CardSlot" {
    smiv2:oid "1.3.6.1.4.1.9.12.3.1.5.100";
  }

  smiv2:alias "cevContainerONS15530FanTraySlot" {
    smiv2:oid "1.3.6.1.4.1.9.12.3.1.5.102";
  }

  smiv2:alias "cevContainerONS15530PSSlot" {
    smiv2:oid "1.3.6.1.4.1.9.12.3.1.5.103";
  }

  smiv2:alias "cevContainerONS15530SubCardSlot" {
    smiv2:oid "1.3.6.1.4.1.9.12.3.1.5.104";
  }

  smiv2:alias "cevContainerONS15530PortSlot" {
    smiv2:oid "1.3.6.1.4.1.9.12.3.1.5.105";
  }

  smiv2:alias "cevContainerONS15540PortSlot" {
    smiv2:oid "1.3.6.1.4.1.9.12.3.1.5.106";
  }

  smiv2:alias "cevContainerCat4kContainerPSBay" {
    smiv2:oid "1.3.6.1.4.1.9.12.3.1.5.111";
  }

  smiv2:alias "cevContainerSPABay" {
    smiv2:oid "1.3.6.1.4.1.9.12.3.1.5.114";
  }

  smiv2:alias "cevContainerSFP" {
    smiv2:oid "1.3.6.1.4.1.9.12.3.1.5.115";
  }

  smiv2:alias "cevContainerGsrAlarmSlot" {
    smiv2:oid "1.3.6.1.4.1.9.12.3.1.5.116";
  }

  smiv2:alias "cevContainerGsrPowerSupplySlot" {
    smiv2:oid "1.3.6.1.4.1.9.12.3.1.5.117";
  }

  smiv2:alias "cevContainerGsrFanBlowerSlot" {
    smiv2:oid "1.3.6.1.4.1.9.12.3.1.5.118";
  }

  smiv2:alias "cevContainerGsrSwitchFabricSlot" {
    smiv2:oid "1.3.6.1.4.1.9.12.3.1.5.119";
  }

  smiv2:alias "cevContainerONS15252CardSlot" {
    smiv2:oid "1.3.6.1.4.1.9.12.3.1.5.120";
  }

  smiv2:alias "cevContainerONS15201CardSlot" {
    smiv2:oid "1.3.6.1.4.1.9.12.3.1.5.121";
  }

  smiv2:alias "cevContainerSupFabricSlot" {
    smiv2:oid "1.3.6.1.4.1.9.12.3.1.5.122";
  }

  smiv2:alias "cevContainerLineCardSlot" {
    smiv2:oid "1.3.6.1.4.1.9.12.3.1.5.123";
  }

  smiv2:alias "cevContainer9506PowerSupplyBay" {
    smiv2:oid "1.3.6.1.4.1.9.12.3.1.5.124";
  }

  smiv2:alias "cevContainer9509PowerSupplyBay" {
    smiv2:oid "1.3.6.1.4.1.9.12.3.1.5.125";
  }

  smiv2:alias "cevContainer9513PowerSupplyBay" {
    smiv2:oid "1.3.6.1.4.1.9.12.3.1.5.126";
  }

  smiv2:alias "cevContainer9506FanBay" {
    smiv2:oid "1.3.6.1.4.1.9.12.3.1.5.127";
  }

  smiv2:alias "cevContainer9509FanBay" {
    smiv2:oid "1.3.6.1.4.1.9.12.3.1.5.128";
  }

  smiv2:alias "cevContainer9513FanBay" {
    smiv2:oid "1.3.6.1.4.1.9.12.3.1.5.129";
  }

  smiv2:alias "cevContainer9216FanBay" {
    smiv2:oid "1.3.6.1.4.1.9.12.3.1.5.130";
  }

  smiv2:alias "cevContainer9216PowerSupplyBay" {
    smiv2:oid "1.3.6.1.4.1.9.12.3.1.5.131";
  }

  smiv2:alias "cevContainerC7300CCPA" {
    smiv2:oid "1.3.6.1.4.1.9.12.3.1.5.132";
  }

  smiv2:alias "cevContainerPABay" {
    smiv2:oid "1.3.6.1.4.1.9.12.3.1.5.133";
  }

  smiv2:alias "cevChassisCr4430" {
    smiv2:oid "1.3.6.1.4.1.9.12.3.1.5.134";
  }

  smiv2:alias "cevMgx2uPlenumFanTray" {
    smiv2:oid "1.3.6.1.4.1.9.12.3.1.5.135";
  }

  smiv2:alias "cevContainerMDSPowerSupplyBay" {
    smiv2:oid "1.3.6.1.4.1.9.12.3.1.5.136";
  }

  smiv2:alias "cevContainerMDSFanTrayBay" {
    smiv2:oid "1.3.6.1.4.1.9.12.3.1.5.137";
  }

  smiv2:alias "cevContainerFlashCardSlot" {
    smiv2:oid "1.3.6.1.4.1.9.12.3.1.5.138";
  }

  smiv2:alias "cevContainerFanTraySlot" {
    smiv2:oid "1.3.6.1.4.1.9.12.3.1.5.139";
  }

  smiv2:alias "cevContainerPowerSupplyBay" {
    smiv2:oid "1.3.6.1.4.1.9.12.3.1.5.140";
  }

  smiv2:alias "cevContainerPowerSupply" {
    smiv2:oid "1.3.6.1.4.1.9.12.3.1.5.141";
  }

  smiv2:alias "cevContainerGbic" {
    smiv2:oid "1.3.6.1.4.1.9.12.3.1.5.142";
  }

  smiv2:alias "cevContainerCrs1RPSlot" {
    smiv2:oid "1.3.6.1.4.1.9.12.3.1.5.143";
  }

  smiv2:alias "cevContainerCrs1LCDRPSlot" {
    smiv2:oid "1.3.6.1.4.1.9.12.3.1.5.144";
  }

  smiv2:alias "cevContainerCrs1FabricSlot" {
    smiv2:oid "1.3.6.1.4.1.9.12.3.1.5.145";
  }

  smiv2:alias "cevContainerCrs1AlarmSlot" {
    smiv2:oid "1.3.6.1.4.1.9.12.3.1.5.146";
  }

  smiv2:alias "cevContainerCrs1PowerSupplySlot" {
    smiv2:oid "1.3.6.1.4.1.9.12.3.1.5.147";
  }

  smiv2:alias "cevContainerCrs1FanSlot" {
    smiv2:oid "1.3.6.1.4.1.9.12.3.1.5.148";
  }

  smiv2:alias "cevContainerPowerSupplySlot" {
    smiv2:oid "1.3.6.1.4.1.9.12.3.1.5.149";
  }

  smiv2:alias "cevContainerVtt" {
    smiv2:oid "1.3.6.1.4.1.9.12.3.1.5.150";
  }

  smiv2:alias "cevContainerClock" {
    smiv2:oid "1.3.6.1.4.1.9.12.3.1.5.151";
  }

  smiv2:alias "cevContainer10GigBasePort" {
    smiv2:oid "1.3.6.1.4.1.9.12.3.1.5.152";
  }

  smiv2:alias "cevContainerUmg9820ProcessorCard" {
    smiv2:oid "1.3.6.1.4.1.9.12.3.1.5.153";
  }

  smiv2:alias "cevContainerUmg9820PowerSupplyBay" {
    smiv2:oid "1.3.6.1.4.1.9.12.3.1.5.154";
  }

  smiv2:alias "cevContainerUmg9820QamModuleSlot" {
    smiv2:oid "1.3.6.1.4.1.9.12.3.1.5.155";
  }

  smiv2:alias "cevContainerUmg9820FanTraySlot" {
    smiv2:oid "1.3.6.1.4.1.9.12.3.1.5.156";
  }

  smiv2:alias "cevContainer9116FanBay" {
    smiv2:oid "1.3.6.1.4.1.9.12.3.1.5.157";
  }

  smiv2:alias "cevContainer9116PowerSupplyBay" {
    smiv2:oid "1.3.6.1.4.1.9.12.3.1.5.158";
  }

  smiv2:alias "cevContainerONS15310CardSlot" {
    smiv2:oid "1.3.6.1.4.1.9.12.3.1.5.159";
  }

  smiv2:alias "cevContainerGSR6Blwr" {
    smiv2:oid "1.3.6.1.4.1.9.12.3.1.5.160";
  }

  smiv2:alias "cevContainerGSR10GSR16Blwr" {
    smiv2:oid "1.3.6.1.4.1.9.12.3.1.5.161";
  }

  smiv2:alias "cevContainer9513RearFanBay" {
    smiv2:oid "1.3.6.1.4.1.9.12.3.1.5.162";
  }

  smiv2:alias "cevContainerFabricSlot" {
    smiv2:oid "1.3.6.1.4.1.9.12.3.1.5.163";
  }

  smiv2:alias "cevContainerCrs18RPSlot" {
    smiv2:oid "1.3.6.1.4.1.9.12.3.1.5.164";
  }

  smiv2:alias "cevContainerCrs18FabricSlot" {
    smiv2:oid "1.3.6.1.4.1.9.12.3.1.5.165";
  }

  smiv2:alias "cevContainerCrs1FabricShelfControllerSlot" {
    smiv2:oid "1.3.6.1.4.1.9.12.3.1.5.166";
  }

  smiv2:alias "cevContainerCrs1FabricSwitchFabricSlot" {
    smiv2:oid "1.3.6.1.4.1.9.12.3.1.5.167";
  }

  smiv2:alias "cevContainerCrs1FabricFiberModuleSlot" {
    smiv2:oid "1.3.6.1.4.1.9.12.3.1.5.168";
  }

  smiv2:alias "cevContainerCrs1FabricLEDModuleSlot" {
    smiv2:oid "1.3.6.1.4.1.9.12.3.1.5.169";
  }

  smiv2:alias "cevPowerSupplyCrs1PowerSupplyShelf" {
    smiv2:oid "1.3.6.1.4.1.9.12.3.1.5.170";
  }

  smiv2:alias "cevContainerTransceiver" {
    smiv2:oid "1.3.6.1.4.1.9.12.3.1.5.171";
  }

  smiv2:alias "cevContainer9124PowerSupplyBay" {
    smiv2:oid "1.3.6.1.4.1.9.12.3.1.5.173";
  }

  smiv2:alias "cevContainer9124FanBay" {
    smiv2:oid "1.3.6.1.4.1.9.12.3.1.5.174";
  }

  smiv2:alias "cevContainerC3KPowerSupply" {
    smiv2:oid "1.3.6.1.4.1.9.12.3.1.5.175";
  }

  smiv2:alias "cevContainerC3KRemotePowerSupply" {
    smiv2:oid "1.3.6.1.4.1.9.12.3.1.5.176";
  }

  smiv2:alias "cevContainerC3KBlower" {
    smiv2:oid "1.3.6.1.4.1.9.12.3.1.5.177";
  }

  smiv2:alias "cevContainer9222iFanBay" {
    smiv2:oid "1.3.6.1.4.1.9.12.3.1.5.178";
  }

  smiv2:alias "cevContainerN7Kc7010PowerSupplyBay" {
    smiv2:oid "1.3.6.1.4.1.9.12.3.1.5.179";
  }

  smiv2:alias "cevContainerN7KC7010MainFanBay" {
    smiv2:oid "1.3.6.1.4.1.9.12.3.1.5.180";
  }

  smiv2:alias "cevContainerN7KC7010FabricFanBay" {
    smiv2:oid "1.3.6.1.4.1.9.12.3.1.5.181";
  }

  smiv2:alias "cevContainerASR1000RPSlot" {
    smiv2:oid "1.3.6.1.4.1.9.12.3.1.5.182";
  }

  smiv2:alias "cevContainerASR1000FPSlot" {
    smiv2:oid "1.3.6.1.4.1.9.12.3.1.5.183";
  }

  smiv2:alias "cevContainerASR1000CCSlot" {
    smiv2:oid "1.3.6.1.4.1.9.12.3.1.5.184";
  }

  smiv2:alias "cevContainerASR1000PowerSupplyBay" {
    smiv2:oid "1.3.6.1.4.1.9.12.3.1.5.185";
  }

  smiv2:alias "cevContainerN5kC5020FanBay" {
    smiv2:oid "1.3.6.1.4.1.9.12.3.1.5.186";
  }

  smiv2:alias "cevContainerN5kC5020PowerSupplyBay" {
    smiv2:oid "1.3.6.1.4.1.9.12.3.1.5.187";
  }

  smiv2:alias "cevContainerASR9KFanTraySlot" {
    smiv2:oid "1.3.6.1.4.1.9.12.3.1.5.188";
  }

  smiv2:alias "cevContainerASR9KPowerSupplySlotDC" {
    smiv2:oid "1.3.6.1.4.1.9.12.3.1.5.189";
  }

  smiv2:alias "cevContainerASR9KPowerSupplySlotAC" {
    smiv2:oid "1.3.6.1.4.1.9.12.3.1.5.190";
  }

  smiv2:alias "cevContainerASR9KRSPSlot" {
    smiv2:oid "1.3.6.1.4.1.9.12.3.1.5.191";
  }

  smiv2:alias "cevContainerASR9KLCSlot" {
    smiv2:oid "1.3.6.1.4.1.9.12.3.1.5.192";
  }

  smiv2:alias "cevContainerN7Kc7018PowerSupplyBay" {
    smiv2:oid "1.3.6.1.4.1.9.12.3.1.5.193";
  }

  smiv2:alias "cevContainerN7KC7018FanBay" {
    smiv2:oid "1.3.6.1.4.1.9.12.3.1.5.194";
  }

  smiv2:alias "cevContainerCrs1PowerShelfSlot" {
    smiv2:oid "1.3.6.1.4.1.9.12.3.1.5.195";
  }

  smiv2:alias "cevContainerN5kC5010FanBay" {
    smiv2:oid "1.3.6.1.4.1.9.12.3.1.5.196";
  }

  smiv2:alias "cevContainerN5kC5010PowerSupplyBay" {
    smiv2:oid "1.3.6.1.4.1.9.12.3.1.5.197";
  }

  smiv2:alias "cevContainerXFP" {
    smiv2:oid "1.3.6.1.4.1.9.12.3.1.5.198";
  }

  smiv2:alias "cevContainerAsr14kPowerSupplySlot" {
    smiv2:oid "1.3.6.1.4.1.9.12.3.1.5.199";
  }

  smiv2:alias "cevContainerAsr14kPowerShelfSlot" {
    smiv2:oid "1.3.6.1.4.1.9.12.3.1.5.200";
  }

  smiv2:alias "cevContainerAsr14kFanTraySlot" {
    smiv2:oid "1.3.6.1.4.1.9.12.3.1.5.201";
  }

  smiv2:alias "cevContainerAsr14kFabricCardSlot" {
    smiv2:oid "1.3.6.1.4.1.9.12.3.1.5.202";
  }

  smiv2:alias "cevContainerAsr14kFPSlot" {
    smiv2:oid "1.3.6.1.4.1.9.12.3.1.5.203";
  }

  smiv2:alias "cevContainerAsr14kRPSlot" {
    smiv2:oid "1.3.6.1.4.1.9.12.3.1.5.204";
  }

  smiv2:alias "cevContainerHardDiskSlot" {
    smiv2:oid "1.3.6.1.4.1.9.12.3.1.5.205";
  }

  smiv2:alias "cevContainerNexusLogicalFabric" {
    smiv2:oid "1.3.6.1.4.1.9.12.3.1.5.206";
  }

  smiv2:alias "cevContainerN2kC2148T1GEPowerSupplyBay" {
    smiv2:oid "1.3.6.1.4.1.9.12.3.1.5.207";
  }

  smiv2:alias "cevContainerN2kC2148T1GEFanBay" {
    smiv2:oid "1.3.6.1.4.1.9.12.3.1.5.208";
  }

  smiv2:alias "cevContainerUCSN10S6100FanBay" {
    smiv2:oid "1.3.6.1.4.1.9.12.3.1.5.209";
  }

  smiv2:alias "cevContainerUCSN10S6100PowerSupplyBay" {
    smiv2:oid "1.3.6.1.4.1.9.12.3.1.5.210";
  }

  smiv2:alias "cevContainerMXE5600PowerSupplyBay" {
    smiv2:oid "1.3.6.1.4.1.9.12.3.1.5.213";
  }

  smiv2:alias "cevContainerMXE5600FanTray" {
    smiv2:oid "1.3.6.1.4.1.9.12.3.1.5.214";
  }

  smiv2:alias "cevContainerN2kC2248TP1GEPowerSupplyBay" {
    smiv2:oid "1.3.6.1.4.1.9.12.3.1.5.218";
  }

  smiv2:alias "cevContainerN7Kc7009PowerSupplyBay" {
    smiv2:oid "1.3.6.1.4.1.9.12.3.1.5.219";
  }

  smiv2:alias "cevContainerN7KC7009FanBay" {
    smiv2:oid "1.3.6.1.4.1.9.12.3.1.5.220";
  }

  smiv2:alias "cevContainerFruLinkModuleSlot" {
    smiv2:oid "1.3.6.1.4.1.9.12.3.1.5.221";
  }

  smiv2:alias "cevContainerFlexStackModuleSlot" {
    smiv2:oid "1.3.6.1.4.1.9.12.3.1.5.222";
  }

  smiv2:alias "cevContainerMXE5600ShelfManagerBay" {
    smiv2:oid "1.3.6.1.4.1.9.12.3.1.5.223";
  }

  smiv2:alias "cevContainerMXE5600NpmSlot" {
    smiv2:oid "1.3.6.1.4.1.9.12.3.1.5.224";
  }

  smiv2:alias "cevContainerMXE5600MpmSlot" {
    smiv2:oid "1.3.6.1.4.1.9.12.3.1.5.225";
  }

  smiv2:alias "cevContainerN5KC5548FanBay" {
    smiv2:oid "1.3.6.1.4.1.9.12.3.1.5.226";
  }

  smiv2:alias "cevContainerN5kC5548PowerSupplyBay" {
    smiv2:oid "1.3.6.1.4.1.9.12.3.1.5.227";
  }

  smiv2:alias "cevContainerCrs18PowerShelfVirtual" {
    smiv2:oid "1.3.6.1.4.1.9.12.3.1.5.228";
  }

  smiv2:alias "cevContainer40GigBasePort" {
    smiv2:oid "1.3.6.1.4.1.9.12.3.1.5.229";
  }

  smiv2:alias "cevContainerSAMBay" {
    smiv2:oid "1.3.6.1.4.1.9.12.3.1.5.230";
  }

  smiv2:alias "cevContainerN5KC5596FanBay" {
    smiv2:oid "1.3.6.1.4.1.9.12.3.1.5.231";
  }

  smiv2:alias "cevContainerN5kC5596PowerSupplyBay" {
    smiv2:oid "1.3.6.1.4.1.9.12.3.1.5.232";
  }

  smiv2:alias "cevContainerN3KC3064FanBay" {
    smiv2:oid "1.3.6.1.4.1.9.12.3.1.5.235";
  }

  smiv2:alias "cevContainerUCS6248FanBay" {
    smiv2:oid "1.3.6.1.4.1.9.12.3.1.5.236";
  }

  smiv2:alias "cevContainerUCS6248PowerSupplyBay" {
    smiv2:oid "1.3.6.1.4.1.9.12.3.1.5.237";
  }

  smiv2:alias "cevContainerUCS6296FanBay" {
    smiv2:oid "1.3.6.1.4.1.9.12.3.1.5.238";
  }

  smiv2:alias "cevContainerUCS6296PowerSupplyBay" {
    smiv2:oid "1.3.6.1.4.1.9.12.3.1.5.239";
  }

  smiv2:alias "cevContainerDIMM8541Slot" {
    smiv2:oid "1.3.6.1.4.1.9.12.3.1.5.240";
  }

  smiv2:alias "cevContainerDIMM7571Slot" {
    smiv2:oid "1.3.6.1.4.1.9.12.3.1.5.241";
  }

  smiv2:alias "cevContainerDIMM7541Slot" {
    smiv2:oid "1.3.6.1.4.1.9.12.3.1.5.242";
  }

  smiv2:alias "cevContainerDIMM694Slot" {
    smiv2:oid "1.3.6.1.4.1.9.12.3.1.5.243";
  }

  smiv2:alias "cevContainerDIMM594Slot" {
    smiv2:oid "1.3.6.1.4.1.9.12.3.1.5.244";
  }

  smiv2:alias "cevContainerDIMM294Slot" {
    smiv2:oid "1.3.6.1.4.1.9.12.3.1.5.245";
  }

  smiv2:alias "cevContainerASR900RSPSlot" {
    smiv2:oid "1.3.6.1.4.1.9.12.3.1.5.246";
  }

  smiv2:alias "cevContainerASR900PowerSupplyBay" {
    smiv2:oid "1.3.6.1.4.1.9.12.3.1.5.247";
  }

  smiv2:alias "cevContainerASR900FanTrayBay" {
    smiv2:oid "1.3.6.1.4.1.9.12.3.1.5.248";
  }

  smiv2:alias "cevContainerIMBay" {
    smiv2:oid "1.3.6.1.4.1.9.12.3.1.5.249";
  }

  smiv2:alias "cevContainerN7Kc7004FanBay" {
    smiv2:oid "1.3.6.1.4.1.9.12.3.1.5.250";
  }

  smiv2:alias "cevContainerN7Kc7004PowerSupplyBay" {
    smiv2:oid "1.3.6.1.4.1.9.12.3.1.5.251";
  }

  smiv2:alias "cevContainerN3KC3048FanBay" {
    smiv2:oid "1.3.6.1.4.1.9.12.3.1.5.252";
  }

  smiv2:alias "cevContainerN6kC6004FanBay" {
    smiv2:oid "1.3.6.1.4.1.9.12.3.1.5.262";
  }

  smiv2:alias "cevContainerN6kC6004PowerSupplyBay" {
    smiv2:oid "1.3.6.1.4.1.9.12.3.1.5.263";
  }

  smiv2:alias "cevContainerASR9KSwitchFabricSlot" {
    smiv2:oid "1.3.6.1.4.1.9.12.3.1.5.264";
  }

  smiv2:alias "cevContainerCFP" {
    smiv2:oid "1.3.6.1.4.1.9.12.3.1.5.265";
  }

  smiv2:alias "cevContainerISR4400ESMSlot" {
    smiv2:oid "1.3.6.1.4.1.9.12.3.1.5.268";
  }

  smiv2:alias "cevContainerISR4400PSBay" {
    smiv2:oid "1.3.6.1.4.1.9.12.3.1.5.269";
  }

  smiv2:alias "cevContainerISR4400FanTrayBay" {
    smiv2:oid "1.3.6.1.4.1.9.12.3.1.5.270";
  }

  smiv2:alias "cevContainerISR4400POEBay" {
    smiv2:oid "1.3.6.1.4.1.9.12.3.1.5.271";
  }

  smiv2:alias "cevContainerISR4400InternalPOEBay" {
    smiv2:oid "1.3.6.1.4.1.9.12.3.1.5.272";
  }

  smiv2:alias "cevContainerDSC9710FanBay" {
    smiv2:oid "1.3.6.1.4.1.9.12.3.1.5.273";
  }

  smiv2:alias "cevContainerMDS9250iFanBay" {
    smiv2:oid "1.3.6.1.4.1.9.12.3.1.5.274";
  }

  smiv2:alias "cevContainerNCSProcessorSlot" {
    smiv2:oid "1.3.6.1.4.1.9.12.3.1.5.275";
  }

  smiv2:alias "cevContainerNCSLineCardSlot" {
    smiv2:oid "1.3.6.1.4.1.9.12.3.1.5.276";
  }

  smiv2:alias "cevContainerNCSFabcardSlot" {
    smiv2:oid "1.3.6.1.4.1.9.12.3.1.5.277";
  }

  smiv2:alias "cevContainerNCSPwrTraySlot" {
    smiv2:oid "1.3.6.1.4.1.9.12.3.1.5.278";
  }

  smiv2:alias "cevContainerNCSFanTraySlot" {
    smiv2:oid "1.3.6.1.4.1.9.12.3.1.5.279";
  }

  smiv2:alias "cevContainerNCSPwrSupSlot" {
    smiv2:oid "1.3.6.1.4.1.9.12.3.1.5.280";
  }

  smiv2:alias "cevContainerNCSDisplaySlot" {
    smiv2:oid "1.3.6.1.4.1.9.12.3.1.5.281";
  }

  smiv2:alias "cevContainerN77c7718PowerSupplyBay" {
    smiv2:oid "1.3.6.1.4.1.9.12.3.1.5.282";
  }

  smiv2:alias "cevContainerN77c7710PowerSupplyBay" {
    smiv2:oid "1.3.6.1.4.1.9.12.3.1.5.283";
  }

  smiv2:alias "cevContainerN77c7706PowerSupplyBay" {
    smiv2:oid "1.3.6.1.4.1.9.12.3.1.5.284";
  }

  smiv2:alias "cevContainerN77c7718FanBay" {
    smiv2:oid "1.3.6.1.4.1.9.12.3.1.5.285";
  }

  smiv2:alias "cevContainerN77c7710FanBay" {
    smiv2:oid "1.3.6.1.4.1.9.12.3.1.5.286";
  }

  smiv2:alias "cevContainerN77c7706FanBay" {
    smiv2:oid "1.3.6.1.4.1.9.12.3.1.5.287";
  }

  smiv2:alias "cevContainerCXP" {
    smiv2:oid "1.3.6.1.4.1.9.12.3.1.5.288";
  }

  smiv2:alias "cevContainerCPAK" {
    smiv2:oid "1.3.6.1.4.1.9.12.3.1.5.289";
  }

  smiv2:alias "cevContainerPsConverter" {
    smiv2:oid "1.3.6.1.4.1.9.12.3.1.5.290";
  }

  smiv2:alias "cevContainerQIron22Qzinc2" {
    smiv2:oid "1.3.6.1.4.1.9.12.3.1.5.292";
  }

  smiv2:alias "cevContainerDSC9706" {
    smiv2:oid "1.3.6.1.4.1.9.12.3.1.5.293";
  }

  smiv2:alias "cevContainerN9Kc9508FanBay" {
    smiv2:oid "1.3.6.1.4.1.9.12.3.1.5.301";
  }

  smiv2:alias "cevContainerN9Kc9508PowerSupplyBay" {
    smiv2:oid "1.3.6.1.4.1.9.12.3.1.5.302";
  }

  smiv2:alias "cevContainerASR5000SPCSlot" {
    smiv2:oid "1.3.6.1.4.1.9.12.3.1.5.303";
  }

  smiv2:alias "cevContainerASR5000PTACSlot" {
    smiv2:oid "1.3.6.1.4.1.9.12.3.1.5.304";
  }

  smiv2:alias "cevContainerASR5000RCCSlot" {
    smiv2:oid "1.3.6.1.4.1.9.12.3.1.5.305";
  }

  smiv2:alias "cevContainerASR5000SPIOSlot" {
    smiv2:oid "1.3.6.1.4.1.9.12.3.1.5.306";
  }

  smiv2:alias "cevContainerASR5000LCSlot" {
    smiv2:oid "1.3.6.1.4.1.9.12.3.1.5.307";
  }

  smiv2:alias "cevContainerASR5000FanTraySlot" {
    smiv2:oid "1.3.6.1.4.1.9.12.3.1.5.308";
  }

  smiv2:alias "cevContainerASR5000PowerSupplySlot" {
    smiv2:oid "1.3.6.1.4.1.9.12.3.1.5.309";
  }

  smiv2:alias "cevContainerASR5500MMIOSlot" {
    smiv2:oid "1.3.6.1.4.1.9.12.3.1.5.310";
  }

  smiv2:alias "cevContainerASR5500DPCSlot" {
    smiv2:oid "1.3.6.1.4.1.9.12.3.1.5.311";
  }

  smiv2:alias "cevContainerASR5500FSCSlot" {
    smiv2:oid "1.3.6.1.4.1.9.12.3.1.5.312";
  }

  smiv2:alias "cevContainerASR5500SSCSlot" {
    smiv2:oid "1.3.6.1.4.1.9.12.3.1.5.313";
  }

  smiv2:alias "cevContainerASR5500SIOSlot" {
    smiv2:oid "1.3.6.1.4.1.9.12.3.1.5.314";
  }

  smiv2:alias "cevContainerASR5500FanTraySlot" {
    smiv2:oid "1.3.6.1.4.1.9.12.3.1.5.315";
  }

  smiv2:alias "cevContainerASR5500PowerSupplySlot" {
    smiv2:oid "1.3.6.1.4.1.9.12.3.1.5.316";
  }

  smiv2:alias "cevContainerDSC48SFAN" {
    smiv2:oid "1.3.6.1.4.1.9.12.3.1.5.317";
  }

  smiv2:alias "cevContainerN9Kc9516FanBay" {
    smiv2:oid "1.3.6.1.4.1.9.12.3.1.5.318";
  }

  smiv2:alias "cevContainerN9Kc9504FanBay" {
    smiv2:oid "1.3.6.1.4.1.9.12.3.1.5.319";
  }

  smiv2:alias "cevContainerN9KC9300FanBay2" {
    smiv2:oid "1.3.6.1.4.1.9.12.3.1.5.320";
  }

  smiv2:alias "cevContainerN9KC9300FanBay1" {
    smiv2:oid "1.3.6.1.4.1.9.12.3.1.5.321";
  }

  smiv2:alias "cevContainerN5KC56128FanBay" {
    smiv2:oid "1.3.6.1.4.1.9.12.3.1.5.327";
  }

  smiv2:alias "cevContainerNXAPowerSupplyBay" {
    smiv2:oid "1.3.6.1.4.1.9.12.3.1.5.328";
  }

  smiv2:alias "cevContainerN6kC6001FanBay" {
    smiv2:oid "1.3.6.1.4.1.9.12.3.1.5.329";
  }

  smiv2:alias "cevContainerCCEPowerSupplyBay" {
    smiv2:oid "1.3.6.1.4.1.9.12.3.1.5.334";
  }

  smiv2:alias "cevContainerCCEFanTraySlot" {
    smiv2:oid "1.3.6.1.4.1.9.12.3.1.5.335";
  }

  smiv2:alias "cevContainerDSCAC1200W" {
    smiv2:oid "1.3.6.1.4.1.9.12.3.1.5.339";
  }

  smiv2:alias "cevContainerDSC96SFAN" {
    smiv2:oid "1.3.6.1.4.1.9.12.3.1.5.340";
  }

  smiv2:alias "cevPowerSupply" {
    smiv2:oid "1.3.6.1.4.1.9.12.3.1.6";
  }

  smiv2:alias "cevPowerSupplyAC1360W" {
    smiv2:oid "1.3.6.1.4.1.9.12.3.1.6.1";
  }

  smiv2:alias "cevPowerSupplyDC1360W" {
    smiv2:oid "1.3.6.1.4.1.9.12.3.1.6.2";
  }

  smiv2:alias "cevPowerSupplyAC1000W" {
    smiv2:oid "1.3.6.1.4.1.9.12.3.1.6.3";
  }

  smiv2:alias "cevPowerSupplyDC1000W" {
    smiv2:oid "1.3.6.1.4.1.9.12.3.1.6.4";
  }

  smiv2:alias "cevPowerSupplyPowerone" {
    smiv2:oid "1.3.6.1.4.1.9.12.3.1.6.5";
  }

  smiv2:alias "cevPowerSupplyAstec" {
    smiv2:oid "1.3.6.1.4.1.9.12.3.1.6.6";
  }

  smiv2:alias "cevPowerSupplyMinus48VDC" {
    smiv2:oid "1.3.6.1.4.1.9.12.3.1.6.7";
  }

  smiv2:alias "cevPowerSupplyEmpty" {
    smiv2:oid "1.3.6.1.4.1.9.12.3.1.6.8";
  }

  smiv2:alias "cevPowerSupplyAC1100W" {
    smiv2:oid "1.3.6.1.4.1.9.12.3.1.6.9";
  }

  smiv2:alias "cevPowerSupplyAC1200W" {
    smiv2:oid "1.3.6.1.4.1.9.12.3.1.6.10";
  }

  smiv2:alias "cevPowerSupplyDC1200W" {
    smiv2:oid "1.3.6.1.4.1.9.12.3.1.6.11";
  }

  smiv2:alias "cevPowerSupplyPem" {
    smiv2:oid "1.3.6.1.4.1.9.12.3.1.6.12";
  }

  smiv2:alias "cevPowerSupplyAC2000W" {
    smiv2:oid "1.3.6.1.4.1.9.12.3.1.6.13";
  }

  smiv2:alias "cevPowerSupplyDC2000W" {
    smiv2:oid "1.3.6.1.4.1.9.12.3.1.6.14";
  }

  smiv2:alias "cevPowerSupply6260DC" {
    smiv2:oid "1.3.6.1.4.1.9.12.3.1.6.15";
  }

  smiv2:alias "cevPowerSupply6260AC" {
    smiv2:oid "1.3.6.1.4.1.9.12.3.1.6.16";
  }

  smiv2:alias "cevPowerSupplyMGX8800Pem" {
    smiv2:oid "1.3.6.1.4.1.9.12.3.1.6.17";
  }

  smiv2:alias "cevPowerSupply12012DC" {
    smiv2:oid "1.3.6.1.4.1.9.12.3.1.6.18";
  }

  smiv2:alias "cevPowerSupply12012AC" {
    smiv2:oid "1.3.6.1.4.1.9.12.3.1.6.19";
  }

  smiv2:alias "cevPowerSupply12008DC" {
    smiv2:oid "1.3.6.1.4.1.9.12.3.1.6.20";
  }

  smiv2:alias "cevPowerSupply12008AC" {
    smiv2:oid "1.3.6.1.4.1.9.12.3.1.6.21";
  }

  smiv2:alias "cevPowerSupplyDC2500W" {
    smiv2:oid "1.3.6.1.4.1.9.12.3.1.6.22";
  }

  smiv2:alias "cevPowerSupplyAC1050W" {
    smiv2:oid "1.3.6.1.4.1.9.12.3.1.6.23";
  }

  smiv2:alias "cevPowerSupplyAC2500W" {
    smiv2:oid "1.3.6.1.4.1.9.12.3.1.6.24";
  }

  smiv2:alias "cevPowerSupply6160DC" {
    smiv2:oid "1.3.6.1.4.1.9.12.3.1.6.25";
  }

  smiv2:alias "cevPowerSupplyAC4000W" {
    smiv2:oid "1.3.6.1.4.1.9.12.3.1.6.28";
  }

  smiv2:alias "cevPowerSupplyDC4000W" {
    smiv2:oid "1.3.6.1.4.1.9.12.3.1.6.29";
  }

  smiv2:alias "cevPowerSupply12010DC" {
    smiv2:oid "1.3.6.1.4.1.9.12.3.1.6.31";
  }

  smiv2:alias "cevPowerSupply12010AC" {
    smiv2:oid "1.3.6.1.4.1.9.12.3.1.6.32";
  }

  smiv2:alias "cevPowerSupply5850DC" {
    smiv2:oid "1.3.6.1.4.1.9.12.3.1.6.33";
  }

  smiv2:alias "cevPowerSupply12406DC" {
    smiv2:oid "1.3.6.1.4.1.9.12.3.1.6.34";
  }

  smiv2:alias "cevPowerSupply12406AC" {
    smiv2:oid "1.3.6.1.4.1.9.12.3.1.6.35";
  }

  smiv2:alias "cevPowerSupply12410DC" {
    smiv2:oid "1.3.6.1.4.1.9.12.3.1.6.36";
  }

  smiv2:alias "cevPowerSupply12410AC" {
    smiv2:oid "1.3.6.1.4.1.9.12.3.1.6.37";
  }

  smiv2:alias "cevPowerSupplyAC1900W" {
    smiv2:oid "1.3.6.1.4.1.9.12.3.1.6.38";
  }

  smiv2:alias "cevPowerSupplyDC1900W" {
    smiv2:oid "1.3.6.1.4.1.9.12.3.1.6.39";
  }

  smiv2:alias "cevPowerSupplyDC950W" {
    smiv2:oid "1.3.6.1.4.1.9.12.3.1.6.40";
  }

  smiv2:alias "cevPowerSupplyAC950W" {
    smiv2:oid "1.3.6.1.4.1.9.12.3.1.6.41";
  }

  smiv2:alias "cevPowerSupply12404DC" {
    smiv2:oid "1.3.6.1.4.1.9.12.3.1.6.42";
  }

  smiv2:alias "cevPowerSupply12404AC" {
    smiv2:oid "1.3.6.1.4.1.9.12.3.1.6.43";
  }

  smiv2:alias "cevPowerSupplyBP7513AC1200W" {
    smiv2:oid "1.3.6.1.4.1.9.12.3.1.6.44";
  }

  smiv2:alias "cevPowerSupplyBP7513DC1200W" {
    smiv2:oid "1.3.6.1.4.1.9.12.3.1.6.45";
  }

  smiv2:alias "cevPowerSupplyBP7505AC600W" {
    smiv2:oid "1.3.6.1.4.1.9.12.3.1.6.46";
  }

  smiv2:alias "cevPowerSupplyBP7505DC600W" {
    smiv2:oid "1.3.6.1.4.1.9.12.3.1.6.47";
  }

  smiv2:alias "cevPowerSupplyBP7507AC700W" {
    smiv2:oid "1.3.6.1.4.1.9.12.3.1.6.48";
  }

  smiv2:alias "cevPowerSupplyBP7507DC700W" {
    smiv2:oid "1.3.6.1.4.1.9.12.3.1.6.49";
  }

  smiv2:alias "cevPowerSupplyAC1900W6" {
    smiv2:oid "1.3.6.1.4.1.9.12.3.1.6.50";
  }

  smiv2:alias "cevPowerSupplyC7300AC" {
    smiv2:oid "1.3.6.1.4.1.9.12.3.1.6.51";
  }

  smiv2:alias "cevPowerSupplyC7300DC" {
    smiv2:oid "1.3.6.1.4.1.9.12.3.1.6.52";
  }

  smiv2:alias "cevPowerSupplyAC600W" {
    smiv2:oid "1.3.6.1.4.1.9.12.3.1.6.53";
  }

  smiv2:alias "cevPowerSupplyDC600W" {
    smiv2:oid "1.3.6.1.4.1.9.12.3.1.6.54";
  }

  smiv2:alias "cevPowerSupplyC10KDC" {
    smiv2:oid "1.3.6.1.4.1.9.12.3.1.6.55";
  }

  smiv2:alias "cevPowerSupplyC10KAC" {
    smiv2:oid "1.3.6.1.4.1.9.12.3.1.6.56";
  }

  smiv2:alias "cevPowerSupply15530AC" {
    smiv2:oid "1.3.6.1.4.1.9.12.3.1.6.59";
  }

  smiv2:alias "cevPowerSupply15530DC" {
    smiv2:oid "1.3.6.1.4.1.9.12.3.1.6.60";
  }

  smiv2:alias "cevPowerSupplyAC3000W" {
    smiv2:oid "1.3.6.1.4.1.9.12.3.1.6.61";
  }

  smiv2:alias "cevPowerSupply12016DC" {
    smiv2:oid "1.3.6.1.4.1.9.12.3.1.6.63";
  }

  smiv2:alias "cevPowerSupply12016AC" {
    smiv2:oid "1.3.6.1.4.1.9.12.3.1.6.64";
  }

  smiv2:alias "cevPowerSupplyDC3000W" {
    smiv2:oid "1.3.6.1.4.1.9.12.3.1.6.70";
  }

  smiv2:alias "cevPowerSupplyCat3750AC50W12V" {
    smiv2:oid "1.3.6.1.4.1.9.12.3.1.6.71";
  }

  smiv2:alias "cevPowerSupplyCat3750AC102W12V" {
    smiv2:oid "1.3.6.1.4.1.9.12.3.1.6.72";
  }

  smiv2:alias "cevPowerSupplyCat3750AC204W12V" {
    smiv2:oid "1.3.6.1.4.1.9.12.3.1.6.73";
  }

  smiv2:alias "cevPowerSupplyCat3750AC252W12V" {
    smiv2:oid "1.3.6.1.4.1.9.12.3.1.6.74";
  }

  smiv2:alias "cevPowerSupplyDsCac2500W" {
    smiv2:oid "1.3.6.1.4.1.9.12.3.1.6.76";
  }

  smiv2:alias "cevPowerSupplyRedDsCac2500W" {
    smiv2:oid "1.3.6.1.4.1.9.12.3.1.6.77";
  }

  smiv2:alias "cevPowerSupplyDsCdc2500W" {
    smiv2:oid "1.3.6.1.4.1.9.12.3.1.6.78";
  }

  smiv2:alias "cevPowerSupplyRedDsCdc2500W" {
    smiv2:oid "1.3.6.1.4.1.9.12.3.1.6.79";
  }

  smiv2:alias "cevPowerSupplyDsCac4000WUs" {
    smiv2:oid "1.3.6.1.4.1.9.12.3.1.6.80";
  }

  smiv2:alias "cevPowerSupplyRedDsCac4000WUs" {
    smiv2:oid "1.3.6.1.4.1.9.12.3.1.6.81";
  }

  smiv2:alias "cevPowerSupplyDsCac4000WInt" {
    smiv2:oid "1.3.6.1.4.1.9.12.3.1.6.82";
  }

  smiv2:alias "cevPowerSupplyRedDsCac4000WInt" {
    smiv2:oid "1.3.6.1.4.1.9.12.3.1.6.83";
  }

  smiv2:alias "cevPowerSupplyDsCac1900W" {
    smiv2:oid "1.3.6.1.4.1.9.12.3.1.6.84";
  }

  smiv2:alias "cevPowerSupplyRedDsCac1900W" {
    smiv2:oid "1.3.6.1.4.1.9.12.3.1.6.85";
  }

  smiv2:alias "cevPowerSupplyDsCdc1900W" {
    smiv2:oid "1.3.6.1.4.1.9.12.3.1.6.86";
  }

  smiv2:alias "cevPowerSupplyRedDsCdc1900W" {
    smiv2:oid "1.3.6.1.4.1.9.12.3.1.6.87";
  }

  smiv2:alias "cevPowerSupplyRedDsCac845W" {
    smiv2:oid "1.3.6.1.4.1.9.12.3.1.6.88";
  }

  smiv2:alias "cevPowerSupplyDsCac845W" {
    smiv2:oid "1.3.6.1.4.1.9.12.3.1.6.89";
  }

  smiv2:alias "cevPowerSupplyUnknown" {
    smiv2:oid "1.3.6.1.4.1.9.12.3.1.6.90";
  }

  smiv2:alias "cevPowerSupplyC2970AC156W12V" {
    smiv2:oid "1.3.6.1.4.1.9.12.3.1.6.91";
  }

  smiv2:alias "cevPowerSupplyAc150W" {
    smiv2:oid "1.3.6.1.4.1.9.12.3.1.6.92";
  }

  smiv2:alias "cevPowerSupplyC7200AC" {
    smiv2:oid "1.3.6.1.4.1.9.12.3.1.6.93";
  }

  smiv2:alias "cevPowerSupplyC7200DC" {
    smiv2:oid "1.3.6.1.4.1.9.12.3.1.6.94";
  }

  smiv2:alias "cevPowerSupplyAc465W" {
    smiv2:oid "1.3.6.1.4.1.9.12.3.1.6.95";
  }

  smiv2:alias "cevPowerSupplyDsCac300W" {
    smiv2:oid "1.3.6.1.4.1.9.12.3.1.6.96";
  }

  smiv2:alias "cevPowerSupplyRedDsCac300W" {
    smiv2:oid "1.3.6.1.4.1.9.12.3.1.6.97";
  }

  smiv2:alias "cevPowerSupplyAc1400W" {
    smiv2:oid "1.3.6.1.4.1.9.12.3.1.6.98";
  }

  smiv2:alias "cevPowerSupplyC2970AC204W12V" {
    smiv2:oid "1.3.6.1.4.1.9.12.3.1.6.99";
  }

  smiv2:alias "cevPowerSupplyCrs1PowerSupply" {
    smiv2:oid "1.3.6.1.4.1.9.12.3.1.6.100";
  }

  smiv2:alias "cevPowerSupplyCrs1PowerZone" {
    smiv2:oid "1.3.6.1.4.1.9.12.3.1.6.101";
  }

  smiv2:alias "cevPowerSupplyAC6000W" {
    smiv2:oid "1.3.6.1.4.1.9.12.3.1.6.102";
  }

  smiv2:alias "cevPowerSupplyDc150W" {
    smiv2:oid "1.3.6.1.4.1.9.12.3.1.6.103";
  }

  smiv2:alias "cevPowerSupplyAC2700W" {
    smiv2:oid "1.3.6.1.4.1.9.12.3.1.6.104";
  }

  smiv2:alias "cevPowerSupplyDC2700W" {
    smiv2:oid "1.3.6.1.4.1.9.12.3.1.6.105";
  }

  smiv2:alias "cevPowerSupplyPwrC45300AC" {
    smiv2:oid "1.3.6.1.4.1.9.12.3.1.6.106";
  }

  smiv2:alias "cevPowerSupplyPwrC45300DC" {
    smiv2:oid "1.3.6.1.4.1.9.12.3.1.6.107";
  }

  smiv2:alias "cevPowerSupplyAC2900WE" {
    smiv2:oid "1.3.6.1.4.1.9.12.3.1.6.108";
  }

  smiv2:alias "cevPowerSupplyAC6000WE" {
    smiv2:oid "1.3.6.1.4.1.9.12.3.1.6.109";
  }

  smiv2:alias "cevPowerSupplyAC8700WE" {
    smiv2:oid "1.3.6.1.4.1.9.12.3.1.6.110";
  }

  smiv2:alias "cevPowerSupplyPWR2700AC4" {
    smiv2:oid "1.3.6.1.4.1.9.12.3.1.6.111";
  }

  smiv2:alias "cevPowerSupplyPWR2700DC4" {
    smiv2:oid "1.3.6.1.4.1.9.12.3.1.6.112";
  }

  smiv2:alias "cevPowerSupplyPWRC49AC300W" {
    smiv2:oid "1.3.6.1.4.1.9.12.3.1.6.113";
  }

  smiv2:alias "cevPowerSupplyPWRC49DC300W" {
    smiv2:oid "1.3.6.1.4.1.9.12.3.1.6.114";
  }

  smiv2:alias "cevPowerSupplyGSR6PemAC" {
    smiv2:oid "1.3.6.1.4.1.9.12.3.1.6.115";
  }

  smiv2:alias "cevPowerSupplyGSR6PemDC" {
    smiv2:oid "1.3.6.1.4.1.9.12.3.1.6.116";
  }

  smiv2:alias "cevPowerSupplyGSR10PemAC" {
    smiv2:oid "1.3.6.1.4.1.9.12.3.1.6.117";
  }

  smiv2:alias "cevPowerSupplyGSR10PemDC" {
    smiv2:oid "1.3.6.1.4.1.9.12.3.1.6.118";
  }

  smiv2:alias "cevPowerSupplyGSR4PemAC" {
    smiv2:oid "1.3.6.1.4.1.9.12.3.1.6.119";
  }

  smiv2:alias "cevPowerSupplyGSR4PemDC" {
    smiv2:oid "1.3.6.1.4.1.9.12.3.1.6.120";
  }

  smiv2:alias "cevPowerSupplyGSR16PemAC" {
    smiv2:oid "1.3.6.1.4.1.9.12.3.1.6.121";
  }

  smiv2:alias "cevPowerSupplyGSR16PemDC" {
    smiv2:oid "1.3.6.1.4.1.9.12.3.1.6.122";
  }

  smiv2:alias "cevPowerSupplyC451400DCSP" {
    smiv2:oid "1.3.6.1.4.1.9.12.3.1.6.123";
  }

  smiv2:alias "cevPowerSupplyAc125W" {
    smiv2:oid "1.3.6.1.4.1.9.12.3.1.6.124";
  }

  smiv2:alias "cevPowerSupplyAc60W" {
    smiv2:oid "1.3.6.1.4.1.9.12.3.1.6.125";
  }

  smiv2:alias "cevPowerSupplyC454200ACv" {
    smiv2:oid "1.3.6.1.4.1.9.12.3.1.6.126";
  }

  smiv2:alias "cevPowerSupply400wDC" {
    smiv2:oid "1.3.6.1.4.1.9.12.3.1.6.127";
  }

  smiv2:alias "cevPowerSupplyEnh12404AC" {
    smiv2:oid "1.3.6.1.4.1.9.12.3.1.6.128";
  }

  smiv2:alias "cevPowerSupplyEnh12404DC" {
    smiv2:oid "1.3.6.1.4.1.9.12.3.1.6.129";
  }

  smiv2:alias "cevPowerSupplyEnh12406AC" {
    smiv2:oid "1.3.6.1.4.1.9.12.3.1.6.130";
  }

  smiv2:alias "cevPowerSupplyEnh12406DC" {
    smiv2:oid "1.3.6.1.4.1.9.12.3.1.6.131";
  }

  smiv2:alias "cevPowerSupplyEnh12410AC" {
    smiv2:oid "1.3.6.1.4.1.9.12.3.1.6.132";
  }

  smiv2:alias "cevPowerSupplyEnh12410DC" {
    smiv2:oid "1.3.6.1.4.1.9.12.3.1.6.133";
  }

  smiv2:alias "cevPowerSupplyEnh12416AC" {
    smiv2:oid "1.3.6.1.4.1.9.12.3.1.6.134";
  }

  smiv2:alias "cevPowerSupplyEnh12416DC" {
    smiv2:oid "1.3.6.1.4.1.9.12.3.1.6.135";
  }

  smiv2:alias "cevPowerSupply76xxDC2500W" {
    smiv2:oid "1.3.6.1.4.1.9.12.3.1.6.136";
  }

  smiv2:alias "cevPowerSupply76xxAC3000W" {
    smiv2:oid "1.3.6.1.4.1.9.12.3.1.6.137";
  }

  smiv2:alias "cevPowerSupply76xxAC4000US" {
    smiv2:oid "1.3.6.1.4.1.9.12.3.1.6.138";
  }

  smiv2:alias "cevPowerSupply76xxAC4000INT" {
    smiv2:oid "1.3.6.1.4.1.9.12.3.1.6.139";
  }

  smiv2:alias "cevPowerSupply76xxAC6000W" {
    smiv2:oid "1.3.6.1.4.1.9.12.3.1.6.140";
  }

  smiv2:alias "cevPowerSupplyDC100W" {
    smiv2:oid "1.3.6.1.4.1.9.12.3.1.6.141";
  }

  smiv2:alias "cevPowerSupplyDsCAD6000W" {
    smiv2:oid "1.3.6.1.4.1.9.12.3.1.6.144";
  }

  smiv2:alias "cevPowerSupplyCat2960AC60W12V" {
    smiv2:oid "1.3.6.1.4.1.9.12.3.1.6.145";
  }

  smiv2:alias "cevPowerSupplyCat2960AC125W12V" {
    smiv2:oid "1.3.6.1.4.1.9.12.3.1.6.146";
  }

  smiv2:alias "cevPowerSupplyCat2960AC210W12V" {
    smiv2:oid "1.3.6.1.4.1.9.12.3.1.6.147";
  }

  smiv2:alias "cevPowerSupply6340PWRDC" {
    smiv2:oid "1.3.6.1.4.1.9.12.3.1.6.148";
  }

  smiv2:alias "cevPowerSupply6340PWRAC" {
    smiv2:oid "1.3.6.1.4.1.9.12.3.1.6.149";
  }

  smiv2:alias "cevPowerSupplyUbr10012AC" {
    smiv2:oid "1.3.6.1.4.1.9.12.3.1.6.150";
  }

  smiv2:alias "cevPowerSupplyUbr10012DC" {
    smiv2:oid "1.3.6.1.4.1.9.12.3.1.6.151";
  }

  smiv2:alias "cevPowerSupply400wAC" {
    smiv2:oid "1.3.6.1.4.1.9.12.3.1.6.152";
  }

  smiv2:alias "cevPowerSupplyCE500AC60W12V" {
    smiv2:oid "1.3.6.1.4.1.9.12.3.1.6.153";
  }

  smiv2:alias "cevPowerSupplyCE500AC375W48V" {
    smiv2:oid "1.3.6.1.4.1.9.12.3.1.6.154";
  }

  smiv2:alias "cevPowerSupplyCE500AC75W48V" {
    smiv2:oid "1.3.6.1.4.1.9.12.3.1.6.155";
  }

  smiv2:alias "cevPowerSupplyCE500AC168W12V" {
    smiv2:oid "1.3.6.1.4.1.9.12.3.1.6.156";
  }

  smiv2:alias "cevPowerSupplyCat3750AC210W12V" {
    smiv2:oid "1.3.6.1.4.1.9.12.3.1.6.157";
  }

  smiv2:alias "cevPowerSupplyCat3750AC375W48V" {
    smiv2:oid "1.3.6.1.4.1.9.12.3.1.6.158";
  }

  smiv2:alias "cevPowerSupplyAC50W" {
    smiv2:oid "1.3.6.1.4.1.9.12.3.1.6.159";
  }

  smiv2:alias "cevPowerSupplyDC50W" {
    smiv2:oid "1.3.6.1.4.1.9.12.3.1.6.160";
  }

  smiv2:alias "cevPowerSupplyCrs116PowerShelfACDelta" {
    smiv2:oid "1.3.6.1.4.1.9.12.3.1.6.161";
  }

  smiv2:alias "cevPowerSupplyCrs116PowerShelfACWye" {
    smiv2:oid "1.3.6.1.4.1.9.12.3.1.6.162";
  }

  smiv2:alias "cevPowerSupplyCrs116PowerShelfDC" {
    smiv2:oid "1.3.6.1.4.1.9.12.3.1.6.163";
  }

  smiv2:alias "cevPowerSupplyCrs116ACRectifier" {
    smiv2:oid "1.3.6.1.4.1.9.12.3.1.6.164";
  }

  smiv2:alias "cevPowerSupplyCrs116DCPEM" {
    smiv2:oid "1.3.6.1.4.1.9.12.3.1.6.165";
  }

  smiv2:alias "cevPowerSupplyDsCac3000W" {
    smiv2:oid "1.3.6.1.4.1.9.12.3.1.6.167";
  }

  smiv2:alias "cevPowerSupplyPWR6000DC" {
    smiv2:oid "1.3.6.1.4.1.9.12.3.1.6.168";
  }

  smiv2:alias "cevPowerSupplyCrs18ACRectifier" {
    smiv2:oid "1.3.6.1.4.1.9.12.3.1.6.169";
  }

  smiv2:alias "cevPowerSupplyCrs18DCPem" {
    smiv2:oid "1.3.6.1.4.1.9.12.3.1.6.170";
  }

  smiv2:alias "cevPowerSupplyCrs18ACDelta" {
    smiv2:oid "1.3.6.1.4.1.9.12.3.1.6.171";
  }

  smiv2:alias "cevPowerSupplyCrs18ACW" {
    smiv2:oid "1.3.6.1.4.1.9.12.3.1.6.172";
  }

  smiv2:alias "cevPowerSupplyCrs18DC" {
    smiv2:oid "1.3.6.1.4.1.9.12.3.1.6.173";
  }

  smiv2:alias "cevPowerSupplyCrs18PduACD" {
    smiv2:oid "1.3.6.1.4.1.9.12.3.1.6.174";
  }

  smiv2:alias "cevPowerSupplyCrs18PduACW" {
    smiv2:oid "1.3.6.1.4.1.9.12.3.1.6.175";
  }

  smiv2:alias "cevPowerSupplyCrs18PduDC" {
    smiv2:oid "1.3.6.1.4.1.9.12.3.1.6.176";
  }

  smiv2:alias "cevPowerSupplyCrs1FcACD" {
    smiv2:oid "1.3.6.1.4.1.9.12.3.1.6.177";
  }

  smiv2:alias "cevPowerSupplyCrs1FcACW" {
    smiv2:oid "1.3.6.1.4.1.9.12.3.1.6.178";
  }

  smiv2:alias "cevPowerSupplyCrs1FcDC" {
    smiv2:oid "1.3.6.1.4.1.9.12.3.1.6.179";
  }

  smiv2:alias "cevPowerSupplyCrs14PowerShelfAC" {
    smiv2:oid "1.3.6.1.4.1.9.12.3.1.6.180";
  }

  smiv2:alias "cevPowerSupplyCrs14PowerShelfDC" {
    smiv2:oid "1.3.6.1.4.1.9.12.3.1.6.181";
  }

  smiv2:alias "cevPowerSupplyCrs14PowerSupplyDC" {
    smiv2:oid "1.3.6.1.4.1.9.12.3.1.6.182";
  }

  smiv2:alias "cevPowerSupplyCrs14PowerSupplyAC" {
    smiv2:oid "1.3.6.1.4.1.9.12.3.1.6.183";
  }

  smiv2:alias "cevPowerSupplyC3KPWR265WAC" {
    smiv2:oid "1.3.6.1.4.1.9.12.3.1.6.184";
  }

  smiv2:alias "cevPowerSupplyC3KPWR265WDC" {
    smiv2:oid "1.3.6.1.4.1.9.12.3.1.6.185";
  }

  smiv2:alias "cevPowerSupplyC3KPWR750WAC" {
    smiv2:oid "1.3.6.1.4.1.9.12.3.1.6.186";
  }

  smiv2:alias "cevPowerSupplyCat2960AC36W12V" {
    smiv2:oid "1.3.6.1.4.1.9.12.3.1.6.188";
  }

  smiv2:alias "cevPowerSupplyCat3560AC173W48V" {
    smiv2:oid "1.3.6.1.4.1.9.12.3.1.6.189";
  }

  smiv2:alias "cevPowerSupplyAC345" {
    smiv2:oid "1.3.6.1.4.1.9.12.3.1.6.190";
  }

  smiv2:alias "cevPowerSupplyC3KPWR1150WAC" {
    smiv2:oid "1.3.6.1.4.1.9.12.3.1.6.191";
  }

  smiv2:alias "cevPowerSupplyPwrRPS2300" {
    smiv2:oid "1.3.6.1.4.1.9.12.3.1.6.192";
  }

  smiv2:alias "cevPowerSupplyCrs14DcPim" {
    smiv2:oid "1.3.6.1.4.1.9.12.3.1.6.193";
  }

  smiv2:alias "cevPowerSupplyDC1500W" {
    smiv2:oid "1.3.6.1.4.1.9.12.3.1.6.194";
  }

  smiv2:alias "cevPowerSupplyC7201AC" {
    smiv2:oid "1.3.6.1.4.1.9.12.3.1.6.195";
  }

  smiv2:alias "cevPowerSupplyC7201DC" {
    smiv2:oid "1.3.6.1.4.1.9.12.3.1.6.196";
  }

  smiv2:alias "cevPowerSupplyCE520AC173W48V" {
    smiv2:oid "1.3.6.1.4.1.9.12.3.1.6.197";
  }

  smiv2:alias "cevPowerSupplyAC100W" {
    smiv2:oid "1.3.6.1.4.1.9.12.3.1.6.198";
  }

  smiv2:alias "cevPowerSupplyN7KAC5600W" {
    smiv2:oid "1.3.6.1.4.1.9.12.3.1.6.199";
  }

  smiv2:alias "cevPowerSupplyASR1002AC" {
    smiv2:oid "1.3.6.1.4.1.9.12.3.1.6.200";
  }

  smiv2:alias "cevPowerSupplyASR1002DC" {
    smiv2:oid "1.3.6.1.4.1.9.12.3.1.6.201";
  }

  smiv2:alias "cevPowerSupplyASR1004AC" {
    smiv2:oid "1.3.6.1.4.1.9.12.3.1.6.202";
  }

  smiv2:alias "cevPowerSupplyASR1004DC" {
    smiv2:oid "1.3.6.1.4.1.9.12.3.1.6.203";
  }

  smiv2:alias "cevPowerSupplyASR1006AC" {
    smiv2:oid "1.3.6.1.4.1.9.12.3.1.6.204";
  }

  smiv2:alias "cevPowerSupplyASR1006DC" {
    smiv2:oid "1.3.6.1.4.1.9.12.3.1.6.205";
  }

  smiv2:alias "cevPowerSupplyASR1000Unknown" {
    smiv2:oid "1.3.6.1.4.1.9.12.3.1.6.206";
  }

  smiv2:alias "cevPowerSupplyC49M1000AC" {
    smiv2:oid "1.3.6.1.4.1.9.12.3.1.6.207";
  }

  smiv2:alias "cevPowerSupplyC49M1000DC" {
    smiv2:oid "1.3.6.1.4.1.9.12.3.1.6.208";
  }

  smiv2:alias "cevPowerSupplyN7KAC7500W" {
    smiv2:oid "1.3.6.1.4.1.9.12.3.1.6.209";
  }

  smiv2:alias "cevPowerSupplyCE520LCAC135W12V" {
    smiv2:oid "1.3.6.1.4.1.9.12.3.1.6.210";
  }

  smiv2:alias "cevPowerSupplyCE520PCAC558W12V" {
    smiv2:oid "1.3.6.1.4.1.9.12.3.1.6.211";
  }

  smiv2:alias "cevPowerSupplyCE520TTAC60W12V" {
    smiv2:oid "1.3.6.1.4.1.9.12.3.1.6.212";
  }

  smiv2:alias "cevPowerSupplyCE520GTCAC125W12V" {
    smiv2:oid "1.3.6.1.4.1.9.12.3.1.6.213";
  }

  smiv2:alias "cevPowerSupplyN7KAC6000W" {
    smiv2:oid "1.3.6.1.4.1.9.12.3.1.6.214";
  }

  smiv2:alias "cevPowerSupplyDc4500W" {
    smiv2:oid "1.3.6.1.4.1.9.12.3.1.6.215";
  }

  smiv2:alias "cevPowerSupplyIE3000AC" {
    smiv2:oid "1.3.6.1.4.1.9.12.3.1.6.216";
  }

  smiv2:alias "cevPowerSupplyN5kPac1200W" {
    smiv2:oid "1.3.6.1.4.1.9.12.3.1.6.217";
  }

  smiv2:alias "cevPowerSupplyCat2918AC60W12V" {
    smiv2:oid "1.3.6.1.4.1.9.12.3.1.6.218";
  }

  smiv2:alias "cevPowerSupplyC3KPWR300WAC" {
    smiv2:oid "1.3.6.1.4.1.9.12.3.1.6.220";
  }

  smiv2:alias "cevPowerSupplyC3KPWR300WDC" {
    smiv2:oid "1.3.6.1.4.1.9.12.3.1.6.221";
  }

  smiv2:alias "cevPowerSupplyDCPowerSupply" {
    smiv2:oid "1.3.6.1.4.1.9.12.3.1.6.222";
  }

  smiv2:alias "cevPowerSupplyACPowerSupply" {
    smiv2:oid "1.3.6.1.4.1.9.12.3.1.6.223";
  }

  smiv2:alias "cevPowerSupplyN7KAC7500WINT" {
    smiv2:oid "1.3.6.1.4.1.9.12.3.1.6.228";
  }

  smiv2:alias "cevPowerSupplyN7KAC7500WUS" {
    smiv2:oid "1.3.6.1.4.1.9.12.3.1.6.229";
  }

  smiv2:alias "cevPowerSupplyN5kPac550W" {
    smiv2:oid "1.3.6.1.4.1.9.12.3.1.6.230";
  }

  smiv2:alias "cevPowerSupplyASR9KDC2100W" {
    smiv2:oid "1.3.6.1.4.1.9.12.3.1.6.231";
  }

  smiv2:alias "cevPowerSupplyASR9KDC1500W" {
    smiv2:oid "1.3.6.1.4.1.9.12.3.1.6.232";
  }

  smiv2:alias "cevPowerSupplyASR9KAC3KW" {
    smiv2:oid "1.3.6.1.4.1.9.12.3.1.6.233";
  }

  smiv2:alias "cevPowerSupplyCrs16dcPemB" {
    smiv2:oid "1.3.6.1.4.1.9.12.3.1.6.234";
  }

  smiv2:alias "cevPowerSupplyC3900PWRPOE" {
    smiv2:oid "1.3.6.1.4.1.9.12.3.1.6.235";
  }

  smiv2:alias "cevPowerSupplyC3900PWRAC" {
    smiv2:oid "1.3.6.1.4.1.9.12.3.1.6.236";
  }

  smiv2:alias "cevPowerSupplyC2921C2951PWRPOE" {
    smiv2:oid "1.3.6.1.4.1.9.12.3.1.6.237";
  }

  smiv2:alias "cevPowerSupplyC2921C2951PWRAC" {
    smiv2:oid "1.3.6.1.4.1.9.12.3.1.6.238";
  }

  smiv2:alias "cevPowerSupplyC2911PWRPOE" {
    smiv2:oid "1.3.6.1.4.1.9.12.3.1.6.239";
  }

  smiv2:alias "cevPowerSupplyC2911PWRAC" {
    smiv2:oid "1.3.6.1.4.1.9.12.3.1.6.240";
  }

  smiv2:alias "cevPowerSupplyC2901PWRPOE" {
    smiv2:oid "1.3.6.1.4.1.9.12.3.1.6.241";
  }

  smiv2:alias "cevPowerSupplyC1941C2901PWRAC" {
    smiv2:oid "1.3.6.1.4.1.9.12.3.1.6.242";
  }

  smiv2:alias "cevPowerSupplyC1941PWRPOE" {
    smiv2:oid "1.3.6.1.4.1.9.12.3.1.6.243";
  }

  smiv2:alias "cevPowerSupplyC3900PWRDC" {
    smiv2:oid "1.3.6.1.4.1.9.12.3.1.6.244";
  }

  smiv2:alias "cevPowerSupplyC2921C2951PWRDC" {
    smiv2:oid "1.3.6.1.4.1.9.12.3.1.6.245";
  }

  smiv2:alias "cevPowerSupplyC2911PWRDC" {
    smiv2:oid "1.3.6.1.4.1.9.12.3.1.6.246";
  }

  smiv2:alias "cevPowerSupplyC2921C2951RPSADPTR" {
    smiv2:oid "1.3.6.1.4.1.9.12.3.1.6.247";
  }

  smiv2:alias "cevPowerSupplyC2911RPSADPTR" {
    smiv2:oid "1.3.6.1.4.1.9.12.3.1.6.248";
  }

  smiv2:alias "cevPowerSupplyN2kPac200W" {
    smiv2:oid "1.3.6.1.4.1.9.12.3.1.6.249";
  }

  smiv2:alias "cevPowerSupplyC456000ACV" {
    smiv2:oid "1.3.6.1.4.1.9.12.3.1.6.250";
  }

  smiv2:alias "cevPowerUCSN10PAC1550W" {
    smiv2:oid "1.3.6.1.4.1.9.12.3.1.6.251";
  }

  smiv2:alias "cevPowerSupplyN7KDC6000W" {
    smiv2:oid "1.3.6.1.4.1.9.12.3.1.6.253";
  }

  smiv2:alias "cevPowerSupplyCrs18PowerShelfDCModular" {
    smiv2:oid "1.3.6.1.4.1.9.12.3.1.6.254";
  }

  smiv2:alias "cevPowerSupplyCrs18PowerShelfACModular" {
    smiv2:oid "1.3.6.1.4.1.9.12.3.1.6.255";
  }

  smiv2:alias "cevPowerSupplyCrs116FCCPowerShelfDCModular" {
    smiv2:oid "1.3.6.1.4.1.9.12.3.1.6.256";
  }

  smiv2:alias "cevPowerSupplyCrs116FCCPowerShelfACModular" {
    smiv2:oid "1.3.6.1.4.1.9.12.3.1.6.257";
  }

  smiv2:alias "cevPowerSupplyCrs1DCPowerModule" {
    smiv2:oid "1.3.6.1.4.1.9.12.3.1.6.258";
  }

  smiv2:alias "cevPowerSupplyCrs1ACPowerModule" {
    smiv2:oid "1.3.6.1.4.1.9.12.3.1.6.259";
  }

  smiv2:alias "cevPowerSupplyCrs116LCCPowerShelfDCModular" {
    smiv2:oid "1.3.6.1.4.1.9.12.3.1.6.260";
  }

  smiv2:alias "cevPowerSupplyCrs116LCCPowerShelfACModular" {
    smiv2:oid "1.3.6.1.4.1.9.12.3.1.6.261";
  }

  smiv2:alias "cevPowerSupplyCat2960AC123W12V" {
    smiv2:oid "1.3.6.1.4.1.9.12.3.1.6.262";
  }

  smiv2:alias "cevPowerSupplyCat2960AC370W12V" {
    smiv2:oid "1.3.6.1.4.1.9.12.3.1.6.263";
  }

  smiv2:alias "cevPowerSupplyCat2960AC235W12V" {
    smiv2:oid "1.3.6.1.4.1.9.12.3.1.6.264";
  }

  smiv2:alias "cevPowerSupplyCat2960AC525W12V" {
    smiv2:oid "1.3.6.1.4.1.9.12.3.1.6.265";
  }

  smiv2:alias "cevPowerSupplyASR1001AC" {
    smiv2:oid "1.3.6.1.4.1.9.12.3.1.6.267";
  }

  smiv2:alias "cevPowerSupplyASR1001DC" {
    smiv2:oid "1.3.6.1.4.1.9.12.3.1.6.268";
  }

  smiv2:alias "cevPowerSupplyASR1013AC" {
    smiv2:oid "1.3.6.1.4.1.9.12.3.1.6.269";
  }

  smiv2:alias "cevPowerSupplyASR1013DC" {
    smiv2:oid "1.3.6.1.4.1.9.12.3.1.6.270";
  }

  smiv2:alias "cevPowerSupplyC1941PWRAC" {
    smiv2:oid "1.3.6.1.4.1.9.12.3.1.6.271";
  }

  smiv2:alias "cevPowerSupplyASR1002DC24V" {
    smiv2:oid "1.3.6.1.4.1.9.12.3.1.6.272";
  }

  smiv2:alias "cevPowerSupplyN2kC2200Pac400W" {
    smiv2:oid "1.3.6.1.4.1.9.12.3.1.6.273";
  }

  smiv2:alias "cevPowerSupplyC3kxPwr350wAc" {
    smiv2:oid "1.3.6.1.4.1.9.12.3.1.6.278";
  }

  smiv2:alias "cevPowerSupplyC3kxPwr715wAc" {
    smiv2:oid "1.3.6.1.4.1.9.12.3.1.6.279";
  }

  smiv2:alias "cevPowerSupplyC3kxPwr1100wAc" {
    smiv2:oid "1.3.6.1.4.1.9.12.3.1.6.280";
  }

  smiv2:alias "cevPowerSupplyPWRME3KXAC" {
    smiv2:oid "1.3.6.1.4.1.9.12.3.1.6.282";
  }

  smiv2:alias "cevPowerSupplyPWRME3KXDC" {
    smiv2:oid "1.3.6.1.4.1.9.12.3.1.6.283";
  }

  smiv2:alias "cevPowerSupplyCGR20xxCGS25xxPWRACPOE" {
    smiv2:oid "1.3.6.1.4.1.9.12.3.1.6.284";
  }

  smiv2:alias "cevPowerSupplyCGR20xxCGS25xxPWRDCPOE" {
    smiv2:oid "1.3.6.1.4.1.9.12.3.1.6.285";
  }

  smiv2:alias "cevPowerSupplyMXE5600" {
    smiv2:oid "1.3.6.1.4.1.9.12.3.1.6.286";
  }

  smiv2:alias "cevPowerSupplyC7225AC" {
    smiv2:oid "1.3.6.1.4.1.9.12.3.1.6.287";
  }

  smiv2:alias "cevPowerSupplyPWRC49EAC300WR" {
    smiv2:oid "1.3.6.1.4.1.9.12.3.1.6.288";
  }

  smiv2:alias "cevPowerSupplyC2360Pwr135wac" {
    smiv2:oid "1.3.6.1.4.1.9.12.3.1.6.290";
  }

  smiv2:alias "cevPowerSupplyN55Pac750W" {
    smiv2:oid "1.3.6.1.4.1.9.12.3.1.6.291";
  }

  smiv2:alias "cevPowerSupplyCrs16PshDcB" {
    smiv2:oid "1.3.6.1.4.1.9.12.3.1.6.293";
  }

  smiv2:alias "cevPowerSupplyCrs16PshAcB" {
    smiv2:oid "1.3.6.1.4.1.9.12.3.1.6.294";
  }

  smiv2:alias "cevPowerSupplyPWRC49EAC300WF" {
    smiv2:oid "1.3.6.1.4.1.9.12.3.1.6.295";
  }

  smiv2:alias "cevPowerSupplyPWRC49DC300WF" {
    smiv2:oid "1.3.6.1.4.1.9.12.3.1.6.296";
  }

  smiv2:alias "cevPowerSupplyN2kN2200Pdc400W" {
    smiv2:oid "1.3.6.1.4.1.9.12.3.1.6.297";
  }

  smiv2:alias "cevPowerSupplyASR1000PS" {
    smiv2:oid "1.3.6.1.4.1.9.12.3.1.6.298";
  }

  smiv2:alias "cevPowerSupplyCat2928AC60W12V" {
    smiv2:oid "1.3.6.1.4.1.9.12.3.1.6.299";
  }

  smiv2:alias "cevPowerSupplyCat2928AC100W12V" {
    smiv2:oid "1.3.6.1.4.1.9.12.3.1.6.300";
  }

  smiv2:alias "cevPowerSupplyPwrXPS2200" {
    smiv2:oid "1.3.6.1.4.1.9.12.3.1.6.301";
  }

  smiv2:alias "cevPowerSupplyN55Pac1100W" {
    smiv2:oid "1.3.6.1.4.1.9.12.3.1.6.302";
  }

  smiv2:alias "cevPowerSupplyN2kN2200Pac400WB" {
    smiv2:oid "1.3.6.1.4.1.9.12.3.1.6.303";
  }

  smiv2:alias "cevPowerSupplyUCS6248UpAC750W" {
    smiv2:oid "1.3.6.1.4.1.9.12.3.1.6.306";
  }

  smiv2:alias "cevPowerSupplyUCS6248UpDC750W" {
    smiv2:oid "1.3.6.1.4.1.9.12.3.1.6.307";
  }

  smiv2:alias "cevPowerSupplyUCS6296UpDC1100W" {
    smiv2:oid "1.3.6.1.4.1.9.12.3.1.6.308";
  }

  smiv2:alias "cevPowerSupplyUCS6296UpAC1100W" {
    smiv2:oid "1.3.6.1.4.1.9.12.3.1.6.309";
  }

  smiv2:alias "cevPowerSupplyN7KDC3KW" {
    smiv2:oid "1.3.6.1.4.1.9.12.3.1.6.310";
  }

  smiv2:alias "cevPowerSupplyCat2960CAC167W" {
    smiv2:oid "1.3.6.1.4.1.9.12.3.1.6.311";
  }

  smiv2:alias "cevPowerSupplyCat2960CAC36W12V" {
    smiv2:oid "1.3.6.1.4.1.9.12.3.1.6.312";
  }

  smiv2:alias "cevPowerSupplyN7KAC3KW" {
    smiv2:oid "1.3.6.1.4.1.9.12.3.1.6.313";
  }

  smiv2:alias "cevPowerSupplyN55Pdc750W" {
    smiv2:oid "1.3.6.1.4.1.9.12.3.1.6.314";
  }

  smiv2:alias "cevPowerSupplyOe8541" {
    smiv2:oid "1.3.6.1.4.1.9.12.3.1.6.315";
  }

  smiv2:alias "cevPowerSupplyOe7571" {
    smiv2:oid "1.3.6.1.4.1.9.12.3.1.6.316";
  }

  smiv2:alias "cevPowerSupplyOe7541" {
    smiv2:oid "1.3.6.1.4.1.9.12.3.1.6.317";
  }

  smiv2:alias "cevPowerSupplyOe694" {
    smiv2:oid "1.3.6.1.4.1.9.12.3.1.6.318";
  }

  smiv2:alias "cevPowerSupplyOe594" {
    smiv2:oid "1.3.6.1.4.1.9.12.3.1.6.319";
  }

  smiv2:alias "cevPowerSupplyOe294" {
    smiv2:oid "1.3.6.1.4.1.9.12.3.1.6.320";
  }

  smiv2:alias "cevPowerSupplyASA5555PSInput" {
    smiv2:oid "1.3.6.1.4.1.9.12.3.1.6.324";
  }

  smiv2:alias "cevPowerSupplyN2kN2200Pac400W" {
    smiv2:oid "1.3.6.1.4.1.9.12.3.1.6.325";
  }

  smiv2:alias "cevPowerSupplyN55Pac750WB" {
    smiv2:oid "1.3.6.1.4.1.9.12.3.1.6.326";
  }

  smiv2:alias "cevPowerSupplyN55Pac1100WB" {
    smiv2:oid "1.3.6.1.4.1.9.12.3.1.6.327";
  }

  smiv2:alias "cevPowerSupplyASR900DC500W" {
    smiv2:oid "1.3.6.1.4.1.9.12.3.1.6.328";
  }

  smiv2:alias "cevPowerSupplyCrs8PshDcB" {
    smiv2:oid "1.3.6.1.4.1.9.12.3.1.6.330";
  }

  smiv2:alias "cevPowerSupplyCrs8PshAcB" {
    smiv2:oid "1.3.6.1.4.1.9.12.3.1.6.331";
  }

  smiv2:alias "cevPowerSupplyASR5KPfu" {
    smiv2:oid "1.3.6.1.4.1.9.12.3.1.6.332";
  }

  smiv2:alias "cevPowerSupplyASR55PFU" {
    smiv2:oid "1.3.6.1.4.1.9.12.3.1.6.333";
  }

  smiv2:alias "cevPowerSupplyIE2000AC" {
    smiv2:oid "1.3.6.1.4.1.9.12.3.1.6.334";
  }

  smiv2:alias "cevPowerSupplyC459000ACV" {
    smiv2:oid "1.3.6.1.4.1.9.12.3.1.6.337";
  }

  smiv2:alias "cevPowerSupplyN2kN2200Pdc350WB" {
    smiv2:oid "1.3.6.1.4.1.9.12.3.1.6.338";
  }

  smiv2:alias "cevPowerSupplyVG350PWRAC" {
    smiv2:oid "1.3.6.1.4.1.9.12.3.1.6.339";
  }

  smiv2:alias "cevPowerSupplyVG350PWRDC" {
    smiv2:oid "1.3.6.1.4.1.9.12.3.1.6.340";
  }

  smiv2:alias "cevPowerSupplyASR9KAC3KWV2" {
    smiv2:oid "1.3.6.1.4.1.9.12.3.1.6.341";
  }

  smiv2:alias "cevPowerSupplyASR9KDC2100WV2" {
    smiv2:oid "1.3.6.1.4.1.9.12.3.1.6.342";
  }

  smiv2:alias "cevPowerSupplyASR9KAC750W" {
    smiv2:oid "1.3.6.1.4.1.9.12.3.1.6.343";
  }

  smiv2:alias "cevPowerSupplyASR9KDC750W" {
    smiv2:oid "1.3.6.1.4.1.9.12.3.1.6.344";
  }

  smiv2:alias "cevPowerSupplyISR4400PWR1000" {
    smiv2:oid "1.3.6.1.4.1.9.12.3.1.6.345";
  }

  smiv2:alias "cevPowerSupplyISR4400PWR450" {
    smiv2:oid "1.3.6.1.4.1.9.12.3.1.6.346";
  }

  smiv2:alias "cevPowerSupplyC4KXPWR750DCF" {
    smiv2:oid "1.3.6.1.4.1.9.12.3.1.6.347";
  }

  smiv2:alias "cevPowerSupplyC4KXPWR750ACF" {
    smiv2:oid "1.3.6.1.4.1.9.12.3.1.6.348";
  }

  smiv2:alias "cevPowerSupplyC4KXPWR750DCR" {
    smiv2:oid "1.3.6.1.4.1.9.12.3.1.6.349";
  }

  smiv2:alias "cevPowerSupplyC4KXPWR750ACR" {
    smiv2:oid "1.3.6.1.4.1.9.12.3.1.6.350";
  }

  smiv2:alias "cevPowerSupplyNXAPac200WB" {
    smiv2:oid "1.3.6.1.4.1.9.12.3.1.6.351";
  }

  smiv2:alias "cevPowerSupplyNXAPac200W" {
    smiv2:oid "1.3.6.1.4.1.9.12.3.1.6.352";
  }

  smiv2:alias "cevPowerSupplyISR4400Unknown" {
    smiv2:oid "1.3.6.1.4.1.9.12.3.1.6.353";
  }

  smiv2:alias "cevPowerSupplyASR9000vGenericPm" {
    smiv2:oid "1.3.6.1.4.1.9.12.3.1.6.354";
  }

  smiv2:alias "cevPowerSupplyNXAPac1100W" {
    smiv2:oid "1.3.6.1.4.1.9.12.3.1.6.355";
  }

  smiv2:alias "cevPowerSupplyNXAPac1100WB" {
    smiv2:oid "1.3.6.1.4.1.9.12.3.1.6.359";
  }

  smiv2:alias "cevPowerSupplyN3kPac400WB" {
    smiv2:oid "1.3.6.1.4.1.9.12.3.1.6.360";
  }

  smiv2:alias "cevPowerSupplyN3kPac400W" {
    smiv2:oid "1.3.6.1.4.1.9.12.3.1.6.361";
  }

  smiv2:alias "cevPowerSupplyNXAPAC500W" {
    smiv2:oid "1.3.6.1.4.1.9.12.3.1.6.362";
  }

  smiv2:alias "cevPowerSupplyNXAPAC500WB" {
    smiv2:oid "1.3.6.1.4.1.9.12.3.1.6.363";
  }

  smiv2:alias "cevPowerSupplyISR4400PS" {
    smiv2:oid "1.3.6.1.4.1.9.12.3.1.6.364";
  }

  smiv2:alias "cevPowerSupplyN55PDC1100W" {
    smiv2:oid "1.3.6.1.4.1.9.12.3.1.6.365";
  }

  smiv2:alias "cevPowerSupplyASA5545PSInputSensor" {
    smiv2:oid "1.3.6.1.4.1.9.12.3.1.6.366";
  }

  smiv2:alias "cevPowerSupplyASA5555PSInputSensor" {
    smiv2:oid "1.3.6.1.4.1.9.12.3.1.6.367";
  }

  smiv2:alias "cevPowerSupplyASA5545K7PSInputSensor" {
    smiv2:oid "1.3.6.1.4.1.9.12.3.1.6.368";
  }

  smiv2:alias "cevPowerSupplyASA5555K7PSInputSensor" {
    smiv2:oid "1.3.6.1.4.1.9.12.3.1.6.369";
  }

  smiv2:alias "cevPowerSupplyCat2960XAC173W" {
    smiv2:oid "1.3.6.1.4.1.9.12.3.1.6.370";
  }

  smiv2:alias "cevPowerSupplyC6880X3KWAC" {
    smiv2:oid "1.3.6.1.4.1.9.12.3.1.6.372";
  }

  smiv2:alias "cevPowerSupplyC6880X3KWDC" {
    smiv2:oid "1.3.6.1.4.1.9.12.3.1.6.373";
  }

  smiv2:alias "cevPowerSupplyDS9710" {
    smiv2:oid "1.3.6.1.4.1.9.12.3.1.6.374";
  }

  smiv2:alias "cevPowerSupplyPWR3KWACV2" {
    smiv2:oid "1.3.6.1.4.1.9.12.3.1.6.376";
  }

  smiv2:alias "cevPowerSupplyNCSDCPWRTRAY" {
    smiv2:oid "1.3.6.1.4.1.9.12.3.1.6.377";
  }

  smiv2:alias "cevPowerSupplyNCSACPWRTRAY" {
    smiv2:oid "1.3.6.1.4.1.9.12.3.1.6.378";
  }

  smiv2:alias "cevPowerSupplyDSC50I300AC" {
    smiv2:oid "1.3.6.1.4.1.9.12.3.1.6.380";
  }

  smiv2:alias "cevPowerSupplyDSCAC973KW" {
    smiv2:oid "1.3.6.1.4.1.9.12.3.1.6.381";
  }

  smiv2:alias "cevPowerSupplyDSCDC973KW" {
    smiv2:oid "1.3.6.1.4.1.9.12.3.1.6.382";
  }

  smiv2:alias "cevPowerSupplyN77AC3KW" {
    smiv2:oid "1.3.6.1.4.1.9.12.3.1.6.383";
  }

  smiv2:alias "cevPowerSupplyN77DC3KW" {
    smiv2:oid "1.3.6.1.4.1.9.12.3.1.6.384";
  }

  smiv2:alias "cevPowerSupplyC6800XL3KWAC" {
    smiv2:oid "1.3.6.1.4.1.9.12.3.1.6.385";
  }

  smiv2:alias "cevPowerSupplyVG3X0PWRAC" {
    smiv2:oid "1.3.6.1.4.1.9.12.3.1.6.397";
  }

  smiv2:alias "cevPowerSupplyVG3X0PWRDC" {
    smiv2:oid "1.3.6.1.4.1.9.12.3.1.6.398";
  }

  smiv2:alias "cevPowerSupplyNXAPDC500W" {
    smiv2:oid "1.3.6.1.4.1.9.12.3.1.6.399";
  }

  smiv2:alias "cevPowerSupplyNXAPDC500WB" {
    smiv2:oid "1.3.6.1.4.1.9.12.3.1.6.400";
  }

  smiv2:alias "cevPowerSupplyN9KAC3000W" {
    smiv2:oid "1.3.6.1.4.1.9.12.3.1.6.404";
  }

  smiv2:alias "cevPowerSupplyN9KPac1200WB" {
    smiv2:oid "1.3.6.1.4.1.9.12.3.1.6.405";
  }

  smiv2:alias "cevPowerSupplyN9KPac1200W" {
    smiv2:oid "1.3.6.1.4.1.9.12.3.1.6.406";
  }

  smiv2:alias "cevPowerSupplyN9KPac650WB" {
    smiv2:oid "1.3.6.1.4.1.9.12.3.1.6.407";
  }

  smiv2:alias "cevPowerSupplyN9KPac650W" {
    smiv2:oid "1.3.6.1.4.1.9.12.3.1.6.408";
  }

  smiv2:alias "cevPowerSupply30WAC" {
    smiv2:oid "1.3.6.1.4.1.9.12.3.1.6.416";
  }

  smiv2:alias "cevPowerSupply60WAC" {
    smiv2:oid "1.3.6.1.4.1.9.12.3.1.6.417";
  }

  smiv2:alias "cevPowerSupply60WACV2" {
    smiv2:oid "1.3.6.1.4.1.9.12.3.1.6.418";
  }

  smiv2:alias "cevPowerSupply125WAC" {
    smiv2:oid "1.3.6.1.4.1.9.12.3.1.6.419";
  }

  smiv2:alias "cevPowerSupplyRT2241PWRAC" {
    smiv2:oid "1.3.6.1.4.1.9.12.3.1.6.420";
  }

  smiv2:alias "cevPowerSupplyRT3201PWRAC" {
    smiv2:oid "1.3.6.1.4.1.9.12.3.1.6.421";
  }

  smiv2:alias "cevPowerSupplyRT3211PWRAC" {
    smiv2:oid "1.3.6.1.4.1.9.12.3.1.6.422";
  }

  smiv2:alias "cevPowerSupplyRT3211PWRDC" {
    smiv2:oid "1.3.6.1.4.1.9.12.3.1.6.423";
  }

  smiv2:alias "cevPowerSupplyRT32PWRAC" {
    smiv2:oid "1.3.6.1.4.1.9.12.3.1.6.424";
  }

  smiv2:alias "cevPowerSupplyRT3211RPSADPTR" {
    smiv2:oid "1.3.6.1.4.1.9.12.3.1.6.425";
  }

  smiv2:alias "cevPowerSupplyRT32RPSADPTR" {
    smiv2:oid "1.3.6.1.4.1.9.12.3.1.6.426";
  }

  smiv2:alias "cevPowerSupplyDSC48S300AC" {
    smiv2:oid "1.3.6.1.4.1.9.12.3.1.6.439";
  }

  smiv2:alias "cevPowerSupply540WPSU" {
    smiv2:oid "1.3.6.1.4.1.9.12.3.1.6.446";
  }

  smiv2:alias "cevPowerSupplyNXAPHV500WB" {
    smiv2:oid "1.3.6.1.4.1.9.12.3.1.6.447";
  }

  smiv2:alias "cevPowerSupplyNXAPHV500W" {
    smiv2:oid "1.3.6.1.4.1.9.12.3.1.6.448";
  }

  smiv2:alias "cevPowerSupplyNXAPHV1100WB" {
    smiv2:oid "1.3.6.1.4.1.9.12.3.1.6.449";
  }

  smiv2:alias "cevPowerSupplyNXAPHV1100W" {
    smiv2:oid "1.3.6.1.4.1.9.12.3.1.6.450";
  }

  smiv2:alias "cevPowerSupplyUCS6248HVDC750W" {
    smiv2:oid "1.3.6.1.4.1.9.12.3.1.6.451";
  }

  smiv2:alias "cevPowerSupplyASR92024SZIM" {
    smiv2:oid "1.3.6.1.4.1.9.12.3.1.6.463";
  }

  smiv2:alias "cevPowerSupplyASR92024SZM" {
    smiv2:oid "1.3.6.1.4.1.9.12.3.1.6.464";
  }

  smiv2:alias "cevPowerSupplyASR92024TZM" {
    smiv2:oid "1.3.6.1.4.1.9.12.3.1.6.465";
  }

  smiv2:alias "cevPowerSupplyASR920PWRA" {
    smiv2:oid "1.3.6.1.4.1.9.12.3.1.6.471";
  }

  smiv2:alias "cevPowerSupplyASR920PWRD" {
    smiv2:oid "1.3.6.1.4.1.9.12.3.1.6.472";
  }

  smiv2:alias "cevPowerSupplyC2911PWRDCPOE" {
    smiv2:oid "1.3.6.1.4.1.9.12.3.1.6.473";
  }

  smiv2:alias "cevPowerSupplySCE10000AC1200W" {
    smiv2:oid "1.3.6.1.4.1.9.12.3.1.6.480";
  }

  smiv2:alias "cevPowerSupplySCE10000DC930W" {
    smiv2:oid "1.3.6.1.4.1.9.12.3.1.6.481";
  }

  smiv2:alias "cevPowerSupplyDSCAC1200WE" {
    smiv2:oid "1.3.6.1.4.1.9.12.3.1.6.482";
  }

  smiv2:alias "cevPowerSupplyDSCAC1200W" {
    smiv2:oid "1.3.6.1.4.1.9.12.3.1.6.483";
  }

  smiv2:alias "cevFan" {
    smiv2:oid "1.3.6.1.4.1.9.12.3.1.7";
  }

  smiv2:alias "cevFanC6260FanTray" {
    smiv2:oid "1.3.6.1.4.1.9.12.3.1.7.3";
  }

  smiv2:alias "cevFanSinglePulse" {
    smiv2:oid "1.3.6.1.4.1.9.12.3.1.7.4";
  }

  smiv2:alias "cevFanDualPulse" {
    smiv2:oid "1.3.6.1.4.1.9.12.3.1.7.5";
  }

  smiv2:alias "cevFan12012FanTray3" {
    smiv2:oid "1.3.6.1.4.1.9.12.3.1.7.6";
  }

  smiv2:alias "cevFan12008FanTray6" {
    smiv2:oid "1.3.6.1.4.1.9.12.3.1.7.7";
  }

  smiv2:alias "cevFan12008FanTray4" {
    smiv2:oid "1.3.6.1.4.1.9.12.3.1.7.8";
  }

  smiv2:alias "cevFanC6160FanTray" {
    smiv2:oid "1.3.6.1.4.1.9.12.3.1.7.9";
  }

  smiv2:alias "cevFanC6100FanTray" {
    smiv2:oid "1.3.6.1.4.1.9.12.3.1.7.11";
  }

  smiv2:alias "cevFan12010FanTray3" {
    smiv2:oid "1.3.6.1.4.1.9.12.3.1.7.13";
  }

  smiv2:alias "cevFan12406FanTray3" {
    smiv2:oid "1.3.6.1.4.1.9.12.3.1.7.14";
  }

  smiv2:alias "cevFan12410FanTray3" {
    smiv2:oid "1.3.6.1.4.1.9.12.3.1.7.15";
  }

  smiv2:alias "cevFanONS15540FanTray8" {
    smiv2:oid "1.3.6.1.4.1.9.12.3.1.7.16";
  }

  smiv2:alias "cevFan12404FanTray7" {
    smiv2:oid "1.3.6.1.4.1.9.12.3.1.7.17";
  }

  smiv2:alias "cevFanBP7513MainFan" {
    smiv2:oid "1.3.6.1.4.1.9.12.3.1.7.18";
  }

  smiv2:alias "cevFanBP7513PS1Fan" {
    smiv2:oid "1.3.6.1.4.1.9.12.3.1.7.19";
  }

  smiv2:alias "cevFanBP7513PS2Fan" {
    smiv2:oid "1.3.6.1.4.1.9.12.3.1.7.20";
  }

  smiv2:alias "cevFan7505Fan" {
    smiv2:oid "1.3.6.1.4.1.9.12.3.1.7.21";
  }

  smiv2:alias "cevFan7507Fan" {
    smiv2:oid "1.3.6.1.4.1.9.12.3.1.7.22";
  }

  smiv2:alias "cevFanC7300PowerSupplyFan" {
    smiv2:oid "1.3.6.1.4.1.9.12.3.1.7.23";
  }

  smiv2:alias "cevFanC7300FanModule" {
    smiv2:oid "1.3.6.1.4.1.9.12.3.1.7.24";
  }

  smiv2:alias "cevFanTrayC10008" {
    smiv2:oid "1.3.6.1.4.1.9.12.3.1.7.25";
  }

  smiv2:alias "cevFanTrayC10005" {
    smiv2:oid "1.3.6.1.4.1.9.12.3.1.7.26";
  }

  smiv2:alias "cevFanCat4kFanTray" {
    smiv2:oid "1.3.6.1.4.1.9.12.3.1.7.27";
  }

  smiv2:alias "cevFanCat4kPowerSupplyFan" {
    smiv2:oid "1.3.6.1.4.1.9.12.3.1.7.28";
  }

  smiv2:alias "cevFanC6160ITempFanTray" {
    smiv2:oid "1.3.6.1.4.1.9.12.3.1.7.29";
  }

  smiv2:alias "cevFanONS15530FanTray6" {
    smiv2:oid "1.3.6.1.4.1.9.12.3.1.7.30";
  }

  smiv2:alias "cevFan12016FanTray3" {
    smiv2:oid "1.3.6.1.4.1.9.12.3.1.7.31";
  }

  smiv2:alias "cevFanCat3750CFM26" {
    smiv2:oid "1.3.6.1.4.1.9.12.3.1.7.34";
  }

  smiv2:alias "cevFanDs6SlotFanTray" {
    smiv2:oid "1.3.6.1.4.1.9.12.3.1.7.35";
  }

  smiv2:alias "cevFanDs9SlotFanTray" {
    smiv2:oid "1.3.6.1.4.1.9.12.3.1.7.36";
  }

  smiv2:alias "cevFanDs13SlotFanTray" {
    smiv2:oid "1.3.6.1.4.1.9.12.3.1.7.37";
  }

  smiv2:alias "cevFanTrayUnknown" {
    smiv2:oid "1.3.6.1.4.1.9.12.3.1.7.38";
  }

  smiv2:alias "cevFanDs2SlotFanTray" {
    smiv2:oid "1.3.6.1.4.1.9.12.3.1.7.39";
  }

  smiv2:alias "cevFanCat3710CFM26" {
    smiv2:oid "1.3.6.1.4.1.9.12.3.1.7.40";
  }

  smiv2:alias "cevFanCat37xx12" {
    smiv2:oid "1.3.6.1.4.1.9.12.3.1.7.41";
  }

  smiv2:alias "cevFanWS9SlotFanTray" {
    smiv2:oid "1.3.6.1.4.1.9.12.3.1.7.42";
  }

  smiv2:alias "cevFanMod9FanTray" {
    smiv2:oid "1.3.6.1.4.1.9.12.3.1.7.43";
  }

  smiv2:alias "cevFanCat2970CFM26" {
    smiv2:oid "1.3.6.1.4.1.9.12.3.1.7.44";
  }

  smiv2:alias "cevFanDs1RUFanTray" {
    smiv2:oid "1.3.6.1.4.1.9.12.3.1.7.45";
  }

  smiv2:alias "cevFanFanMod3" {
    smiv2:oid "1.3.6.1.4.1.9.12.3.1.7.46";
  }

  smiv2:alias "cevFanWSC6k6SlotFan" {
    smiv2:oid "1.3.6.1.4.1.9.12.3.1.7.47";
  }

  smiv2:alias "cevFanWSC6k6SlotFan2" {
    smiv2:oid "1.3.6.1.4.1.9.12.3.1.7.48";
  }

  smiv2:alias "cevFanWSC6k9SlotFan" {
    smiv2:oid "1.3.6.1.4.1.9.12.3.1.7.49";
  }

  smiv2:alias "cevFanWSC6k9SlotFan2" {
    smiv2:oid "1.3.6.1.4.1.9.12.3.1.7.50";
  }

  smiv2:alias "cevFanWSC6509NebFan" {
    smiv2:oid "1.3.6.1.4.1.9.12.3.1.7.51";
  }

  smiv2:alias "cevFanWSC6k13SlotFan" {
    smiv2:oid "1.3.6.1.4.1.9.12.3.1.7.52";
  }

  smiv2:alias "cevFanWSC6k13SlotFan2" {
    smiv2:oid "1.3.6.1.4.1.9.12.3.1.7.53";
  }

  smiv2:alias "cevFanFanMod3HS" {
    smiv2:oid "1.3.6.1.4.1.9.12.3.1.7.54";
  }

  smiv2:alias "cevFanWSC6509NebFan2" {
    smiv2:oid "1.3.6.1.4.1.9.12.3.1.7.55";
  }

  smiv2:alias "cevFanFanMod6" {
    smiv2:oid "1.3.6.1.4.1.9.12.3.1.7.56";
  }

  smiv2:alias "cevFanFanMod6HS" {
    smiv2:oid "1.3.6.1.4.1.9.12.3.1.7.57";
  }

  smiv2:alias "cevFanCrs1Fan" {
    smiv2:oid "1.3.6.1.4.1.9.12.3.1.7.58";
  }

  smiv2:alias "cevFanCat3560CFM26" {
    smiv2:oid "1.3.6.1.4.1.9.12.3.1.7.59";
  }

  smiv2:alias "cevFanDs1RUFanTray9116" {
    smiv2:oid "1.3.6.1.4.1.9.12.3.1.7.60";
  }

  smiv2:alias "cevFanWSC6506eFanTray" {
    smiv2:oid "1.3.6.1.4.1.9.12.3.1.7.61";
  }

  smiv2:alias "cevFanWSC6509eFanTray" {
    smiv2:oid "1.3.6.1.4.1.9.12.3.1.7.62";
  }

  smiv2:alias "cevFanWSC6513eFanTray" {
    smiv2:oid "1.3.6.1.4.1.9.12.3.1.7.63";
  }

  smiv2:alias "cevFanWSC6503eFanTray" {
    smiv2:oid "1.3.6.1.4.1.9.12.3.1.7.64";
  }

  smiv2:alias "cevFanUmg9820FanTray" {
    smiv2:oid "1.3.6.1.4.1.9.12.3.1.7.65";
  }

  smiv2:alias "cevFanMod4HS" {
    smiv2:oid "1.3.6.1.4.1.9.12.3.1.7.66";
  }

  smiv2:alias "cevFanC4kFCFanTray" {
    smiv2:oid "1.3.6.1.4.1.9.12.3.1.7.67";
  }

  smiv2:alias "cevFan12410EnhFanTray3" {
    smiv2:oid "1.3.6.1.4.1.9.12.3.1.7.68";
  }

  smiv2:alias "cevFan12406EnhFanTray3" {
    smiv2:oid "1.3.6.1.4.1.9.12.3.1.7.69";
  }

  smiv2:alias "cevFan12416EnhFanTray3" {
    smiv2:oid "1.3.6.1.4.1.9.12.3.1.7.70";
  }

  smiv2:alias "cevFan12404FanTray6" {
    smiv2:oid "1.3.6.1.4.1.9.12.3.1.7.71";
  }

  smiv2:alias "cevFan12404EnhFanTray6" {
    smiv2:oid "1.3.6.1.4.1.9.12.3.1.7.72";
  }

  smiv2:alias "cevFan9513FanTrayR" {
    smiv2:oid "1.3.6.1.4.1.9.12.3.1.7.73";
  }

  smiv2:alias "cevFanCat2960CFM22" {
    smiv2:oid "1.3.6.1.4.1.9.12.3.1.7.74";
  }

  smiv2:alias "cevFanCat2960CFM26" {
    smiv2:oid "1.3.6.1.4.1.9.12.3.1.7.75";
  }

  smiv2:alias "cevFanTrayUbr10012" {
    smiv2:oid "1.3.6.1.4.1.9.12.3.1.7.76";
  }

  smiv2:alias "cevFanC6524" {
    smiv2:oid "1.3.6.1.4.1.9.12.3.1.7.77";
  }

  smiv2:alias "cevFanCatEx500CFM22" {
    smiv2:oid "1.3.6.1.4.1.9.12.3.1.7.78";
  }

  smiv2:alias "cevFanCatEx500CFM32" {
    smiv2:oid "1.3.6.1.4.1.9.12.3.1.7.79";
  }

  smiv2:alias "cevFanCat3750CFM35" {
    smiv2:oid "1.3.6.1.4.1.9.12.3.1.7.80";
  }

  smiv2:alias "cevFanCFM15" {
    smiv2:oid "1.3.6.1.4.1.9.12.3.1.7.81";
  }

  smiv2:alias "cevFanCrs1FabricFanTray" {
    smiv2:oid "1.3.6.1.4.1.9.12.3.1.7.82";
  }

  smiv2:alias "cevModuleCrs116FanTray" {
    smiv2:oid "1.3.6.1.4.1.9.12.3.1.7.83";
  }

  smiv2:alias "cevModuleCrs18FanTray" {
    smiv2:oid "1.3.6.1.4.1.9.12.3.1.7.84";
  }

  smiv2:alias "cevModuleCrs14FanTray" {
    smiv2:oid "1.3.6.1.4.1.9.12.3.1.7.85";
  }

  smiv2:alias "cevFanC3KBLWR60CFM" {
    smiv2:oid "1.3.6.1.4.1.9.12.3.1.7.86";
  }

  smiv2:alias "cevFanMod6ShsFanTray" {
    smiv2:oid "1.3.6.1.4.1.9.12.3.1.7.87";
  }

  smiv2:alias "cevFanMod9ShsFanTray" {
    smiv2:oid "1.3.6.1.4.1.9.12.3.1.7.88";
  }

  smiv2:alias "cevFanMod9StFanTray" {
    smiv2:oid "1.3.6.1.4.1.9.12.3.1.7.89";
  }

  smiv2:alias "cevFanBlwrRPS2300" {
    smiv2:oid "1.3.6.1.4.1.9.12.3.1.7.90";
  }

  smiv2:alias "cevFanACE4710K9CpuFan" {
    smiv2:oid "1.3.6.1.4.1.9.12.3.1.7.91";
  }

  smiv2:alias "cevFanACE4710K9DimmFan" {
    smiv2:oid "1.3.6.1.4.1.9.12.3.1.7.92";
  }

  smiv2:alias "cevFanACE4710K9PciFan" {
    smiv2:oid "1.3.6.1.4.1.9.12.3.1.7.93";
  }

  smiv2:alias "cevFanWSC6509veFan" {
    smiv2:oid "1.3.6.1.4.1.9.12.3.1.7.94";
  }

  smiv2:alias "cevFanMod3ShsFanTray" {
    smiv2:oid "1.3.6.1.4.1.9.12.3.1.7.95";
  }

  smiv2:alias "cevFanSce8000FanTray" {
    smiv2:oid "1.3.6.1.4.1.9.12.3.1.7.96";
  }

  smiv2:alias "cevFanN7Kc7010MainFanTray" {
    smiv2:oid "1.3.6.1.4.1.9.12.3.1.7.97";
  }

  smiv2:alias "cevFanN7KC7010FabricFanTray" {
    smiv2:oid "1.3.6.1.4.1.9.12.3.1.7.98";
  }

  smiv2:alias "cevFanASR1002" {
    smiv2:oid "1.3.6.1.4.1.9.12.3.1.7.99";
  }

  smiv2:alias "cevFanASR1004" {
    smiv2:oid "1.3.6.1.4.1.9.12.3.1.7.100";
  }

  smiv2:alias "cevFanASR1006" {
    smiv2:oid "1.3.6.1.4.1.9.12.3.1.7.101";
  }

  smiv2:alias "cevFanCe520Cfm22" {
    smiv2:oid "1.3.6.1.4.1.9.12.3.1.7.102";
  }

  smiv2:alias "cevFanCe520Cfm32" {
    smiv2:oid "1.3.6.1.4.1.9.12.3.1.7.103";
  }

  smiv2:alias "cevFanN5kC5020Fan" {
    smiv2:oid "1.3.6.1.4.1.9.12.3.1.7.104";
  }

  smiv2:alias "cevFanCat2918Cfm22" {
    smiv2:oid "1.3.6.1.4.1.9.12.3.1.7.105";
  }

  smiv2:alias "cevFanC3KFAN16CFM" {
    smiv2:oid "1.3.6.1.4.1.9.12.3.1.7.106";
  }

  smiv2:alias "cevFanPowerSupplyFan" {
    smiv2:oid "1.3.6.1.4.1.9.12.3.1.7.107";
  }

  smiv2:alias "cevFanN7Kc7018FanTray" {
    smiv2:oid "1.3.6.1.4.1.9.12.3.1.7.109";
  }

  smiv2:alias "cevFanCrs16lccFntrB" {
    smiv2:oid "1.3.6.1.4.1.9.12.3.1.7.110";
  }

  smiv2:alias "cevFanASR14K4FanTray" {
    smiv2:oid "1.3.6.1.4.1.9.12.3.1.7.111";
  }

  smiv2:alias "cevFanASR14K8FanTray" {
    smiv2:oid "1.3.6.1.4.1.9.12.3.1.7.112";
  }

  smiv2:alias "cevFanN5kC5010Fan" {
    smiv2:oid "1.3.6.1.4.1.9.12.3.1.7.113";
  }

  smiv2:alias "cevFanASR9KFan" {
    smiv2:oid "1.3.6.1.4.1.9.12.3.1.7.114";
  }

  smiv2:alias "cevFanASR9010" {
    smiv2:oid "1.3.6.1.4.1.9.12.3.1.7.115";
  }

  smiv2:alias "cevFanASR9006" {
    smiv2:oid "1.3.6.1.4.1.9.12.3.1.7.116";
  }

  smiv2:alias "cevFanASR14K4Fan" {
    smiv2:oid "1.3.6.1.4.1.9.12.3.1.7.117";
  }

  smiv2:alias "cevFanASR14K8Fan" {
    smiv2:oid "1.3.6.1.4.1.9.12.3.1.7.118";
  }

  smiv2:alias "cevFanCrs14Fan" {
    smiv2:oid "1.3.6.1.4.1.9.12.3.1.7.119";
  }

  smiv2:alias "cevFanCrs18Fan" {
    smiv2:oid "1.3.6.1.4.1.9.12.3.1.7.120";
  }

  smiv2:alias "cevFanCrs116Fan" {
    smiv2:oid "1.3.6.1.4.1.9.12.3.1.7.121";
  }

  smiv2:alias "cevFanN2kC2148TFan" {
    smiv2:oid "1.3.6.1.4.1.9.12.3.1.7.122";
  }

  smiv2:alias "cevContainerUCSN10S6100Fan1" {
    smiv2:oid "1.3.6.1.4.1.9.12.3.1.7.124";
  }

  smiv2:alias "cevFanCat2960CFM32" {
    smiv2:oid "1.3.6.1.4.1.9.12.3.1.7.125";
  }

  smiv2:alias "cevFanContainerUCSN10Fan2" {
    smiv2:oid "1.3.6.1.4.1.9.12.3.1.7.126";
  }

  smiv2:alias "cevFanN7Kc7009FanTray" {
    smiv2:oid "1.3.6.1.4.1.9.12.3.1.7.129";
  }

  smiv2:alias "cevFanMEFanTray" {
    smiv2:oid "1.3.6.1.4.1.9.12.3.1.7.130";
  }

  smiv2:alias "cevFanMXE5600" {
    smiv2:oid "1.3.6.1.4.1.9.12.3.1.7.131";
  }

  smiv2:alias "cevFanC2360Fan" {
    smiv2:oid "1.3.6.1.4.1.9.12.3.1.7.132";
  }

  smiv2:alias "cevFanASR1001FanTray" {
    smiv2:oid "1.3.6.1.4.1.9.12.3.1.7.133";
  }

  smiv2:alias "cevFanASR1000Fan" {
    smiv2:oid "1.3.6.1.4.1.9.12.3.1.7.134";
  }

  smiv2:alias "cevFanN5548PFan" {
    smiv2:oid "1.3.6.1.4.1.9.12.3.1.7.135";
  }

  smiv2:alias "cevFanCrs16FanTrB" {
    smiv2:oid "1.3.6.1.4.1.9.12.3.1.7.139";
  }

  smiv2:alias "cevFanCat2928Cfm22" {
    smiv2:oid "1.3.6.1.4.1.9.12.3.1.7.140";
  }

  smiv2:alias "cevFanCat2928Cfm32" {
    smiv2:oid "1.3.6.1.4.1.9.12.3.1.7.141";
  }

  smiv2:alias "cevFanBlwrXPS2200" {
    smiv2:oid "1.3.6.1.4.1.9.12.3.1.7.142";
  }

  smiv2:alias "cevFanN5596UPFan" {
    smiv2:oid "1.3.6.1.4.1.9.12.3.1.7.143";
  }

  smiv2:alias "cevFanN2kC2248TBFan" {
    smiv2:oid "1.3.6.1.4.1.9.12.3.1.7.144";
  }

  smiv2:alias "cevFanN2kC2232TBFan" {
    smiv2:oid "1.3.6.1.4.1.9.12.3.1.7.145";
  }

  smiv2:alias "cevFanN3kC3064Fan" {
    smiv2:oid "1.3.6.1.4.1.9.12.3.1.7.148";
  }

  smiv2:alias "cevFanUCS6248UPFan" {
    smiv2:oid "1.3.6.1.4.1.9.12.3.1.7.149";
  }

  smiv2:alias "cevFanUCS6296UPFan" {
    smiv2:oid "1.3.6.1.4.1.9.12.3.1.7.150";
  }

  smiv2:alias "cevFanOe694" {
    smiv2:oid "1.3.6.1.4.1.9.12.3.1.7.151";
  }

  smiv2:alias "cevFanOe594" {
    smiv2:oid "1.3.6.1.4.1.9.12.3.1.7.152";
  }

  smiv2:alias "cevFanOe294" {
    smiv2:oid "1.3.6.1.4.1.9.12.3.1.7.153";
  }

  smiv2:alias "cevFanOe7571" {
    smiv2:oid "1.3.6.1.4.1.9.12.3.1.7.154";
  }

  smiv2:alias "cevFanOe7541" {
    smiv2:oid "1.3.6.1.4.1.9.12.3.1.7.155";
  }

  smiv2:alias "cevFanOe8541" {
    smiv2:oid "1.3.6.1.4.1.9.12.3.1.7.156";
  }

  smiv2:alias "cevFanCrs16SBFan" {
    smiv2:oid "1.3.6.1.4.1.9.12.3.1.7.157";
  }

  smiv2:alias "cevFanCrs16FabricFan" {
    smiv2:oid "1.3.6.1.4.1.9.12.3.1.7.158";
  }

  smiv2:alias "cevFanASA5555PSFan" {
    smiv2:oid "1.3.6.1.4.1.9.12.3.1.7.160";
  }

  smiv2:alias "cevFanASA5555ChassisFan" {
    smiv2:oid "1.3.6.1.4.1.9.12.3.1.7.167";
  }

  smiv2:alias "cevFanN3kC3064FanB" {
    smiv2:oid "1.3.6.1.4.1.9.12.3.1.7.173";
  }

  smiv2:alias "cevFanASR903FanTray" {
    smiv2:oid "1.3.6.1.4.1.9.12.3.1.7.174";
  }

  smiv2:alias "cevFanASR900Fan" {
    smiv2:oid "1.3.6.1.4.1.9.12.3.1.7.175";
  }

  smiv2:alias "cevFanASR5KFANTLW" {
    smiv2:oid "1.3.6.1.4.1.9.12.3.1.7.176";
  }

  smiv2:alias "cevFanASR5KFANTUP" {
    smiv2:oid "1.3.6.1.4.1.9.12.3.1.7.177";
  }

  smiv2:alias "cevFanASR55FANTF" {
    smiv2:oid "1.3.6.1.4.1.9.12.3.1.7.178";
  }

  smiv2:alias "cevFanASR55FANTR" {
    smiv2:oid "1.3.6.1.4.1.9.12.3.1.7.179";
  }

  smiv2:alias "cevFanN7Kc7004FanTray" {
    smiv2:oid "1.3.6.1.4.1.9.12.3.1.7.180";
  }

  smiv2:alias "cevFanN3kC3048Fan" {
    smiv2:oid "1.3.6.1.4.1.9.12.3.1.7.181";
  }

  smiv2:alias "cevFanN3kC3048FanB" {
    smiv2:oid "1.3.6.1.4.1.9.12.3.1.7.182";
  }

  smiv2:alias "cevFanASR9001" {
    smiv2:oid "1.3.6.1.4.1.9.12.3.1.7.183";
  }

  smiv2:alias "cevFanTrayISR4400" {
    smiv2:oid "1.3.6.1.4.1.9.12.3.1.7.185";
  }

  smiv2:alias "cevFanAsr9922Fan" {
    smiv2:oid "1.3.6.1.4.1.9.12.3.1.7.187";
  }

  smiv2:alias "cevFanAirstrikeCpuBlower" {
    smiv2:oid "1.3.6.1.4.1.9.12.3.1.7.188";
  }

  smiv2:alias "cevFanMod13SeFanTray" {
    smiv2:oid "1.3.6.1.4.1.9.12.3.1.7.189";
  }

  smiv2:alias "cevFanN6kC600496PQFanB" {
    smiv2:oid "1.3.6.1.4.1.9.12.3.1.7.190";
  }

  smiv2:alias "cevFanN6kC600496PQFanF" {
    smiv2:oid "1.3.6.1.4.1.9.12.3.1.7.191";
  }

  smiv2:alias "cevFanN3kC3548PFanB" {
    smiv2:oid "1.3.6.1.4.1.9.12.3.1.7.192";
  }

  smiv2:alias "cevFanN3kC3548PFan" {
    smiv2:oid "1.3.6.1.4.1.9.12.3.1.7.193";
  }

  smiv2:alias "cevFanA9K9912FAN" {
    smiv2:oid "1.3.6.1.4.1.9.12.3.1.7.194";
  }

  smiv2:alias "cevFanISR4400Fan" {
    smiv2:oid "1.3.6.1.4.1.9.12.3.1.7.195";
  }

  smiv2:alias "cevFanAsr9010FanV2" {
    smiv2:oid "1.3.6.1.4.1.9.12.3.1.7.196";
  }

  smiv2:alias "cevFanCat2960XCFM23" {
    smiv2:oid "1.3.6.1.4.1.9.12.3.1.7.197";
  }

  smiv2:alias "cevFanCat2960XCFM38" {
    smiv2:oid "1.3.6.1.4.1.9.12.3.1.7.198";
  }

  smiv2:alias "cevFanDSC9710" {
    smiv2:oid "1.3.6.1.4.1.9.12.3.1.7.200";
  }

  smiv2:alias "cevFanAsr9904Fan" {
    smiv2:oid "1.3.6.1.4.1.9.12.3.1.7.201";
  }

  smiv2:alias "cevFanNCSFANTRAY" {
    smiv2:oid "1.3.6.1.4.1.9.12.3.1.7.202";
  }

  smiv2:alias "cevFanDSC50I" {
    smiv2:oid "1.3.6.1.4.1.9.12.3.1.7.203";
  }

  smiv2:alias "cevFanC6880xFan" {
    smiv2:oid "1.3.6.1.4.1.9.12.3.1.7.204";
  }

  smiv2:alias "cevFanCrs18SBFan" {
    smiv2:oid "1.3.6.1.4.1.9.12.3.1.7.205";
  }

  smiv2:alias "cevFanCrs18FanTrayB" {
    smiv2:oid "1.3.6.1.4.1.9.12.3.1.7.206";
  }

  smiv2:alias "cevFanN77c7718Fan" {
    smiv2:oid "1.3.6.1.4.1.9.12.3.1.7.207";
  }

  smiv2:alias "cevFanN77c7710Fan" {
    smiv2:oid "1.3.6.1.4.1.9.12.3.1.7.208";
  }

  smiv2:alias "cevFanN77c7706Fan" {
    smiv2:oid "1.3.6.1.4.1.9.12.3.1.7.209";
  }

  smiv2:alias "cevFanC6807xlFan" {
    smiv2:oid "1.3.6.1.4.1.9.12.3.1.7.210";
  }

  smiv2:alias "cevFanNCSFan" {
    smiv2:oid "1.3.6.1.4.1.9.12.3.1.7.211";
  }

  smiv2:alias "cevFanN3KC3172TQFAN" {
    smiv2:oid "1.3.6.1.4.1.9.12.3.1.7.213";
  }

  smiv2:alias "cevFanN3KC3172TQFANB" {
    smiv2:oid "1.3.6.1.4.1.9.12.3.1.7.214";
  }

  smiv2:alias "cevFanN3KC3172PQFANB" {
    smiv2:oid "1.3.6.1.4.1.9.12.3.1.7.215";
  }

  smiv2:alias "cevFanN3KC3172PQFAN" {
    smiv2:oid "1.3.6.1.4.1.9.12.3.1.7.216";
  }

  smiv2:alias "cevFanN3KC3132FAN" {
    smiv2:oid "1.3.6.1.4.1.9.12.3.1.7.217";
  }

  smiv2:alias "cevFanN3KC3132FANB" {
    smiv2:oid "1.3.6.1.4.1.9.12.3.1.7.218";
  }

  smiv2:alias "cevFanDSC9706FAN" {
    smiv2:oid "1.3.6.1.4.1.9.12.3.1.7.219";
  }

  smiv2:alias "cevFanN9Kc9508FanTray" {
    smiv2:oid "1.3.6.1.4.1.9.12.3.1.7.222";
  }

  smiv2:alias "cevFanASR902FanTray" {
    smiv2:oid "1.3.6.1.4.1.9.12.3.1.7.226";
  }

  smiv2:alias "cevFanN56128FanB" {
    smiv2:oid "1.3.6.1.4.1.9.12.3.1.7.227";
  }

  smiv2:alias "cevFanN56128FanF" {
    smiv2:oid "1.3.6.1.4.1.9.12.3.1.7.228";
  }

  smiv2:alias "cevFanDSC48SFAN" {
    smiv2:oid "1.3.6.1.4.1.9.12.3.1.7.229";
  }

  smiv2:alias "cevFanN9Kc9516FanTray" {
    smiv2:oid "1.3.6.1.4.1.9.12.3.1.7.230";
  }

  smiv2:alias "cevFanN9Kc9504FanTray" {
    smiv2:oid "1.3.6.1.4.1.9.12.3.1.7.231";
  }

  smiv2:alias "cevFanN9Kc9300FanTray2B" {
    smiv2:oid "1.3.6.1.4.1.9.12.3.1.7.232";
  }

  smiv2:alias "cevFanN9Kc9300FanTray2" {
    smiv2:oid "1.3.6.1.4.1.9.12.3.1.7.233";
  }

  smiv2:alias "cevFanN9Kc9300FanTray1B" {
    smiv2:oid "1.3.6.1.4.1.9.12.3.1.7.234";
  }

  smiv2:alias "cevFanN9Kc9300FanTray1" {
    smiv2:oid "1.3.6.1.4.1.9.12.3.1.7.235";
  }

  smiv2:alias "cevFanNXAFAN30CFMB" {
    smiv2:oid "1.3.6.1.4.1.9.12.3.1.7.237";
  }

  smiv2:alias "cevFanNXAFAN30CFMF" {
    smiv2:oid "1.3.6.1.4.1.9.12.3.1.7.238";
  }

  smiv2:alias "cevFanASR9001V2" {
    smiv2:oid "1.3.6.1.4.1.9.12.3.1.7.239";
  }

  smiv2:alias "cevFanN6kC6001FanF" {
    smiv2:oid "1.3.6.1.4.1.9.12.3.1.7.240";
  }

  smiv2:alias "cevFanN6kC6001FanB" {
    smiv2:oid "1.3.6.1.4.1.9.12.3.1.7.241";
  }

  smiv2:alias "cevFanAsr9KvV2Fan" {
    smiv2:oid "1.3.6.1.4.1.9.12.3.1.7.250";
  }

  smiv2:alias "cevFanASR920FanTray15ru" {
    smiv2:oid "1.3.6.1.4.1.9.12.3.1.7.251";
  }

  smiv2:alias "cevFanASR920FanTray1ru" {
    smiv2:oid "1.3.6.1.4.1.9.12.3.1.7.252";
  }

  smiv2:alias "cevFanN5K5696FanB" {
    smiv2:oid "1.3.6.1.4.1.9.12.3.1.7.253";
  }

  smiv2:alias "cevFanN5K5696FanF" {
    smiv2:oid "1.3.6.1.4.1.9.12.3.1.7.254";
  }

  smiv2:alias "cevFanSce10000Fan" {
    smiv2:oid "1.3.6.1.4.1.9.12.3.1.7.261";
  }

  smiv2:alias "cevFanDSC96SFANE" {
    smiv2:oid "1.3.6.1.4.1.9.12.3.1.7.262";
  }

  smiv2:alias "cevFanDSC96SFANI" {
    smiv2:oid "1.3.6.1.4.1.9.12.3.1.7.263";
  }

  smiv2:alias "cevSensor" {
    smiv2:oid "1.3.6.1.4.1.9.12.3.1.8";
  }

  smiv2:alias "cevSensorMGX8800Temp" {
    smiv2:oid "1.3.6.1.4.1.9.12.3.1.8.11";
  }

  smiv2:alias "cevSensorMGX8800PSVoltage" {
    smiv2:oid "1.3.6.1.4.1.9.12.3.1.8.12";
  }

  smiv2:alias "cevSensorMGX8800FanSpeed" {
    smiv2:oid "1.3.6.1.4.1.9.12.3.1.8.13";
  }

  smiv2:alias "cevSensorONS15540Temp" {
    smiv2:oid "1.3.6.1.4.1.9.12.3.1.8.14";
  }

  smiv2:alias "cevSensorONS15540Power" {
    smiv2:oid "1.3.6.1.4.1.9.12.3.1.8.15";
  }

  smiv2:alias "cevSensor7500ChassisInterface" {
    smiv2:oid "1.3.6.1.4.1.9.12.3.1.8.16";
  }

  smiv2:alias "cevSensorC7300InletTempVoltage" {
    smiv2:oid "1.3.6.1.4.1.9.12.3.1.8.17";
  }

  smiv2:alias "cevSensorC7300OutletTempVoltage" {
    smiv2:oid "1.3.6.1.4.1.9.12.3.1.8.18";
  }

  smiv2:alias "cevSensorC7300HotspotTempVoltage" {
    smiv2:oid "1.3.6.1.4.1.9.12.3.1.8.19";
  }

  smiv2:alias "cevSensorC7300NseDbTempVoltage" {
    smiv2:oid "1.3.6.1.4.1.9.12.3.1.8.20";
  }

  smiv2:alias "cevSensorC7300PSFanState" {
    smiv2:oid "1.3.6.1.4.1.9.12.3.1.8.21";
  }

  smiv2:alias "cevSensorC10KInletTemp" {
    smiv2:oid "1.3.6.1.4.1.9.12.3.1.8.22";
  }

  smiv2:alias "cevSensorC10000CoreTemp" {
    smiv2:oid "1.3.6.1.4.1.9.12.3.1.8.23";
  }

  smiv2:alias "cevSensorCat4kTemp" {
    smiv2:oid "1.3.6.1.4.1.9.12.3.1.8.24";
  }

  smiv2:alias "cevSensorONS15530Temp" {
    smiv2:oid "1.3.6.1.4.1.9.12.3.1.8.25";
  }

  smiv2:alias "cevSensorONS15530Power" {
    smiv2:oid "1.3.6.1.4.1.9.12.3.1.8.26";
  }

  smiv2:alias "cevSensorVxsmVoltage" {
    smiv2:oid "1.3.6.1.4.1.9.12.3.1.8.27";
  }

  smiv2:alias "cevSensorVxsmTemp" {
    smiv2:oid "1.3.6.1.4.1.9.12.3.1.8.28";
  }

  smiv2:alias "cevSensor15302701Temp" {
    smiv2:oid "1.3.6.1.4.1.9.12.3.1.8.29";
  }

  smiv2:alias "cevSensorUnknown" {
    smiv2:oid "1.3.6.1.4.1.9.12.3.1.8.30";
  }

  smiv2:alias "cevSensorModuleDeviceTemp" {
    smiv2:oid "1.3.6.1.4.1.9.12.3.1.8.31";
  }

  smiv2:alias "cevSensorClock" {
    smiv2:oid "1.3.6.1.4.1.9.12.3.1.8.32";
  }

  smiv2:alias "cevSensorVtt" {
    smiv2:oid "1.3.6.1.4.1.9.12.3.1.8.33";
  }

  smiv2:alias "cevSensorModulePowerOutputFail" {
    smiv2:oid "1.3.6.1.4.1.9.12.3.1.8.34";
  }

  smiv2:alias "cevSensorModuleOutletTemp" {
    smiv2:oid "1.3.6.1.4.1.9.12.3.1.8.35";
  }

  smiv2:alias "cevSensorModuleInletTemp" {
    smiv2:oid "1.3.6.1.4.1.9.12.3.1.8.36";
  }

  smiv2:alias "cevSensorFanTrayStatus" {
    smiv2:oid "1.3.6.1.4.1.9.12.3.1.8.37";
  }

  smiv2:alias "cevSensorPSFan" {
    smiv2:oid "1.3.6.1.4.1.9.12.3.1.8.38";
  }

  smiv2:alias "cevSensorPSOutput" {
    smiv2:oid "1.3.6.1.4.1.9.12.3.1.8.39";
  }

  smiv2:alias "cevSensorPSInput" {
    smiv2:oid "1.3.6.1.4.1.9.12.3.1.8.40";
  }

  smiv2:alias "cevSensorCrs1Voltage" {
    smiv2:oid "1.3.6.1.4.1.9.12.3.1.8.41";
  }

  smiv2:alias "cevSensorCrs1Temp" {
    smiv2:oid "1.3.6.1.4.1.9.12.3.1.8.42";
  }

  smiv2:alias "cevSensorCrs1Current" {
    smiv2:oid "1.3.6.1.4.1.9.12.3.1.8.43";
  }

  smiv2:alias "cevSensorCrs1FanSpeed" {
    smiv2:oid "1.3.6.1.4.1.9.12.3.1.8.44";
  }

  smiv2:alias "cevSensorModuleDeviceVoltage" {
    smiv2:oid "1.3.6.1.4.1.9.12.3.1.8.45";
  }

  smiv2:alias "cevSensorTransceiverRxPwr" {
    smiv2:oid "1.3.6.1.4.1.9.12.3.1.8.46";
  }

  smiv2:alias "cevSensorTransceiverTxPwr" {
    smiv2:oid "1.3.6.1.4.1.9.12.3.1.8.47";
  }

  smiv2:alias "cevSensorTransceiverCurrent" {
    smiv2:oid "1.3.6.1.4.1.9.12.3.1.8.48";
  }

  smiv2:alias "cevSensorTransceiverVoltage" {
    smiv2:oid "1.3.6.1.4.1.9.12.3.1.8.49";
  }

  smiv2:alias "cevSensorTransceiverTemp" {
    smiv2:oid "1.3.6.1.4.1.9.12.3.1.8.50";
  }

  smiv2:alias "cevSensorModuleFanUpgradeRequired" {
    smiv2:oid "1.3.6.1.4.1.9.12.3.1.8.51";
  }

  smiv2:alias "cevSensorModuleInsufficientCooling" {
    smiv2:oid "1.3.6.1.4.1.9.12.3.1.8.52";
  }

  smiv2:alias "cevSensorPSFanIncompatible" {
    smiv2:oid "1.3.6.1.4.1.9.12.3.1.8.55";
  }

  smiv2:alias "cevSensorACE4710K9CPUTemp" {
    smiv2:oid "1.3.6.1.4.1.9.12.3.1.8.56";
  }

  smiv2:alias "cevSensorACE4710K9AmbientTemp" {
    smiv2:oid "1.3.6.1.4.1.9.12.3.1.8.57";
  }

  smiv2:alias "cevSensorCpuFanSpeed" {
    smiv2:oid "1.3.6.1.4.1.9.12.3.1.8.58";
  }

  smiv2:alias "cevSensorACE4710K9DimmFanSpeed" {
    smiv2:oid "1.3.6.1.4.1.9.12.3.1.8.59";
  }

  smiv2:alias "cevSensorACE4710K9PciFanSpeed" {
    smiv2:oid "1.3.6.1.4.1.9.12.3.1.8.60";
  }

  smiv2:alias "cevSensorModuleDeviceCurrent" {
    smiv2:oid "1.3.6.1.4.1.9.12.3.1.8.61";
  }

  smiv2:alias "cevSensorCrs16dcPemB" {
    smiv2:oid "1.3.6.1.4.1.9.12.3.1.8.62";
  }

  smiv2:alias "cevSensorExternalContact" {
    smiv2:oid "1.3.6.1.4.1.9.12.3.1.8.63";
  }

  smiv2:alias "cevSensorFanSpeed" {
    smiv2:oid "1.3.6.1.4.1.9.12.3.1.8.64";
  }

  smiv2:alias "cevSensorCrs1PwrVoltage" {
    smiv2:oid "1.3.6.1.4.1.9.12.3.1.8.65";
  }

  smiv2:alias "cevSensorCrs1Led" {
    smiv2:oid "1.3.6.1.4.1.9.12.3.1.8.66";
  }

  smiv2:alias "cevSensorMXE5600Temp" {
    smiv2:oid "1.3.6.1.4.1.9.12.3.1.8.67";
  }

  smiv2:alias "cevSensorMXE5600FanSpeed" {
    smiv2:oid "1.3.6.1.4.1.9.12.3.1.8.68";
  }

  smiv2:alias "cevSensorMXE5600Voltage" {
    smiv2:oid "1.3.6.1.4.1.9.12.3.1.8.69";
  }

  smiv2:alias "cevSensorMXE5600Current" {
    smiv2:oid "1.3.6.1.4.1.9.12.3.1.8.70";
  }

  smiv2:alias "cevSensorModuleDevicePower" {
    smiv2:oid "1.3.6.1.4.1.9.12.3.1.8.132";
  }

  smiv2:alias "cevSensorModuleDeviceFanRotation" {
    smiv2:oid "1.3.6.1.4.1.9.12.3.1.8.133";
  }

  smiv2:alias "cevSensorModuleDevicePressure" {
    smiv2:oid "1.3.6.1.4.1.9.12.3.1.8.134";
  }

  smiv2:alias "cevSensorVoltagesensor" {
    smiv2:oid "1.3.6.1.4.1.9.12.3.1.8.135";
  }

  smiv2:alias "cevSensorCursensor" {
    smiv2:oid "1.3.6.1.4.1.9.12.3.1.8.136";
  }

  smiv2:alias "cevSensorTempsensor" {
    smiv2:oid "1.3.6.1.4.1.9.12.3.1.8.137";
  }

  smiv2:alias "cevSensorLEDsensor" {
    smiv2:oid "1.3.6.1.4.1.9.12.3.1.8.138";
  }

  smiv2:alias "cevSensorFanSpeedsensor" {
    smiv2:oid "1.3.6.1.4.1.9.12.3.1.8.139";
  }

  smiv2:alias "cevSensorMultiSensorModule" {
    smiv2:oid "1.3.6.1.4.1.9.12.3.1.8.140";
  }

  smiv2:alias "cevSensorPowersensor" {
    smiv2:oid "1.3.6.1.4.1.9.12.3.1.8.141";
  }

  smiv2:alias "cevSensorDiagStatus" {
    smiv2:oid "1.3.6.1.4.1.9.12.3.1.8.143";
  }

  smiv2:alias "cevSensorASR5000CardTemp" {
    smiv2:oid "1.3.6.1.4.1.9.12.3.1.8.151";
  }

  smiv2:alias "cevSensorASR5000CardVoltage" {
    smiv2:oid "1.3.6.1.4.1.9.12.3.1.8.152";
  }

  smiv2:alias "cevSensorASR5000FanTemp" {
    smiv2:oid "1.3.6.1.4.1.9.12.3.1.8.153";
  }

  smiv2:alias "cevSensorASR5500CardTemp" {
    smiv2:oid "1.3.6.1.4.1.9.12.3.1.8.154";
  }

  smiv2:alias "cevSensorASR5500CardVoltage" {
    smiv2:oid "1.3.6.1.4.1.9.12.3.1.8.155";
  }

  smiv2:alias "cevSensorASR5500CardPower" {
    smiv2:oid "1.3.6.1.4.1.9.12.3.1.8.156";
  }

  smiv2:alias "cevSensorASR5500CardAirFlow" {
    smiv2:oid "1.3.6.1.4.1.9.12.3.1.8.157";
  }

  smiv2:alias "cevSensorASR5500CardBinary" {
    smiv2:oid "1.3.6.1.4.1.9.12.3.1.8.158";
  }

  smiv2:alias "cevSensorASR5500CardPercentage" {
    smiv2:oid "1.3.6.1.4.1.9.12.3.1.8.159";
  }

  smiv2:alias "cevSensorASR5500CardCurrent" {
    smiv2:oid "1.3.6.1.4.1.9.12.3.1.8.160";
  }

  smiv2:alias "cevSensorASR5500FanTemp" {
    smiv2:oid "1.3.6.1.4.1.9.12.3.1.8.161";
  }

  smiv2:alias "cevModule" {
    smiv2:oid "1.3.6.1.4.1.9.12.3.1.9";
  }

  smiv2:alias "cevModuleUnknownCard" {
    smiv2:oid "1.3.6.1.4.1.9.12.3.1.9.1";
  }

  smiv2:alias "cevModuleCommonCards" {
    smiv2:oid "1.3.6.1.4.1.9.12.3.1.9.2";
  }

  smiv2:alias "cevWicSerial1t" {
    smiv2:oid "1.3.6.1.4.1.9.12.3.1.9.2.1";
  }

  smiv2:alias "cevWicST3420" {
    smiv2:oid "1.3.6.1.4.1.9.12.3.1.9.2.5";
  }

  smiv2:alias "cevWicST2186" {
    smiv2:oid "1.3.6.1.4.1.9.12.3.1.9.2.6";
  }

  smiv2:alias "cevWicU3420" {
    smiv2:oid "1.3.6.1.4.1.9.12.3.1.9.2.7";
  }

  smiv2:alias "cevWicU2091" {
    smiv2:oid "1.3.6.1.4.1.9.12.3.1.9.2.8";
  }

  smiv2:alias "cevWicU20912081" {
    smiv2:oid "1.3.6.1.4.1.9.12.3.1.9.2.9";
  }

  smiv2:alias "cevWicST2186Leased" {
    smiv2:oid "1.3.6.1.4.1.9.12.3.1.9.2.10";
  }

  smiv2:alias "cevVicFxs" {
    smiv2:oid "1.3.6.1.4.1.9.12.3.1.9.2.11";
  }

  smiv2:alias "cevVicFxo" {
    smiv2:oid "1.3.6.1.4.1.9.12.3.1.9.2.12";
  }

  smiv2:alias "cevVicEm" {
    smiv2:oid "1.3.6.1.4.1.9.12.3.1.9.2.13";
  }

  smiv2:alias "cevAimCompression" {
    smiv2:oid "1.3.6.1.4.1.9.12.3.1.9.2.14";
  }

  smiv2:alias "cevWvic1dsuT1" {
    smiv2:oid "1.3.6.1.4.1.9.12.3.1.9.2.16";
  }

  smiv2:alias "cevWvic1dsuE1" {
    smiv2:oid "1.3.6.1.4.1.9.12.3.1.9.2.17";
  }

  smiv2:alias "cevWvic2dsuT1" {
    smiv2:oid "1.3.6.1.4.1.9.12.3.1.9.2.18";
  }

  smiv2:alias "cevWvic2dsuE1" {
    smiv2:oid "1.3.6.1.4.1.9.12.3.1.9.2.19";
  }

  smiv2:alias "cevWvic2dsuT1Di" {
    smiv2:oid "1.3.6.1.4.1.9.12.3.1.9.2.20";
  }

  smiv2:alias "cevWvic2dsuE1Di" {
    smiv2:oid "1.3.6.1.4.1.9.12.3.1.9.2.21";
  }

  smiv2:alias "cevAimEncryption" {
    smiv2:oid "1.3.6.1.4.1.9.12.3.1.9.2.22";
  }

  smiv2:alias "cevPmNmToAim" {
    smiv2:oid "1.3.6.1.4.1.9.12.3.1.9.2.23";
  }

  smiv2:alias "cevDfc8ce1" {
    smiv2:oid "1.3.6.1.4.1.9.12.3.1.9.2.24";
  }

  smiv2:alias "cevDfc8ct1" {
    smiv2:oid "1.3.6.1.4.1.9.12.3.1.9.2.25";
  }

  smiv2:alias "cevDfcCt3" {
    smiv2:oid "1.3.6.1.4.1.9.12.3.1.9.2.26";
  }

  smiv2:alias "cevDfcNp108" {
    smiv2:oid "1.3.6.1.4.1.9.12.3.1.9.2.27";
  }

  smiv2:alias "cevWicSerial2as" {
    smiv2:oid "1.3.6.1.4.1.9.12.3.1.9.2.29";
  }

  smiv2:alias "cevWicCsuDsuFT1" {
    smiv2:oid "1.3.6.1.4.1.9.12.3.1.9.2.30";
  }

  smiv2:alias "cevIsaIpsecMppe" {
    smiv2:oid "1.3.6.1.4.1.9.12.3.1.9.2.31";
  }

  smiv2:alias "cevWicDslsar20150" {
    smiv2:oid "1.3.6.1.4.1.9.12.3.1.9.2.32";
  }

  smiv2:alias "cevDfc2ce1" {
    smiv2:oid "1.3.6.1.4.1.9.12.3.1.9.2.35";
  }

  smiv2:alias "cevDfcNp60" {
    smiv2:oid "1.3.6.1.4.1.9.12.3.1.9.2.37";
  }

  smiv2:alias "cevSpeNp6" {
    smiv2:oid "1.3.6.1.4.1.9.12.3.1.9.2.43";
  }

  smiv2:alias "cevWvic2dsuT1DIR" {
    smiv2:oid "1.3.6.1.4.1.9.12.3.1.9.2.47";
  }

  smiv2:alias "cevWvic2dsuE1DIR" {
    smiv2:oid "1.3.6.1.4.1.9.12.3.1.9.2.48";
  }

  smiv2:alias "cevVic4vpFxsDid" {
    smiv2:oid "1.3.6.1.4.1.9.12.3.1.9.2.49";
  }

  smiv2:alias "cevVic4fxoUsM1" {
    smiv2:oid "1.3.6.1.4.1.9.12.3.1.9.2.50";
  }

  smiv2:alias "cevVic4fxoM2M3" {
    smiv2:oid "1.3.6.1.4.1.9.12.3.1.9.2.51";
  }

  smiv2:alias "cevVic4fxoCAMA" {
    smiv2:oid "1.3.6.1.4.1.9.12.3.1.9.2.52";
  }

  smiv2:alias "cevWicEthernet" {
    smiv2:oid "1.3.6.1.4.1.9.12.3.1.9.2.55";
  }

  smiv2:alias "cevCeSA6DC" {
    smiv2:oid "1.3.6.1.4.1.9.12.3.1.9.2.56";
  }

  smiv2:alias "cevCeSA6AC" {
    smiv2:oid "1.3.6.1.4.1.9.12.3.1.9.2.57";
  }

  smiv2:alias "cevCeSA12AC" {
    smiv2:oid "1.3.6.1.4.1.9.12.3.1.9.2.58";
  }

  smiv2:alias "cevC2610XM1Fe" {
    smiv2:oid "1.3.6.1.4.1.9.12.3.1.9.2.59";
  }

  smiv2:alias "cevC2611XM2Fe" {
    smiv2:oid "1.3.6.1.4.1.9.12.3.1.9.2.60";
  }

  smiv2:alias "cevC2620XM1Fe" {
    smiv2:oid "1.3.6.1.4.1.9.12.3.1.9.2.61";
  }

  smiv2:alias "cevC2621XM2Fe" {
    smiv2:oid "1.3.6.1.4.1.9.12.3.1.9.2.62";
  }

  smiv2:alias "cevC2650XM1Fe" {
    smiv2:oid "1.3.6.1.4.1.9.12.3.1.9.2.63";
  }

  smiv2:alias "cevC2651XM2Fe" {
    smiv2:oid "1.3.6.1.4.1.9.12.3.1.9.2.64";
  }

  smiv2:alias "cevVic8fxoUsM1" {
    smiv2:oid "1.3.6.1.4.1.9.12.3.1.9.2.65";
  }

  smiv2:alias "cevCeSA14" {
    smiv2:oid "1.3.6.1.4.1.9.12.3.1.9.2.66";
  }

  smiv2:alias "cevWicDslsar20174Isdn" {
    smiv2:oid "1.3.6.1.4.1.9.12.3.1.9.2.67";
  }

  smiv2:alias "cevWicDslsar20174Pots" {
    smiv2:oid "1.3.6.1.4.1.9.12.3.1.9.2.68";
  }

  smiv2:alias "cevSpaIpSec2G" {
    smiv2:oid "1.3.6.1.4.1.9.12.3.1.9.2.69";
  }

  smiv2:alias "cevNmSe" {
    smiv2:oid "1.3.6.1.4.1.9.12.3.1.9.2.70";
  }

  smiv2:alias "cevAimSe" {
    smiv2:oid "1.3.6.1.4.1.9.12.3.1.9.2.71";
  }

  smiv2:alias "cevWicSe" {
    smiv2:oid "1.3.6.1.4.1.9.12.3.1.9.2.72";
  }

  smiv2:alias "cevCeDs2100" {
    smiv2:oid "1.3.6.1.4.1.9.12.3.1.9.2.73";
  }

  smiv2:alias "cevDfc16ce1" {
    smiv2:oid "1.3.6.1.4.1.9.12.3.1.9.2.74";
  }

  smiv2:alias "cevDfc16ct1" {
    smiv2:oid "1.3.6.1.4.1.9.12.3.1.9.2.75";
  }

  smiv2:alias "cevSpa2pOc3Atm" {
    smiv2:oid "1.3.6.1.4.1.9.12.3.1.9.2.76";
  }

  smiv2:alias "cevSpa4pOc3Atm" {
    smiv2:oid "1.3.6.1.4.1.9.12.3.1.9.2.77";
  }

  smiv2:alias "cevSpa1pOc12Atm" {
    smiv2:oid "1.3.6.1.4.1.9.12.3.1.9.2.78";
  }

  smiv2:alias "cevSpa1pOc48Atm" {
    smiv2:oid "1.3.6.1.4.1.9.12.3.1.9.2.80";
  }

  smiv2:alias "cevSpa2pOc3Pos" {
    smiv2:oid "1.3.6.1.4.1.9.12.3.1.9.2.83";
  }

  smiv2:alias "cevSpa4pOc3Pos" {
    smiv2:oid "1.3.6.1.4.1.9.12.3.1.9.2.84";
  }

  smiv2:alias "cevSpa1pOc12Pos" {
    smiv2:oid "1.3.6.1.4.1.9.12.3.1.9.2.85";
  }

  smiv2:alias "cevSpa2pOc12Pos" {
    smiv2:oid "1.3.6.1.4.1.9.12.3.1.9.2.86";
  }

  smiv2:alias "cevSpa8pOc12Pos" {
    smiv2:oid "1.3.6.1.4.1.9.12.3.1.9.2.87";
  }

  smiv2:alias "cevSpa4pFe7304" {
    smiv2:oid "1.3.6.1.4.1.9.12.3.1.9.2.88";
  }

  smiv2:alias "cevSpa2pGe7304" {
    smiv2:oid "1.3.6.1.4.1.9.12.3.1.9.2.89";
  }

  smiv2:alias "cevWicEswitch4" {
    smiv2:oid "1.3.6.1.4.1.9.12.3.1.9.2.90";
  }

  smiv2:alias "cevWicBri3086u" {
    smiv2:oid "1.3.6.1.4.1.9.12.3.1.9.2.91";
  }

  smiv2:alias "cevSpa1pOc192PosRprXfp" {
    smiv2:oid "1.3.6.1.4.1.9.12.3.1.9.2.92";
  }

  smiv2:alias "cevSpa1pOc192PosRprSmLr" {
    smiv2:oid "1.3.6.1.4.1.9.12.3.1.9.2.94";
  }

  smiv2:alias "cevSpa1pOc192PosRprVsr" {
    smiv2:oid "1.3.6.1.4.1.9.12.3.1.9.2.95";
  }

  smiv2:alias "cevSpa2pT3E3Serial" {
    smiv2:oid "1.3.6.1.4.1.9.12.3.1.9.2.96";
  }

  smiv2:alias "cevSpa4pT3E3Serial" {
    smiv2:oid "1.3.6.1.4.1.9.12.3.1.9.2.97";
  }

  smiv2:alias "cevSpa8pCT1E1" {
    smiv2:oid "1.3.6.1.4.1.9.12.3.1.9.2.98";
  }

  smiv2:alias "cevSpa2pCT3" {
    smiv2:oid "1.3.6.1.4.1.9.12.3.1.9.2.99";
  }

  smiv2:alias "cevSpa4pCT3" {
    smiv2:oid "1.3.6.1.4.1.9.12.3.1.9.2.100";
  }

  smiv2:alias "cevNmAONS" {
    smiv2:oid "1.3.6.1.4.1.9.12.3.1.9.2.101";
  }

  smiv2:alias "cevHwic4fe" {
    smiv2:oid "1.3.6.1.4.1.9.12.3.1.9.2.102";
  }

  smiv2:alias "cevHwic9fes" {
    smiv2:oid "1.3.6.1.4.1.9.12.3.1.9.2.103";
  }

  smiv2:alias "cevHwic4fes" {
    smiv2:oid "1.3.6.1.4.1.9.12.3.1.9.2.104";
  }

  smiv2:alias "cevHwic4ilp" {
    smiv2:oid "1.3.6.1.4.1.9.12.3.1.9.2.105";
  }

  smiv2:alias "cevHwic9ilp" {
    smiv2:oid "1.3.6.1.4.1.9.12.3.1.9.2.106";
  }

  smiv2:alias "cevSpa10pGe" {
    smiv2:oid "1.3.6.1.4.1.9.12.3.1.9.2.107";
  }

  smiv2:alias "cevSpa1p10GeXfp" {
    smiv2:oid "1.3.6.1.4.1.9.12.3.1.9.2.108";
  }

  smiv2:alias "cevSpa5pGe" {
    smiv2:oid "1.3.6.1.4.1.9.12.3.1.9.2.109";
  }

  smiv2:alias "cevSpa2pGe" {
    smiv2:oid "1.3.6.1.4.1.9.12.3.1.9.2.115";
  }

  smiv2:alias "cevCompactFlash64MB" {
    smiv2:oid "1.3.6.1.4.1.9.12.3.1.9.2.116";
  }

  smiv2:alias "cevCompactFlash128MB" {
    smiv2:oid "1.3.6.1.4.1.9.12.3.1.9.2.117";
  }

  smiv2:alias "cevCompactFlash256MB" {
    smiv2:oid "1.3.6.1.4.1.9.12.3.1.9.2.118";
  }

  smiv2:alias "cevCompactFlash512MB" {
    smiv2:oid "1.3.6.1.4.1.9.12.3.1.9.2.119";
  }

  smiv2:alias "cevCompactFlash" {
    smiv2:oid "1.3.6.1.4.1.9.12.3.1.9.2.120";
  }

  smiv2:alias "cevSpa1pChOc3Stm1" {
    smiv2:oid "1.3.6.1.4.1.9.12.3.1.9.2.121";
  }

  smiv2:alias "cevFlashCard48MB" {
    smiv2:oid "1.3.6.1.4.1.9.12.3.1.9.2.122";
  }

  smiv2:alias "cevFlashCard64MB" {
    smiv2:oid "1.3.6.1.4.1.9.12.3.1.9.2.123";
  }

  smiv2:alias "cevFlashCard128MB" {
    smiv2:oid "1.3.6.1.4.1.9.12.3.1.9.2.124";
  }

  smiv2:alias "cevFlashCard256MB" {
    smiv2:oid "1.3.6.1.4.1.9.12.3.1.9.2.125";
  }

  smiv2:alias "cevFlashCard512MB" {
    smiv2:oid "1.3.6.1.4.1.9.12.3.1.9.2.126";
  }

  smiv2:alias "cevFlashCard" {
    smiv2:oid "1.3.6.1.4.1.9.12.3.1.9.2.127";
  }

  smiv2:alias "cevHwicdot11abg" {
    smiv2:oid "1.3.6.1.4.1.9.12.3.1.9.2.128";
  }

  smiv2:alias "cevHwicdot11bg" {
    smiv2:oid "1.3.6.1.4.1.9.12.3.1.9.2.129";
  }

  smiv2:alias "cevAimVpnBp" {
    smiv2:oid "1.3.6.1.4.1.9.12.3.1.9.2.130";
  }

  smiv2:alias "cevAimVpnEp" {
    smiv2:oid "1.3.6.1.4.1.9.12.3.1.9.2.131";
  }

  smiv2:alias "cevNmVpnMp" {
    smiv2:oid "1.3.6.1.4.1.9.12.3.1.9.2.132";
  }

  smiv2:alias "cevAimVpnHp" {
    smiv2:oid "1.3.6.1.4.1.9.12.3.1.9.2.133";
  }

  smiv2:alias "cevAimVpnBp2" {
    smiv2:oid "1.3.6.1.4.1.9.12.3.1.9.2.134";
  }

  smiv2:alias "cevAimVpnEp2" {
    smiv2:oid "1.3.6.1.4.1.9.12.3.1.9.2.135";
  }

  smiv2:alias "cevAimVpnHp2" {
    smiv2:oid "1.3.6.1.4.1.9.12.3.1.9.2.136";
  }

  smiv2:alias "cevAimVpnBp2Plus" {
    smiv2:oid "1.3.6.1.4.1.9.12.3.1.9.2.137";
  }

  smiv2:alias "cevAimVpnEp2Plus" {
    smiv2:oid "1.3.6.1.4.1.9.12.3.1.9.2.138";
  }

  smiv2:alias "cevAimVpnHp2Plus" {
    smiv2:oid "1.3.6.1.4.1.9.12.3.1.9.2.139";
  }

  smiv2:alias "cevHwicAdslBriPots" {
    smiv2:oid "1.3.6.1.4.1.9.12.3.1.9.2.140";
  }

  smiv2:alias "cevHwicAdslBriIsdn" {
    smiv2:oid "1.3.6.1.4.1.9.12.3.1.9.2.141";
  }

  smiv2:alias "cevHwicAdslIsdn" {
    smiv2:oid "1.3.6.1.4.1.9.12.3.1.9.2.142";
  }

  smiv2:alias "cevHwicAdslPots" {
    smiv2:oid "1.3.6.1.4.1.9.12.3.1.9.2.143";
  }

  smiv2:alias "cevSpa2pOc48PosRprHH" {
    smiv2:oid "1.3.6.1.4.1.9.12.3.1.9.2.144";
  }

  smiv2:alias "cevNMCueEc" {
    smiv2:oid "1.3.6.1.4.1.9.12.3.1.9.2.146";
  }

  smiv2:alias "cevC180xdot11abg" {
    smiv2:oid "1.3.6.1.4.1.9.12.3.1.9.2.147";
  }

  smiv2:alias "cevC180xdot11bg" {
    smiv2:oid "1.3.6.1.4.1.9.12.3.1.9.2.148";
  }

  smiv2:alias "cevC180x8ilp" {
    smiv2:oid "1.3.6.1.4.1.9.12.3.1.9.2.149";
  }

  smiv2:alias "cevDfcDl108" {
    smiv2:oid "1.3.6.1.4.1.9.12.3.1.9.2.150";
  }

  smiv2:alias "cevDfcDl60" {
    smiv2:oid "1.3.6.1.4.1.9.12.3.1.9.2.151";
  }

  smiv2:alias "cevNmWlanController" {
    smiv2:oid "1.3.6.1.4.1.9.12.3.1.9.2.152";
  }

  smiv2:alias "cevWicCsuDsuFT1v2" {
    smiv2:oid "1.3.6.1.4.1.9.12.3.1.9.2.153";
  }

  smiv2:alias "cevSpa8xfeTx" {
    smiv2:oid "1.3.6.1.4.1.9.12.3.1.9.2.154";
  }

  smiv2:alias "cevNMIntegratedServiceEngine" {
    smiv2:oid "1.3.6.1.4.1.9.12.3.1.9.2.155";
  }

  smiv2:alias "cevNmWaEngine" {
    smiv2:oid "1.3.6.1.4.1.9.12.3.1.9.2.156";
  }

  smiv2:alias "cevSpa2pGeV2" {
    smiv2:oid "1.3.6.1.4.1.9.12.3.1.9.2.157";
  }

  smiv2:alias "cevSpa5pGeV2" {
    smiv2:oid "1.3.6.1.4.1.9.12.3.1.9.2.158";
  }

  smiv2:alias "cevSpa8pGeV2" {
    smiv2:oid "1.3.6.1.4.1.9.12.3.1.9.2.159";
  }

  smiv2:alias "cevSpa10pGeV2" {
    smiv2:oid "1.3.6.1.4.1.9.12.3.1.9.2.160";
  }

  smiv2:alias "cevSpa1p10GeXfpV2" {
    smiv2:oid "1.3.6.1.4.1.9.12.3.1.9.2.161";
  }

  smiv2:alias "cevSpa8xfeTxV2" {
    smiv2:oid "1.3.6.1.4.1.9.12.3.1.9.2.162";
  }

  smiv2:alias "cevModuleCrs14OC192IRPlim" {
    smiv2:oid "1.3.6.1.4.1.9.12.3.1.9.2.163";
  }

  smiv2:alias "cevSpa8xGe" {
    smiv2:oid "1.3.6.1.4.1.9.12.3.1.9.2.164";
  }

  smiv2:alias "cevSpa8xoc3Pos" {
    smiv2:oid "1.3.6.1.4.1.9.12.3.1.9.2.166";
  }

  smiv2:alias "cevSpa4xoc12Pos" {
    smiv2:oid "1.3.6.1.4.1.9.12.3.1.9.2.167";
  }

  smiv2:alias "cevWic1ShdslV3" {
    smiv2:oid "1.3.6.1.4.1.9.12.3.1.9.2.168";
  }

  smiv2:alias "cevUsbFlash" {
    smiv2:oid "1.3.6.1.4.1.9.12.3.1.9.2.169";
  }

  smiv2:alias "cevUsbToken" {
    smiv2:oid "1.3.6.1.4.1.9.12.3.1.9.2.170";
  }

  smiv2:alias "cevUsbHub" {
    smiv2:oid "1.3.6.1.4.1.9.12.3.1.9.2.171";
  }

  smiv2:alias "cevVEncM" {
    smiv2:oid "1.3.6.1.4.1.9.12.3.1.9.2.172";
  }

  smiv2:alias "cevUsbDevice" {
    smiv2:oid "1.3.6.1.4.1.9.12.3.1.9.2.173";
  }

  smiv2:alias "cevSpa1pOc48PosSfp" {
    smiv2:oid "1.3.6.1.4.1.9.12.3.1.9.2.174";
  }

  smiv2:alias "cevSpa4pOc48PosSfp" {
    smiv2:oid "1.3.6.1.4.1.9.12.3.1.9.2.175";
  }

  smiv2:alias "cevIpRanOpt4P" {
    smiv2:oid "1.3.6.1.4.1.9.12.3.1.9.2.176";
  }

  smiv2:alias "cevAimIps1" {
    smiv2:oid "1.3.6.1.4.1.9.12.3.1.9.2.177";
  }

  smiv2:alias "cevAimIps2" {
    smiv2:oid "1.3.6.1.4.1.9.12.3.1.9.2.178";
  }

  smiv2:alias "cevNmCips" {
    smiv2:oid "1.3.6.1.4.1.9.12.3.1.9.2.180";
  }

  smiv2:alias "cevHwic1fe" {
    smiv2:oid "1.3.6.1.4.1.9.12.3.1.9.2.181";
  }

  smiv2:alias "cevHwic2fe" {
    smiv2:oid "1.3.6.1.4.1.9.12.3.1.9.2.182";
  }

  smiv2:alias "cevHwicBriU82912" {
    smiv2:oid "1.3.6.1.4.1.9.12.3.1.9.2.183";
  }

  smiv2:alias "cevHwicBri4bST" {
    smiv2:oid "1.3.6.1.4.1.9.12.3.1.9.2.184";
  }

  smiv2:alias "cevModuleCrs1RPB" {
    smiv2:oid "1.3.6.1.4.1.9.12.3.1.9.2.185";
  }

  smiv2:alias "cevModuleCrs1FccSCGe" {
    smiv2:oid "1.3.6.1.4.1.9.12.3.1.9.2.186";
  }

  smiv2:alias "cevModuleCrs1SPAInfCard" {
    smiv2:oid "1.3.6.1.4.1.9.12.3.1.9.2.187";
  }

  smiv2:alias "cevModule4OC192DptIr" {
    smiv2:oid "1.3.6.1.4.1.9.12.3.1.9.2.188";
  }

  smiv2:alias "cevModuleCrs116mFabricCard" {
    smiv2:oid "1.3.6.1.4.1.9.12.3.1.9.2.189";
  }

  smiv2:alias "cevHwicAdslPotsAnnexM" {
    smiv2:oid "1.3.6.1.4.1.9.12.3.1.9.2.190";
  }

  smiv2:alias "cevSpa4pOc3PosV2" {
    smiv2:oid "1.3.6.1.4.1.9.12.3.1.9.2.191";
  }

  smiv2:alias "cevCVRX2SFP" {
    smiv2:oid "1.3.6.1.4.1.9.12.3.1.9.2.192";
  }

  smiv2:alias "cevSpaIPSEC2g2" {
    smiv2:oid "1.3.6.1.4.1.9.12.3.1.9.2.193";
  }

  smiv2:alias "cevSpa8pCt1e1CemAtm" {
    smiv2:oid "1.3.6.1.4.1.9.12.3.1.9.2.194";
  }

  smiv2:alias "cevSpa24pCt1e1CemAtm" {
    smiv2:oid "1.3.6.1.4.1.9.12.3.1.9.2.195";
  }

  smiv2:alias "cevSpa2pCt3e3CemAtm" {
    smiv2:oid "1.3.6.1.4.1.9.12.3.1.9.2.196";
  }

  smiv2:alias "cevSpa1pChoc3CemAtm" {
    smiv2:oid "1.3.6.1.4.1.9.12.3.1.9.2.197";
  }

  smiv2:alias "cevSpa1x10geWlV2" {
    smiv2:oid "1.3.6.1.4.1.9.12.3.1.9.2.198";
  }

  smiv2:alias "cevSpa1x10geDwdmV2" {
    smiv2:oid "1.3.6.1.4.1.9.12.3.1.9.2.199";
  }

  smiv2:alias "cevSpa1pChoc48Ds3" {
    smiv2:oid "1.3.6.1.4.1.9.12.3.1.9.2.200";
  }

  smiv2:alias "cevSpa1pChoc12Ds0" {
    smiv2:oid "1.3.6.1.4.1.9.12.3.1.9.2.201";
  }

  smiv2:alias "cevAimAtm8" {
    smiv2:oid "1.3.6.1.4.1.9.12.3.1.9.2.202";
  }

  smiv2:alias "cevSpa4xtSerial" {
    smiv2:oid "1.3.6.1.4.1.9.12.3.1.9.2.203";
  }

  smiv2:alias "cevSpa1xOC3AtmV2" {
    smiv2:oid "1.3.6.1.4.1.9.12.3.1.9.2.204";
  }

  smiv2:alias "cevSpa2xOC3AtmV2" {
    smiv2:oid "1.3.6.1.4.1.9.12.3.1.9.2.205";
  }

  smiv2:alias "cevSpa3xOC3AtmV2" {
    smiv2:oid "1.3.6.1.4.1.9.12.3.1.9.2.206";
  }

  smiv2:alias "cevSpa1xOC12AtmV2" {
    smiv2:oid "1.3.6.1.4.1.9.12.3.1.9.2.207";
  }

  smiv2:alias "cevNmTransOptSrvcEng1" {
    smiv2:oid "1.3.6.1.4.1.9.12.3.1.9.2.208";
  }

  smiv2:alias "cevAimTransOptSrvcEng1" {
    smiv2:oid "1.3.6.1.4.1.9.12.3.1.9.2.209";
  }

  smiv2:alias "cevNmTransOptSrvcEng2" {
    smiv2:oid "1.3.6.1.4.1.9.12.3.1.9.2.210";
  }

  smiv2:alias "cevAimTransOptSrvcEng2" {
    smiv2:oid "1.3.6.1.4.1.9.12.3.1.9.2.211";
  }

  smiv2:alias "cevOnboardSe" {
    smiv2:oid "1.3.6.1.4.1.9.12.3.1.9.2.212";
  }

  smiv2:alias "cevAimIpsK9" {
    smiv2:oid "1.3.6.1.4.1.9.12.3.1.9.2.213";
  }

  smiv2:alias "cevNmeApaModule" {
    smiv2:oid "1.3.6.1.4.1.9.12.3.1.9.2.214";
  }

  smiv2:alias "cevHwicVdslPots" {
    smiv2:oid "1.3.6.1.4.1.9.12.3.1.9.2.215";
  }

  smiv2:alias "cevHwicVdslIsdn" {
    smiv2:oid "1.3.6.1.4.1.9.12.3.1.9.2.216";
  }

  smiv2:alias "cevWsIpsec3" {
    smiv2:oid "1.3.6.1.4.1.9.12.3.1.9.2.217";
  }

  smiv2:alias "cevHwic2as" {
    smiv2:oid "1.3.6.1.4.1.9.12.3.1.9.2.218";
  }

  smiv2:alias "cevHwic2t" {
    smiv2:oid "1.3.6.1.4.1.9.12.3.1.9.2.219";
  }

  smiv2:alias "cevHwic1t" {
    smiv2:oid "1.3.6.1.4.1.9.12.3.1.9.2.220";
  }

  smiv2:alias "cevHwic1dsuT1" {
    smiv2:oid "1.3.6.1.4.1.9.12.3.1.9.2.221";
  }

  smiv2:alias "cevDsx930418fk9" {
    smiv2:oid "1.3.6.1.4.1.9.12.3.1.9.2.222";
  }

  smiv2:alias "cevC7600SSC400" {
    smiv2:oid "1.3.6.1.4.1.9.12.3.1.9.2.223";
  }

  smiv2:alias "cevWSSSC600" {
    smiv2:oid "1.3.6.1.4.1.9.12.3.1.9.2.224";
  }

  smiv2:alias "cevSpa2pGeSynce" {
    smiv2:oid "1.3.6.1.4.1.9.12.3.1.9.2.225";
  }

  smiv2:alias "cevSpa2pChoc12Ds0" {
    smiv2:oid "1.3.6.1.4.1.9.12.3.1.9.2.226";
  }

  smiv2:alias "cevAimVpnSsl1" {
    smiv2:oid "1.3.6.1.4.1.9.12.3.1.9.2.227";
  }

  smiv2:alias "cevAimVpnSsl2" {
    smiv2:oid "1.3.6.1.4.1.9.12.3.1.9.2.228";
  }

  smiv2:alias "cevAimVpnSsl3" {
    smiv2:oid "1.3.6.1.4.1.9.12.3.1.9.2.229";
  }

  smiv2:alias "cevWsIpsec2" {
    smiv2:oid "1.3.6.1.4.1.9.12.3.1.9.2.230";
  }

  smiv2:alias "cevCVRX2SFP10G" {
    smiv2:oid "1.3.6.1.4.1.9.12.3.1.9.2.231";
  }

  smiv2:alias "cevHardDisk" {
    smiv2:oid "1.3.6.1.4.1.9.12.3.1.9.2.232";
  }

  smiv2:alias "cevIsmSre300K9" {
    smiv2:oid "1.3.6.1.4.1.9.12.3.1.9.2.234";
  }

  smiv2:alias "cevSmSre700K9" {
    smiv2:oid "1.3.6.1.4.1.9.12.3.1.9.2.237";
  }

  smiv2:alias "cevSmSre900K9" {
    smiv2:oid "1.3.6.1.4.1.9.12.3.1.9.2.239";
  }

  smiv2:alias "cevSpaWmaSw" {
    smiv2:oid "1.3.6.1.4.1.9.12.3.1.9.2.240";
  }

  smiv2:alias "cevHwic4ShdslEfm" {
    smiv2:oid "1.3.6.1.4.1.9.12.3.1.9.2.242";
  }

  smiv2:alias "cevAimAxp102" {
    smiv2:oid "1.3.6.1.4.1.9.12.3.1.9.2.243";
  }

  smiv2:alias "cevAim2Axp104" {
    smiv2:oid "1.3.6.1.4.1.9.12.3.1.9.2.244";
  }

  smiv2:alias "cevNmAxp302" {
    smiv2:oid "1.3.6.1.4.1.9.12.3.1.9.2.245";
  }

  smiv2:alias "cevNmAxp502" {
    smiv2:oid "1.3.6.1.4.1.9.12.3.1.9.2.246";
  }

  smiv2:alias "cevNmAxp522" {
    smiv2:oid "1.3.6.1.4.1.9.12.3.1.9.2.247";
  }

  smiv2:alias "cevWicGshdslEfm" {
    smiv2:oid "1.3.6.1.4.1.9.12.3.1.9.2.248";
  }

  smiv2:alias "cevNmeIss" {
    smiv2:oid "1.3.6.1.4.1.9.12.3.1.9.2.249";
  }

  smiv2:alias "cevNmeVmss216" {
    smiv2:oid "1.3.6.1.4.1.9.12.3.1.9.2.250";
  }

  smiv2:alias "cevNmeVmssHp32" {
    smiv2:oid "1.3.6.1.4.1.9.12.3.1.9.2.251";
  }

  smiv2:alias "cevNmeVmss2Hp32" {
    smiv2:oid "1.3.6.1.4.1.9.12.3.1.9.2.252";
  }

  smiv2:alias "cevNmeVmssHp16" {
    smiv2:oid "1.3.6.1.4.1.9.12.3.1.9.2.253";
  }

  smiv2:alias "cevNmeVmss16" {
    smiv2:oid "1.3.6.1.4.1.9.12.3.1.9.2.254";
  }

  smiv2:alias "cevNamWaasVirtualBlade" {
    smiv2:oid "1.3.6.1.4.1.9.12.3.1.9.2.260";
  }

  smiv2:alias "cevSpaDsp" {
    smiv2:oid "1.3.6.1.4.1.9.12.3.1.9.2.273";
  }

  smiv2:alias "cevModuleCrs4S140GFabricCard" {
    smiv2:oid "1.3.6.1.4.1.9.12.3.1.9.2.274";
  }

  smiv2:alias "cevModuleCrs8S140GFabricCard" {
    smiv2:oid "1.3.6.1.4.1.9.12.3.1.9.2.275";
  }

  smiv2:alias "cevModuleCrs16S140GFabricCard" {
    smiv2:oid "1.3.6.1.4.1.9.12.3.1.9.2.276";
  }

  smiv2:alias "cevModuleCrs16S140GFabricCardMulti" {
    smiv2:oid "1.3.6.1.4.1.9.12.3.1.9.2.277";
  }

  smiv2:alias "cevModuleCrs1140GFCCSFC" {
    smiv2:oid "1.3.6.1.4.1.9.12.3.1.9.2.278";
  }

  smiv2:alias "cevC3KxNm1g" {
    smiv2:oid "1.3.6.1.4.1.9.12.3.1.9.2.279";
  }

  smiv2:alias "cevC3KxNm10g" {
    smiv2:oid "1.3.6.1.4.1.9.12.3.1.9.2.280";
  }

  smiv2:alias "cevHwic2tC" {
    smiv2:oid "1.3.6.1.4.1.9.12.3.1.9.2.282";
  }

  smiv2:alias "cevHwic1tC" {
    smiv2:oid "1.3.6.1.4.1.9.12.3.1.9.2.283";
  }

  smiv2:alias "cevHwic4fesC" {
    smiv2:oid "1.3.6.1.4.1.9.12.3.1.9.2.284";
  }

  smiv2:alias "cevHwic9fesC" {
    smiv2:oid "1.3.6.1.4.1.9.12.3.1.9.2.285";
  }

  smiv2:alias "cevVwic2Mft1G703C" {
    smiv2:oid "1.3.6.1.4.1.9.12.3.1.9.2.286";
  }

  smiv2:alias "cevVwic2Mft2G703C" {
    smiv2:oid "1.3.6.1.4.1.9.12.3.1.9.2.287";
  }

  smiv2:alias "cevNmEswitch16C" {
    smiv2:oid "1.3.6.1.4.1.9.12.3.1.9.2.288";
  }

  smiv2:alias "cevC2960sStack" {
    smiv2:oid "1.3.6.1.4.1.9.12.3.1.9.2.291";
  }

  smiv2:alias "cevHardiskIdc" {
    smiv2:oid "1.3.6.1.4.1.9.12.3.1.9.2.292";
  }

  smiv2:alias "cevEhwic4esg" {
    smiv2:oid "1.3.6.1.4.1.9.12.3.1.9.2.293";
  }

  smiv2:alias "cevEhwicD8esg" {
    smiv2:oid "1.3.6.1.4.1.9.12.3.1.9.2.294";
  }

  smiv2:alias "cevEhwicD8esgP" {
    smiv2:oid "1.3.6.1.4.1.9.12.3.1.9.2.295";
  }

  smiv2:alias "cevEhwic4esgP" {
    smiv2:oid "1.3.6.1.4.1.9.12.3.1.9.2.296";
  }

  smiv2:alias "cevVmssSmSre700K9" {
    smiv2:oid "1.3.6.1.4.1.9.12.3.1.9.2.297";
  }

  smiv2:alias "cevVmssSmSre900K9" {
    smiv2:oid "1.3.6.1.4.1.9.12.3.1.9.2.298";
  }

  smiv2:alias "cevIssSmSre700K9" {
    smiv2:oid "1.3.6.1.4.1.9.12.3.1.9.2.299";
  }

  smiv2:alias "cevIssSmSre900K9" {
    smiv2:oid "1.3.6.1.4.1.9.12.3.1.9.2.300";
  }

  smiv2:alias "cevModem3gGsm504A" {
    smiv2:oid "1.3.6.1.4.1.9.12.3.1.9.2.301";
  }

  smiv2:alias "cevModem3gGsm504G" {
    smiv2:oid "1.3.6.1.4.1.9.12.3.1.9.2.302";
  }

  smiv2:alias "cevCvrCfp4sfp10g" {
    smiv2:oid "1.3.6.1.4.1.9.12.3.1.9.2.303";
  }

  smiv2:alias "cevModem3gCdma5728V" {
    smiv2:oid "1.3.6.1.4.1.9.12.3.1.9.2.304";
  }

  smiv2:alias "cevModem3gGsmMC8705" {
    smiv2:oid "1.3.6.1.4.1.9.12.3.1.9.2.305";
  }

  smiv2:alias "cevModem3gGsmMC8795" {
    smiv2:oid "1.3.6.1.4.1.9.12.3.1.9.2.306";
  }

  smiv2:alias "cevModem3gGsmMc8705A" {
    smiv2:oid "1.3.6.1.4.1.9.12.3.1.9.2.313";
  }

  smiv2:alias "cevHardDisk8541" {
    smiv2:oid "1.3.6.1.4.1.9.12.3.1.9.2.314";
  }

  smiv2:alias "cevHardDisk7571" {
    smiv2:oid "1.3.6.1.4.1.9.12.3.1.9.2.315";
  }

  smiv2:alias "cevHardDisk7541" {
    smiv2:oid "1.3.6.1.4.1.9.12.3.1.9.2.316";
  }

  smiv2:alias "cevHardDisk694" {
    smiv2:oid "1.3.6.1.4.1.9.12.3.1.9.2.317";
  }

  smiv2:alias "cevHardDisk594" {
    smiv2:oid "1.3.6.1.4.1.9.12.3.1.9.2.318";
  }

  smiv2:alias "cevHardDisk294" {
    smiv2:oid "1.3.6.1.4.1.9.12.3.1.9.2.319";
  }

  smiv2:alias "cevModuleDIMM8541" {
    smiv2:oid "1.3.6.1.4.1.9.12.3.1.9.2.320";
  }

  smiv2:alias "cevModuleDIMM7541" {
    smiv2:oid "1.3.6.1.4.1.9.12.3.1.9.2.321";
  }

  smiv2:alias "cevModuleDIMM7571" {
    smiv2:oid "1.3.6.1.4.1.9.12.3.1.9.2.322";
  }

  smiv2:alias "cevModuleDIMM294" {
    smiv2:oid "1.3.6.1.4.1.9.12.3.1.9.2.323";
  }

  smiv2:alias "cevModuleDIMM694" {
    smiv2:oid "1.3.6.1.4.1.9.12.3.1.9.2.324";
  }

  smiv2:alias "cevModuleDIMM594" {
    smiv2:oid "1.3.6.1.4.1.9.12.3.1.9.2.325";
  }

  smiv2:alias "cevModuleIOM294" {
    smiv2:oid "1.3.6.1.4.1.9.12.3.1.9.2.328";
  }

  smiv2:alias "cevModuleIOM594" {
    smiv2:oid "1.3.6.1.4.1.9.12.3.1.9.2.329";
  }

  smiv2:alias "cevModuleIOM694" {
    smiv2:oid "1.3.6.1.4.1.9.12.3.1.9.2.330";
  }

  smiv2:alias "cevModuleIOM7541" {
    smiv2:oid "1.3.6.1.4.1.9.12.3.1.9.2.331";
  }

  smiv2:alias "cevModuleIOM7571" {
    smiv2:oid "1.3.6.1.4.1.9.12.3.1.9.2.332";
  }

  smiv2:alias "cevModuleIOM8541" {
    smiv2:oid "1.3.6.1.4.1.9.12.3.1.9.2.333";
  }

  smiv2:alias "cevIM8pGeCu" {
    smiv2:oid "1.3.6.1.4.1.9.12.3.1.9.2.334";
  }

  smiv2:alias "cevIM8pGeSFP" {
    smiv2:oid "1.3.6.1.4.1.9.12.3.1.9.2.335";
  }

  smiv2:alias "cevIM16pT1E1" {
    smiv2:oid "1.3.6.1.4.1.9.12.3.1.9.2.336";
  }

  smiv2:alias "cevIM1p10GeXfp" {
    smiv2:oid "1.3.6.1.4.1.9.12.3.1.9.2.337";
  }

  smiv2:alias "cevIM4pOc3R1pOc12" {
    smiv2:oid "1.3.6.1.4.1.9.12.3.1.9.2.338";
  }

  smiv2:alias "cevEp1p40GeQsfp" {
    smiv2:oid "1.3.6.1.4.1.9.12.3.1.9.2.343";
  }

  smiv2:alias "cevEp2p40GeQsfp" {
    smiv2:oid "1.3.6.1.4.1.9.12.3.1.9.2.344";
  }

  smiv2:alias "cevMpa2X10GE" {
    smiv2:oid "1.3.6.1.4.1.9.12.3.1.9.2.350";
  }

  smiv2:alias "cevMpa4X10GE" {
    smiv2:oid "1.3.6.1.4.1.9.12.3.1.9.2.351";
  }

  smiv2:alias "cevMpa20X1GE" {
    smiv2:oid "1.3.6.1.4.1.9.12.3.1.9.2.352";
  }

  smiv2:alias "cevMpa1X40GE" {
    smiv2:oid "1.3.6.1.4.1.9.12.3.1.9.2.353";
  }

  smiv2:alias "cevMpa2X40GE" {
    smiv2:oid "1.3.6.1.4.1.9.12.3.1.9.2.354";
  }

  smiv2:alias "cevModuleNic2x10GeSfp" {
    smiv2:oid "1.3.6.1.4.1.9.12.3.1.9.2.359";
  }

  smiv2:alias "cevModuleNic4x10GeSfp" {
    smiv2:oid "1.3.6.1.4.1.9.12.3.1.9.2.360";
  }

  smiv2:alias "cevModuleNic4x1GeSfp" {
    smiv2:oid "1.3.6.1.4.1.9.12.3.1.9.2.361";
  }

  smiv2:alias "cevModule4portNic4x1GeCu" {
    smiv2:oid "1.3.6.1.4.1.9.12.3.1.9.2.362";
  }

  smiv2:alias "cevModule1xNitrox3" {
    smiv2:oid "1.3.6.1.4.1.9.12.3.1.9.2.363";
  }

  smiv2:alias "cevModule4xNitrox3" {
    smiv2:oid "1.3.6.1.4.1.9.12.3.1.9.2.364";
  }

  smiv2:alias "cevSpaHDwbdSfp" {
    smiv2:oid "1.3.6.1.4.1.9.12.3.1.9.2.365";
  }

  smiv2:alias "cevSpa8pT3E3Serial" {
    smiv2:oid "1.3.6.1.4.1.9.12.3.1.9.2.366";
  }

  smiv2:alias "cevSolidStateDisk8541" {
    smiv2:oid "1.3.6.1.4.1.9.12.3.1.9.2.367";
  }

  smiv2:alias "cevSolidStateDisk7541" {
    smiv2:oid "1.3.6.1.4.1.9.12.3.1.9.2.368";
  }

  smiv2:alias "cevSolidStateDisk7571" {
    smiv2:oid "1.3.6.1.4.1.9.12.3.1.9.2.369";
  }

  smiv2:alias "cevSolidStateDisk694" {
    smiv2:oid "1.3.6.1.4.1.9.12.3.1.9.2.370";
  }

  smiv2:alias "cevSolidStateDisk594" {
    smiv2:oid "1.3.6.1.4.1.9.12.3.1.9.2.371";
  }

  smiv2:alias "cevSolidStateDisk294" {
    smiv2:oid "1.3.6.1.4.1.9.12.3.1.9.2.372";
  }

  smiv2:alias "cevWaveInlnGe4T" {
    smiv2:oid "1.3.6.1.4.1.9.12.3.1.9.2.373";
  }

  smiv2:alias "cevWaveInlnGe8T" {
    smiv2:oid "1.3.6.1.4.1.9.12.3.1.9.2.374";
  }

  smiv2:alias "cevWaveInlnGe4SX" {
    smiv2:oid "1.3.6.1.4.1.9.12.3.1.9.2.375";
  }

  smiv2:alias "cevWave10Ge2SFP" {
    smiv2:oid "1.3.6.1.4.1.9.12.3.1.9.2.376";
  }

  smiv2:alias "cevA9kMpa8X10GE" {
    smiv2:oid "1.3.6.1.4.1.9.12.3.1.9.2.378";
  }

  smiv2:alias "cevA9KMpa8X10GE" {
    smiv2:oid "1.3.6.1.4.1.9.12.3.1.9.2.379";
  }

  smiv2:alias "cevIom4GeInln" {
    smiv2:oid "1.3.6.1.4.1.9.12.3.1.9.2.380";
  }

  smiv2:alias "cevIom8GeInln" {
    smiv2:oid "1.3.6.1.4.1.9.12.3.1.9.2.381";
  }

  smiv2:alias "cevIom4GefInln" {
    smiv2:oid "1.3.6.1.4.1.9.12.3.1.9.2.382";
  }

  smiv2:alias "cevIom2X10Ge" {
    smiv2:oid "1.3.6.1.4.1.9.12.3.1.9.2.383";
  }

  smiv2:alias "cevSfpH10GbCu5M" {
    smiv2:oid "1.3.6.1.4.1.9.12.3.1.9.2.384";
  }

  smiv2:alias "cevWaveScGe12T" {
    smiv2:oid "1.3.6.1.4.1.9.12.3.1.9.2.385";
  }

  smiv2:alias "cevWaveScGe12Sfp" {
    smiv2:oid "1.3.6.1.4.1.9.12.3.1.9.2.386";
  }

  smiv2:alias "cevWaveSc10Ge4Sfp" {
    smiv2:oid "1.3.6.1.4.1.9.12.3.1.9.2.387";
  }

  smiv2:alias "cevWaveApnvGe12T" {
    smiv2:oid "1.3.6.1.4.1.9.12.3.1.9.2.388";
  }

  smiv2:alias "cevWaveApnvGe12Sfp" {
    smiv2:oid "1.3.6.1.4.1.9.12.3.1.9.2.389";
  }

  smiv2:alias "cevWaveApnv10Ge4Sfp" {
    smiv2:oid "1.3.6.1.4.1.9.12.3.1.9.2.390";
  }

  smiv2:alias "cevModuleNCSFCS" {
    smiv2:oid "1.3.6.1.4.1.9.12.3.1.9.2.403";
  }

  smiv2:alias "cevModuleNCS10X100GMK" {
    smiv2:oid "1.3.6.1.4.1.9.12.3.1.9.2.404";
  }

  smiv2:alias "cevModuleNCS10X100GMP" {
    smiv2:oid "1.3.6.1.4.1.9.12.3.1.9.2.405";
  }

  smiv2:alias "cevModuleNCSRP" {
    smiv2:oid "1.3.6.1.4.1.9.12.3.1.9.2.406";
  }

  smiv2:alias "cevIM14pSerial" {
    smiv2:oid "1.3.6.1.4.1.9.12.3.1.9.2.407";
  }

  smiv2:alias "cevModuleNCSCRFT" {
    smiv2:oid "1.3.6.1.4.1.9.12.3.1.9.2.413";
  }

  smiv2:alias "cevModuleCommonCardsPSEASIC" {
    smiv2:oid "1.3.6.1.4.1.9.12.3.1.9.2.414";
  }

  smiv2:alias "cevModuleCommonCardsFIA" {
    smiv2:oid "1.3.6.1.4.1.9.12.3.1.9.2.415";
  }

  smiv2:alias "cevModulePowerController" {
    smiv2:oid "1.3.6.1.4.1.9.12.3.1.9.2.418";
  }

  smiv2:alias "cevModuleDIMM" {
    smiv2:oid "1.3.6.1.4.1.9.12.3.1.9.2.419";
  }

  smiv2:alias "cevModuleNCS10X100GLP" {
    smiv2:oid "1.3.6.1.4.1.9.12.3.1.9.2.420";
  }

  smiv2:alias "cevModuleNCS10X100GLK" {
    smiv2:oid "1.3.6.1.4.1.9.12.3.1.9.2.421";
  }

  smiv2:alias "cevModuleFPD" {
    smiv2:oid "1.3.6.1.4.1.9.12.3.1.9.2.422";
  }

  smiv2:alias "cevModuleI2CMUX" {
    smiv2:oid "1.3.6.1.4.1.9.12.3.1.9.2.423";
  }

  smiv2:alias "cevModulePCIESwitch" {
    smiv2:oid "1.3.6.1.4.1.9.12.3.1.9.2.424";
  }

  smiv2:alias "cevModuleStorage" {
    smiv2:oid "1.3.6.1.4.1.9.12.3.1.9.2.425";
  }

  smiv2:alias "cevModuleControlSwitch" {
    smiv2:oid "1.3.6.1.4.1.9.12.3.1.9.2.426";
  }

  smiv2:alias "cevModuleC3KxNm4x10g" {
    smiv2:oid "1.3.6.1.4.1.9.12.3.1.9.2.427";
  }

  smiv2:alias "cevModuleNC6410X100GMK" {
    smiv2:oid "1.3.6.1.4.1.9.12.3.1.9.2.429";
  }

  smiv2:alias "cevModuleNC6610X100GLK" {
    smiv2:oid "1.3.6.1.4.1.9.12.3.1.9.2.430";
  }

  smiv2:alias "cevModulePseAsicPlim" {
    smiv2:oid "1.3.6.1.4.1.9.12.3.1.9.2.445";
  }

  smiv2:alias "cevModuleCisco60P10GeSFPPlusLsrLC" {
    smiv2:oid "1.3.6.1.4.1.9.12.3.1.9.2.446";
  }

  smiv2:alias "cevModuleCisco30P10GeSFPPlusLsrLC" {
    smiv2:oid "1.3.6.1.4.1.9.12.3.1.9.2.447";
  }

  smiv2:alias "cevModuleCisco15P10GeSFPPlusLsrLC" {
    smiv2:oid "1.3.6.1.4.1.9.12.3.1.9.2.448";
  }

  smiv2:alias "cevModuleCisco15P10GeSFPPlusLC" {
    smiv2:oid "1.3.6.1.4.1.9.12.3.1.9.2.449";
  }

  smiv2:alias "cevModuleCisco30P10GeSFPPlusLC" {
    smiv2:oid "1.3.6.1.4.1.9.12.3.1.9.2.450";
  }

  smiv2:alias "cevModuleCisco60P10GeSFPPlusLC" {
    smiv2:oid "1.3.6.1.4.1.9.12.3.1.9.2.451";
  }

  smiv2:alias "cevModuleVirtualBlade" {
    smiv2:oid "1.3.6.1.4.1.9.12.3.1.9.2.452";
  }

  smiv2:alias "cevModuleASA55125515ASAIC6GECUA" {
    smiv2:oid "1.3.6.1.4.1.9.12.3.1.9.2.453";
  }

  smiv2:alias "cevModuleASA5525ASAIC6GECUB" {
    smiv2:oid "1.3.6.1.4.1.9.12.3.1.9.2.454";
  }

  smiv2:alias "cevModuleASA55455555ASAIC6GECUC" {
    smiv2:oid "1.3.6.1.4.1.9.12.3.1.9.2.455";
  }

  smiv2:alias "cevModuleASA55125515ASAIC6GESFPA" {
    smiv2:oid "1.3.6.1.4.1.9.12.3.1.9.2.456";
  }

  smiv2:alias "cevModuleASA5525ASAIC6GESFPB" {
    smiv2:oid "1.3.6.1.4.1.9.12.3.1.9.2.457";
  }

  smiv2:alias "cevModuleASA55455555ASAIC6GESFPC" {
    smiv2:oid "1.3.6.1.4.1.9.12.3.1.9.2.458";
  }

  smiv2:alias "cevModuleNCS4KDCPWF" {
    smiv2:oid "1.3.6.1.4.1.9.12.3.1.9.2.459";
  }

  smiv2:alias "cevModuleNCS4KECU" {
    smiv2:oid "1.3.6.1.4.1.9.12.3.1.9.2.460";
  }

  smiv2:alias "cevPEhwic4Esg" {
    smiv2:oid "1.3.6.1.4.1.9.12.3.1.9.2.470";
  }

  smiv2:alias "cevPEhwicD8Esg" {
    smiv2:oid "1.3.6.1.4.1.9.12.3.1.9.2.471";
  }

  smiv2:alias "cevPWic1BStV3" {
    smiv2:oid "1.3.6.1.4.1.9.12.3.1.9.2.472";
  }

  smiv2:alias "cevPhwic1Adsl" {
    smiv2:oid "1.3.6.1.4.1.9.12.3.1.9.2.473";
  }

  smiv2:alias "cevPhwic1Adslm" {
    smiv2:oid "1.3.6.1.4.1.9.12.3.1.9.2.474";
  }

  smiv2:alias "cevPHwic1Dsut1" {
    smiv2:oid "1.3.6.1.4.1.9.12.3.1.9.2.475";
  }

  smiv2:alias "cevPHwic1t" {
    smiv2:oid "1.3.6.1.4.1.9.12.3.1.9.2.476";
  }

  smiv2:alias "cevPHwic2as" {
    smiv2:oid "1.3.6.1.4.1.9.12.3.1.9.2.477";
  }

  smiv2:alias "cevPHwic2Fe" {
    smiv2:oid "1.3.6.1.4.1.9.12.3.1.9.2.478";
  }

  smiv2:alias "cevPHwic2t" {
    smiv2:oid "1.3.6.1.4.1.9.12.3.1.9.2.479";
  }

  smiv2:alias "cevPIsmSre300K9" {
    smiv2:oid "1.3.6.1.4.1.9.12.3.1.9.2.480";
  }

  smiv2:alias "cevSpa14pSaSerial" {
    smiv2:oid "1.3.6.1.4.1.9.12.3.1.9.2.481";
  }

  smiv2:alias "cevPEhwicVaMMDslA" {
    smiv2:oid "1.3.6.1.4.1.9.12.3.1.9.2.484";
  }

  smiv2:alias "cevPEhwicVaMMDslM" {
    smiv2:oid "1.3.6.1.4.1.9.12.3.1.9.2.485";
  }

  smiv2:alias "cevModuleA900IMA8S1Z" {
    smiv2:oid "1.3.6.1.4.1.9.12.3.1.9.2.491";
  }

  smiv2:alias "cevModuleA900IMA8T1Z" {
    smiv2:oid "1.3.6.1.4.1.9.12.3.1.9.2.492";
  }

  smiv2:alias "cevModuleA900IMA2Z" {
    smiv2:oid "1.3.6.1.4.1.9.12.3.1.9.2.493";
  }

  smiv2:alias "cevModuleNCSSfpPlusOpticsMod" {
    smiv2:oid "1.3.6.1.4.1.9.12.3.1.9.2.506";
  }

  smiv2:alias "cevModuleNCS6KSRTCAM" {
    smiv2:oid "1.3.6.1.4.1.9.12.3.1.9.2.507";
  }

  smiv2:alias "cevModuleNCS6K210X100GMK" {
    smiv2:oid "1.3.6.1.4.1.9.12.3.1.9.2.508";
  }

  smiv2:alias "cevModuleNCS6K210X100GLK" {
    smiv2:oid "1.3.6.1.4.1.9.12.3.1.9.2.509";
  }

  smiv2:alias "cevModuleNCS6K230X10GMS" {
    smiv2:oid "1.3.6.1.4.1.9.12.3.1.9.2.510";
  }

  smiv2:alias "cevModuleNCS6K230X10GLS" {
    smiv2:oid "1.3.6.1.4.1.9.12.3.1.9.2.511";
  }

  smiv2:alias "cevModuleSPAETHER24xGE4x10GECU" {
    smiv2:oid "1.3.6.1.4.1.9.12.3.1.9.2.512";
  }

  smiv2:alias "cevModuleSPAETHER24xGE4x10GESFP" {
    smiv2:oid "1.3.6.1.4.1.9.12.3.1.9.2.513";
  }

  smiv2:alias "cevModuleSPAETHER24xGE4x10GE" {
    smiv2:oid "1.3.6.1.4.1.9.12.3.1.9.2.514";
  }

  smiv2:alias "cevModuleSPAETHER12xGE2x10GEDUAL" {
    smiv2:oid "1.3.6.1.4.1.9.12.3.1.9.2.515";
  }

  smiv2:alias "cevModuleSPAETHER2xGE4x10GEDUAL" {
    smiv2:oid "1.3.6.1.4.1.9.12.3.1.9.2.516";
  }

  smiv2:alias "cevModuleSPAETHER10xGE2x10GEDUAL" {
    smiv2:oid "1.3.6.1.4.1.9.12.3.1.9.2.517";
  }

  smiv2:alias "cevModuleA900IMA32D" {
    smiv2:oid "1.3.6.1.4.1.9.12.3.1.9.2.518";
  }

  smiv2:alias "cevModuleA900IMA8D" {
    smiv2:oid "1.3.6.1.4.1.9.12.3.1.9.2.519";
  }

  smiv2:alias "cevModuleC36xxType" {
    smiv2:oid "1.3.6.1.4.1.9.12.3.1.9.3";
  }

  smiv2:alias "cevPmCpm1e2w" {
    smiv2:oid "1.3.6.1.4.1.9.12.3.1.9.3.1";
  }

  smiv2:alias "cevPmCpm2e2w" {
    smiv2:oid "1.3.6.1.4.1.9.12.3.1.9.3.2";
  }

  smiv2:alias "cevPmCpm1e1r2w" {
    smiv2:oid "1.3.6.1.4.1.9.12.3.1.9.3.3";
  }

  smiv2:alias "cevPmCt1Csu" {
    smiv2:oid "1.3.6.1.4.1.9.12.3.1.9.3.4";
  }

  smiv2:alias "cevPm2ct1Csu" {
    smiv2:oid "1.3.6.1.4.1.9.12.3.1.9.3.5";
  }

  smiv2:alias "cevPmCt1Dsx1" {
    smiv2:oid "1.3.6.1.4.1.9.12.3.1.9.3.6";
  }

  smiv2:alias "cevPm2ct1Dsx1" {
    smiv2:oid "1.3.6.1.4.1.9.12.3.1.9.3.7";
  }

  smiv2:alias "cevPmCe1Balanced" {
    smiv2:oid "1.3.6.1.4.1.9.12.3.1.9.3.8";
  }

  smiv2:alias "cevPm2ce1Balanced" {
    smiv2:oid "1.3.6.1.4.1.9.12.3.1.9.3.9";
  }

  smiv2:alias "cevPmCe1Unbalanced" {
    smiv2:oid "1.3.6.1.4.1.9.12.3.1.9.3.10";
  }

  smiv2:alias "cevPm2ce1Unbalanced" {
    smiv2:oid "1.3.6.1.4.1.9.12.3.1.9.3.11";
  }

  smiv2:alias "cevPm4bU" {
    smiv2:oid "1.3.6.1.4.1.9.12.3.1.9.3.12";
  }

  smiv2:alias "cevPm4bSt" {
    smiv2:oid "1.3.6.1.4.1.9.12.3.1.9.3.13";
  }

  smiv2:alias "cevPm8bU" {
    smiv2:oid "1.3.6.1.4.1.9.12.3.1.9.3.14";
  }

  smiv2:alias "cevPm8bSt" {
    smiv2:oid "1.3.6.1.4.1.9.12.3.1.9.3.15";
  }

  smiv2:alias "cevPm4as" {
    smiv2:oid "1.3.6.1.4.1.9.12.3.1.9.3.16";
  }

  smiv2:alias "cevPm8as" {
    smiv2:oid "1.3.6.1.4.1.9.12.3.1.9.3.17";
  }

  smiv2:alias "cevPm4e" {
    smiv2:oid "1.3.6.1.4.1.9.12.3.1.9.3.18";
  }

  smiv2:alias "cevPm1e" {
    smiv2:oid "1.3.6.1.4.1.9.12.3.1.9.3.19";
  }

  smiv2:alias "cevPmM4t" {
    smiv2:oid "1.3.6.1.4.1.9.12.3.1.9.3.21";
  }

  smiv2:alias "cevPm16a" {
    smiv2:oid "1.3.6.1.4.1.9.12.3.1.9.3.22";
  }

  smiv2:alias "cevPm32a" {
    smiv2:oid "1.3.6.1.4.1.9.12.3.1.9.3.23";
  }

  smiv2:alias "cevPmC36001fe" {
    smiv2:oid "1.3.6.1.4.1.9.12.3.1.9.3.24";
  }

  smiv2:alias "cevPmC3600Compression" {
    smiv2:oid "1.3.6.1.4.1.9.12.3.1.9.3.25";
  }

  smiv2:alias "cevPmDmodem" {
    smiv2:oid "1.3.6.1.4.1.9.12.3.1.9.3.26";
  }

  smiv2:alias "cevPm8admodem" {
    smiv2:oid "1.3.6.1.4.1.9.12.3.1.9.3.27";
  }

  smiv2:alias "cevPm16admodem" {
    smiv2:oid "1.3.6.1.4.1.9.12.3.1.9.3.28";
  }

  smiv2:alias "cevVpm2v" {
    smiv2:oid "1.3.6.1.4.1.9.12.3.1.9.3.29";
  }

  smiv2:alias "cevVpm4v" {
    smiv2:oid "1.3.6.1.4.1.9.12.3.1.9.3.30";
  }

  smiv2:alias "cevPmC36001feTx" {
    smiv2:oid "1.3.6.1.4.1.9.12.3.1.9.3.31";
  }

  smiv2:alias "cevPmC36001feFx" {
    smiv2:oid "1.3.6.1.4.1.9.12.3.1.9.3.32";
  }

  smiv2:alias "cevPm1fe1t1" {
    smiv2:oid "1.3.6.1.4.1.9.12.3.1.9.3.33";
  }

  smiv2:alias "cevPm1fe2t1" {
    smiv2:oid "1.3.6.1.4.1.9.12.3.1.9.3.34";
  }

  smiv2:alias "cevPm1fe1e1" {
    smiv2:oid "1.3.6.1.4.1.9.12.3.1.9.3.35";
  }

  smiv2:alias "cevPm1fe2e1" {
    smiv2:oid "1.3.6.1.4.1.9.12.3.1.9.3.36";
  }

  smiv2:alias "cevPm1fe1t1Csu" {
    smiv2:oid "1.3.6.1.4.1.9.12.3.1.9.3.37";
  }

  smiv2:alias "cevPm1fe2t1Csu" {
    smiv2:oid "1.3.6.1.4.1.9.12.3.1.9.3.38";
  }

  smiv2:alias "cevC36xx2feTx" {
    smiv2:oid "1.3.6.1.4.1.9.12.3.1.9.3.39";
  }

  smiv2:alias "cevPmOc3mm" {
    smiv2:oid "1.3.6.1.4.1.9.12.3.1.9.3.40";
  }

  smiv2:alias "cevPmOc3mmVpd" {
    smiv2:oid "1.3.6.1.4.1.9.12.3.1.9.3.41";
  }

  smiv2:alias "cevPmOc3smiVpd" {
    smiv2:oid "1.3.6.1.4.1.9.12.3.1.9.3.42";
  }

  smiv2:alias "cevPmOc3smlVpd" {
    smiv2:oid "1.3.6.1.4.1.9.12.3.1.9.3.43";
  }

  smiv2:alias "cevPmOc3sml" {
    smiv2:oid "1.3.6.1.4.1.9.12.3.1.9.3.44";
  }

  smiv2:alias "cevPmOc3smi" {
    smiv2:oid "1.3.6.1.4.1.9.12.3.1.9.3.45";
  }

  smiv2:alias "cevVic2fxoEu" {
    smiv2:oid "1.3.6.1.4.1.9.12.3.1.9.3.46";
  }

  smiv2:alias "cevVic2fxoM3" {
    smiv2:oid "1.3.6.1.4.1.9.12.3.1.9.3.47";
  }

  smiv2:alias "cevVic2fxoM4" {
    smiv2:oid "1.3.6.1.4.1.9.12.3.1.9.3.48";
  }

  smiv2:alias "cevVic2fxoM5" {
    smiv2:oid "1.3.6.1.4.1.9.12.3.1.9.3.49";
  }

  smiv2:alias "cevVic2fxoM6" {
    smiv2:oid "1.3.6.1.4.1.9.12.3.1.9.3.50";
  }

  smiv2:alias "cevVic2fxoM7" {
    smiv2:oid "1.3.6.1.4.1.9.12.3.1.9.3.51";
  }

  smiv2:alias "cevVic2fxoM8" {
    smiv2:oid "1.3.6.1.4.1.9.12.3.1.9.3.52";
  }

  smiv2:alias "cevVic2ST2086" {
    smiv2:oid "1.3.6.1.4.1.9.12.3.1.9.3.53";
  }

  smiv2:alias "cevHdv" {
    smiv2:oid "1.3.6.1.4.1.9.12.3.1.9.3.54";
  }

  smiv2:alias "cevNm1fe2w" {
    smiv2:oid "1.3.6.1.4.1.9.12.3.1.9.3.59";
  }

  smiv2:alias "cevNm2fe2w" {
    smiv2:oid "1.3.6.1.4.1.9.12.3.1.9.3.60";
  }

  smiv2:alias "cevNm1fe1r2w" {
    smiv2:oid "1.3.6.1.4.1.9.12.3.1.9.3.61";
  }

  smiv2:alias "cevNm2w" {
    smiv2:oid "1.3.6.1.4.1.9.12.3.1.9.3.62";
  }

  smiv2:alias "cevC36xx1feTx" {
    smiv2:oid "1.3.6.1.4.1.9.12.3.1.9.3.63";
  }

  smiv2:alias "cevAimLc4e1Compression" {
    smiv2:oid "1.3.6.1.4.1.9.12.3.1.9.3.64";
  }

  smiv2:alias "cevVic2fxoM1" {
    smiv2:oid "1.3.6.1.4.1.9.12.3.1.9.3.65";
  }

  smiv2:alias "cevVic2fxoM2" {
    smiv2:oid "1.3.6.1.4.1.9.12.3.1.9.3.68";
  }

  smiv2:alias "cevPmDs3" {
    smiv2:oid "1.3.6.1.4.1.9.12.3.1.9.3.69";
  }

  smiv2:alias "cevPmE3" {
    smiv2:oid "1.3.6.1.4.1.9.12.3.1.9.3.70";
  }

  smiv2:alias "cevVic2vpFxsDid" {
    smiv2:oid "1.3.6.1.4.1.9.12.3.1.9.3.74";
  }

  smiv2:alias "cevVic2ST2086NtTe" {
    smiv2:oid "1.3.6.1.4.1.9.12.3.1.9.3.75";
  }

  smiv2:alias "cevNmAic64" {
    smiv2:oid "1.3.6.1.4.1.9.12.3.1.9.3.76";
  }

  smiv2:alias "cevMIX366064" {
    smiv2:oid "1.3.6.1.4.1.9.12.3.1.9.3.77";
  }

  smiv2:alias "cevWicAsync1am" {
    smiv2:oid "1.3.6.1.4.1.9.12.3.1.9.3.78";
  }

  smiv2:alias "cevWicAsync2am" {
    smiv2:oid "1.3.6.1.4.1.9.12.3.1.9.3.79";
  }

  smiv2:alias "cevAim4Dsps" {
    smiv2:oid "1.3.6.1.4.1.9.12.3.1.9.3.81";
  }

  smiv2:alias "cevHdaNm4fxs" {
    smiv2:oid "1.3.6.1.4.1.9.12.3.1.9.3.82";
  }

  smiv2:alias "cevC2610M" {
    smiv2:oid "1.3.6.1.4.1.9.12.3.1.9.3.84";
  }

  smiv2:alias "cevC2611M" {
    smiv2:oid "1.3.6.1.4.1.9.12.3.1.9.3.85";
  }

  smiv2:alias "cevNm1t3e3" {
    smiv2:oid "1.3.6.1.4.1.9.12.3.1.9.3.91";
  }

  smiv2:alias "cevNm1ct3e3" {
    smiv2:oid "1.3.6.1.4.1.9.12.3.1.9.3.92";
  }

  smiv2:alias "cevNm8ct1e1" {
    smiv2:oid "1.3.6.1.4.1.9.12.3.1.9.3.93";
  }

  smiv2:alias "cevHdaEm4fxo" {
    smiv2:oid "1.3.6.1.4.1.9.12.3.1.9.3.94";
  }

  smiv2:alias "cevNm16AS" {
    smiv2:oid "1.3.6.1.4.1.9.12.3.1.9.3.95";
  }

  smiv2:alias "cevNm1ct1e1Pri" {
    smiv2:oid "1.3.6.1.4.1.9.12.3.1.9.3.102";
  }

  smiv2:alias "cevNm2ct1e1Pri" {
    smiv2:oid "1.3.6.1.4.1.9.12.3.1.9.3.103";
  }

  smiv2:alias "cevNmCeoip4t1e1" {
    smiv2:oid "1.3.6.1.4.1.9.12.3.1.9.3.104";
  }

  smiv2:alias "cevNmCeoip4Serial" {
    smiv2:oid "1.3.6.1.4.1.9.12.3.1.9.3.105";
  }

  smiv2:alias "cevNm1aOc3mmEp" {
    smiv2:oid "1.3.6.1.4.1.9.12.3.1.9.3.106";
  }

  smiv2:alias "cevNm1aOc3smiEp" {
    smiv2:oid "1.3.6.1.4.1.9.12.3.1.9.3.107";
  }

  smiv2:alias "cevNm1aOc3smlEp" {
    smiv2:oid "1.3.6.1.4.1.9.12.3.1.9.3.108";
  }

  smiv2:alias "cevNmCids" {
    smiv2:oid "1.3.6.1.4.1.9.12.3.1.9.3.109";
  }

  smiv2:alias "cevHwic1GeSfp" {
    smiv2:oid "1.3.6.1.4.1.9.12.3.1.9.3.119";
  }

  smiv2:alias "cevPortHdDsp" {
    smiv2:oid "1.3.6.1.4.1.9.12.3.1.9.3.120";
  }

  smiv2:alias "cevHdv2port0" {
    smiv2:oid "1.3.6.1.4.1.9.12.3.1.9.3.121";
  }

  smiv2:alias "cevHdv2port2" {
    smiv2:oid "1.3.6.1.4.1.9.12.3.1.9.3.122";
  }

  smiv2:alias "cevHdv2port1" {
    smiv2:oid "1.3.6.1.4.1.9.12.3.1.9.3.123";
  }

  smiv2:alias "cevNmAtm25" {
    smiv2:oid "1.3.6.1.4.1.9.12.3.1.9.3.124";
  }

  smiv2:alias "cevNmNam" {
    smiv2:oid "1.3.6.1.4.1.9.12.3.1.9.3.125";
  }

  smiv2:alias "cevNm8amV2" {
    smiv2:oid "1.3.6.1.4.1.9.12.3.1.9.3.126";
  }

  smiv2:alias "cevNm16amV2" {
    smiv2:oid "1.3.6.1.4.1.9.12.3.1.9.3.127";
  }

  smiv2:alias "cevCpuC28112fe" {
    smiv2:oid "1.3.6.1.4.1.9.12.3.1.9.3.129";
  }

  smiv2:alias "cevCpuC28212ge" {
    smiv2:oid "1.3.6.1.4.1.9.12.3.1.9.3.130";
  }

  smiv2:alias "cevCpuC28512ge" {
    smiv2:oid "1.3.6.1.4.1.9.12.3.1.9.3.131";
  }

  smiv2:alias "cevHWicSerial4t" {
    smiv2:oid "1.3.6.1.4.1.9.12.3.1.9.3.132";
  }

  smiv2:alias "cevHWicSerial4as" {
    smiv2:oid "1.3.6.1.4.1.9.12.3.1.9.3.133";
  }

  smiv2:alias "cevHWicSerial8as" {
    smiv2:oid "1.3.6.1.4.1.9.12.3.1.9.3.134";
  }

  smiv2:alias "cevHWicSerial8a" {
    smiv2:oid "1.3.6.1.4.1.9.12.3.1.9.3.135";
  }

  smiv2:alias "cevHWicSerial16a" {
    smiv2:oid "1.3.6.1.4.1.9.12.3.1.9.3.136";
  }

  smiv2:alias "cevNm1AOc3Pom" {
    smiv2:oid "1.3.6.1.4.1.9.12.3.1.9.3.137";
  }

  smiv2:alias "cevHWic1DOCSIS20CableModem" {
    smiv2:oid "1.3.6.1.4.1.9.12.3.1.9.3.146";
  }

  smiv2:alias "cevNm8ce1t1Pri" {
    smiv2:oid "1.3.6.1.4.1.9.12.3.1.9.3.148";
  }

  smiv2:alias "cevHWic4t1e1" {
    smiv2:oid "1.3.6.1.4.1.9.12.3.1.9.3.149";
  }

  smiv2:alias "cevHWic2ce1t1Pri" {
    smiv2:oid "1.3.6.1.4.1.9.12.3.1.9.3.150";
  }

  smiv2:alias "cevHWic1ce1t1Pri" {
    smiv2:oid "1.3.6.1.4.1.9.12.3.1.9.3.151";
  }

  smiv2:alias "cevHWic1DOCSIS20CableModemEJ" {
    smiv2:oid "1.3.6.1.4.1.9.12.3.1.9.3.152";
  }

  smiv2:alias "cevHwic1t1e1" {
    smiv2:oid "1.3.6.1.4.1.9.12.3.1.9.3.154";
  }

  smiv2:alias "cevHwic4Shdsl" {
    smiv2:oid "1.3.6.1.4.1.9.12.3.1.9.3.157";
  }

  smiv2:alias "cevHwic2Shdsl" {
    smiv2:oid "1.3.6.1.4.1.9.12.3.1.9.3.158";
  }

  smiv2:alias "cevNmRvpnSterra" {
    smiv2:oid "1.3.6.1.4.1.9.12.3.1.9.3.159";
  }

  smiv2:alias "cevNmRvpn" {
    smiv2:oid "1.3.6.1.4.1.9.12.3.1.9.3.160";
  }

  smiv2:alias "cevNmSpclSrvcEng" {
    smiv2:oid "1.3.6.1.4.1.9.12.3.1.9.3.161";
  }

  smiv2:alias "cevNmIntgrtdSrvcEng2" {
    smiv2:oid "1.3.6.1.4.1.9.12.3.1.9.3.162";
  }

  smiv2:alias "cevHWIC1Ser" {
    smiv2:oid "1.3.6.1.4.1.9.12.3.1.9.3.163";
  }

  smiv2:alias "cevHWIC2Ser" {
    smiv2:oid "1.3.6.1.4.1.9.12.3.1.9.3.164";
  }

  smiv2:alias "cevInternalServiceModuleAIM" {
    smiv2:oid "1.3.6.1.4.1.9.12.3.1.9.3.165";
  }

  smiv2:alias "cevSm1nm" {
    smiv2:oid "1.3.6.1.4.1.9.12.3.1.9.3.167";
  }

  smiv2:alias "cevSm2k15Es1GePoe" {
    smiv2:oid "1.3.6.1.4.1.9.12.3.1.9.3.168";
  }

  smiv2:alias "cevSm3k15Es1GePoe" {
    smiv2:oid "1.3.6.1.4.1.9.12.3.1.9.3.169";
  }

  smiv2:alias "cevSm3k16GePoe" {
    smiv2:oid "1.3.6.1.4.1.9.12.3.1.9.3.170";
  }

  smiv2:alias "cevSm2k23Es1Ge" {
    smiv2:oid "1.3.6.1.4.1.9.12.3.1.9.3.171";
  }

  smiv2:alias "cevSm2k23Es1GePoe" {
    smiv2:oid "1.3.6.1.4.1.9.12.3.1.9.3.172";
  }

  smiv2:alias "cevSm3k23Es1GePoe" {
    smiv2:oid "1.3.6.1.4.1.9.12.3.1.9.3.173";
  }

  smiv2:alias "cevSm3k24GePoe" {
    smiv2:oid "1.3.6.1.4.1.9.12.3.1.9.3.174";
  }

  smiv2:alias "cevSmXd2k48Es2SFP" {
    smiv2:oid "1.3.6.1.4.1.9.12.3.1.9.3.175";
  }

  smiv2:alias "cevSmXd3k48Es2SFPPoe" {
    smiv2:oid "1.3.6.1.4.1.9.12.3.1.9.3.176";
  }

  smiv2:alias "cevSmXd3k48Ge2SFPPoe" {
    smiv2:oid "1.3.6.1.4.1.9.12.3.1.9.3.177";
  }

  smiv2:alias "cevHwic4ce1t1Pri" {
    smiv2:oid "1.3.6.1.4.1.9.12.3.1.9.3.180";
  }

  smiv2:alias "cevEHwic1GeSfpCu" {
    smiv2:oid "1.3.6.1.4.1.9.12.3.1.9.3.181";
  }

  smiv2:alias "cevEhwic3gEvdo" {
    smiv2:oid "1.3.6.1.4.1.9.12.3.1.9.3.182";
  }

  smiv2:alias "cevEhwic3gHspaU" {
    smiv2:oid "1.3.6.1.4.1.9.12.3.1.9.3.183";
  }

  smiv2:alias "cevSm1pa" {
    smiv2:oid "1.3.6.1.4.1.9.12.3.1.9.3.184";
  }

  smiv2:alias "cevSm1Stm1Smi" {
    smiv2:oid "1.3.6.1.4.1.9.12.3.1.9.3.185";
  }

  smiv2:alias "cevSm1Stm1Mm" {
    smiv2:oid "1.3.6.1.4.1.9.12.3.1.9.3.186";
  }

  smiv2:alias "cevEhwic3gHspa7" {
    smiv2:oid "1.3.6.1.4.1.9.12.3.1.9.3.187";
  }

  smiv2:alias "cevIsmVpnSsl3" {
    smiv2:oid "1.3.6.1.4.1.9.12.3.1.9.3.188";
  }

  smiv2:alias "cevIsmVpnSsl2" {
    smiv2:oid "1.3.6.1.4.1.9.12.3.1.9.3.189";
  }

  smiv2:alias "cevIsmVpnSsl1" {
    smiv2:oid "1.3.6.1.4.1.9.12.3.1.9.3.190";
  }

  smiv2:alias "cevEhwic3gHspa7A" {
    smiv2:oid "1.3.6.1.4.1.9.12.3.1.9.3.191";
  }

  smiv2:alias "cevEhwic4gLteA" {
    smiv2:oid "1.3.6.1.4.1.9.12.3.1.9.3.193";
  }

  smiv2:alias "cevEhwic4gLteG" {
    smiv2:oid "1.3.6.1.4.1.9.12.3.1.9.3.194";
  }

  smiv2:alias "cevEhwic4gLteV" {
    smiv2:oid "1.3.6.1.4.1.9.12.3.1.9.3.195";
  }

  smiv2:alias "cevSm1T3E3" {
    smiv2:oid "1.3.6.1.4.1.9.12.3.1.9.3.196";
  }

  smiv2:alias "cevSM32A" {
    smiv2:oid "1.3.6.1.4.1.9.12.3.1.9.3.197";
  }

  smiv2:alias "cevSmD48FxsE" {
    smiv2:oid "1.3.6.1.4.1.9.12.3.1.9.3.202";
  }

  smiv2:alias "cevSmD72Fxs" {
    smiv2:oid "1.3.6.1.4.1.9.12.3.1.9.3.203";
  }

  smiv2:alias "cevNgsmXd3k48ge2sfpPoeplus" {
    smiv2:oid "1.3.6.1.4.1.9.12.3.1.9.3.206";
  }

  smiv2:alias "cevNgsm3k24gePoeplus" {
    smiv2:oid "1.3.6.1.4.1.9.12.3.1.9.3.207";
  }

  smiv2:alias "cevNgsm3k16gePoeplus" {
    smiv2:oid "1.3.6.1.4.1.9.12.3.1.9.3.208";
  }

  smiv2:alias "cevGrwicSerial4t" {
    smiv2:oid "1.3.6.1.4.1.9.12.3.1.9.3.209";
  }

  smiv2:alias "cevEhwic4gLteJp" {
    smiv2:oid "1.3.6.1.4.1.9.12.3.1.9.3.210";
  }

  smiv2:alias "cevEhwic4gLteBe" {
    smiv2:oid "1.3.6.1.4.1.9.12.3.1.9.3.211";
  }

  smiv2:alias "cevPEhwic1GeSfpCu" {
    smiv2:oid "1.3.6.1.4.1.9.12.3.1.9.3.212";
  }

  smiv2:alias "cevPEhwic3gHspa7" {
    smiv2:oid "1.3.6.1.4.1.9.12.3.1.9.3.213";
  }

  smiv2:alias "cevPHwicSerial16a" {
    smiv2:oid "1.3.6.1.4.1.9.12.3.1.9.3.214";
  }

  smiv2:alias "cevPhwic1Ce1T1Pri" {
    smiv2:oid "1.3.6.1.4.1.9.12.3.1.9.3.215";
  }

  smiv2:alias "cevPHwic2Ce1t1Pri" {
    smiv2:oid "1.3.6.1.4.1.9.12.3.1.9.3.216";
  }

  smiv2:alias "cevPHwicSerial4As" {
    smiv2:oid "1.3.6.1.4.1.9.12.3.1.9.3.217";
  }

  smiv2:alias "cevPHwicSerial4t" {
    smiv2:oid "1.3.6.1.4.1.9.12.3.1.9.3.218";
  }

  smiv2:alias "cevPHwic4T1E1" {
    smiv2:oid "1.3.6.1.4.1.9.12.3.1.9.3.219";
  }

  smiv2:alias "cevPHwicSerial8a" {
    smiv2:oid "1.3.6.1.4.1.9.12.3.1.9.3.220";
  }

  smiv2:alias "cevPHwicSerial8as" {
    smiv2:oid "1.3.6.1.4.1.9.12.3.1.9.3.221";
  }

  smiv2:alias "cevPIsmVpn29" {
    smiv2:oid "1.3.6.1.4.1.9.12.3.1.9.3.222";
  }

  smiv2:alias "cevPVic2Fxo2" {
    smiv2:oid "1.3.6.1.4.1.9.12.3.1.9.3.223";
  }

  smiv2:alias "cevPVic2Fxo4" {
    smiv2:oid "1.3.6.1.4.1.9.12.3.1.9.3.224";
  }

  smiv2:alias "cevPSm2k23Es1Ge" {
    smiv2:oid "1.3.6.1.4.1.9.12.3.1.9.3.225";
  }

  smiv2:alias "cevPSm3k16GePoe" {
    smiv2:oid "1.3.6.1.4.1.9.12.3.1.9.3.226";
  }

  smiv2:alias "cevPSmXd2k48Es2SFP" {
    smiv2:oid "1.3.6.1.4.1.9.12.3.1.9.3.227";
  }

  smiv2:alias "cevPSmXd3k48Es2SFPPoe" {
    smiv2:oid "1.3.6.1.4.1.9.12.3.1.9.3.228";
  }

  smiv2:alias "cevPSmXd3k48Ge2SFPPoe" {
    smiv2:oid "1.3.6.1.4.1.9.12.3.1.9.3.229";
  }

  smiv2:alias "cevPSm2k15Es1GePoe" {
    smiv2:oid "1.3.6.1.4.1.9.12.3.1.9.3.230";
  }

  smiv2:alias "cevPSm2k23Es1GePoe" {
    smiv2:oid "1.3.6.1.4.1.9.12.3.1.9.3.231";
  }

  smiv2:alias "cevPSm3k15Es1GePoe" {
    smiv2:oid "1.3.6.1.4.1.9.12.3.1.9.3.232";
  }

  smiv2:alias "cevPSm3k23Es1GePoe" {
    smiv2:oid "1.3.6.1.4.1.9.12.3.1.9.3.233";
  }

  smiv2:alias "cevPSm3k24GePoe" {
    smiv2:oid "1.3.6.1.4.1.9.12.3.1.9.3.234";
  }

  smiv2:alias "cevPSm1nm" {
    smiv2:oid "1.3.6.1.4.1.9.12.3.1.9.3.235";
  }

  smiv2:alias "cevPHdv2port2" {
    smiv2:oid "1.3.6.1.4.1.9.12.3.1.9.3.236";
  }

  smiv2:alias "cevModuleVipPortAdapters" {
    smiv2:oid "1.3.6.1.4.1.9.12.3.1.9.4";
  }

  smiv2:alias "cevPa1fe" {
    smiv2:oid "1.3.6.1.4.1.9.12.3.1.9.4.1";
  }

  smiv2:alias "cevPa8e" {
    smiv2:oid "1.3.6.1.4.1.9.12.3.1.9.4.2";
  }

  smiv2:alias "cevPa4e" {
    smiv2:oid "1.3.6.1.4.1.9.12.3.1.9.4.3";
  }

  smiv2:alias "cevPa5e" {
    smiv2:oid "1.3.6.1.4.1.9.12.3.1.9.4.4";
  }

  smiv2:alias "cevPa4t" {
    smiv2:oid "1.3.6.1.4.1.9.12.3.1.9.4.5";
  }

  smiv2:alias "cevPa4r" {
    smiv2:oid "1.3.6.1.4.1.9.12.3.1.9.4.6";
  }

  smiv2:alias "cevPaFddi" {
    smiv2:oid "1.3.6.1.4.1.9.12.3.1.9.4.7";
  }

  smiv2:alias "cevSaEncryption" {
    smiv2:oid "1.3.6.1.4.1.9.12.3.1.9.4.8";
  }

  smiv2:alias "cevPaAh1t" {
    smiv2:oid "1.3.6.1.4.1.9.12.3.1.9.4.9";
  }

  smiv2:alias "cevPaAh2t" {
    smiv2:oid "1.3.6.1.4.1.9.12.3.1.9.4.10";
  }

  smiv2:alias "cevPaA8tV35" {
    smiv2:oid "1.3.6.1.4.1.9.12.3.1.9.4.12";
  }

  smiv2:alias "cevPa1feTxIsl" {
    smiv2:oid "1.3.6.1.4.1.9.12.3.1.9.4.13";
  }

  smiv2:alias "cevPa1feFxIsl" {
    smiv2:oid "1.3.6.1.4.1.9.12.3.1.9.4.14";
  }

  smiv2:alias "cevPa1feTxNisl" {
    smiv2:oid "1.3.6.1.4.1.9.12.3.1.9.4.15";
  }

  smiv2:alias "cevSaCompression" {
    smiv2:oid "1.3.6.1.4.1.9.12.3.1.9.4.16";
  }

  smiv2:alias "cevPaAtmLite1" {
    smiv2:oid "1.3.6.1.4.1.9.12.3.1.9.4.17";
  }

  smiv2:alias "cevPaCt3" {
    smiv2:oid "1.3.6.1.4.1.9.12.3.1.9.4.18";
  }

  smiv2:alias "cevPaOc3smMuxCbrt1" {
    smiv2:oid "1.3.6.1.4.1.9.12.3.1.9.4.19";
  }

  smiv2:alias "cevPaOc3smMuxCbr120e1" {
    smiv2:oid "1.3.6.1.4.1.9.12.3.1.9.4.20";
  }

  smiv2:alias "cevPaOc3smMuxCbr75e1" {
    smiv2:oid "1.3.6.1.4.1.9.12.3.1.9.4.21";
  }

  smiv2:alias "cevPaOc3mmMuxCbrt1" {
    smiv2:oid "1.3.6.1.4.1.9.12.3.1.9.4.22";
  }

  smiv2:alias "cevPaOc3mmMuxCbr120e1" {
    smiv2:oid "1.3.6.1.4.1.9.12.3.1.9.4.23";
  }

  smiv2:alias "cevPaOc3mmMuxCbr75e1" {
    smiv2:oid "1.3.6.1.4.1.9.12.3.1.9.4.24";
  }

  smiv2:alias "cevPaDs3MuxCbrt1" {
    smiv2:oid "1.3.6.1.4.1.9.12.3.1.9.4.25";
  }

  smiv2:alias "cevPaE3MuxCbr120e1" {
    smiv2:oid "1.3.6.1.4.1.9.12.3.1.9.4.26";
  }

  smiv2:alias "cevPaE3smMuxCbr75e1" {
    smiv2:oid "1.3.6.1.4.1.9.12.3.1.9.4.27";
  }

  smiv2:alias "cevPa8bSt" {
    smiv2:oid "1.3.6.1.4.1.9.12.3.1.9.4.28";
  }

  smiv2:alias "cevPa4bU" {
    smiv2:oid "1.3.6.1.4.1.9.12.3.1.9.4.29";
  }

  smiv2:alias "cevPaFddiFd" {
    smiv2:oid "1.3.6.1.4.1.9.12.3.1.9.4.30";
  }

  smiv2:alias "cevPaJt2" {
    smiv2:oid "1.3.6.1.4.1.9.12.3.1.9.4.31";
  }

  smiv2:alias "cevPaPosdw" {
    smiv2:oid "1.3.6.1.4.1.9.12.3.1.9.4.32";
  }

  smiv2:alias "cevPa4me1Bal" {
    smiv2:oid "1.3.6.1.4.1.9.12.3.1.9.4.33";
  }

  smiv2:alias "cevPa2ce1Balanced" {
    smiv2:oid "1.3.6.1.4.1.9.12.3.1.9.4.34";
  }

  smiv2:alias "cevPa2ct1" {
    smiv2:oid "1.3.6.1.4.1.9.12.3.1.9.4.35";
  }

  smiv2:alias "cevPa1vg" {
    smiv2:oid "1.3.6.1.4.1.9.12.3.1.9.4.36";
  }

  smiv2:alias "cevPaAtmdxDs3" {
    smiv2:oid "1.3.6.1.4.1.9.12.3.1.9.4.37";
  }

  smiv2:alias "cevPaAtmdxE3" {
    smiv2:oid "1.3.6.1.4.1.9.12.3.1.9.4.38";
  }

  smiv2:alias "cevPaAtmdxSmlOc3" {
    smiv2:oid "1.3.6.1.4.1.9.12.3.1.9.4.39";
  }

  smiv2:alias "cevPaAtmdxSmiOc3" {
    smiv2:oid "1.3.6.1.4.1.9.12.3.1.9.4.40";
  }

  smiv2:alias "cevPaAtmdxMmOc3" {
    smiv2:oid "1.3.6.1.4.1.9.12.3.1.9.4.41";
  }

  smiv2:alias "cevPaA8tX21" {
    smiv2:oid "1.3.6.1.4.1.9.12.3.1.9.4.42";
  }

  smiv2:alias "cevPaA8tRs232" {
    smiv2:oid "1.3.6.1.4.1.9.12.3.1.9.4.43";
  }

  smiv2:alias "cevPa4me1Unbal" {
    smiv2:oid "1.3.6.1.4.1.9.12.3.1.9.4.44";
  }

  smiv2:alias "cevPa4rFdx" {
    smiv2:oid "1.3.6.1.4.1.9.12.3.1.9.4.45";
  }

  smiv2:alias "cevPa1e3" {
    smiv2:oid "1.3.6.1.4.1.9.12.3.1.9.4.46";
  }

  smiv2:alias "cevPa2e3" {
    smiv2:oid "1.3.6.1.4.1.9.12.3.1.9.4.47";
  }

  smiv2:alias "cevPa1t3" {
    smiv2:oid "1.3.6.1.4.1.9.12.3.1.9.4.48";
  }

  smiv2:alias "cevPa2t3" {
    smiv2:oid "1.3.6.1.4.1.9.12.3.1.9.4.49";
  }

  smiv2:alias "cevPa2ce1Unbalanced" {
    smiv2:oid "1.3.6.1.4.1.9.12.3.1.9.4.50";
  }

  smiv2:alias "cevPa14eSwitch" {
    smiv2:oid "1.3.6.1.4.1.9.12.3.1.9.4.51";
  }

  smiv2:alias "cevas58001fedsi" {
    smiv2:oid "1.3.6.1.4.1.9.12.3.1.9.4.52";
  }

  smiv2:alias "cevPa1feFxNisl" {
    smiv2:oid "1.3.6.1.4.1.9.12.3.1.9.4.53";
  }

  smiv2:alias "cevPaIo1fe" {
    smiv2:oid "1.3.6.1.4.1.9.12.3.1.9.4.54";
  }

  smiv2:alias "cevPaIo" {
    smiv2:oid "1.3.6.1.4.1.9.12.3.1.9.4.55";
  }

  smiv2:alias "cevPa2feTx" {
    smiv2:oid "1.3.6.1.4.1.9.12.3.1.9.4.56";
  }

  smiv2:alias "cevPa2feFx" {
    smiv2:oid "1.3.6.1.4.1.9.12.3.1.9.4.57";
  }

  smiv2:alias "cevPaGe" {
    smiv2:oid "1.3.6.1.4.1.9.12.3.1.9.4.59";
  }

  smiv2:alias "cevPaPosswSm" {
    smiv2:oid "1.3.6.1.4.1.9.12.3.1.9.4.60";
  }

  smiv2:alias "cevPaPosswMm" {
    smiv2:oid "1.3.6.1.4.1.9.12.3.1.9.4.61";
  }

  smiv2:alias "cevPaPosswLr" {
    smiv2:oid "1.3.6.1.4.1.9.12.3.1.9.4.62";
  }

  smiv2:alias "cevPa4ct1Csu" {
    smiv2:oid "1.3.6.1.4.1.9.12.3.1.9.4.63";
  }

  smiv2:alias "cevPa8ct1Csu" {
    smiv2:oid "1.3.6.1.4.1.9.12.3.1.9.4.64";
  }

  smiv2:alias "cevPa8ct1" {
    smiv2:oid "1.3.6.1.4.1.9.12.3.1.9.4.65";
  }

  smiv2:alias "cevPa8ce1" {
    smiv2:oid "1.3.6.1.4.1.9.12.3.1.9.4.66";
  }

  smiv2:alias "cevPaVxc2t1e1" {
    smiv2:oid "1.3.6.1.4.1.9.12.3.1.9.4.67";
  }

  smiv2:alias "cevPaVxb2t1e1" {
    smiv2:oid "1.3.6.1.4.1.9.12.3.1.9.4.68";
  }

  smiv2:alias "cevPaAtmOc12Mm" {
    smiv2:oid "1.3.6.1.4.1.9.12.3.1.9.4.69";
  }

  smiv2:alias "cevPaAtmOc12Smi" {
    smiv2:oid "1.3.6.1.4.1.9.12.3.1.9.4.70";
  }

  smiv2:alias "cevPaMct3" {
    smiv2:oid "1.3.6.1.4.1.9.12.3.1.9.4.71";
  }

  smiv2:alias "cevPaMc2t3" {
    smiv2:oid "1.3.6.1.4.1.9.12.3.1.9.4.72";
  }

  smiv2:alias "cevPa1t3Plus" {
    smiv2:oid "1.3.6.1.4.1.9.12.3.1.9.4.73";
  }

  smiv2:alias "cevPa2t3Plus" {
    smiv2:oid "1.3.6.1.4.1.9.12.3.1.9.4.74";
  }

  smiv2:alias "cevPaPosOc12Mm" {
    smiv2:oid "1.3.6.1.4.1.9.12.3.1.9.4.75";
  }

  smiv2:alias "cevPaPosOc12Sm" {
    smiv2:oid "1.3.6.1.4.1.9.12.3.1.9.4.76";
  }

  smiv2:alias "cevPaImaT1" {
    smiv2:oid "1.3.6.1.4.1.9.12.3.1.9.4.77";
  }

  smiv2:alias "cevPaImaE1" {
    smiv2:oid "1.3.6.1.4.1.9.12.3.1.9.4.78";
  }

  smiv2:alias "cevSrpPaOc12Mm" {
    smiv2:oid "1.3.6.1.4.1.9.12.3.1.9.4.79";
  }

  smiv2:alias "cevSrpPaOc12SmIr" {
    smiv2:oid "1.3.6.1.4.1.9.12.3.1.9.4.80";
  }

  smiv2:alias "cevSrpPaOc12Lr" {
    smiv2:oid "1.3.6.1.4.1.9.12.3.1.9.4.81";
  }

  smiv2:alias "cevPa2ct1Csu" {
    smiv2:oid "1.3.6.1.4.1.9.12.3.1.9.4.82";
  }

  smiv2:alias "cevPa2ce1" {
    smiv2:oid "1.3.6.1.4.1.9.12.3.1.9.4.83";
  }

  smiv2:alias "cevPaMcx2te1" {
    smiv2:oid "1.3.6.1.4.1.9.12.3.1.9.4.84";
  }

  smiv2:alias "cevPaMcx4te1" {
    smiv2:oid "1.3.6.1.4.1.9.12.3.1.9.4.85";
  }

  smiv2:alias "cevPaMcx8te1" {
    smiv2:oid "1.3.6.1.4.1.9.12.3.1.9.4.86";
  }

  smiv2:alias "cevSrpPaOc12SmXr" {
    smiv2:oid "1.3.6.1.4.1.9.12.3.1.9.4.87";
  }

  smiv2:alias "cevPaMcStm1Smi" {
    smiv2:oid "1.3.6.1.4.1.9.12.3.1.9.4.90";
  }

  smiv2:alias "cevPaMcStm1Mm" {
    smiv2:oid "1.3.6.1.4.1.9.12.3.1.9.4.91";
  }

  smiv2:alias "cevPa2feTxI82543" {
    smiv2:oid "1.3.6.1.4.1.9.12.3.1.9.4.92";
  }

  smiv2:alias "cevPa2feFxI82543" {
    smiv2:oid "1.3.6.1.4.1.9.12.3.1.9.4.93";
  }

  smiv2:alias "cevPaDualWideGe" {
    smiv2:oid "1.3.6.1.4.1.9.12.3.1.9.4.94";
  }

  smiv2:alias "cevPaVxa1T1E124" {
    smiv2:oid "1.3.6.1.4.1.9.12.3.1.9.4.95";
  }

  smiv2:alias "cevPaVxa1T1E130" {
    smiv2:oid "1.3.6.1.4.1.9.12.3.1.9.4.96";
  }

  smiv2:alias "cevPaMcT1E1" {
    smiv2:oid "1.3.6.1.4.1.9.12.3.1.9.4.97";
  }

  smiv2:alias "cevPaMcx8te1M" {
    smiv2:oid "1.3.6.1.4.1.9.12.3.1.9.4.99";
  }

  smiv2:alias "cevPa1ce3" {
    smiv2:oid "1.3.6.1.4.1.9.12.3.1.9.4.100";
  }

  smiv2:alias "cevPa2OC3PosSw" {
    smiv2:oid "1.3.6.1.4.1.9.12.3.1.9.4.101";
  }

  smiv2:alias "cevPa2feFxIsl" {
    smiv2:oid "1.3.6.1.4.1.9.12.3.1.9.4.102";
  }

  smiv2:alias "cevPa4Dtr" {
    smiv2:oid "1.3.6.1.4.1.9.12.3.1.9.4.103";
  }

  smiv2:alias "cevPaVmHda8FxsDid" {
    smiv2:oid "1.3.6.1.4.1.9.12.3.1.9.4.104";
  }

  smiv2:alias "cevPa1OC3PosSw" {
    smiv2:oid "1.3.6.1.4.1.9.12.3.1.9.4.105";
  }

  smiv2:alias "cevPaA6mmOc3" {
    smiv2:oid "1.3.6.1.4.1.9.12.3.1.9.4.106";
  }

  smiv2:alias "cevPaA6SmiOc3" {
    smiv2:oid "1.3.6.1.4.1.9.12.3.1.9.4.107";
  }

  smiv2:alias "cevPaA6SmlOc3" {
    smiv2:oid "1.3.6.1.4.1.9.12.3.1.9.4.108";
  }

  smiv2:alias "cevPaA6Ds3" {
    smiv2:oid "1.3.6.1.4.1.9.12.3.1.9.4.109";
  }

  smiv2:alias "cevPaA6E3" {
    smiv2:oid "1.3.6.1.4.1.9.12.3.1.9.4.110";
  }

  smiv2:alias "cevPaMcx4te1Q" {
    smiv2:oid "1.3.6.1.4.1.9.12.3.1.9.4.111";
  }

  smiv2:alias "cevPaMct3ec" {
    smiv2:oid "1.3.6.1.4.1.9.12.3.1.9.4.112";
  }

  smiv2:alias "cevPaMc2t3ec" {
    smiv2:oid "1.3.6.1.4.1.9.12.3.1.9.4.113";
  }

  smiv2:alias "cevPa1t3e3ec" {
    smiv2:oid "1.3.6.1.4.1.9.12.3.1.9.4.114";
  }

  smiv2:alias "cevPa2t3e3ec" {
    smiv2:oid "1.3.6.1.4.1.9.12.3.1.9.4.115";
  }

  smiv2:alias "cevModuleCpuType" {
    smiv2:oid "1.3.6.1.4.1.9.12.3.1.9.5";
  }

  smiv2:alias "cevC7200Io1fe" {
    smiv2:oid "1.3.6.1.4.1.9.12.3.1.9.5.1";
  }

  smiv2:alias "cevC7200Io" {
    smiv2:oid "1.3.6.1.4.1.9.12.3.1.9.5.2";
  }

  smiv2:alias "cevCpuAS5300" {
    smiv2:oid "1.3.6.1.4.1.9.12.3.1.9.5.3";
  }

  smiv2:alias "cevCpuRpm" {
    smiv2:oid "1.3.6.1.4.1.9.12.3.1.9.5.7";
  }

  smiv2:alias "cevCpu2600" {
    smiv2:oid "1.3.6.1.4.1.9.12.3.1.9.5.8";
  }

  smiv2:alias "cevCpu7200Npe300" {
    smiv2:oid "1.3.6.1.4.1.9.12.3.1.9.5.9";
  }

  smiv2:alias "cevCpu1400" {
    smiv2:oid "1.3.6.1.4.1.9.12.3.1.9.5.10";
  }

  smiv2:alias "cevCpu800" {
    smiv2:oid "1.3.6.1.4.1.9.12.3.1.9.5.11";
  }

  smiv2:alias "cevCpuPSM1Gbps" {
    smiv2:oid "1.3.6.1.4.1.9.12.3.1.9.5.12";
  }

  smiv2:alias "cevCpu7200Npe175" {
    smiv2:oid "1.3.6.1.4.1.9.12.3.1.9.5.14";
  }

  smiv2:alias "cevCpu7200Npe225" {
    smiv2:oid "1.3.6.1.4.1.9.12.3.1.9.5.15";
  }

  smiv2:alias "cevCpu1417" {
    smiv2:oid "1.3.6.1.4.1.9.12.3.1.9.5.17";
  }

  smiv2:alias "cevCpuPsm11oc12" {
    smiv2:oid "1.3.6.1.4.1.9.12.3.1.9.5.18";
  }

  smiv2:alias "cevCpuOpticalRegenerator" {
    smiv2:oid "1.3.6.1.4.1.9.12.3.1.9.5.19";
  }

  smiv2:alias "cevCpuUbr924" {
    smiv2:oid "1.3.6.1.4.1.9.12.3.1.9.5.20";
  }

  smiv2:alias "cevCpu7120" {
    smiv2:oid "1.3.6.1.4.1.9.12.3.1.9.5.21";
  }

  smiv2:alias "cevCpu7140" {
    smiv2:oid "1.3.6.1.4.1.9.12.3.1.9.5.22";
  }

  smiv2:alias "cevCpuPsm12t3e3" {
    smiv2:oid "1.3.6.1.4.1.9.12.3.1.9.5.23";
  }

  smiv2:alias "cevCpuPsm14oc3" {
    smiv2:oid "1.3.6.1.4.1.9.12.3.1.9.5.24";
  }

  smiv2:alias "cevCpu7200Npe100" {
    smiv2:oid "1.3.6.1.4.1.9.12.3.1.9.5.26";
  }

  smiv2:alias "cevCpu7200Npe150" {
    smiv2:oid "1.3.6.1.4.1.9.12.3.1.9.5.27";
  }

  smiv2:alias "cevCpu7200Npe200" {
    smiv2:oid "1.3.6.1.4.1.9.12.3.1.9.5.28";
  }

  smiv2:alias "cevCpuCreRp" {
    smiv2:oid "1.3.6.1.4.1.9.12.3.1.9.5.29";
  }

  smiv2:alias "cevCpuCreFp" {
    smiv2:oid "1.3.6.1.4.1.9.12.3.1.9.5.30";
  }

  smiv2:alias "cevCpuAs5400" {
    smiv2:oid "1.3.6.1.4.1.9.12.3.1.9.5.31";
  }

  smiv2:alias "cevCpuAS5200" {
    smiv2:oid "1.3.6.1.4.1.9.12.3.1.9.5.34";
  }

  smiv2:alias "cevCpuGrp" {
    smiv2:oid "1.3.6.1.4.1.9.12.3.1.9.5.35";
  }

  smiv2:alias "cevCpuMc3810V3" {
    smiv2:oid "1.3.6.1.4.1.9.12.3.1.9.5.36";
  }

  smiv2:alias "cevCpuAs5850" {
    smiv2:oid "1.3.6.1.4.1.9.12.3.1.9.5.38";
  }

  smiv2:alias "cevCpu7200Npe400" {
    smiv2:oid "1.3.6.1.4.1.9.12.3.1.9.5.39";
  }

  smiv2:alias "cevCpuAs5350" {
    smiv2:oid "1.3.6.1.4.1.9.12.3.1.9.5.40";
  }

  smiv2:alias "cevCpuRsp4Plus" {
    smiv2:oid "1.3.6.1.4.1.9.12.3.1.9.5.41";
  }

  smiv2:alias "cevCpuUbr91x" {
    smiv2:oid "1.3.6.1.4.1.9.12.3.1.9.5.42";
  }

  smiv2:alias "cevCpu7150" {
    smiv2:oid "1.3.6.1.4.1.9.12.3.1.9.5.43";
  }

  smiv2:alias "cevCpuPXMB45Gbps" {
    smiv2:oid "1.3.6.1.4.1.9.12.3.1.9.5.44";
  }

  smiv2:alias "cevCpuONS15540" {
    smiv2:oid "1.3.6.1.4.1.9.12.3.1.9.5.47";
  }

  smiv2:alias "cevCpuRsp16" {
    smiv2:oid "1.3.6.1.4.1.9.12.3.1.9.5.48";
  }

  smiv2:alias "cevCpuPrp1" {
    smiv2:oid "1.3.6.1.4.1.9.12.3.1.9.5.49";
  }

  smiv2:alias "cevCpuC7300Nse100" {
    smiv2:oid "1.3.6.1.4.1.9.12.3.1.9.5.50";
  }

  smiv2:alias "cevCpuPXM1E1Gbps" {
    smiv2:oid "1.3.6.1.4.1.9.12.3.1.9.5.51";
  }

  smiv2:alias "cevCpuPXM1E2Oc12" {
    smiv2:oid "1.3.6.1.4.1.9.12.3.1.9.5.52";
  }

  smiv2:alias "cevCpuPXM1E8Oc3" {
    smiv2:oid "1.3.6.1.4.1.9.12.3.1.9.5.53";
  }

  smiv2:alias "cevCpuPXM1E8T3E3" {
    smiv2:oid "1.3.6.1.4.1.9.12.3.1.9.5.54";
  }

  smiv2:alias "cevCpuPXM1EComboT3E3Oc3" {
    smiv2:oid "1.3.6.1.4.1.9.12.3.1.9.5.55";
  }

  smiv2:alias "cevCpu7200Npeg1" {
    smiv2:oid "1.3.6.1.4.1.9.12.3.1.9.5.56";
  }

  smiv2:alias "cevCpu26912fe" {
    smiv2:oid "1.3.6.1.4.1.9.12.3.1.9.5.57";
  }

  smiv2:alias "cevCpu37452fe" {
    smiv2:oid "1.3.6.1.4.1.9.12.3.1.9.5.58";
  }

  smiv2:alias "cevCpu37252fe" {
    smiv2:oid "1.3.6.1.4.1.9.12.3.1.9.5.59";
  }

  smiv2:alias "cevCpu36311fe" {
    smiv2:oid "1.3.6.1.4.1.9.12.3.1.9.5.60";
  }

  smiv2:alias "cevCpu19002fe" {
    smiv2:oid "1.3.6.1.4.1.9.12.3.1.9.5.61";
  }

  smiv2:alias "cevCpuONS15530SW" {
    smiv2:oid "1.3.6.1.4.1.9.12.3.1.9.5.62";
  }

  smiv2:alias "cevCpu6400Nsp" {
    smiv2:oid "1.3.6.1.4.1.9.12.3.1.9.5.63";
  }

  smiv2:alias "cevCpu6400Nrp" {
    smiv2:oid "1.3.6.1.4.1.9.12.3.1.9.5.64";
  }

  smiv2:alias "cevCpu6400Nrp2" {
    smiv2:oid "1.3.6.1.4.1.9.12.3.1.9.5.65";
  }

  smiv2:alias "cevCpu6400Nrp2Sv" {
    smiv2:oid "1.3.6.1.4.1.9.12.3.1.9.5.66";
  }

  smiv2:alias "cevCpuPXM1E4Oc3" {
    smiv2:oid "1.3.6.1.4.1.9.12.3.1.9.5.67";
  }

  smiv2:alias "cevCpu1700" {
    smiv2:oid "1.3.6.1.4.1.9.12.3.1.9.5.68";
  }

  smiv2:alias "cevCpu7301Npeg1" {
    smiv2:oid "1.3.6.1.4.1.9.12.3.1.9.5.71";
  }

  smiv2:alias "cevCpuPXM1E16t1e1" {
    smiv2:oid "1.3.6.1.4.1.9.12.3.1.9.5.72";
  }

  smiv2:alias "cevCpu7300Nse100Plus" {
    smiv2:oid "1.3.6.1.4.1.9.12.3.1.9.5.73";
  }

  smiv2:alias "cevCpuPxm1eB8t3e34Oc3" {
    smiv2:oid "1.3.6.1.4.1.9.12.3.1.9.5.74";
  }

  smiv2:alias "cevCpu4604" {
    smiv2:oid "1.3.6.1.4.1.9.12.3.1.9.5.75";
  }

  smiv2:alias "cevCpu4224" {
    smiv2:oid "1.3.6.1.4.1.9.12.3.1.9.5.76";
  }

  smiv2:alias "cevCpuAs5400HPX" {
    smiv2:oid "1.3.6.1.4.1.9.12.3.1.9.5.77";
  }

  smiv2:alias "cevCpuAs5350HPX" {
    smiv2:oid "1.3.6.1.4.1.9.12.3.1.9.5.78";
  }

  smiv2:alias "cevCpuAs5850tb" {
    smiv2:oid "1.3.6.1.4.1.9.12.3.1.9.5.80";
  }

  smiv2:alias "cevCpuC7300Npeg100" {
    smiv2:oid "1.3.6.1.4.1.9.12.3.1.9.5.81";
  }

  smiv2:alias "cevCpuMdsCpp" {
    smiv2:oid "1.3.6.1.4.1.9.12.3.1.9.5.82";
  }

  smiv2:alias "cevCpuMdsDpp" {
    smiv2:oid "1.3.6.1.4.1.9.12.3.1.9.5.83";
  }

  smiv2:alias "cevCpuMdsSup" {
    smiv2:oid "1.3.6.1.4.1.9.12.3.1.9.5.84";
  }

  smiv2:alias "cevCpu2430Iad24Fxs" {
    smiv2:oid "1.3.6.1.4.1.9.12.3.1.9.5.85";
  }

  smiv2:alias "cevCpu2431Iad8Fxs" {
    smiv2:oid "1.3.6.1.4.1.9.12.3.1.9.5.86";
  }

  smiv2:alias "cevCpu2431Iad16Fxs" {
    smiv2:oid "1.3.6.1.4.1.9.12.3.1.9.5.87";
  }

  smiv2:alias "cevCpu2431Iad1T1E1" {
    smiv2:oid "1.3.6.1.4.1.9.12.3.1.9.5.88";
  }

  smiv2:alias "cevCpu2432Iad24Fxs" {
    smiv2:oid "1.3.6.1.4.1.9.12.3.1.9.5.89";
  }

  smiv2:alias "cevCpu3220" {
    smiv2:oid "1.3.6.1.4.1.9.12.3.1.9.5.90";
  }

  smiv2:alias "cevCpuVG224" {
    smiv2:oid "1.3.6.1.4.1.9.12.3.1.9.5.91";
  }

  smiv2:alias "cevCpuCat6kWsSup720RP" {
    smiv2:oid "1.3.6.1.4.1.9.12.3.1.9.5.92";
  }

  smiv2:alias "cevCpuCat6kMsfc" {
    smiv2:oid "1.3.6.1.4.1.9.12.3.1.9.5.93";
  }

  smiv2:alias "cevCpuCat6kMsfc2" {
    smiv2:oid "1.3.6.1.4.1.9.12.3.1.9.5.94";
  }

  smiv2:alias "cevCpuCat6kWsxSup12ge" {
    smiv2:oid "1.3.6.1.4.1.9.12.3.1.9.5.95";
  }

  smiv2:alias "cevCpuCat6kWsxSup22ge" {
    smiv2:oid "1.3.6.1.4.1.9.12.3.1.9.5.96";
  }

  smiv2:alias "cevCpuCat6kWsxSup1a2ge" {
    smiv2:oid "1.3.6.1.4.1.9.12.3.1.9.5.97";
  }

  smiv2:alias "cevCpuCat6kWsSup720SP" {
    smiv2:oid "1.3.6.1.4.1.9.12.3.1.9.5.98";
  }

  smiv2:alias "cevCpu3845ge2" {
    smiv2:oid "1.3.6.1.4.1.9.12.3.1.9.5.99";
  }

  smiv2:alias "cevCpu3825ge2" {
    smiv2:oid "1.3.6.1.4.1.9.12.3.1.9.5.100";
  }

  smiv2:alias "cevCpuCrs1AsmpRoute" {
    smiv2:oid "1.3.6.1.4.1.9.12.3.1.9.5.101";
  }

  smiv2:alias "cevCpuCrs1DsmpRoute" {
    smiv2:oid "1.3.6.1.4.1.9.12.3.1.9.5.102";
  }

  smiv2:alias "cevCpuCrs1pfeAsic" {
    smiv2:oid "1.3.6.1.4.1.9.12.3.1.9.5.103";
  }

  smiv2:alias "cevCpuCrs1EgressqAsic" {
    smiv2:oid "1.3.6.1.4.1.9.12.3.1.9.5.104";
  }

  smiv2:alias "cevCpuCrs1FabricqAsic" {
    smiv2:oid "1.3.6.1.4.1.9.12.3.1.9.5.105";
  }

  smiv2:alias "cevCpuCrs1IngressqAsic" {
    smiv2:oid "1.3.6.1.4.1.9.12.3.1.9.5.106";
  }

  smiv2:alias "cevCpuCrs1SPLC" {
    smiv2:oid "1.3.6.1.4.1.9.12.3.1.9.5.107";
  }

  smiv2:alias "cevCpuCrs1SPFC" {
    smiv2:oid "1.3.6.1.4.1.9.12.3.1.9.5.108";
  }

  smiv2:alias "cevCpu1800Mod" {
    smiv2:oid "1.3.6.1.4.1.9.12.3.1.9.5.109";
  }

  smiv2:alias "cevCpuPrp2" {
    smiv2:oid "1.3.6.1.4.1.9.12.3.1.9.5.110";
  }

  smiv2:alias "cevCpuCat6kWsSup32ge" {
    smiv2:oid "1.3.6.1.4.1.9.12.3.1.9.5.111";
  }

  smiv2:alias "cevCpuCat6kWsSup3210ge" {
    smiv2:oid "1.3.6.1.4.1.9.12.3.1.9.5.112";
  }

  smiv2:alias "cevCpuAs5400XM" {
    smiv2:oid "1.3.6.1.4.1.9.12.3.1.9.5.113";
  }

  smiv2:alias "cevCpuAs5350XM" {
    smiv2:oid "1.3.6.1.4.1.9.12.3.1.9.5.114";
  }

  smiv2:alias "cevCpu1800" {
    smiv2:oid "1.3.6.1.4.1.9.12.3.1.9.5.115";
  }

  smiv2:alias "cevCpu7200Npeg2" {
    smiv2:oid "1.3.6.1.4.1.9.12.3.1.9.5.118";
  }

  smiv2:alias "cevCpuCat6kMsfc2a" {
    smiv2:oid "1.3.6.1.4.1.9.12.3.1.9.5.119";
  }

  smiv2:alias "cevCpuC28012fe" {
    smiv2:oid "1.3.6.1.4.1.9.12.3.1.9.5.120";
  }

  smiv2:alias "cevCpuIXP2350WestportNP" {
    smiv2:oid "1.3.6.1.4.1.9.12.3.1.9.5.121";
  }

  smiv2:alias "cevCpuC7300Nse150" {
    smiv2:oid "1.3.6.1.4.1.9.12.3.1.9.5.122";
  }

  smiv2:alias "cevCpuCre1Rp" {
    smiv2:oid "1.3.6.1.4.1.9.12.3.1.9.5.123";
  }

  smiv2:alias "cevCpuCre2Rp" {
    smiv2:oid "1.3.6.1.4.1.9.12.3.1.9.5.124";
  }

  smiv2:alias "cevCpuCre3Rp" {
    smiv2:oid "1.3.6.1.4.1.9.12.3.1.9.5.125";
  }

  smiv2:alias "cevCpuCre1Fp" {
    smiv2:oid "1.3.6.1.4.1.9.12.3.1.9.5.126";
  }

  smiv2:alias "cevCpuCre2Fp" {
    smiv2:oid "1.3.6.1.4.1.9.12.3.1.9.5.127";
  }

  smiv2:alias "cevCpuCre3Fp" {
    smiv2:oid "1.3.6.1.4.1.9.12.3.1.9.5.128";
  }

  smiv2:alias "cevCpu7600Sip600DC" {
    smiv2:oid "1.3.6.1.4.1.9.12.3.1.9.5.130";
  }

  smiv2:alias "cevCpuCat6kVsF6kMsfc3" {
    smiv2:oid "1.3.6.1.4.1.9.12.3.1.9.5.131";
  }

  smiv2:alias "cevCpuCat6kVsS72010G" {
    smiv2:oid "1.3.6.1.4.1.9.12.3.1.9.5.132";
  }

  smiv2:alias "cevCpu7201Npeg2" {
    smiv2:oid "1.3.6.1.4.1.9.12.3.1.9.5.133";
  }

  smiv2:alias "cevCpuSamiDc8548H" {
    smiv2:oid "1.3.6.1.4.1.9.12.3.1.9.5.134";
  }

  smiv2:alias "cevCpuUC500" {
    smiv2:oid "1.3.6.1.4.1.9.12.3.1.9.5.135";
  }

  smiv2:alias "cevCpuBroadcomSB1A" {
    smiv2:oid "1.3.6.1.4.1.9.12.3.1.9.5.138";
  }

  smiv2:alias "cevCpuCrs1SPLCB" {
    smiv2:oid "1.3.6.1.4.1.9.12.3.1.9.5.139";
  }

  smiv2:alias "cevCpuUc520s" {
    smiv2:oid "1.3.6.1.4.1.9.12.3.1.9.5.140";
  }

  smiv2:alias "cevCpuUc520m" {
    smiv2:oid "1.3.6.1.4.1.9.12.3.1.9.5.141";
  }

  smiv2:alias "cevCpu1861" {
    smiv2:oid "1.3.6.1.4.1.9.12.3.1.9.5.144";
  }

  smiv2:alias "cevCpuTraffic" {
    smiv2:oid "1.3.6.1.4.1.9.12.3.1.9.5.145";
  }

  smiv2:alias "cevCpuCat6kWsSup32Pge" {
    smiv2:oid "1.3.6.1.4.1.9.12.3.1.9.5.146";
  }

  smiv2:alias "cevCpuCat6kWsSup32P10ge" {
    smiv2:oid "1.3.6.1.4.1.9.12.3.1.9.5.147";
  }

  smiv2:alias "cevCpuCat6kWsF6kPisa" {
    smiv2:oid "1.3.6.1.4.1.9.12.3.1.9.5.148";
  }

  smiv2:alias "cevCpuCrs1PlimAsic" {
    smiv2:oid "1.3.6.1.4.1.9.12.3.1.9.5.152";
  }

  smiv2:alias "cevCpu2435Iad8Fxs" {
    smiv2:oid "1.3.6.1.4.1.9.12.3.1.9.5.153";
  }

  smiv2:alias "cevCpuVG204" {
    smiv2:oid "1.3.6.1.4.1.9.12.3.1.9.5.154";
  }

  smiv2:alias "cevCpuVG202" {
    smiv2:oid "1.3.6.1.4.1.9.12.3.1.9.5.155";
  }

  smiv2:alias "cevCpu2941" {
    smiv2:oid "1.3.6.1.4.1.9.12.3.1.9.5.157";
  }

  smiv2:alias "cevCPU8641D" {
    smiv2:oid "1.3.6.1.4.1.9.12.3.1.9.5.158";
  }

  smiv2:alias "cevCpuCat6kVsSup2t10g" {
    smiv2:oid "1.3.6.1.4.1.9.12.3.1.9.5.159";
  }

  smiv2:alias "cevCpu19412ge" {
    smiv2:oid "1.3.6.1.4.1.9.12.3.1.9.5.160";
  }

  smiv2:alias "cevCpu29012ge" {
    smiv2:oid "1.3.6.1.4.1.9.12.3.1.9.5.161";
  }

  smiv2:alias "cevCpu29113ge" {
    smiv2:oid "1.3.6.1.4.1.9.12.3.1.9.5.162";
  }

  smiv2:alias "cevCpu29213ge" {
    smiv2:oid "1.3.6.1.4.1.9.12.3.1.9.5.163";
  }

  smiv2:alias "cevCpu29513ge" {
    smiv2:oid "1.3.6.1.4.1.9.12.3.1.9.5.164";
  }

  smiv2:alias "cevCpu39253ge" {
    smiv2:oid "1.3.6.1.4.1.9.12.3.1.9.5.165";
  }

  smiv2:alias "cevCpu39453ge" {
    smiv2:oid "1.3.6.1.4.1.9.12.3.1.9.5.166";
  }

  smiv2:alias "cevCpuSr520T1" {
    smiv2:oid "1.3.6.1.4.1.9.12.3.1.9.5.167";
  }

  smiv2:alias "cevCpu1941w2ge" {
    smiv2:oid "1.3.6.1.4.1.9.12.3.1.9.5.168";
  }

  smiv2:alias "cevCpu3825nvge2" {
    smiv2:oid "1.3.6.1.4.1.9.12.3.1.9.5.169";
  }

  smiv2:alias "cevCpu3845nvge2" {
    smiv2:oid "1.3.6.1.4.1.9.12.3.1.9.5.170";
  }

  smiv2:alias "cevCpuCrs1SPFP" {
    smiv2:oid "1.3.6.1.4.1.9.12.3.1.9.5.175";
  }

  smiv2:alias "cevCpu3900SPE2004ge" {
    smiv2:oid "1.3.6.1.4.1.9.12.3.1.9.5.179";
  }

  smiv2:alias "cevCpu3900Spe100K9" {
    smiv2:oid "1.3.6.1.4.1.9.12.3.1.9.5.182";
  }

  smiv2:alias "cevCpu3900Spe150K9" {
    smiv2:oid "1.3.6.1.4.1.9.12.3.1.9.5.183";
  }

  smiv2:alias "cevCpu3900SPE2504ge" {
    smiv2:oid "1.3.6.1.4.1.9.12.3.1.9.5.186";
  }

  smiv2:alias "cevCpuCrs1FP140" {
    smiv2:oid "1.3.6.1.4.1.9.12.3.1.9.5.187";
  }

  smiv2:alias "cevCpuCrs1MSC140G" {
    smiv2:oid "1.3.6.1.4.1.9.12.3.1.9.5.188";
  }

  smiv2:alias "cevCpuC1841C2fek9" {
    smiv2:oid "1.3.6.1.4.1.9.12.3.1.9.5.189";
  }

  smiv2:alias "cevCpuC2801C2fek9" {
    smiv2:oid "1.3.6.1.4.1.9.12.3.1.9.5.190";
  }

  smiv2:alias "cevCpuC2811C2fek9" {
    smiv2:oid "1.3.6.1.4.1.9.12.3.1.9.5.191";
  }

  smiv2:alias "cevCpuC2821C2gek9" {
    smiv2:oid "1.3.6.1.4.1.9.12.3.1.9.5.192";
  }

  smiv2:alias "cevCpu3825C2gek9" {
    smiv2:oid "1.3.6.1.4.1.9.12.3.1.9.5.194";
  }

  smiv2:alias "cevCpu3845C2gek9" {
    smiv2:oid "1.3.6.1.4.1.9.12.3.1.9.5.195";
  }

  smiv2:alias "cevCpuCGR20102ge" {
    smiv2:oid "1.3.6.1.4.1.9.12.3.1.9.5.198";
  }

  smiv2:alias "cevCpu1906Ck9" {
    smiv2:oid "1.3.6.1.4.1.9.12.3.1.9.5.199";
  }

  smiv2:alias "cevCpuDsp" {
    smiv2:oid "1.3.6.1.4.1.9.12.3.1.9.5.201";
  }

  smiv2:alias "cevCpu5915" {
    smiv2:oid "1.3.6.1.4.1.9.12.3.1.9.5.202";
  }

  smiv2:alias "cevCpu86xVAE" {
    smiv2:oid "1.3.6.1.4.1.9.12.3.1.9.5.212";
  }

  smiv2:alias "cevCpuCryptoAsic" {
    smiv2:oid "1.3.6.1.4.1.9.12.3.1.9.5.213";
  }

  smiv2:alias "cevCpu2811ve2fe" {
    smiv2:oid "1.3.6.1.4.1.9.12.3.1.9.5.214";
  }

  smiv2:alias "cevCpu1841ve2fe" {
    smiv2:oid "1.3.6.1.4.1.9.12.3.1.9.5.215";
  }

  smiv2:alias "cevCpu819HG" {
    smiv2:oid "1.3.6.1.4.1.9.12.3.1.9.5.216";
  }

  smiv2:alias "cevCpu819G" {
    smiv2:oid "1.3.6.1.4.1.9.12.3.1.9.5.217";
  }

  smiv2:alias "cevCpu881W" {
    smiv2:oid "1.3.6.1.4.1.9.12.3.1.9.5.218";
  }

  smiv2:alias "cevCpu886VAW" {
    smiv2:oid "1.3.6.1.4.1.9.12.3.1.9.5.219";
  }

  smiv2:alias "cevCpu887VAMW" {
    smiv2:oid "1.3.6.1.4.1.9.12.3.1.9.5.220";
  }

  smiv2:alias "cevCpu887VAW" {
    smiv2:oid "1.3.6.1.4.1.9.12.3.1.9.5.221";
  }

  smiv2:alias "cevCpuAsaSm1" {
    smiv2:oid "1.3.6.1.4.1.9.12.3.1.9.5.222";
  }

  smiv2:alias "cevCpuAsaSm1K7" {
    smiv2:oid "1.3.6.1.4.1.9.12.3.1.9.5.223";
  }

  smiv2:alias "cevCpuCrsLSP140" {
    smiv2:oid "1.3.6.1.4.1.9.12.3.1.9.5.234";
  }

  smiv2:alias "cevCpuCre5Fp" {
    smiv2:oid "1.3.6.1.4.1.9.12.3.1.9.5.243";
  }

  smiv2:alias "cevCpuCre5Rp" {
    smiv2:oid "1.3.6.1.4.1.9.12.3.1.9.5.244";
  }

  smiv2:alias "cevCpuVG350" {
    smiv2:oid "1.3.6.1.4.1.9.12.3.1.9.5.245";
  }

  smiv2:alias "cevCpu819HGW" {
    smiv2:oid "1.3.6.1.4.1.9.12.3.1.9.5.250";
  }

  smiv2:alias "cevCpu819H" {
    smiv2:oid "1.3.6.1.4.1.9.12.3.1.9.5.251";
  }

  smiv2:alias "cevCpu819HWD" {
    smiv2:oid "1.3.6.1.4.1.9.12.3.1.9.5.252";
  }

  smiv2:alias "cevCpu812G" {
    smiv2:oid "1.3.6.1.4.1.9.12.3.1.9.5.253";
  }

  smiv2:alias "cevCpu812GCIFI" {
    smiv2:oid "1.3.6.1.4.1.9.12.3.1.9.5.254";
  }

  smiv2:alias "cevCpu819HGM" {
    smiv2:oid "1.3.6.1.4.1.9.12.3.1.9.5.255";
  }

  smiv2:alias "cevCpu819GM" {
    smiv2:oid "1.3.6.1.4.1.9.12.3.1.9.5.256";
  }

  smiv2:alias "cevCpuCgrSup" {
    smiv2:oid "1.3.6.1.4.1.9.12.3.1.9.5.266";
  }

  smiv2:alias "cevCpu86xVAEW" {
    smiv2:oid "1.3.6.1.4.1.9.12.3.1.9.5.267";
  }

  smiv2:alias "cevCpuvg202xm" {
    smiv2:oid "1.3.6.1.4.1.9.12.3.1.9.5.268";
  }

  smiv2:alias "cevCpuvg204xm" {
    smiv2:oid "1.3.6.1.4.1.9.12.3.1.9.5.269";
  }

  smiv2:alias "cevCpuC6880x" {
    smiv2:oid "1.3.6.1.4.1.9.12.3.1.9.5.270";
  }

  smiv2:alias "cevCpu1783SR" {
    smiv2:oid "1.3.6.1.4.1.9.12.3.1.9.5.280";
  }

  smiv2:alias "cevCpuTypeCPU" {
    smiv2:oid "1.3.6.1.4.1.9.12.3.1.9.5.281";
  }

  smiv2:alias "cevCpuC881" {
    smiv2:oid "1.3.6.1.4.1.9.12.3.1.9.5.282";
  }

  smiv2:alias "cevCpuC886VA" {
    smiv2:oid "1.3.6.1.4.1.9.12.3.1.9.5.283";
  }

  smiv2:alias "cevCpuC887VA" {
    smiv2:oid "1.3.6.1.4.1.9.12.3.1.9.5.284";
  }

  smiv2:alias "cevCpuC888" {
    smiv2:oid "1.3.6.1.4.1.9.12.3.1.9.5.285";
  }

  smiv2:alias "cevCpuC891F" {
    smiv2:oid "1.3.6.1.4.1.9.12.3.1.9.5.286";
  }

  smiv2:alias "cevCpuC891FW" {
    smiv2:oid "1.3.6.1.4.1.9.12.3.1.9.5.287";
  }

  smiv2:alias "cevCpuVG310" {
    smiv2:oid "1.3.6.1.4.1.9.12.3.1.9.5.288";
  }

  smiv2:alias "cevCpuVG320" {
    smiv2:oid "1.3.6.1.4.1.9.12.3.1.9.5.289";
  }

  smiv2:alias "cevCPURT1081K9" {
    smiv2:oid "1.3.6.1.4.1.9.12.3.1.9.5.293";
  }

  smiv2:alias "cevCPURT1091K9" {
    smiv2:oid "1.3.6.1.4.1.9.12.3.1.9.5.294";
  }

  smiv2:alias "cevCpuRT2241K9" {
    smiv2:oid "1.3.6.1.4.1.9.12.3.1.9.5.295";
  }

  smiv2:alias "cevCpuRT2221K9" {
    smiv2:oid "1.3.6.1.4.1.9.12.3.1.9.5.296";
  }

  smiv2:alias "cevCpuRT2241WCK9" {
    smiv2:oid "1.3.6.1.4.1.9.12.3.1.9.5.297";
  }

  smiv2:alias "cevCpuRT3211K9" {
    smiv2:oid "1.3.6.1.4.1.9.12.3.1.9.5.298";
  }

  smiv2:alias "cevCpuRT3221K9" {
    smiv2:oid "1.3.6.1.4.1.9.12.3.1.9.5.299";
  }

  smiv2:alias "cevCpuRT3201K9" {
    smiv2:oid "1.3.6.1.4.1.9.12.3.1.9.5.300";
  }

  smiv2:alias "cevCpu897VAB" {
    smiv2:oid "1.3.6.1.4.1.9.12.3.1.9.5.306";
  }

  smiv2:alias "cevCpuCrs1LSPX" {
    smiv2:oid "1.3.6.1.4.1.9.12.3.1.9.5.307";
  }

  smiv2:alias "cevCpuCrs1FPX" {
    smiv2:oid "1.3.6.1.4.1.9.12.3.1.9.5.308";
  }

  smiv2:alias "cevCpuCrs1MSCX" {
    smiv2:oid "1.3.6.1.4.1.9.12.3.1.9.5.309";
  }

  smiv2:alias "cevCpu891x24X" {
    smiv2:oid "1.3.6.1.4.1.9.12.3.1.9.5.318";
  }

  smiv2:alias "cevCpu841Mx4X" {
    smiv2:oid "1.3.6.1.4.1.9.12.3.1.9.5.321";
  }

  smiv2:alias "cevCpu841Mx8X" {
    smiv2:oid "1.3.6.1.4.1.9.12.3.1.9.5.322";
  }

  smiv2:alias "cevCpuCrs1MSCXL" {
    smiv2:oid "1.3.6.1.4.1.9.12.3.1.9.5.323";
  }

  smiv2:alias "cevCpuCrs1FPXL" {
    smiv2:oid "1.3.6.1.4.1.9.12.3.1.9.5.324";
  }

  smiv2:alias "cevModuleCscType" {
    smiv2:oid "1.3.6.1.4.1.9.12.3.1.9.6";
  }

  smiv2:alias "cevModuleC7xxxType" {
    smiv2:oid "1.3.6.1.4.1.9.12.3.1.9.7";
  }

  smiv2:alias "cevC7xxxMc14a" {
    smiv2:oid "1.3.6.1.4.1.9.12.3.1.9.7.1";
  }

  smiv2:alias "cevC7xxxMc16a" {
    smiv2:oid "1.3.6.1.4.1.9.12.3.1.9.7.2";
  }

  smiv2:alias "cevC7xxxMc11" {
    smiv2:oid "1.3.6.1.4.1.9.12.3.1.9.7.3";
  }

  smiv2:alias "cevC7xxxMc12a" {
    smiv2:oid "1.3.6.1.4.1.9.12.3.1.9.7.4";
  }

  smiv2:alias "cevC7xxxMc11a" {
    smiv2:oid "1.3.6.1.4.1.9.12.3.1.9.7.5";
  }

  smiv2:alias "cevC7xxxIo1feTxIsl" {
    smiv2:oid "1.3.6.1.4.1.9.12.3.1.9.7.6";
  }

  smiv2:alias "cevC7xxxMc28" {
    smiv2:oid "1.3.6.1.4.1.9.12.3.1.9.7.8";
  }

  smiv2:alias "cevVip480" {
    smiv2:oid "1.3.6.1.4.1.9.12.3.1.9.7.9";
  }

  smiv2:alias "cevVip450" {
    smiv2:oid "1.3.6.1.4.1.9.12.3.1.9.7.10";
  }

  smiv2:alias "cevC7xxxIoEGE" {
    smiv2:oid "1.3.6.1.4.1.9.12.3.1.9.7.11";
  }

  smiv2:alias "cevC7xxxIo2FE" {
    smiv2:oid "1.3.6.1.4.1.9.12.3.1.9.7.12";
  }

  smiv2:alias "cevC7xxxEIP" {
    smiv2:oid "1.3.6.1.4.1.9.12.3.1.9.7.16";
  }

  smiv2:alias "cevC7xxxFIP" {
    smiv2:oid "1.3.6.1.4.1.9.12.3.1.9.7.17";
  }

  smiv2:alias "cevC7xxxSrsFIP" {
    smiv2:oid "1.3.6.1.4.1.9.12.3.1.9.7.18";
  }

  smiv2:alias "cevC7xxxTRIP" {
    smiv2:oid "1.3.6.1.4.1.9.12.3.1.9.7.19";
  }

  smiv2:alias "cevC7xxxSrsTRIP" {
    smiv2:oid "1.3.6.1.4.1.9.12.3.1.9.7.20";
  }

  smiv2:alias "cevC7xxxFSIP" {
    smiv2:oid "1.3.6.1.4.1.9.12.3.1.9.7.21";
  }

  smiv2:alias "cevC7xxxSSIP" {
    smiv2:oid "1.3.6.1.4.1.9.12.3.1.9.7.22";
  }

  smiv2:alias "cevC7xxxMIP" {
    smiv2:oid "1.3.6.1.4.1.9.12.3.1.9.7.23";
  }

  smiv2:alias "cevC7xxxSMIP" {
    smiv2:oid "1.3.6.1.4.1.9.12.3.1.9.7.24";
  }

  smiv2:alias "cevC7xxxVIP2" {
    smiv2:oid "1.3.6.1.4.1.9.12.3.1.9.7.25";
  }

  smiv2:alias "cevC7xxxVIP250" {
    smiv2:oid "1.3.6.1.4.1.9.12.3.1.9.7.26";
  }

  smiv2:alias "cevC7xxxRSP1" {
    smiv2:oid "1.3.6.1.4.1.9.12.3.1.9.7.27";
  }

  smiv2:alias "cevC7xxxRSP2" {
    smiv2:oid "1.3.6.1.4.1.9.12.3.1.9.7.28";
  }

  smiv2:alias "cevC7xxxRSP4" {
    smiv2:oid "1.3.6.1.4.1.9.12.3.1.9.7.29";
  }

  smiv2:alias "cevC7xxxPosIP" {
    smiv2:oid "1.3.6.1.4.1.9.12.3.1.9.7.30";
  }

  smiv2:alias "cevC7xxxFeIP2" {
    smiv2:oid "1.3.6.1.4.1.9.12.3.1.9.7.31";
  }

  smiv2:alias "cevC73004Oc3PosMm" {
    smiv2:oid "1.3.6.1.4.1.9.12.3.1.9.7.33";
  }

  smiv2:alias "cevC73004Oc3PosSmIr" {
    smiv2:oid "1.3.6.1.4.1.9.12.3.1.9.7.34";
  }

  smiv2:alias "cevC73004Oc3PosSmLr" {
    smiv2:oid "1.3.6.1.4.1.9.12.3.1.9.7.35";
  }

  smiv2:alias "cevC7300Oc48PosSmSr" {
    smiv2:oid "1.3.6.1.4.1.9.12.3.1.9.7.36";
  }

  smiv2:alias "cevC7300Oc48PosSmIr" {
    smiv2:oid "1.3.6.1.4.1.9.12.3.1.9.7.37";
  }

  smiv2:alias "cevC7300Oc48PosSmLr" {
    smiv2:oid "1.3.6.1.4.1.9.12.3.1.9.7.38";
  }

  smiv2:alias "cevC7500AIP" {
    smiv2:oid "1.3.6.1.4.1.9.12.3.1.9.7.58";
  }

  smiv2:alias "cevC7500CIP" {
    smiv2:oid "1.3.6.1.4.1.9.12.3.1.9.7.59";
  }

  smiv2:alias "cevC7500CIP2" {
    smiv2:oid "1.3.6.1.4.1.9.12.3.1.9.7.60";
  }

  smiv2:alias "cevC7500GEIP" {
    smiv2:oid "1.3.6.1.4.1.9.12.3.1.9.7.61";
  }

  smiv2:alias "cevC7500FEIP" {
    smiv2:oid "1.3.6.1.4.1.9.12.3.1.9.7.62";
  }

  smiv2:alias "cevC7xxxSIP" {
    smiv2:oid "1.3.6.1.4.1.9.12.3.1.9.7.63";
  }

  smiv2:alias "cevC7xxxRSP" {
    smiv2:oid "1.3.6.1.4.1.9.12.3.1.9.7.64";
  }

  smiv2:alias "cevC7xxxHSSI" {
    smiv2:oid "1.3.6.1.4.1.9.12.3.1.9.7.65";
  }

  smiv2:alias "cevC7411" {
    smiv2:oid "1.3.6.1.4.1.9.12.3.1.9.7.66";
  }

  smiv2:alias "cevC7411IoGE" {
    smiv2:oid "1.3.6.1.4.1.9.12.3.1.9.7.67";
  }

  smiv2:alias "cevC7301" {
    smiv2:oid "1.3.6.1.4.1.9.12.3.1.9.7.68";
  }

  smiv2:alias "cevC7301IoGE" {
    smiv2:oid "1.3.6.1.4.1.9.12.3.1.9.7.69";
  }

  smiv2:alias "cevVip680" {
    smiv2:oid "1.3.6.1.4.1.9.12.3.1.9.7.70";
  }

  smiv2:alias "cevC7300CCPA" {
    smiv2:oid "1.3.6.1.4.1.9.12.3.1.9.7.76";
  }

  smiv2:alias "cevC7304MSC100" {
    smiv2:oid "1.3.6.1.4.1.9.12.3.1.9.7.77";
  }

  smiv2:alias "cevC73006E3" {
    smiv2:oid "1.3.6.1.4.1.9.12.3.1.9.7.78";
  }

  smiv2:alias "cevC73001Oc12Atm" {
    smiv2:oid "1.3.6.1.4.1.9.12.3.1.9.7.79";
  }

  smiv2:alias "cevC7200Vsa" {
    smiv2:oid "1.3.6.1.4.1.9.12.3.1.9.7.81";
  }

  smiv2:alias "cevModuleC4xxxType" {
    smiv2:oid "1.3.6.1.4.1.9.12.3.1.9.8";
  }

  smiv2:alias "cevC4xxxUnknown" {
    smiv2:oid "1.3.6.1.4.1.9.12.3.1.9.8.1";
  }

  smiv2:alias "cevC4xxxNp4Gb" {
    smiv2:oid "1.3.6.1.4.1.9.12.3.1.9.8.2";
  }

  smiv2:alias "cevC4wsx4548GbRj45VPlus" {
    smiv2:oid "1.3.6.1.4.1.9.12.3.1.9.8.3";
  }

  smiv2:alias "cevCat4kWsx4948e10GE" {
    smiv2:oid "1.3.6.1.4.1.9.12.3.1.9.8.4";
  }

  smiv2:alias "cevCat4kWsx45Sup7LE" {
    smiv2:oid "1.3.6.1.4.1.9.12.3.1.9.8.5";
  }

  smiv2:alias "cevCat4kWsx45Sup8e" {
    smiv2:oid "1.3.6.1.4.1.9.12.3.1.9.8.6";
  }

  smiv2:alias "cevNIM4gLteNA7354" {
    smiv2:oid "1.3.6.1.4.1.9.12.3.1.9.8.7";
  }

  smiv2:alias "cevNIM4gLteGA7304" {
    smiv2:oid "1.3.6.1.4.1.9.12.3.1.9.8.8";
  }

  smiv2:alias "cevNIM4gLteVZ7350" {
    smiv2:oid "1.3.6.1.4.1.9.12.3.1.9.8.9";
  }

  smiv2:alias "cevNIM4gLteST7350" {
    smiv2:oid "1.3.6.1.4.1.9.12.3.1.9.8.10";
  }

  smiv2:alias "cevModuleAS5200Type" {
    smiv2:oid "1.3.6.1.4.1.9.12.3.1.9.9";
  }

  smiv2:alias "cevAS5200Carrier" {
    smiv2:oid "1.3.6.1.4.1.9.12.3.1.9.9.1";
  }

  smiv2:alias "cevAS5200DtdCarrier" {
    smiv2:oid "1.3.6.1.4.1.9.12.3.1.9.9.2";
  }

  smiv2:alias "cevPmAS5xxx12m56k" {
    smiv2:oid "1.3.6.1.4.1.9.12.3.1.9.9.3";
  }

  smiv2:alias "cevPmAS5xxx12mV110" {
    smiv2:oid "1.3.6.1.4.1.9.12.3.1.9.9.4";
  }

  smiv2:alias "cevModuleC25xxType" {
    smiv2:oid "1.3.6.1.4.1.9.12.3.1.9.10";
  }

  smiv2:alias "cevModuleAS5300Type" {
    smiv2:oid "1.3.6.1.4.1.9.12.3.1.9.11";
  }

  smiv2:alias "cevAS53004ct1" {
    smiv2:oid "1.3.6.1.4.1.9.12.3.1.9.11.1";
  }

  smiv2:alias "cevAS53004ce1" {
    smiv2:oid "1.3.6.1.4.1.9.12.3.1.9.11.2";
  }

  smiv2:alias "cevPmDtdCarrier" {
    smiv2:oid "1.3.6.1.4.1.9.12.3.1.9.11.3";
  }

  smiv2:alias "cevPmDtd6m" {
    smiv2:oid "1.3.6.1.4.1.9.12.3.1.9.11.4";
  }

  smiv2:alias "cevAS5300Carrier" {
    smiv2:oid "1.3.6.1.4.1.9.12.3.1.9.11.5";
  }

  smiv2:alias "cevPmAS5xxx12m" {
    smiv2:oid "1.3.6.1.4.1.9.12.3.1.9.11.6";
  }

  smiv2:alias "cevAS5300VoiceCarrierCard" {
    smiv2:oid "1.3.6.1.4.1.9.12.3.1.9.11.7";
  }

  smiv2:alias "cevAS5300Dspmc542" {
    smiv2:oid "1.3.6.1.4.1.9.12.3.1.9.11.8";
  }

  smiv2:alias "cevAS5300Dsp" {
    smiv2:oid "1.3.6.1.4.1.9.12.3.1.9.11.9";
  }

  smiv2:alias "cevAS5300PmDtd12m" {
    smiv2:oid "1.3.6.1.4.1.9.12.3.1.9.11.10";
  }

  smiv2:alias "cevAS53008ct14t" {
    smiv2:oid "1.3.6.1.4.1.9.12.3.1.9.11.11";
  }

  smiv2:alias "cevAS53008ce14t" {
    smiv2:oid "1.3.6.1.4.1.9.12.3.1.9.11.12";
  }

  smiv2:alias "cevAS53004ct14t" {
    smiv2:oid "1.3.6.1.4.1.9.12.3.1.9.11.13";
  }

  smiv2:alias "cevAS53004ce14t" {
    smiv2:oid "1.3.6.1.4.1.9.12.3.1.9.11.14";
  }

  smiv2:alias "cevAS5300Amazon2Carrier" {
    smiv2:oid "1.3.6.1.4.1.9.12.3.1.9.11.15";
  }

  smiv2:alias "cevAS5300Dspm6c549" {
    smiv2:oid "1.3.6.1.4.1.9.12.3.1.9.11.16";
  }

  smiv2:alias "cevModuleAS5800Type" {
    smiv2:oid "1.3.6.1.4.1.9.12.3.1.9.12";
  }

  smiv2:alias "cevMAs5800Dsc" {
    smiv2:oid "1.3.6.1.4.1.9.12.3.1.9.12.1";
  }

  smiv2:alias "cevMAs5800E1" {
    smiv2:oid "1.3.6.1.4.1.9.12.3.1.9.12.2";
  }

  smiv2:alias "cevMAs5800T1" {
    smiv2:oid "1.3.6.1.4.1.9.12.3.1.9.12.3";
  }

  smiv2:alias "cevMAs5800MicaHmm" {
    smiv2:oid "1.3.6.1.4.1.9.12.3.1.9.12.4";
  }

  smiv2:alias "cevMAs5800T3" {
    smiv2:oid "1.3.6.1.4.1.9.12.3.1.9.12.5";
  }

  smiv2:alias "cevMAs5800FeDsi" {
    smiv2:oid "1.3.6.1.4.1.9.12.3.1.9.12.6";
  }

  smiv2:alias "cevMAs5800MicaDmm" {
    smiv2:oid "1.3.6.1.4.1.9.12.3.1.9.12.7";
  }

  smiv2:alias "cevMAs5800Vcc" {
    smiv2:oid "1.3.6.1.4.1.9.12.3.1.9.12.8";
  }

  smiv2:alias "cevMAs5800Dspm6c549" {
    smiv2:oid "1.3.6.1.4.1.9.12.3.1.9.12.9";
  }

  smiv2:alias "cevMAs5800Dsp" {
    smiv2:oid "1.3.6.1.4.1.9.12.3.1.9.12.10";
  }

  smiv2:alias "cevModuleFabricType" {
    smiv2:oid "1.3.6.1.4.1.9.12.3.1.9.14";
  }

  smiv2:alias "cev12012Sfc" {
    smiv2:oid "1.3.6.1.4.1.9.12.3.1.9.14.3";
  }

  smiv2:alias "cev12012Csc" {
    smiv2:oid "1.3.6.1.4.1.9.12.3.1.9.14.4";
  }

  smiv2:alias "cev12008Sfc8" {
    smiv2:oid "1.3.6.1.4.1.9.12.3.1.9.14.5";
  }

  smiv2:alias "cev12008Csc8" {
    smiv2:oid "1.3.6.1.4.1.9.12.3.1.9.14.6";
  }

  smiv2:alias "cev12016Sfc16" {
    smiv2:oid "1.3.6.1.4.1.9.12.3.1.9.14.7";
  }

  smiv2:alias "cev12016Csc16" {
    smiv2:oid "1.3.6.1.4.1.9.12.3.1.9.14.8";
  }

  smiv2:alias "cev12016Sfc16Oc192" {
    smiv2:oid "1.3.6.1.4.1.9.12.3.1.9.14.9";
  }

  smiv2:alias "cev12016Csc16Oc192" {
    smiv2:oid "1.3.6.1.4.1.9.12.3.1.9.14.10";
  }

  smiv2:alias "cev12010Sfc10" {
    smiv2:oid "1.3.6.1.4.1.9.12.3.1.9.14.11";
  }

  smiv2:alias "cev12010Csc10" {
    smiv2:oid "1.3.6.1.4.1.9.12.3.1.9.14.12";
  }

  smiv2:alias "cev12406Sfc6" {
    smiv2:oid "1.3.6.1.4.1.9.12.3.1.9.14.13";
  }

  smiv2:alias "cev12406Csc6" {
    smiv2:oid "1.3.6.1.4.1.9.12.3.1.9.14.14";
  }

  smiv2:alias "cev12410Sfc10" {
    smiv2:oid "1.3.6.1.4.1.9.12.3.1.9.14.15";
  }

  smiv2:alias "cev12410Csc10" {
    smiv2:oid "1.3.6.1.4.1.9.12.3.1.9.14.16";
  }

  smiv2:alias "cev12404Csc64" {
    smiv2:oid "1.3.6.1.4.1.9.12.3.1.9.14.17";
  }

  smiv2:alias "cev12816Csc16Oc768" {
    smiv2:oid "1.3.6.1.4.1.9.12.3.1.9.14.18";
  }

  smiv2:alias "cev12810Csc10Oc768" {
    smiv2:oid "1.3.6.1.4.1.9.12.3.1.9.14.19";
  }

  smiv2:alias "cev12810Sfc10Oc768" {
    smiv2:oid "1.3.6.1.4.1.9.12.3.1.9.14.20";
  }

  smiv2:alias "cev12816Sfc16Oc768" {
    smiv2:oid "1.3.6.1.4.1.9.12.3.1.9.14.21";
  }

  smiv2:alias "cev12006CscAdvncd" {
    smiv2:oid "1.3.6.1.4.1.9.12.3.1.9.14.22";
  }

  smiv2:alias "cev12010CscAdvncd" {
    smiv2:oid "1.3.6.1.4.1.9.12.3.1.9.14.23";
  }

  smiv2:alias "cev12016CscAdvncd" {
    smiv2:oid "1.3.6.1.4.1.9.12.3.1.9.14.24";
  }

  smiv2:alias "cev12006SfcAdvncd" {
    smiv2:oid "1.3.6.1.4.1.9.12.3.1.9.14.25";
  }

  smiv2:alias "cev12010SfcAdvncd" {
    smiv2:oid "1.3.6.1.4.1.9.12.3.1.9.14.26";
  }

  smiv2:alias "cev12016SfcAdvncd" {
    smiv2:oid "1.3.6.1.4.1.9.12.3.1.9.14.27";
  }

  smiv2:alias "cev12004FabAdvncd" {
    smiv2:oid "1.3.6.1.4.1.9.12.3.1.9.14.28";
  }

  smiv2:alias "cev12816Csc16Oc768B" {
    smiv2:oid "1.3.6.1.4.1.9.12.3.1.9.14.29";
  }

  smiv2:alias "cev12810Csc10Oc768B" {
    smiv2:oid "1.3.6.1.4.1.9.12.3.1.9.14.30";
  }

  smiv2:alias "cevModuleFabricTypeAsic" {
    smiv2:oid "1.3.6.1.4.1.9.12.3.1.9.14.45";
  }

  smiv2:alias "cevModuleDaughterCard" {
    smiv2:oid "1.3.6.1.4.1.9.12.3.1.9.15";
  }

  smiv2:alias "cevDslamNi2Controller" {
    smiv2:oid "1.3.6.1.4.1.9.12.3.1.9.15.4";
  }

  smiv2:alias "cevWvic2dsuE1DiG703" {
    smiv2:oid "1.3.6.1.4.1.9.12.3.1.9.15.5";
  }

  smiv2:alias "cevWvic1dsuE1G703" {
    smiv2:oid "1.3.6.1.4.1.9.12.3.1.9.15.6";
  }

  smiv2:alias "cevDspmPvdm3" {
    smiv2:oid "1.3.6.1.4.1.9.12.3.1.9.15.7";
  }

  smiv2:alias "cevDspmPvdm1" {
    smiv2:oid "1.3.6.1.4.1.9.12.3.1.9.15.12";
  }

  smiv2:alias "cevDspmPvdm2" {
    smiv2:oid "1.3.6.1.4.1.9.12.3.1.9.15.13";
  }

  smiv2:alias "cevDspmPvdm4" {
    smiv2:oid "1.3.6.1.4.1.9.12.3.1.9.15.14";
  }

  smiv2:alias "cevDspmPvdm5" {
    smiv2:oid "1.3.6.1.4.1.9.12.3.1.9.15.15";
  }

  smiv2:alias "cevHdaEm10fxs" {
    smiv2:oid "1.3.6.1.4.1.9.12.3.1.9.15.17";
  }

  smiv2:alias "cevHdaEm4dsp" {
    smiv2:oid "1.3.6.1.4.1.9.12.3.1.9.15.18";
  }

  smiv2:alias "cevC7300Nse100Db" {
    smiv2:oid "1.3.6.1.4.1.9.12.3.1.9.15.19";
  }

  smiv2:alias "cevCeScsi2636" {
    smiv2:oid "1.3.6.1.4.1.9.12.3.1.9.15.24";
  }

  smiv2:alias "cevCeIde2636" {
    smiv2:oid "1.3.6.1.4.1.9.12.3.1.9.15.25";
  }

  smiv2:alias "cevVic4vpFxs4Did" {
    smiv2:oid "1.3.6.1.4.1.9.12.3.1.9.15.26";
  }

  smiv2:alias "cevC7300Nse100PlusDb" {
    smiv2:oid "1.3.6.1.4.1.9.12.3.1.9.15.27";
  }

  smiv2:alias "cevModuleCat4000DaughterCardType" {
    smiv2:oid "1.3.6.1.4.1.9.12.3.1.9.15.28";
  }

  smiv2:alias "cevCat4kDCWsf4531" {
    smiv2:oid "1.3.6.1.4.1.9.12.3.1.9.15.28.1";
  }

  smiv2:alias "cevCat4kDCWsu4504FxMt" {
    smiv2:oid "1.3.6.1.4.1.9.12.3.1.9.15.28.2";
  }

  smiv2:alias "cevVwic2Mft1T1E1" {
    smiv2:oid "1.3.6.1.4.1.9.12.3.1.9.15.29";
  }

  smiv2:alias "cevVwic2Mft1G703" {
    smiv2:oid "1.3.6.1.4.1.9.12.3.1.9.15.30";
  }

  smiv2:alias "cevVwic2Mft2T1E1" {
    smiv2:oid "1.3.6.1.4.1.9.12.3.1.9.15.31";
  }

  smiv2:alias "cevVwic2Mft2G703" {
    smiv2:oid "1.3.6.1.4.1.9.12.3.1.9.15.32";
  }

  smiv2:alias "cevEcMft32" {
    smiv2:oid "1.3.6.1.4.1.9.12.3.1.9.15.33";
  }

  smiv2:alias "cevEcMft64" {
    smiv2:oid "1.3.6.1.4.1.9.12.3.1.9.15.34";
  }

  smiv2:alias "cevEm4Fxs4Fxo" {
    smiv2:oid "1.3.6.1.4.1.9.12.3.1.9.15.35";
  }

  smiv2:alias "cevEm6Fxo" {
    smiv2:oid "1.3.6.1.4.1.9.12.3.1.9.15.36";
  }

  smiv2:alias "cevEm4BriNtTe" {
    smiv2:oid "1.3.6.1.4.1.9.12.3.1.9.15.37";
  }

  smiv2:alias "cevpvdm2dsphalf" {
    smiv2:oid "1.3.6.1.4.1.9.12.3.1.9.15.38";
  }

  smiv2:alias "cevpvdm2dsp4" {
    smiv2:oid "1.3.6.1.4.1.9.12.3.1.9.15.39";
  }

  smiv2:alias "cevpvdm2dsp3" {
    smiv2:oid "1.3.6.1.4.1.9.12.3.1.9.15.40";
  }

  smiv2:alias "cevpvdm2dsp2" {
    smiv2:oid "1.3.6.1.4.1.9.12.3.1.9.15.41";
  }

  smiv2:alias "cevpvdm2dsp1" {
    smiv2:oid "1.3.6.1.4.1.9.12.3.1.9.15.42";
  }

  smiv2:alias "cevpvdm2hwecan3" {
    smiv2:oid "1.3.6.1.4.1.9.12.3.1.9.15.43";
  }

  smiv2:alias "cevpvdm2hwecan2" {
    smiv2:oid "1.3.6.1.4.1.9.12.3.1.9.15.44";
  }

  smiv2:alias "cevpvdm2hwecan1" {
    smiv2:oid "1.3.6.1.4.1.9.12.3.1.9.15.45";
  }

  smiv2:alias "cevNetworkProcessor" {
    smiv2:oid "1.3.6.1.4.1.9.12.3.1.9.15.46";
  }

  smiv2:alias "cevVic2Mft1T1E1" {
    smiv2:oid "1.3.6.1.4.1.9.12.3.1.9.15.47";
  }

  smiv2:alias "cevVic2Mft2T1E1" {
    smiv2:oid "1.3.6.1.4.1.9.12.3.1.9.15.48";
  }

  smiv2:alias "cevEm2Hda4Fxo" {
    smiv2:oid "1.3.6.1.4.1.9.12.3.1.9.15.49";
  }

  smiv2:alias "cevVic1J1" {
    smiv2:oid "1.3.6.1.4.1.9.12.3.1.9.15.50";
  }

  smiv2:alias "cevWic1amV2" {
    smiv2:oid "1.3.6.1.4.1.9.12.3.1.9.15.51";
  }

  smiv2:alias "cevWic2amV2" {
    smiv2:oid "1.3.6.1.4.1.9.12.3.1.9.15.52";
  }

  smiv2:alias "cevPvdmII12dm" {
    smiv2:oid "1.3.6.1.4.1.9.12.3.1.9.15.53";
  }

  smiv2:alias "cevVwic2T1E1Ran" {
    smiv2:oid "1.3.6.1.4.1.9.12.3.1.9.15.59";
  }

  smiv2:alias "cev7300Nse150Db" {
    smiv2:oid "1.3.6.1.4.1.9.12.3.1.9.15.60";
  }

  smiv2:alias "cevVic3Em2" {
    smiv2:oid "1.3.6.1.4.1.9.12.3.1.9.15.61";
  }

  smiv2:alias "cevVic3FxsDid2" {
    smiv2:oid "1.3.6.1.4.1.9.12.3.1.9.15.62";
  }

  smiv2:alias "cevVic3FxsDid4" {
    smiv2:oid "1.3.6.1.4.1.9.12.3.1.9.15.63";
  }

  smiv2:alias "cevHdaEm3FxsDid8" {
    smiv2:oid "1.3.6.1.4.1.9.12.3.1.9.15.64";
  }

  smiv2:alias "cev1DOCSIS20CableModemDC" {
    smiv2:oid "1.3.6.1.4.1.9.12.3.1.9.15.65";
  }

  smiv2:alias "cev1DOCSIS20CableModemDCEJ" {
    smiv2:oid "1.3.6.1.4.1.9.12.3.1.9.15.66";
  }

  smiv2:alias "cevAsmM2900Top" {
    smiv2:oid "1.3.6.1.4.1.9.12.3.1.9.15.67";
  }

  smiv2:alias "cevVic3FxsEDid2" {
    smiv2:oid "1.3.6.1.4.1.9.12.3.1.9.15.68";
  }

  smiv2:alias "cevModuleASR9KLCDb" {
    smiv2:oid "1.3.6.1.4.1.9.12.3.1.9.15.69";
  }

  smiv2:alias "cevModemWan3g" {
    smiv2:oid "1.3.6.1.4.1.9.12.3.1.9.15.70";
  }

  smiv2:alias "cevModulePVDM3c64" {
    smiv2:oid "1.3.6.1.4.1.9.12.3.1.9.15.73";
  }

  smiv2:alias "cevModulePVDM3c32" {
    smiv2:oid "1.3.6.1.4.1.9.12.3.1.9.15.74";
  }

  smiv2:alias "cevModulePVDM3c128" {
    smiv2:oid "1.3.6.1.4.1.9.12.3.1.9.15.75";
  }

  smiv2:alias "cevModulePVDM3c192" {
    smiv2:oid "1.3.6.1.4.1.9.12.3.1.9.15.76";
  }

  smiv2:alias "cevModulePVDM3c256" {
    smiv2:oid "1.3.6.1.4.1.9.12.3.1.9.15.77";
  }

  smiv2:alias "cevNM2838" {
    smiv2:oid "1.3.6.1.4.1.9.12.3.1.9.15.78";
  }

  smiv2:alias "cevPANO2838" {
    smiv2:oid "1.3.6.1.4.1.9.12.3.1.9.15.79";
  }

  smiv2:alias "cevVwic3Mft4T1E1" {
    smiv2:oid "1.3.6.1.4.1.9.12.3.1.9.15.82";
  }

  smiv2:alias "cevVwic3Mft1T1E1" {
    smiv2:oid "1.3.6.1.4.1.9.12.3.1.9.15.83";
  }

  smiv2:alias "cevVwic3Mft1G703" {
    smiv2:oid "1.3.6.1.4.1.9.12.3.1.9.15.84";
  }

  smiv2:alias "cevVwic3Mft2T1E1" {
    smiv2:oid "1.3.6.1.4.1.9.12.3.1.9.15.85";
  }

  smiv2:alias "cevVwic3Mft2G703" {
    smiv2:oid "1.3.6.1.4.1.9.12.3.1.9.15.86";
  }

  smiv2:alias "cevPrp3Smdc" {
    smiv2:oid "1.3.6.1.4.1.9.12.3.1.9.15.87";
  }

  smiv2:alias "cevMdcC6880xPfc" {
    smiv2:oid "1.3.6.1.4.1.9.12.3.1.9.15.89";
  }

  smiv2:alias "cevMdcC6880xlePfc" {
    smiv2:oid "1.3.6.1.4.1.9.12.3.1.9.15.90";
  }

  smiv2:alias "cevPWic1AmV2" {
    smiv2:oid "1.3.6.1.4.1.9.12.3.1.9.15.93";
  }

  smiv2:alias "cevPVwic3Mft1G703" {
    smiv2:oid "1.3.6.1.4.1.9.12.3.1.9.15.94";
  }

  smiv2:alias "cevPVwic3Mft1T1E1" {
    smiv2:oid "1.3.6.1.4.1.9.12.3.1.9.15.95";
  }

  smiv2:alias "cevPVwic3Mft2G703" {
    smiv2:oid "1.3.6.1.4.1.9.12.3.1.9.15.96";
  }

  smiv2:alias "cevPVwic3Mft2T1E1" {
    smiv2:oid "1.3.6.1.4.1.9.12.3.1.9.15.97";
  }

  smiv2:alias "cevPVwic3Mft4T1E1" {
    smiv2:oid "1.3.6.1.4.1.9.12.3.1.9.15.98";
  }

  smiv2:alias "cevModulePPVDM3c128" {
    smiv2:oid "1.3.6.1.4.1.9.12.3.1.9.15.99";
  }

  smiv2:alias "cevModulePPVDM3c16" {
    smiv2:oid "1.3.6.1.4.1.9.12.3.1.9.15.100";
  }

  smiv2:alias "cevModulePPVDM3c192" {
    smiv2:oid "1.3.6.1.4.1.9.12.3.1.9.15.101";
  }

  smiv2:alias "cevModulePPVDM3c256" {
    smiv2:oid "1.3.6.1.4.1.9.12.3.1.9.15.102";
  }

  smiv2:alias "cevModulePPVDM3c32" {
    smiv2:oid "1.3.6.1.4.1.9.12.3.1.9.15.103";
  }

  smiv2:alias "cevModulePPVDM3c64" {
    smiv2:oid "1.3.6.1.4.1.9.12.3.1.9.15.104";
  }

  smiv2:alias "cevPVic3Em2" {
    smiv2:oid "1.3.6.1.4.1.9.12.3.1.9.15.105";
  }

  smiv2:alias "cevPVic3Fxs2Did" {
    smiv2:oid "1.3.6.1.4.1.9.12.3.1.9.15.106";
  }

  smiv2:alias "cevPVic3Fxs4Did" {
    smiv2:oid "1.3.6.1.4.1.9.12.3.1.9.15.107";
  }

  smiv2:alias "cevModuleGBICs" {
    smiv2:oid "1.3.6.1.4.1.9.12.3.1.9.16";
  }

  smiv2:alias "cevMGBIC1000BaseLX" {
    smiv2:oid "1.3.6.1.4.1.9.12.3.1.9.16.1";
  }

  smiv2:alias "cevMGBIC1000BaseSX" {
    smiv2:oid "1.3.6.1.4.1.9.12.3.1.9.16.2";
  }

  smiv2:alias "cevMGBIC1000BaseCX" {
    smiv2:oid "1.3.6.1.4.1.9.12.3.1.9.16.3";
  }

  smiv2:alias "cevMGBIC1000BaseLH" {
    smiv2:oid "1.3.6.1.4.1.9.12.3.1.9.16.4";
  }

  smiv2:alias "cevMGBIC1000BaseZX" {
    smiv2:oid "1.3.6.1.4.1.9.12.3.1.9.16.5";
  }

  smiv2:alias "cevMGBIC1000BaseCXSTACK" {
    smiv2:oid "1.3.6.1.4.1.9.12.3.1.9.16.6";
  }

  smiv2:alias "cevMGBIC1000BaseT" {
    smiv2:oid "1.3.6.1.4.1.9.12.3.1.9.16.7";
  }

  smiv2:alias "cevMGBICDWDM6061" {
    smiv2:oid "1.3.6.1.4.1.9.12.3.1.9.16.16";
  }

  smiv2:alias "cevMGBICDWDM5979" {
    smiv2:oid "1.3.6.1.4.1.9.12.3.1.9.16.17";
  }

  smiv2:alias "cevMGBICDWDM5898" {
    smiv2:oid "1.3.6.1.4.1.9.12.3.1.9.16.18";
  }

  smiv2:alias "cevMGBICDWDM5817" {
    smiv2:oid "1.3.6.1.4.1.9.12.3.1.9.16.19";
  }

  smiv2:alias "cevMGBICDWDM5655" {
    smiv2:oid "1.3.6.1.4.1.9.12.3.1.9.16.20";
  }

  smiv2:alias "cevMGBICDWDM5575" {
    smiv2:oid "1.3.6.1.4.1.9.12.3.1.9.16.21";
  }

  smiv2:alias "cevMGBICDWDM5494" {
    smiv2:oid "1.3.6.1.4.1.9.12.3.1.9.16.22";
  }

  smiv2:alias "cevMGBICDWDM5413" {
    smiv2:oid "1.3.6.1.4.1.9.12.3.1.9.16.23";
  }

  smiv2:alias "cevMGBICDWDM5252" {
    smiv2:oid "1.3.6.1.4.1.9.12.3.1.9.16.24";
  }

  smiv2:alias "cevMGBICDWDM5172" {
    smiv2:oid "1.3.6.1.4.1.9.12.3.1.9.16.25";
  }

  smiv2:alias "cevMGBICDWDM5092" {
    smiv2:oid "1.3.6.1.4.1.9.12.3.1.9.16.26";
  }

  smiv2:alias "cevMGBICDWDM5012" {
    smiv2:oid "1.3.6.1.4.1.9.12.3.1.9.16.27";
  }

  smiv2:alias "cevMGBICDWDM4851" {
    smiv2:oid "1.3.6.1.4.1.9.12.3.1.9.16.28";
  }

  smiv2:alias "cevMGBICDWDM4772" {
    smiv2:oid "1.3.6.1.4.1.9.12.3.1.9.16.29";
  }

  smiv2:alias "cevMGBICDWDM4692" {
    smiv2:oid "1.3.6.1.4.1.9.12.3.1.9.16.30";
  }

  smiv2:alias "cevMGBICDWDM4612" {
    smiv2:oid "1.3.6.1.4.1.9.12.3.1.9.16.31";
  }

  smiv2:alias "cevMGBICDWDM4453" {
    smiv2:oid "1.3.6.1.4.1.9.12.3.1.9.16.32";
  }

  smiv2:alias "cevMGBICDWDM4373" {
    smiv2:oid "1.3.6.1.4.1.9.12.3.1.9.16.33";
  }

  smiv2:alias "cevMGBICDWDM4294" {
    smiv2:oid "1.3.6.1.4.1.9.12.3.1.9.16.34";
  }

  smiv2:alias "cevMGBICDWDM4214" {
    smiv2:oid "1.3.6.1.4.1.9.12.3.1.9.16.35";
  }

  smiv2:alias "cevMGBICDWDM4056" {
    smiv2:oid "1.3.6.1.4.1.9.12.3.1.9.16.36";
  }

  smiv2:alias "cevMGBICDWDM3977" {
    smiv2:oid "1.3.6.1.4.1.9.12.3.1.9.16.37";
  }

  smiv2:alias "cevMGBICDWDM3898" {
    smiv2:oid "1.3.6.1.4.1.9.12.3.1.9.16.38";
  }

  smiv2:alias "cevMGBICDWDM3819" {
    smiv2:oid "1.3.6.1.4.1.9.12.3.1.9.16.39";
  }

  smiv2:alias "cevMGBICDWDM3661" {
    smiv2:oid "1.3.6.1.4.1.9.12.3.1.9.16.40";
  }

  smiv2:alias "cevMGBICDWDM3582" {
    smiv2:oid "1.3.6.1.4.1.9.12.3.1.9.16.41";
  }

  smiv2:alias "cevMGBICDWDM3504" {
    smiv2:oid "1.3.6.1.4.1.9.12.3.1.9.16.42";
  }

  smiv2:alias "cevMGBICDWDM3425" {
    smiv2:oid "1.3.6.1.4.1.9.12.3.1.9.16.43";
  }

  smiv2:alias "cevMGBICDWDM3268" {
    smiv2:oid "1.3.6.1.4.1.9.12.3.1.9.16.44";
  }

  smiv2:alias "cevMGBICDWDM3190" {
    smiv2:oid "1.3.6.1.4.1.9.12.3.1.9.16.45";
  }

  smiv2:alias "cevMGBICDWDM3112" {
    smiv2:oid "1.3.6.1.4.1.9.12.3.1.9.16.46";
  }

  smiv2:alias "cevMGBICDWDM3033" {
    smiv2:oid "1.3.6.1.4.1.9.12.3.1.9.16.47";
  }

  smiv2:alias "cevMGBICXWDMRxOnly" {
    smiv2:oid "1.3.6.1.4.1.9.12.3.1.9.16.48";
  }

  smiv2:alias "cevMGBIC1490BaseBX10D" {
    smiv2:oid "1.3.6.1.4.1.9.12.3.1.9.16.49";
  }

  smiv2:alias "cevMGBIC1310BaseBX10U" {
    smiv2:oid "1.3.6.1.4.1.9.12.3.1.9.16.50";
  }

  smiv2:alias "cevMGBICDWDM6141" {
    smiv2:oid "1.3.6.1.4.1.9.12.3.1.9.16.51";
  }

  smiv2:alias "cevMGBICDWDM5736" {
    smiv2:oid "1.3.6.1.4.1.9.12.3.1.9.16.52";
  }

  smiv2:alias "cevMGBICDWDM5332" {
    smiv2:oid "1.3.6.1.4.1.9.12.3.1.9.16.53";
  }

  smiv2:alias "cevMGBICDWDM4931" {
    smiv2:oid "1.3.6.1.4.1.9.12.3.1.9.16.54";
  }

  smiv2:alias "cevMGBICDWDM4532" {
    smiv2:oid "1.3.6.1.4.1.9.12.3.1.9.16.55";
  }

  smiv2:alias "cevMGBICDWDM4134" {
    smiv2:oid "1.3.6.1.4.1.9.12.3.1.9.16.56";
  }

  smiv2:alias "cevMGBICDWDM3739" {
    smiv2:oid "1.3.6.1.4.1.9.12.3.1.9.16.57";
  }

  smiv2:alias "cevMGBICDWDM3346" {
    smiv2:oid "1.3.6.1.4.1.9.12.3.1.9.16.58";
  }

  smiv2:alias "cevModuleC6xxxType" {
    smiv2:oid "1.3.6.1.4.1.9.12.3.1.9.17";
  }

  smiv2:alias "cevC6xxxSlcCap8" {
    smiv2:oid "1.3.6.1.4.1.9.12.3.1.9.17.1";
  }

  smiv2:alias "cevC6xxxNtcOc3si" {
    smiv2:oid "1.3.6.1.4.1.9.12.3.1.9.17.2";
  }

  smiv2:alias "cevC6xxxNtcOc3mm" {
    smiv2:oid "1.3.6.1.4.1.9.12.3.1.9.17.3";
  }

  smiv2:alias "cevC6xxxNtcStm1si" {
    smiv2:oid "1.3.6.1.4.1.9.12.3.1.9.17.4";
  }

  smiv2:alias "cevC6xxxNtcStm1mm" {
    smiv2:oid "1.3.6.1.4.1.9.12.3.1.9.17.5";
  }

  smiv2:alias "cevC6xxxSlcDmt8" {
    smiv2:oid "1.3.6.1.4.1.9.12.3.1.9.17.6";
  }

  smiv2:alias "cevC6xxxSlcDmt16" {
    smiv2:oid "1.3.6.1.4.1.9.12.3.1.9.17.7";
  }

  smiv2:alias "cevC6xxxNtcDs3" {
    smiv2:oid "1.3.6.1.4.1.9.12.3.1.9.17.8";
  }

  smiv2:alias "cevC6xxxOsm1Oc48PosSs" {
    smiv2:oid "1.3.6.1.4.1.9.12.3.1.9.17.10";
  }

  smiv2:alias "cevC6xxxOsm1Oc48PosSl" {
    smiv2:oid "1.3.6.1.4.1.9.12.3.1.9.17.11";
  }

  smiv2:alias "cevC6xxxOsm1Oc48PosSi" {
    smiv2:oid "1.3.6.1.4.1.9.12.3.1.9.17.12";
  }

  smiv2:alias "cevC6xxxOsm2Oc12PosSl" {
    smiv2:oid "1.3.6.1.4.1.9.12.3.1.9.17.15";
  }

  smiv2:alias "cevC6xxxOsm4Oc12PosSl" {
    smiv2:oid "1.3.6.1.4.1.9.12.3.1.9.17.16";
  }

  smiv2:alias "cevC6xxxOsm2Oc12PosMm" {
    smiv2:oid "1.3.6.1.4.1.9.12.3.1.9.17.17";
  }

  smiv2:alias "cevC6xxxOsm4Oc12PosMm" {
    smiv2:oid "1.3.6.1.4.1.9.12.3.1.9.17.18";
  }

  smiv2:alias "cevC6xxxOsm2Oc12PosSi" {
    smiv2:oid "1.3.6.1.4.1.9.12.3.1.9.17.19";
  }

  smiv2:alias "cevC6xxxOsm4Oc12PosSi" {
    smiv2:oid "1.3.6.1.4.1.9.12.3.1.9.17.20";
  }

  smiv2:alias "cevC6xxxOsm8Oc3PosSi" {
    smiv2:oid "1.3.6.1.4.1.9.12.3.1.9.17.21";
  }

  smiv2:alias "cevC6xxxOsm16Oc3PosSi" {
    smiv2:oid "1.3.6.1.4.1.9.12.3.1.9.17.22";
  }

  smiv2:alias "cevC6xxxOsm8Oc3PosMm" {
    smiv2:oid "1.3.6.1.4.1.9.12.3.1.9.17.23";
  }

  smiv2:alias "cevC6xxxOsm16Oc3PosMm" {
    smiv2:oid "1.3.6.1.4.1.9.12.3.1.9.17.24";
  }

  smiv2:alias "cevC6xxxOsm8Oc3PosSl" {
    smiv2:oid "1.3.6.1.4.1.9.12.3.1.9.17.25";
  }

  smiv2:alias "cevC6xxxOsm16Oc3PosSl" {
    smiv2:oid "1.3.6.1.4.1.9.12.3.1.9.17.26";
  }

  smiv2:alias "cevC6xxx4GeWanGbic" {
    smiv2:oid "1.3.6.1.4.1.9.12.3.1.9.17.27";
  }

  smiv2:alias "cevC6xxxOsm4ge4oc12ChDs3SmIr" {
    smiv2:oid "1.3.6.1.4.1.9.12.3.1.9.17.31";
  }

  smiv2:alias "cevC6xxxOsm4ge8oc12ChDs3SmIr" {
    smiv2:oid "1.3.6.1.4.1.9.12.3.1.9.17.32";
  }

  smiv2:alias "cevC6xxxOsm4geoc48ChDs3SmSr" {
    smiv2:oid "1.3.6.1.4.1.9.12.3.1.9.17.33";
  }

  smiv2:alias "ceC6xxxOsm4ge2oc48ChDs3SmSr" {
    smiv2:oid "1.3.6.1.4.1.9.12.3.1.9.17.34";
  }

  smiv2:alias "cevC6xxxOsm4geoc48ChDs3SmIr" {
    smiv2:oid "1.3.6.1.4.1.9.12.3.1.9.17.35";
  }

  smiv2:alias "cevC6xxxOsm4ge2oc48ChDs3SmIr" {
    smiv2:oid "1.3.6.1.4.1.9.12.3.1.9.17.36";
  }

  smiv2:alias "cevC6xxxOsm4geoc12ChDs3SmIr" {
    smiv2:oid "1.3.6.1.4.1.9.12.3.1.9.17.37";
  }

  smiv2:alias "cevC6xxxOsm4ge2oc12ChDs3SmIr" {
    smiv2:oid "1.3.6.1.4.1.9.12.3.1.9.17.38";
  }

  smiv2:alias "cevC6xxxOsm2Oc12AtmMmPlus" {
    smiv2:oid "1.3.6.1.4.1.9.12.3.1.9.17.40";
  }

  smiv2:alias "cevC6xxxOsm2Oc12AtmSiPlus" {
    smiv2:oid "1.3.6.1.4.1.9.12.3.1.9.17.41";
  }

  smiv2:alias "cevC6xxx4GeWanGbicPlus" {
    smiv2:oid "1.3.6.1.4.1.9.12.3.1.9.17.42";
  }

  smiv2:alias "cevC6xxxOsm1Oc48PosSsPlus" {
    smiv2:oid "1.3.6.1.4.1.9.12.3.1.9.17.43";
  }

  smiv2:alias "cevC6xxxOsm1Oc48PosSiPlus" {
    smiv2:oid "1.3.6.1.4.1.9.12.3.1.9.17.44";
  }

  smiv2:alias "cevC6xxxOsm1Oc48PosSlPlus" {
    smiv2:oid "1.3.6.1.4.1.9.12.3.1.9.17.45";
  }

  smiv2:alias "cevC6xxxOsm4Oc12PosSiPlus" {
    smiv2:oid "1.3.6.1.4.1.9.12.3.1.9.17.46";
  }

  smiv2:alias "cevC6xxxOsm2Oc12PosMmPlus" {
    smiv2:oid "1.3.6.1.4.1.9.12.3.1.9.17.47";
  }

  smiv2:alias "cevC6xxxOsm4Oc3PosSiPlus" {
    smiv2:oid "1.3.6.1.4.1.9.12.3.1.9.17.48";
  }

  smiv2:alias "cevC6xxxOsm8Oc3PosSiPlus" {
    smiv2:oid "1.3.6.1.4.1.9.12.3.1.9.17.49";
  }

  smiv2:alias "cevC6xxxOsm8Oc3PosSlPlus" {
    smiv2:oid "1.3.6.1.4.1.9.12.3.1.9.17.50";
  }

  smiv2:alias "cevC6xxxOsm16Oc3PosSiPlus" {
    smiv2:oid "1.3.6.1.4.1.9.12.3.1.9.17.51";
  }

  smiv2:alias "cevC6xxxOsm12Ct3T1" {
    smiv2:oid "1.3.6.1.4.1.9.12.3.1.9.17.52";
  }

  smiv2:alias "cevC6xxxCwpa2" {
    smiv2:oid "1.3.6.1.4.1.9.12.3.1.9.17.53";
  }

  smiv2:alias "cevC6xxxSIP200" {
    smiv2:oid "1.3.6.1.4.1.9.12.3.1.9.17.54";
  }

  smiv2:alias "cevC6xxxSIP400" {
    smiv2:oid "1.3.6.1.4.1.9.12.3.1.9.17.55";
  }

  smiv2:alias "cevC6xxxSIP600" {
    smiv2:oid "1.3.6.1.4.1.9.12.3.1.9.17.56";
  }

  smiv2:alias "cevC6xxxOsm2Oc12PosSiPlus" {
    smiv2:oid "1.3.6.1.4.1.9.12.3.1.9.17.57";
  }

  smiv2:alias "cevC6xxxOsm4Oc3PosSi" {
    smiv2:oid "1.3.6.1.4.1.9.12.3.1.9.17.58";
  }

  smiv2:alias "cevC6xxxOsm4Oc3PosSl" {
    smiv2:oid "1.3.6.1.4.1.9.12.3.1.9.17.59";
  }

  smiv2:alias "cevC6xxxOsm4Oc3PosMm" {
    smiv2:oid "1.3.6.1.4.1.9.12.3.1.9.17.60";
  }

  smiv2:alias "cevC6xxxOsm24Ct3T1" {
    smiv2:oid "1.3.6.1.4.1.9.12.3.1.9.17.61";
  }

  smiv2:alias "cevCat6kWsx6600" {
    smiv2:oid "1.3.6.1.4.1.9.12.3.1.9.17.62";
  }

  smiv2:alias "cevC6xxxSSC600" {
    smiv2:oid "1.3.6.1.4.1.9.12.3.1.9.17.63";
  }

  smiv2:alias "cevC6xxxSSC400" {
    smiv2:oid "1.3.6.1.4.1.9.12.3.1.9.17.64";
  }

  smiv2:alias "cevC6xxxRSP720Base" {
    smiv2:oid "1.3.6.1.4.1.9.12.3.1.9.17.65";
  }

  smiv2:alias "cevC6xxxRSP32GEBase" {
    smiv2:oid "1.3.6.1.4.1.9.12.3.1.9.17.66";
  }

  smiv2:alias "cevC6xxxRSP3210GEBase" {
    smiv2:oid "1.3.6.1.4.1.9.12.3.1.9.17.67";
  }

  smiv2:alias "cevC6xxxRSP720" {
    smiv2:oid "1.3.6.1.4.1.9.12.3.1.9.17.68";
  }

  smiv2:alias "cevC6xxxRSP32" {
    smiv2:oid "1.3.6.1.4.1.9.12.3.1.9.17.69";
  }

  smiv2:alias "cevC6xxxSIP600DC" {
    smiv2:oid "1.3.6.1.4.1.9.12.3.1.9.17.71";
  }

  smiv2:alias "cevC6xxxRSP720MsfcNaboo" {
    smiv2:oid "1.3.6.1.4.1.9.12.3.1.9.17.72";
  }

  smiv2:alias "cevC6xxxRSP720PfcGanges" {
    smiv2:oid "1.3.6.1.4.1.9.12.3.1.9.17.73";
  }

  smiv2:alias "cevC6xxxEsm20G" {
    smiv2:oid "1.3.6.1.4.1.9.12.3.1.9.17.74";
  }

  smiv2:alias "cevC6xxxEsm20GCpuDc" {
    smiv2:oid "1.3.6.1.4.1.9.12.3.1.9.17.75";
  }

  smiv2:alias "cevC6xxxEsm20GPfc3CxlDc" {
    smiv2:oid "1.3.6.1.4.1.9.12.3.1.9.17.76";
  }

  smiv2:alias "cevC6xxxEsm20GPfc3CDc" {
    smiv2:oid "1.3.6.1.4.1.9.12.3.1.9.17.77";
  }

  smiv2:alias "cevC6xxxEsm20G2x10gDc" {
    smiv2:oid "1.3.6.1.4.1.9.12.3.1.9.17.78";
  }

  smiv2:alias "cevC6xxxEsm20G20x1gDc" {
    smiv2:oid "1.3.6.1.4.1.9.12.3.1.9.17.79";
  }

  smiv2:alias "cevC6xxxRSP72010GEBase" {
    smiv2:oid "1.3.6.1.4.1.9.12.3.1.9.17.80";
  }

  smiv2:alias "cevC6xxxEs20C3c" {
    smiv2:oid "1.3.6.1.4.1.9.12.3.1.9.17.81";
  }

  smiv2:alias "cevC6xxxEs40C3c" {
    smiv2:oid "1.3.6.1.4.1.9.12.3.1.9.17.82";
  }

  smiv2:alias "cevC6xxxEs20C3cxl" {
    smiv2:oid "1.3.6.1.4.1.9.12.3.1.9.17.83";
  }

  smiv2:alias "cevC6xxxEs40C3cxl" {
    smiv2:oid "1.3.6.1.4.1.9.12.3.1.9.17.84";
  }

  smiv2:alias "cevC6xxxEs20G3c" {
    smiv2:oid "1.3.6.1.4.1.9.12.3.1.9.17.85";
  }

  smiv2:alias "cevC6xxxEs2Tg3c" {
    smiv2:oid "1.3.6.1.4.1.9.12.3.1.9.17.86";
  }

  smiv2:alias "cevC6xxxEs40G3c" {
    smiv2:oid "1.3.6.1.4.1.9.12.3.1.9.17.87";
  }

  smiv2:alias "cevC6xxxEs4Tg3c" {
    smiv2:oid "1.3.6.1.4.1.9.12.3.1.9.17.88";
  }

  smiv2:alias "cevC6xxxEs20G3cxl" {
    smiv2:oid "1.3.6.1.4.1.9.12.3.1.9.17.89";
  }

  smiv2:alias "cevC6xxxEs2Tg3cxl" {
    smiv2:oid "1.3.6.1.4.1.9.12.3.1.9.17.90";
  }

  smiv2:alias "cevC6xxxEs40G3cxl" {
    smiv2:oid "1.3.6.1.4.1.9.12.3.1.9.17.91";
  }

  smiv2:alias "cevC6xxxEs4Tg3cxl" {
    smiv2:oid "1.3.6.1.4.1.9.12.3.1.9.17.92";
  }

  smiv2:alias "cevC6xxxMsfc4" {
    smiv2:oid "1.3.6.1.4.1.9.12.3.1.9.17.93";
  }

  smiv2:alias "cevC6xxxPfc3c" {
    smiv2:oid "1.3.6.1.4.1.9.12.3.1.9.17.94";
  }

  smiv2:alias "cevC6xxxPfc3cxl" {
    smiv2:oid "1.3.6.1.4.1.9.12.3.1.9.17.95";
  }

  smiv2:alias "cevC6xxxEs2Tg20GDc" {
    smiv2:oid "1.3.6.1.4.1.9.12.3.1.9.17.96";
  }

  smiv2:alias "cevC6xxxEs1Tg10GDc" {
    smiv2:oid "1.3.6.1.4.1.9.12.3.1.9.17.97";
  }

  smiv2:alias "cevC6xxxEsBase" {
    smiv2:oid "1.3.6.1.4.1.9.12.3.1.9.17.98";
  }

  smiv2:alias "cevC6xxxEsPfc3CxlDc" {
    smiv2:oid "1.3.6.1.4.1.9.12.3.1.9.17.99";
  }

  smiv2:alias "cevC6xxxEsPfc3CDc" {
    smiv2:oid "1.3.6.1.4.1.9.12.3.1.9.17.100";
  }

  smiv2:alias "cevC6xxxEs20GDc" {
    smiv2:oid "1.3.6.1.4.1.9.12.3.1.9.17.101";
  }

  smiv2:alias "cevC6xxxEs2TgDc" {
    smiv2:oid "1.3.6.1.4.1.9.12.3.1.9.17.102";
  }

  smiv2:alias "cevC6xxxEs40GDc" {
    smiv2:oid "1.3.6.1.4.1.9.12.3.1.9.17.103";
  }

  smiv2:alias "cevC6xxxEs4TgDc" {
    smiv2:oid "1.3.6.1.4.1.9.12.3.1.9.17.104";
  }

  smiv2:alias "cevC6xxxEsItu2TgDc" {
    smiv2:oid "1.3.6.1.4.1.9.12.3.1.9.17.105";
  }

  smiv2:alias "cevC6xxxEsItu4TgDc" {
    smiv2:oid "1.3.6.1.4.1.9.12.3.1.9.17.106";
  }

  smiv2:alias "cevC6xxxEsItu2Tg3cxl" {
    smiv2:oid "1.3.6.1.4.1.9.12.3.1.9.17.107";
  }

  smiv2:alias "cevC6xxxEsItu4Tg3cxl" {
    smiv2:oid "1.3.6.1.4.1.9.12.3.1.9.17.108";
  }

  smiv2:alias "cevC6xxxEsT" {
    smiv2:oid "1.3.6.1.4.1.9.12.3.1.9.17.109";
  }

  smiv2:alias "cevC6xxxEsItu2Tg3c" {
    smiv2:oid "1.3.6.1.4.1.9.12.3.1.9.17.110";
  }

  smiv2:alias "cevC6xxxEsItu4Tg3c" {
    smiv2:oid "1.3.6.1.4.1.9.12.3.1.9.17.111";
  }

  smiv2:alias "cevC6xxxEst20gDc" {
    smiv2:oid "1.3.6.1.4.1.9.12.3.1.9.17.112";
  }

  smiv2:alias "cevC6xxxEst40gDc" {
    smiv2:oid "1.3.6.1.4.1.9.12.3.1.9.17.113";
  }

  smiv2:alias "cevC6xxxEstItu2tgDc" {
    smiv2:oid "1.3.6.1.4.1.9.12.3.1.9.17.114";
  }

  smiv2:alias "cevC6xxxEstItu4tgDc" {
    smiv2:oid "1.3.6.1.4.1.9.12.3.1.9.17.115";
  }

  smiv2:alias "cevC6xxxEst20G3Cxl" {
    smiv2:oid "1.3.6.1.4.1.9.12.3.1.9.17.116";
  }

  smiv2:alias "cevC6xxxEst40G3Cxl" {
    smiv2:oid "1.3.6.1.4.1.9.12.3.1.9.17.117";
  }

  smiv2:alias "cevC6xxxEstItu2TG3Cxl" {
    smiv2:oid "1.3.6.1.4.1.9.12.3.1.9.17.118";
  }

  smiv2:alias "cevC6xxxEstItu4TG3Cxl" {
    smiv2:oid "1.3.6.1.4.1.9.12.3.1.9.17.119";
  }

  smiv2:alias "cevC6xxxEsTXc20G" {
    smiv2:oid "1.3.6.1.4.1.9.12.3.1.9.17.120";
  }

  smiv2:alias "cevC6xxxEsTXc40G" {
    smiv2:oid "1.3.6.1.4.1.9.12.3.1.9.17.121";
  }

  smiv2:alias "cevC6xxxEsT8Tg" {
    smiv2:oid "1.3.6.1.4.1.9.12.3.1.9.17.122";
  }

  smiv2:alias "cevC6xxxEsXt8TG" {
    smiv2:oid "1.3.6.1.4.1.9.12.3.1.9.17.123";
  }

  smiv2:alias "cevC6xxxIA48FPD" {
    smiv2:oid "1.3.6.1.4.1.9.12.3.1.9.17.124";
  }

  smiv2:alias "cevC6xxxIA48TD" {
    smiv2:oid "1.3.6.1.4.1.9.12.3.1.9.17.125";
  }

  smiv2:alias "cevModuleGsrType" {
    smiv2:oid "1.3.6.1.4.1.9.12.3.1.9.18";
  }

  smiv2:alias "cevGsrOc12Chsts3Mm" {
    smiv2:oid "1.3.6.1.4.1.9.12.3.1.9.18.1";
  }

  smiv2:alias "cevGsrOc12Chsts3Sm" {
    smiv2:oid "1.3.6.1.4.1.9.12.3.1.9.18.2";
  }

  smiv2:alias "cevGsrQoc12Mm" {
    smiv2:oid "1.3.6.1.4.1.9.12.3.1.9.18.3";
  }

  smiv2:alias "cevGsrQoc12Sm" {
    smiv2:oid "1.3.6.1.4.1.9.12.3.1.9.18.4";
  }

  smiv2:alias "cevPosOc48SmLrFc" {
    smiv2:oid "1.3.6.1.4.1.9.12.3.1.9.18.5";
  }

  smiv2:alias "cevPosQoc3SmL" {
    smiv2:oid "1.3.6.1.4.1.9.12.3.1.9.18.6";
  }

  smiv2:alias "cevPos8oc3Mm" {
    smiv2:oid "1.3.6.1.4.1.9.12.3.1.9.18.7";
  }

  smiv2:alias "cevPos8oc3Ir" {
    smiv2:oid "1.3.6.1.4.1.9.12.3.1.9.18.8";
  }

  smiv2:alias "cevPos8oc3Lr" {
    smiv2:oid "1.3.6.1.4.1.9.12.3.1.9.18.9";
  }

  smiv2:alias "cevPos16oc3Mm" {
    smiv2:oid "1.3.6.1.4.1.9.12.3.1.9.18.10";
  }

  smiv2:alias "cevPos16oc3Ir" {
    smiv2:oid "1.3.6.1.4.1.9.12.3.1.9.18.11";
  }

  smiv2:alias "cevPos16oc3Lr" {
    smiv2:oid "1.3.6.1.4.1.9.12.3.1.9.18.12";
  }

  smiv2:alias "cevGsr8feTx" {
    smiv2:oid "1.3.6.1.4.1.9.12.3.1.9.18.13";
  }

  smiv2:alias "cevGsr8feFx" {
    smiv2:oid "1.3.6.1.4.1.9.12.3.1.9.18.14";
  }

  smiv2:alias "cevSsrpOc48SmSr" {
    smiv2:oid "1.3.6.1.4.1.9.12.3.1.9.18.15";
  }

  smiv2:alias "cevSsrpOc48SmLr" {
    smiv2:oid "1.3.6.1.4.1.9.12.3.1.9.18.16";
  }

  smiv2:alias "cevPosQoc12SmLr" {
    smiv2:oid "1.3.6.1.4.1.9.12.3.1.9.18.17";
  }

  smiv2:alias "cevPosQoc12MmSr" {
    smiv2:oid "1.3.6.1.4.1.9.12.3.1.9.18.18";
  }

  smiv2:alias "cevPosOc48SmSrFc" {
    smiv2:oid "1.3.6.1.4.1.9.12.3.1.9.18.19";
  }

  smiv2:alias "cevPosOc48SmLrSc" {
    smiv2:oid "1.3.6.1.4.1.9.12.3.1.9.18.20";
  }

  smiv2:alias "cevPosOc48SmSrSc" {
    smiv2:oid "1.3.6.1.4.1.9.12.3.1.9.18.21";
  }

  smiv2:alias "cevSrpOc12SmIr" {
    smiv2:oid "1.3.6.1.4.1.9.12.3.1.9.18.22";
  }

  smiv2:alias "cevSrpOc12SmLr" {
    smiv2:oid "1.3.6.1.4.1.9.12.3.1.9.18.23";
  }

  smiv2:alias "cevSrpOc12Mm" {
    smiv2:oid "1.3.6.1.4.1.9.12.3.1.9.18.24";
  }

  smiv2:alias "cevPosEnOc48SrSc" {
    smiv2:oid "1.3.6.1.4.1.9.12.3.1.9.18.25";
  }

  smiv2:alias "cevPosEnOc48SrFc" {
    smiv2:oid "1.3.6.1.4.1.9.12.3.1.9.18.26";
  }

  smiv2:alias "cevPosEnOc48LrSc" {
    smiv2:oid "1.3.6.1.4.1.9.12.3.1.9.18.27";
  }

  smiv2:alias "cevPosEnOc48LrFc" {
    smiv2:oid "1.3.6.1.4.1.9.12.3.1.9.18.28";
  }

  smiv2:alias "cevPosEnQoc12Sr" {
    smiv2:oid "1.3.6.1.4.1.9.12.3.1.9.18.29";
  }

  smiv2:alias "cevPosEnQoc12Ir" {
    smiv2:oid "1.3.6.1.4.1.9.12.3.1.9.18.30";
  }

  smiv2:alias "cevCopper6ds3" {
    smiv2:oid "1.3.6.1.4.1.9.12.3.1.9.18.31";
  }

  smiv2:alias "cevCopper12ds3" {
    smiv2:oid "1.3.6.1.4.1.9.12.3.1.9.18.32";
  }

  smiv2:alias "cevPosOc192SmIrFc" {
    smiv2:oid "1.3.6.1.4.1.9.12.3.1.9.18.33";
  }

  smiv2:alias "cevPosOc192SmSrFc" {
    smiv2:oid "1.3.6.1.4.1.9.12.3.1.9.18.34";
  }

  smiv2:alias "cevPosOc192SmIrSc" {
    smiv2:oid "1.3.6.1.4.1.9.12.3.1.9.18.35";
  }

  smiv2:alias "cevPosOc192SmSrSc" {
    smiv2:oid "1.3.6.1.4.1.9.12.3.1.9.18.36";
  }

  smiv2:alias "cevPos4Oc3Mm" {
    smiv2:oid "1.3.6.1.4.1.9.12.3.1.9.18.37";
  }

  smiv2:alias "cevPos4Oc3Sm" {
    smiv2:oid "1.3.6.1.4.1.9.12.3.1.9.18.38";
  }

  smiv2:alias "cevPosOc12Mm" {
    smiv2:oid "1.3.6.1.4.1.9.12.3.1.9.18.39";
  }

  smiv2:alias "cevPosOc12Sm" {
    smiv2:oid "1.3.6.1.4.1.9.12.3.1.9.18.40";
  }

  smiv2:alias "cevAtmOc12Mm" {
    smiv2:oid "1.3.6.1.4.1.9.12.3.1.9.18.41";
  }

  smiv2:alias "cevAtmOc12Sm" {
    smiv2:oid "1.3.6.1.4.1.9.12.3.1.9.18.42";
  }

  smiv2:alias "cevPosOc48MmL" {
    smiv2:oid "1.3.6.1.4.1.9.12.3.1.9.18.43";
  }

  smiv2:alias "cevAtm4Oc3Sm" {
    smiv2:oid "1.3.6.1.4.1.9.12.3.1.9.18.44";
  }

  smiv2:alias "cevAtm4Oc3Mm" {
    smiv2:oid "1.3.6.1.4.1.9.12.3.1.9.18.45";
  }

  smiv2:alias "cevOc12ChDs3Mm" {
    smiv2:oid "1.3.6.1.4.1.9.12.3.1.9.18.46";
  }

  smiv2:alias "cevOc12ChDs3Sm" {
    smiv2:oid "1.3.6.1.4.1.9.12.3.1.9.18.47";
  }

  smiv2:alias "cevGsrGe" {
    smiv2:oid "1.3.6.1.4.1.9.12.3.1.9.18.48";
  }

  smiv2:alias "cevGsr3ge" {
    smiv2:oid "1.3.6.1.4.1.9.12.3.1.9.18.49";
  }

  smiv2:alias "cevGsrAlarm16" {
    smiv2:oid "1.3.6.1.4.1.9.12.3.1.9.18.50";
  }

  smiv2:alias "cevGsrBusBoard16" {
    smiv2:oid "1.3.6.1.4.1.9.12.3.1.9.18.51";
  }

  smiv2:alias "cevSrpOc12SmXr" {
    smiv2:oid "1.3.6.1.4.1.9.12.3.1.9.18.52";
  }

  smiv2:alias "cevPosEnQoc12Mm" {
    smiv2:oid "1.3.6.1.4.1.9.12.3.1.9.18.53";
  }

  smiv2:alias "cevPosEnQoc48SmSrFc" {
    smiv2:oid "1.3.6.1.4.1.9.12.3.1.9.18.54";
  }

  smiv2:alias "cevPosEnQoc48SmSrSc" {
    smiv2:oid "1.3.6.1.4.1.9.12.3.1.9.18.55";
  }

  smiv2:alias "cevPosEnQoc48SmLrSc" {
    smiv2:oid "1.3.6.1.4.1.9.12.3.1.9.18.56";
  }

  smiv2:alias "cevPosEnQoc48SmLrFc" {
    smiv2:oid "1.3.6.1.4.1.9.12.3.1.9.18.57";
  }

  smiv2:alias "cevGsr6Ct3" {
    smiv2:oid "1.3.6.1.4.1.9.12.3.1.9.18.58";
  }

  smiv2:alias "cevPosEnOc192SmLrFc" {
    smiv2:oid "1.3.6.1.4.1.9.12.3.1.9.18.59";
  }

  smiv2:alias "cevPosEnOc192SmLrSc" {
    smiv2:oid "1.3.6.1.4.1.9.12.3.1.9.18.60";
  }

  smiv2:alias "cevPosEnOc192SmVsrSc" {
    smiv2:oid "1.3.6.1.4.1.9.12.3.1.9.18.61";
  }

  smiv2:alias "cevPosEnOc192SmVsrFc" {
    smiv2:oid "1.3.6.1.4.1.9.12.3.1.9.18.62";
  }

  smiv2:alias "cevGsrQoc12Chstsds3SmIrSc" {
    smiv2:oid "1.3.6.1.4.1.9.12.3.1.9.18.66";
  }

  smiv2:alias "cevGsrQoc12Chstsds3MmSrSc" {
    smiv2:oid "1.3.6.1.4.1.9.12.3.1.9.18.67";
  }

  smiv2:alias "cevGsrOc48Chstsds3MmSrSc" {
    smiv2:oid "1.3.6.1.4.1.9.12.3.1.9.18.68";
  }

  smiv2:alias "cevGsrOc48Chstsds3SmIrSc" {
    smiv2:oid "1.3.6.1.4.1.9.12.3.1.9.18.69";
  }

  smiv2:alias "cevGsrOc48Chstsds3SmLrSc" {
    smiv2:oid "1.3.6.1.4.1.9.12.3.1.9.18.70";
  }

  smiv2:alias "cevGsr16Oc3Chstsds3MmSrSc" {
    smiv2:oid "1.3.6.1.4.1.9.12.3.1.9.18.71";
  }

  smiv2:alias "cevGsr16Oc3Chstsds3SmIrSc" {
    smiv2:oid "1.3.6.1.4.1.9.12.3.1.9.18.72";
  }

  smiv2:alias "cevGsr16Oc3Chstsds3SmLrSc" {
    smiv2:oid "1.3.6.1.4.1.9.12.3.1.9.18.73";
  }

  smiv2:alias "cevGsr2Oc3ChDs1" {
    smiv2:oid "1.3.6.1.4.1.9.12.3.1.9.18.74";
  }

  smiv2:alias "cevSsrpOc192SmLr" {
    smiv2:oid "1.3.6.1.4.1.9.12.3.1.9.18.75";
  }

  smiv2:alias "cevSsrpOc192SmIr" {
    smiv2:oid "1.3.6.1.4.1.9.12.3.1.9.18.76";
  }

  smiv2:alias "cevSsrpOc192SmSr" {
    smiv2:oid "1.3.6.1.4.1.9.12.3.1.9.18.77";
  }

  smiv2:alias "cevSsrpOc192SmVsr" {
    smiv2:oid "1.3.6.1.4.1.9.12.3.1.9.18.78";
  }

  smiv2:alias "cev2Oc12ChDs3Sm" {
    smiv2:oid "1.3.6.1.4.1.9.12.3.1.9.18.80";
  }

  smiv2:alias "cevGsrAlarm10" {
    smiv2:oid "1.3.6.1.4.1.9.12.3.1.9.18.81";
  }

  smiv2:alias "cevGsrBusBoard10" {
    smiv2:oid "1.3.6.1.4.1.9.12.3.1.9.18.82";
  }

  smiv2:alias "cevGsrOc48Chstsds3SmSrSc" {
    smiv2:oid "1.3.6.1.4.1.9.12.3.1.9.18.83";
  }

  smiv2:alias "cevGsrE48PosOc48SmSrSc" {
    smiv2:oid "1.3.6.1.4.1.9.12.3.1.9.18.84";
  }

  smiv2:alias "cevGsrE48PosOc48SmLrSc" {
    smiv2:oid "1.3.6.1.4.1.9.12.3.1.9.18.85";
  }

  smiv2:alias "cevGsrE48PosQoc12SmIrSc" {
    smiv2:oid "1.3.6.1.4.1.9.12.3.1.9.18.86";
  }

  smiv2:alias "cevGsrE48Pos16oc3SmIrSc" {
    smiv2:oid "1.3.6.1.4.1.9.12.3.1.9.18.87";
  }

  smiv2:alias "cevCopper6e3" {
    smiv2:oid "1.3.6.1.4.1.9.12.3.1.9.18.88";
  }

  smiv2:alias "cevCopper12e3" {
    smiv2:oid "1.3.6.1.4.1.9.12.3.1.9.18.89";
  }

  smiv2:alias "cevGsrE48Pos16oc3SmIrLc" {
    smiv2:oid "1.3.6.1.4.1.9.12.3.1.9.18.93";
  }

  smiv2:alias "cevGsr16oc3Chstsds3SmIrLc" {
    smiv2:oid "1.3.6.1.4.1.9.12.3.1.9.18.94";
  }

  smiv2:alias "cevGsrOc12ChDs1SmIrSc" {
    smiv2:oid "1.3.6.1.4.1.9.12.3.1.9.18.95";
  }

  smiv2:alias "cevGsrAlarm6" {
    smiv2:oid "1.3.6.1.4.1.9.12.3.1.9.18.96";
  }

  smiv2:alias "cevPosEnQoc48Vsr" {
    smiv2:oid "1.3.6.1.4.1.9.12.3.1.9.18.97";
  }

  smiv2:alias "cevPosEnQoc48MmSrSc" {
    smiv2:oid "1.3.6.1.4.1.9.12.3.1.9.18.98";
  }

  smiv2:alias "cevPosEnQoc48SmIrSc" {
    smiv2:oid "1.3.6.1.4.1.9.12.3.1.9.18.99";
  }

  smiv2:alias "cevPosEnQoc48SmIrFc" {
    smiv2:oid "1.3.6.1.4.1.9.12.3.1.9.18.100";
  }

  smiv2:alias "cevPosEnQoc48SmVlrSc" {
    smiv2:oid "1.3.6.1.4.1.9.12.3.1.9.18.101";
  }

  smiv2:alias "cevPosEnQoc48SmVlrFc" {
    smiv2:oid "1.3.6.1.4.1.9.12.3.1.9.18.102";
  }

  smiv2:alias "cevPosEnQoc48SmElrSc" {
    smiv2:oid "1.3.6.1.4.1.9.12.3.1.9.18.103";
  }

  smiv2:alias "cevPosEnQoc48SmElrFc" {
    smiv2:oid "1.3.6.1.4.1.9.12.3.1.9.18.104";
  }

  smiv2:alias "cevPosEnOc192Vsr" {
    smiv2:oid "1.3.6.1.4.1.9.12.3.1.9.18.105";
  }

  smiv2:alias "cevPosEnOc192SmSr2Sc" {
    smiv2:oid "1.3.6.1.4.1.9.12.3.1.9.18.106";
  }

  smiv2:alias "cevPosEnOc192SmSr2Fc" {
    smiv2:oid "1.3.6.1.4.1.9.12.3.1.9.18.107";
  }

  smiv2:alias "cevPosEnOc192SmVlrSc" {
    smiv2:oid "1.3.6.1.4.1.9.12.3.1.9.18.108";
  }

  smiv2:alias "cevPosEnOc192SmVlrFc" {
    smiv2:oid "1.3.6.1.4.1.9.12.3.1.9.18.109";
  }

  smiv2:alias "cevPosEnOc192SmElrSc" {
    smiv2:oid "1.3.6.1.4.1.9.12.3.1.9.18.110";
  }

  smiv2:alias "cevPosEnOc192SmElrFc" {
    smiv2:oid "1.3.6.1.4.1.9.12.3.1.9.18.111";
  }

  smiv2:alias "cevGsrEn8Oc3" {
    smiv2:oid "1.3.6.1.4.1.9.12.3.1.9.18.112";
  }

  smiv2:alias "cevGsr1p10ge" {
    smiv2:oid "1.3.6.1.4.1.9.12.3.1.9.18.113";
  }

  smiv2:alias "cevGsrE48PosOc48SmIrSc" {
    smiv2:oid "1.3.6.1.4.1.9.12.3.1.9.18.114";
  }

  smiv2:alias "cevGsrEOc192SmLrSc" {
    smiv2:oid "1.3.6.1.4.1.9.12.3.1.9.18.116";
  }

  smiv2:alias "cevGsrEOc192SmVsrSc" {
    smiv2:oid "1.3.6.1.4.1.9.12.3.1.9.18.117";
  }

  smiv2:alias "cevGsrEOc192SmVsrFc" {
    smiv2:oid "1.3.6.1.4.1.9.12.3.1.9.18.118";
  }

  smiv2:alias "cevGsrEOc192SmSrFc" {
    smiv2:oid "1.3.6.1.4.1.9.12.3.1.9.18.119";
  }

  smiv2:alias "cevGsrEOc192SmSrSc" {
    smiv2:oid "1.3.6.1.4.1.9.12.3.1.9.18.120";
  }

  smiv2:alias "cevGsrEOc192SmLrFc" {
    smiv2:oid "1.3.6.1.4.1.9.12.3.1.9.18.121";
  }

  smiv2:alias "cevGsrEQoc48SmLrFc" {
    smiv2:oid "1.3.6.1.4.1.9.12.3.1.9.18.122";
  }

  smiv2:alias "cevGsrEQoc48SmLrSc" {
    smiv2:oid "1.3.6.1.4.1.9.12.3.1.9.18.123";
  }

  smiv2:alias "cevGsrEQoc48SmVsrSc" {
    smiv2:oid "1.3.6.1.4.1.9.12.3.1.9.18.124";
  }

  smiv2:alias "cevGsrEQoc48SmVsrFc" {
    smiv2:oid "1.3.6.1.4.1.9.12.3.1.9.18.125";
  }

  smiv2:alias "cevGsrEQoc48SmSrFc" {
    smiv2:oid "1.3.6.1.4.1.9.12.3.1.9.18.126";
  }

  smiv2:alias "cevGsrEQoc48SmSrSc" {
    smiv2:oid "1.3.6.1.4.1.9.12.3.1.9.18.127";
  }

  smiv2:alias "cevGsrEQoc48Vsr" {
    smiv2:oid "1.3.6.1.4.1.9.12.3.1.9.18.128";
  }

  smiv2:alias "cevGsrEQoc48SmSr2Sc" {
    smiv2:oid "1.3.6.1.4.1.9.12.3.1.9.18.129";
  }

  smiv2:alias "cevGsrEQoc48SmSr2Fc" {
    smiv2:oid "1.3.6.1.4.1.9.12.3.1.9.18.130";
  }

  smiv2:alias "cevGsrEQoc48MmSrSc" {
    smiv2:oid "1.3.6.1.4.1.9.12.3.1.9.18.131";
  }

  smiv2:alias "cevGsrEQoc48SmIrSc" {
    smiv2:oid "1.3.6.1.4.1.9.12.3.1.9.18.132";
  }

  smiv2:alias "cevGsrEQoc48SmIrFc" {
    smiv2:oid "1.3.6.1.4.1.9.12.3.1.9.18.133";
  }

  smiv2:alias "cevGsrEQoc48SmVlrSc" {
    smiv2:oid "1.3.6.1.4.1.9.12.3.1.9.18.134";
  }

  smiv2:alias "cevGsrEQoc48SmVlrFc" {
    smiv2:oid "1.3.6.1.4.1.9.12.3.1.9.18.135";
  }

  smiv2:alias "cevGsrEQoc48SmElrSc" {
    smiv2:oid "1.3.6.1.4.1.9.12.3.1.9.18.136";
  }

  smiv2:alias "cevGsrEQoc48SmElrFc" {
    smiv2:oid "1.3.6.1.4.1.9.12.3.1.9.18.137";
  }

  smiv2:alias "cevGsrEOc192Vsr" {
    smiv2:oid "1.3.6.1.4.1.9.12.3.1.9.18.138";
  }

  smiv2:alias "cevGsrEOc192SmSr2Sc" {
    smiv2:oid "1.3.6.1.4.1.9.12.3.1.9.18.139";
  }

  smiv2:alias "cevGsrEOc192SmSr2Fc" {
    smiv2:oid "1.3.6.1.4.1.9.12.3.1.9.18.140";
  }

  smiv2:alias "cevGsrEOc192MmSrSc" {
    smiv2:oid "1.3.6.1.4.1.9.12.3.1.9.18.141";
  }

  smiv2:alias "cevGsrEOc192SmIrSc" {
    smiv2:oid "1.3.6.1.4.1.9.12.3.1.9.18.142";
  }

  smiv2:alias "cevGsrEOc192SmIrFc" {
    smiv2:oid "1.3.6.1.4.1.9.12.3.1.9.18.143";
  }

  smiv2:alias "cevGsrEOc192SmVlrSc" {
    smiv2:oid "1.3.6.1.4.1.9.12.3.1.9.18.144";
  }

  smiv2:alias "cevGsrEOc192SmVlrFc" {
    smiv2:oid "1.3.6.1.4.1.9.12.3.1.9.18.145";
  }

  smiv2:alias "cevGsrEOc192SmElrSc" {
    smiv2:oid "1.3.6.1.4.1.9.12.3.1.9.18.146";
  }

  smiv2:alias "cevGsrEOc192SmElrFc" {
    smiv2:oid "1.3.6.1.4.1.9.12.3.1.9.18.147";
  }

  smiv2:alias "cevSsrp2Oc48SrpSmSrLc" {
    smiv2:oid "1.3.6.1.4.1.9.12.3.1.9.18.148";
  }

  smiv2:alias "cevSsrp2Oc48SrpSmIrLc" {
    smiv2:oid "1.3.6.1.4.1.9.12.3.1.9.18.149";
  }

  smiv2:alias "cevSsrp2Oc48SrpSmLrLc" {
    smiv2:oid "1.3.6.1.4.1.9.12.3.1.9.18.150";
  }

  smiv2:alias "cevSsrp2Oc48PosSmSrLc" {
    smiv2:oid "1.3.6.1.4.1.9.12.3.1.9.18.151";
  }

  smiv2:alias "cevSsrp2Oc48PosSmIrLc" {
    smiv2:oid "1.3.6.1.4.1.9.12.3.1.9.18.152";
  }

  smiv2:alias "cevSsrp2Oc48PosSmLrLc" {
    smiv2:oid "1.3.6.1.4.1.9.12.3.1.9.18.153";
  }

  smiv2:alias "cevGsrE48PosQoc12MmSrSc" {
    smiv2:oid "1.3.6.1.4.1.9.12.3.1.9.18.155";
  }

  smiv2:alias "cevGsrGeFe" {
    smiv2:oid "1.3.6.1.4.1.9.12.3.1.9.18.156";
  }

  smiv2:alias "cevGsrE48Atm4oc12SmIrSc" {
    smiv2:oid "1.3.6.1.4.1.9.12.3.1.9.18.157";
  }

  smiv2:alias "cevGsrE48Atm4oc12MmSrSc" {
    smiv2:oid "1.3.6.1.4.1.9.12.3.1.9.18.158";
  }

  smiv2:alias "cevGsrE48Atm4oc3SmIrSc" {
    smiv2:oid "1.3.6.1.4.1.9.12.3.1.9.18.159";
  }

  smiv2:alias "cevGsrE48Atm4oc3MmSrSc" {
    smiv2:oid "1.3.6.1.4.1.9.12.3.1.9.18.160";
  }

  smiv2:alias "cevGsrE48Pos4oc3SmIrLc" {
    smiv2:oid "1.3.6.1.4.1.9.12.3.1.9.18.162";
  }

  smiv2:alias "cevGsrE48Pos8oc3SmIrLc" {
    smiv2:oid "1.3.6.1.4.1.9.12.3.1.9.18.166";
  }

  smiv2:alias "cevSsrp2Oc12E48SmIr" {
    smiv2:oid "1.3.6.1.4.1.9.12.3.1.9.18.167";
  }

  smiv2:alias "cevSsrp2Oc12E48SmXr" {
    smiv2:oid "1.3.6.1.4.1.9.12.3.1.9.18.168";
  }

  smiv2:alias "cevSsrp1Oc12E48SmIr" {
    smiv2:oid "1.3.6.1.4.1.9.12.3.1.9.18.169";
  }

  smiv2:alias "cevSsrp1Oc12E48SmXr" {
    smiv2:oid "1.3.6.1.4.1.9.12.3.1.9.18.170";
  }

  smiv2:alias "cevGsrSIP600" {
    smiv2:oid "1.3.6.1.4.1.9.12.3.1.9.18.171";
  }

  smiv2:alias "cevGsr4pge" {
    smiv2:oid "1.3.6.1.4.1.9.12.3.1.9.18.173";
  }

  smiv2:alias "cevGsrAtmEn8Oc3Mm" {
    smiv2:oid "1.3.6.1.4.1.9.12.3.1.9.18.174";
  }

  smiv2:alias "cevGsr2Oc192Pos" {
    smiv2:oid "1.3.6.1.4.1.9.12.3.1.9.18.175";
  }

  smiv2:alias "cevGsr8Oc48Pos" {
    smiv2:oid "1.3.6.1.4.1.9.12.3.1.9.18.176";
  }

  smiv2:alias "cevGsrOc48Msr" {
    smiv2:oid "1.3.6.1.4.1.9.12.3.1.9.18.177";
  }

  smiv2:alias "cevPosE2Oc192Vsr" {
    smiv2:oid "1.3.6.1.4.1.9.12.3.1.9.18.178";
  }

  smiv2:alias "cevPosE2Oc192SmSr2Sc" {
    smiv2:oid "1.3.6.1.4.1.9.12.3.1.9.18.179";
  }

  smiv2:alias "cevPosE2Oc192SmSr2Fc" {
    smiv2:oid "1.3.6.1.4.1.9.12.3.1.9.18.180";
  }

  smiv2:alias "cevPosE2Oc192SmSrSc" {
    smiv2:oid "1.3.6.1.4.1.9.12.3.1.9.18.181";
  }

  smiv2:alias "cevPosE2Oc192SmSrFc" {
    smiv2:oid "1.3.6.1.4.1.9.12.3.1.9.18.182";
  }

  smiv2:alias "cevPosE2Oc192SmIrSc" {
    smiv2:oid "1.3.6.1.4.1.9.12.3.1.9.18.183";
  }

  smiv2:alias "cevPosE2Oc192SmIrFc" {
    smiv2:oid "1.3.6.1.4.1.9.12.3.1.9.18.184";
  }

  smiv2:alias "cevPosE2Oc192SmLrSc" {
    smiv2:oid "1.3.6.1.4.1.9.12.3.1.9.18.185";
  }

  smiv2:alias "cevPosE2Oc192SmLrFc" {
    smiv2:oid "1.3.6.1.4.1.9.12.3.1.9.18.186";
  }

  smiv2:alias "cevPosE2Oc192SmVlrSc" {
    smiv2:oid "1.3.6.1.4.1.9.12.3.1.9.18.187";
  }

  smiv2:alias "cevPosE2Oc192SmVlrFc" {
    smiv2:oid "1.3.6.1.4.1.9.12.3.1.9.18.188";
  }

  smiv2:alias "cevPosE2Oc192SmElrSc" {
    smiv2:oid "1.3.6.1.4.1.9.12.3.1.9.18.189";
  }

  smiv2:alias "cevPosE2Oc192SmElrFc" {
    smiv2:oid "1.3.6.1.4.1.9.12.3.1.9.18.190";
  }

  smiv2:alias "cevGsr6Ds3e3Smb" {
    smiv2:oid "1.3.6.1.4.1.9.12.3.1.9.18.191";
  }

  smiv2:alias "cevGsr6Ds3e3Ct3Smb" {
    smiv2:oid "1.3.6.1.4.1.9.12.3.1.9.18.192";
  }

  smiv2:alias "cevGsr2Oc3Chds1ds3e3SmIrSc" {
    smiv2:oid "1.3.6.1.4.1.9.12.3.1.9.18.193";
  }

  smiv2:alias "cevGsrService" {
    smiv2:oid "1.3.6.1.4.1.9.12.3.1.9.18.194";
  }

  smiv2:alias "cevGsrSIP601" {
    smiv2:oid "1.3.6.1.4.1.9.12.3.1.9.18.195";
  }

  smiv2:alias "cevGsrSIP501" {
    smiv2:oid "1.3.6.1.4.1.9.12.3.1.9.18.196";
  }

  smiv2:alias "cevGsrSIP401" {
    smiv2:oid "1.3.6.1.4.1.9.12.3.1.9.18.197";
  }

  smiv2:alias "cevGsrSsrp2Oc48Lc" {
    smiv2:oid "1.3.6.1.4.1.9.12.3.1.9.18.198";
  }

  smiv2:alias "cevGsrE384Cec" {
    smiv2:oid "1.3.6.1.4.1.9.12.3.1.9.18.200";
  }

  smiv2:alias "cevModuleRpmType" {
    smiv2:oid "1.3.6.1.4.1.9.12.3.1.9.19";
  }

  smiv2:alias "cevAtmdxRpm" {
    smiv2:oid "1.3.6.1.4.1.9.12.3.1.9.19.1";
  }

  smiv2:alias "cevModuleCat8500Type" {
    smiv2:oid "1.3.6.1.4.1.9.12.3.1.9.20";
  }

  smiv2:alias "cevCat8500CpuSwitch" {
    smiv2:oid "1.3.6.1.4.1.9.12.3.1.9.20.1";
  }

  smiv2:alias "cevCat8500FeatureFpga" {
    smiv2:oid "1.3.6.1.4.1.9.12.3.1.9.20.2";
  }

  smiv2:alias "cevCat8500FeatureAsic" {
    smiv2:oid "1.3.6.1.4.1.9.12.3.1.9.20.3";
  }

  smiv2:alias "cevCat8500FeaturePVC" {
    smiv2:oid "1.3.6.1.4.1.9.12.3.1.9.20.4";
  }

  smiv2:alias "cevCat8500FeUTP8p16k" {
    smiv2:oid "1.3.6.1.4.1.9.12.3.1.9.20.5";
  }

  smiv2:alias "cevCat8500FeUTP8p64k" {
    smiv2:oid "1.3.6.1.4.1.9.12.3.1.9.20.6";
  }

  smiv2:alias "cevCat8500FeMMF8p16k" {
    smiv2:oid "1.3.6.1.4.1.9.12.3.1.9.20.7";
  }

  smiv2:alias "cevCat8500FeMMF8p64k" {
    smiv2:oid "1.3.6.1.4.1.9.12.3.1.9.20.8";
  }

  smiv2:alias "cevCat8500FeUTP16p16k" {
    smiv2:oid "1.3.6.1.4.1.9.12.3.1.9.20.9";
  }

  smiv2:alias "cevCat8500FeUTP16p64k" {
    smiv2:oid "1.3.6.1.4.1.9.12.3.1.9.20.10";
  }

  smiv2:alias "cevCat8500FeMMF16p16k" {
    smiv2:oid "1.3.6.1.4.1.9.12.3.1.9.20.11";
  }

  smiv2:alias "cevCat8500FeMMF16p64k" {
    smiv2:oid "1.3.6.1.4.1.9.12.3.1.9.20.12";
  }

  smiv2:alias "cevCat8500GeF1p16k" {
    smiv2:oid "1.3.6.1.4.1.9.12.3.1.9.20.13";
  }

  smiv2:alias "cevCat8500GeF1p64k" {
    smiv2:oid "1.3.6.1.4.1.9.12.3.1.9.20.14";
  }

  smiv2:alias "cevCat8500GeF2p16k" {
    smiv2:oid "1.3.6.1.4.1.9.12.3.1.9.20.15";
  }

  smiv2:alias "cevCat8500GeF2p64k" {
    smiv2:oid "1.3.6.1.4.1.9.12.3.1.9.20.16";
  }

  smiv2:alias "cevCat8500FeBridge4p" {
    smiv2:oid "1.3.6.1.4.1.9.12.3.1.9.20.17";
  }

  smiv2:alias "cevCat8500RouteProc" {
    smiv2:oid "1.3.6.1.4.1.9.12.3.1.9.20.18";
  }

  smiv2:alias "cevCat8500Switch10GProc" {
    smiv2:oid "1.3.6.1.4.1.9.12.3.1.9.20.19";
  }

  smiv2:alias "cevCat8500FeatureNetClock" {
    smiv2:oid "1.3.6.1.4.1.9.12.3.1.9.20.20";
  }

  smiv2:alias "cevCat8500FeatureABR" {
    smiv2:oid "1.3.6.1.4.1.9.12.3.1.9.20.21";
  }

  smiv2:alias "cevCat8500FeatureLite" {
    smiv2:oid "1.3.6.1.4.1.9.12.3.1.9.20.22";
  }

  smiv2:alias "cevCat8500m16pOC3Mm" {
    smiv2:oid "1.3.6.1.4.1.9.12.3.1.9.20.23";
  }

  smiv2:alias "cevCat8500m16pOC3Sm" {
    smiv2:oid "1.3.6.1.4.1.9.12.3.1.9.20.24";
  }

  smiv2:alias "cevCat8500m4pOC12Mm" {
    smiv2:oid "1.3.6.1.4.1.9.12.3.1.9.20.25";
  }

  smiv2:alias "cevCat8500m4pOC12Sm" {
    smiv2:oid "1.3.6.1.4.1.9.12.3.1.9.20.26";
  }

  smiv2:alias "cevCat8500m4pOC3Utp5" {
    smiv2:oid "1.3.6.1.4.1.9.12.3.1.9.20.27";
  }

  smiv2:alias "cevCat8500m4pOC3Mixed" {
    smiv2:oid "1.3.6.1.4.1.9.12.3.1.9.20.28";
  }

  smiv2:alias "cevCat8500m4pOC3Sm" {
    smiv2:oid "1.3.6.1.4.1.9.12.3.1.9.20.29";
  }

  smiv2:alias "cevCat8500m4pOC3Mm" {
    smiv2:oid "1.3.6.1.4.1.9.12.3.1.9.20.30";
  }

  smiv2:alias "cevCat8500mATM25" {
    smiv2:oid "1.3.6.1.4.1.9.12.3.1.9.20.31";
  }

  smiv2:alias "cevCat8500m4pE3" {
    smiv2:oid "1.3.6.1.4.1.9.12.3.1.9.20.32";
  }

  smiv2:alias "cevCat8500m4pDs3" {
    smiv2:oid "1.3.6.1.4.1.9.12.3.1.9.20.33";
  }

  smiv2:alias "cevCat8500mCbr75E1" {
    smiv2:oid "1.3.6.1.4.1.9.12.3.1.9.20.34";
  }

  smiv2:alias "cevCat8500mCbr120E1" {
    smiv2:oid "1.3.6.1.4.1.9.12.3.1.9.20.35";
  }

  smiv2:alias "cevCat8500mCbrT1" {
    smiv2:oid "1.3.6.1.4.1.9.12.3.1.9.20.36";
  }

  smiv2:alias "cevCat8500mE1" {
    smiv2:oid "1.3.6.1.4.1.9.12.3.1.9.20.37";
  }

  smiv2:alias "cevCat8500mT1" {
    smiv2:oid "1.3.6.1.4.1.9.12.3.1.9.20.38";
  }

  smiv2:alias "cevCat8500mE1Bnc" {
    smiv2:oid "1.3.6.1.4.1.9.12.3.1.9.20.39";
  }

  smiv2:alias "cevCat8500mE3" {
    smiv2:oid "1.3.6.1.4.1.9.12.3.1.9.20.40";
  }

  smiv2:alias "cevCat8500mDs3" {
    smiv2:oid "1.3.6.1.4.1.9.12.3.1.9.20.41";
  }

  smiv2:alias "cevCat8500m4pFrCE1" {
    smiv2:oid "1.3.6.1.4.1.9.12.3.1.9.20.42";
  }

  smiv2:alias "cevCat8500m1pFrCT3" {
    smiv2:oid "1.3.6.1.4.1.9.12.3.1.9.20.43";
  }

  smiv2:alias "cevCat8500GeF8p64k" {
    smiv2:oid "1.3.6.1.4.1.9.12.3.1.9.20.44";
  }

  smiv2:alias "cevCat8500mArm1p64k" {
    smiv2:oid "1.3.6.1.4.1.9.12.3.1.9.20.45";
  }

  smiv2:alias "cevCat8500mArm2p64k" {
    smiv2:oid "1.3.6.1.4.1.9.12.3.1.9.20.46";
  }

  smiv2:alias "cevCat8500mOC48c1pSm" {
    smiv2:oid "1.3.6.1.4.1.9.12.3.1.9.20.47";
  }

  smiv2:alias "cevCat8500mIma8pT1" {
    smiv2:oid "1.3.6.1.4.1.9.12.3.1.9.20.48";
  }

  smiv2:alias "cevCat8500mIma8pE1" {
    smiv2:oid "1.3.6.1.4.1.9.12.3.1.9.20.49";
  }

  smiv2:alias "cevCat8500mATM25m4p" {
    smiv2:oid "1.3.6.1.4.1.9.12.3.1.9.20.50";
  }

  smiv2:alias "cevCat8500mOC121pMm" {
    smiv2:oid "1.3.6.1.4.1.9.12.3.1.9.20.51";
  }

  smiv2:alias "cevCat8500mOC121pSm" {
    smiv2:oid "1.3.6.1.4.1.9.12.3.1.9.20.52";
  }

  smiv2:alias "cevCat8500m1pOC12Mixed" {
    smiv2:oid "1.3.6.1.4.1.9.12.3.1.9.20.53";
  }

  smiv2:alias "cevCat8500mFimBridge" {
    smiv2:oid "1.3.6.1.4.1.9.12.3.1.9.20.54";
  }

  smiv2:alias "cevCat8500mFimOC12Mm" {
    smiv2:oid "1.3.6.1.4.1.9.12.3.1.9.20.55";
  }

  smiv2:alias "cevCat8500Ge1pXpif16k" {
    smiv2:oid "1.3.6.1.4.1.9.12.3.1.9.20.56";
  }

  smiv2:alias "cevCat8500Ge1pXpif64k" {
    smiv2:oid "1.3.6.1.4.1.9.12.3.1.9.20.57";
  }

  smiv2:alias "cevCat8500Ge1pXpif256k" {
    smiv2:oid "1.3.6.1.4.1.9.12.3.1.9.20.58";
  }

  smiv2:alias "cevCat8500Atm1pXpif64kOc12SmIr" {
    smiv2:oid "1.3.6.1.4.1.9.12.3.1.9.20.59";
  }

  smiv2:alias "cevCat8500Atm1pXpif256kOc12SmIr" {
    smiv2:oid "1.3.6.1.4.1.9.12.3.1.9.20.60";
  }

  smiv2:alias "cevCat8500Atm1pXpif64kOc12Mm" {
    smiv2:oid "1.3.6.1.4.1.9.12.3.1.9.20.61";
  }

  smiv2:alias "cevCat8500Atm1pXpif256kOc12Mm" {
    smiv2:oid "1.3.6.1.4.1.9.12.3.1.9.20.62";
  }

  smiv2:alias "cevCat8500Atm1pXpif64kOc3SmIr" {
    smiv2:oid "1.3.6.1.4.1.9.12.3.1.9.20.63";
  }

  smiv2:alias "cevCat8500Atm1pXpif256kOc3SmIr" {
    smiv2:oid "1.3.6.1.4.1.9.12.3.1.9.20.64";
  }

  smiv2:alias "cevCat8500Atm1pXpif64kOc3Mm" {
    smiv2:oid "1.3.6.1.4.1.9.12.3.1.9.20.65";
  }

  smiv2:alias "cevCat8500Atm1pXpif256kOc3Mm" {
    smiv2:oid "1.3.6.1.4.1.9.12.3.1.9.20.66";
  }

  smiv2:alias "cevCat8500Pos1pXpif64kOc12SmIr" {
    smiv2:oid "1.3.6.1.4.1.9.12.3.1.9.20.67";
  }

  smiv2:alias "cevCat8500Pos1pXpif256kOc12SmIr" {
    smiv2:oid "1.3.6.1.4.1.9.12.3.1.9.20.68";
  }

  smiv2:alias "cevCat8500Pos1pXpif64kOc12SmLr" {
    smiv2:oid "1.3.6.1.4.1.9.12.3.1.9.20.69";
  }

  smiv2:alias "cevCat8500Pos1pXpif256kOc12SmLr" {
    smiv2:oid "1.3.6.1.4.1.9.12.3.1.9.20.70";
  }

  smiv2:alias "cevModuleWASCommonCards" {
    smiv2:oid "1.3.6.1.4.1.9.12.3.1.9.21";
  }

  smiv2:alias "cevAusm8t1" {
    smiv2:oid "1.3.6.1.4.1.9.12.3.1.9.21.1";
  }

  smiv2:alias "cevAusm8e1" {
    smiv2:oid "1.3.6.1.4.1.9.12.3.1.9.21.2";
  }

  smiv2:alias "cevCesm8t1" {
    smiv2:oid "1.3.6.1.4.1.9.12.3.1.9.21.3";
  }

  smiv2:alias "cevCesm8e1" {
    smiv2:oid "1.3.6.1.4.1.9.12.3.1.9.21.4";
  }

  smiv2:alias "cevFrsm8t1" {
    smiv2:oid "1.3.6.1.4.1.9.12.3.1.9.21.5";
  }

  smiv2:alias "cevFrsm8e1" {
    smiv2:oid "1.3.6.1.4.1.9.12.3.1.9.21.6";
  }

  smiv2:alias "cevFrsm4x21" {
    smiv2:oid "1.3.6.1.4.1.9.12.3.1.9.21.7";
  }

  smiv2:alias "cevFrsm2hssi" {
    smiv2:oid "1.3.6.1.4.1.9.12.3.1.9.21.8";
  }

  smiv2:alias "cevAxsm1Oc48" {
    smiv2:oid "1.3.6.1.4.1.9.12.3.1.9.21.9";
  }

  smiv2:alias "cevAxsm4Oc12" {
    smiv2:oid "1.3.6.1.4.1.9.12.3.1.9.21.10";
  }

  smiv2:alias "cevAxsm8Oc3" {
    smiv2:oid "1.3.6.1.4.1.9.12.3.1.9.21.11";
  }

  smiv2:alias "cevAxsm16Oc3" {
    smiv2:oid "1.3.6.1.4.1.9.12.3.1.9.21.12";
  }

  smiv2:alias "cevAxsm16T3E3" {
    smiv2:oid "1.3.6.1.4.1.9.12.3.1.9.21.13";
  }

  smiv2:alias "cevCesm1t3" {
    smiv2:oid "1.3.6.1.4.1.9.12.3.1.9.21.14";
  }

  smiv2:alias "cevCesm1e3" {
    smiv2:oid "1.3.6.1.4.1.9.12.3.1.9.21.15";
  }

  smiv2:alias "cevVism8t1" {
    smiv2:oid "1.3.6.1.4.1.9.12.3.1.9.21.16";
  }

  smiv2:alias "cevVism8e1" {
    smiv2:oid "1.3.6.1.4.1.9.12.3.1.9.21.17";
  }

  smiv2:alias "cevMGXRpm" {
    smiv2:oid "1.3.6.1.4.1.9.12.3.1.9.21.18";
  }

  smiv2:alias "cevMGXSrm3t3" {
    smiv2:oid "1.3.6.1.4.1.9.12.3.1.9.21.19";
  }

  smiv2:alias "cevEnhAxsm1oc12" {
    smiv2:oid "1.3.6.1.4.1.9.12.3.1.9.21.20";
  }

  smiv2:alias "cevEnhAxsm2oc12" {
    smiv2:oid "1.3.6.1.4.1.9.12.3.1.9.21.21";
  }

  smiv2:alias "cevEnhAxsm4oc3" {
    smiv2:oid "1.3.6.1.4.1.9.12.3.1.9.21.22";
  }

  smiv2:alias "cevEnhAxsm8oc3" {
    smiv2:oid "1.3.6.1.4.1.9.12.3.1.9.21.23";
  }

  smiv2:alias "cevEnhAxsm4stm1" {
    smiv2:oid "1.3.6.1.4.1.9.12.3.1.9.21.24";
  }

  smiv2:alias "cevEnhAxsm8stm1" {
    smiv2:oid "1.3.6.1.4.1.9.12.3.1.9.21.25";
  }

  smiv2:alias "cevEnhAxsm8t3e3" {
    smiv2:oid "1.3.6.1.4.1.9.12.3.1.9.21.26";
  }

  smiv2:alias "cevEnhAxsm16t3e3" {
    smiv2:oid "1.3.6.1.4.1.9.12.3.1.9.21.27";
  }

  smiv2:alias "cevEnhAxsm8t1" {
    smiv2:oid "1.3.6.1.4.1.9.12.3.1.9.21.28";
  }

  smiv2:alias "cevEnhAxsm16t1" {
    smiv2:oid "1.3.6.1.4.1.9.12.3.1.9.21.29";
  }

  smiv2:alias "cevEnhAxsm8e1" {
    smiv2:oid "1.3.6.1.4.1.9.12.3.1.9.21.30";
  }

  smiv2:alias "cevEnhAxsm16e1" {
    smiv2:oid "1.3.6.1.4.1.9.12.3.1.9.21.31";
  }

  smiv2:alias "cevAxsm2oc12" {
    smiv2:oid "1.3.6.1.4.1.9.12.3.1.9.21.32";
  }

  smiv2:alias "cevMGXRpmPr" {
    smiv2:oid "1.3.6.1.4.1.9.12.3.1.9.21.34";
  }

  smiv2:alias "cevFrsm4V35" {
    smiv2:oid "1.3.6.1.4.1.9.12.3.1.9.21.38";
  }

  smiv2:alias "cevFrsm2Ct3" {
    smiv2:oid "1.3.6.1.4.1.9.12.3.1.9.21.39";
  }

  smiv2:alias "cevFrsm2t3" {
    smiv2:oid "1.3.6.1.4.1.9.12.3.1.9.21.40";
  }

  smiv2:alias "cevFrsm2e3" {
    smiv2:oid "1.3.6.1.4.1.9.12.3.1.9.21.41";
  }

  smiv2:alias "cevAusmB8t1" {
    smiv2:oid "1.3.6.1.4.1.9.12.3.1.9.21.42";
  }

  smiv2:alias "cevAusmB8e1" {
    smiv2:oid "1.3.6.1.4.1.9.12.3.1.9.21.43";
  }

  smiv2:alias "cevVixm4oc12" {
    smiv2:oid "1.3.6.1.4.1.9.12.3.1.9.21.45";
  }

  smiv2:alias "cevVixm16oc3" {
    smiv2:oid "1.3.6.1.4.1.9.12.3.1.9.21.46";
  }

  smiv2:alias "cevCesmB8e1" {
    smiv2:oid "1.3.6.1.4.1.9.12.3.1.9.21.49";
  }

  smiv2:alias "cevCesmB8t1" {
    smiv2:oid "1.3.6.1.4.1.9.12.3.1.9.21.50";
  }

  smiv2:alias "cevFrsmC8e1" {
    smiv2:oid "1.3.6.1.4.1.9.12.3.1.9.21.51";
  }

  smiv2:alias "cevFrsmC8t1" {
    smiv2:oid "1.3.6.1.4.1.9.12.3.1.9.21.52";
  }

  smiv2:alias "cevFrsmB2hssi" {
    smiv2:oid "1.3.6.1.4.1.9.12.3.1.9.21.53";
  }

  smiv2:alias "cevFrsmB12In1" {
    smiv2:oid "1.3.6.1.4.1.9.12.3.1.9.21.54";
  }

  smiv2:alias "cevHsfr12t3" {
    smiv2:oid "1.3.6.1.4.1.9.12.3.1.9.21.55";
  }

  smiv2:alias "cevHsfr12e3" {
    smiv2:oid "1.3.6.1.4.1.9.12.3.1.9.21.56";
  }

  smiv2:alias "cevFrsm12t3" {
    smiv2:oid "1.3.6.1.4.1.9.12.3.1.9.21.57";
  }

  smiv2:alias "cevFrsm12e3" {
    smiv2:oid "1.3.6.1.4.1.9.12.3.1.9.21.58";
  }

  smiv2:alias "cevFrsmB2T3" {
    smiv2:oid "1.3.6.1.4.1.9.12.3.1.9.21.59";
  }

  smiv2:alias "cevMgxSrme1Sts3" {
    smiv2:oid "1.3.6.1.4.1.9.12.3.1.9.21.60";
  }

  smiv2:alias "cevMgxSrm3t3NoBc" {
    smiv2:oid "1.3.6.1.4.1.9.12.3.1.9.21.61";
  }

  smiv2:alias "cevMgxSrmeNoBc" {
    smiv2:oid "1.3.6.1.4.1.9.12.3.1.9.21.62";
  }

  smiv2:alias "cevAxsmEn16t1e1" {
    smiv2:oid "1.3.6.1.4.1.9.12.3.1.9.21.63";
  }

  smiv2:alias "cevAxsmEn32t1e1" {
    smiv2:oid "1.3.6.1.4.1.9.12.3.1.9.21.64";
  }

  smiv2:alias "cevFrsmB2e3" {
    smiv2:oid "1.3.6.1.4.1.9.12.3.1.9.21.66";
  }

  smiv2:alias "cevVismPr8t1" {
    smiv2:oid "1.3.6.1.4.1.9.12.3.1.9.21.70";
  }

  smiv2:alias "cevVismPr8e1" {
    smiv2:oid "1.3.6.1.4.1.9.12.3.1.9.21.71";
  }

  smiv2:alias "cevMGXSrmE1Oc3" {
    smiv2:oid "1.3.6.1.4.1.9.12.3.1.9.21.72";
  }

  smiv2:alias "cevAxsm2Oc48" {
    smiv2:oid "1.3.6.1.4.1.9.12.3.1.9.21.73";
  }

  smiv2:alias "cevAxsm8Oc12" {
    smiv2:oid "1.3.6.1.4.1.9.12.3.1.9.21.74";
  }

  smiv2:alias "cevVxsm4Oc3" {
    smiv2:oid "1.3.6.1.4.1.9.12.3.1.9.21.81";
  }

  smiv2:alias "cevMGXSrm4Oc3" {
    smiv2:oid "1.3.6.1.4.1.9.12.3.1.9.21.82";
  }

  smiv2:alias "cevMpsm8t1e1" {
    smiv2:oid "1.3.6.1.4.1.9.12.3.1.9.21.87";
  }

  smiv2:alias "cevMpsm8t1Atm" {
    smiv2:oid "1.3.6.1.4.1.9.12.3.1.9.21.88";
  }

  smiv2:alias "cevMpsm8t1Fr" {
    smiv2:oid "1.3.6.1.4.1.9.12.3.1.9.21.89";
  }

  smiv2:alias "cevMpsm8t1Ces" {
    smiv2:oid "1.3.6.1.4.1.9.12.3.1.9.21.90";
  }

  smiv2:alias "cevMpsm8e1Atm" {
    smiv2:oid "1.3.6.1.4.1.9.12.3.1.9.21.91";
  }

  smiv2:alias "cevMpsm8e1Fr" {
    smiv2:oid "1.3.6.1.4.1.9.12.3.1.9.21.92";
  }

  smiv2:alias "cevMpsm8e1Ces" {
    smiv2:oid "1.3.6.1.4.1.9.12.3.1.9.21.93";
  }

  smiv2:alias "cevMpsm16t1e1" {
    smiv2:oid "1.3.6.1.4.1.9.12.3.1.9.21.94";
  }

  smiv2:alias "cevMpsm16t1Atm" {
    smiv2:oid "1.3.6.1.4.1.9.12.3.1.9.21.95";
  }

  smiv2:alias "cevMpsm16t1Fr" {
    smiv2:oid "1.3.6.1.4.1.9.12.3.1.9.21.96";
  }

  smiv2:alias "cevMpsm16t1Ces" {
    smiv2:oid "1.3.6.1.4.1.9.12.3.1.9.21.97";
  }

  smiv2:alias "cevMpsm16e1Atm" {
    smiv2:oid "1.3.6.1.4.1.9.12.3.1.9.21.98";
  }

  smiv2:alias "cevMpsm16e1Fr" {
    smiv2:oid "1.3.6.1.4.1.9.12.3.1.9.21.99";
  }

  smiv2:alias "cevMpsm16e1Ces" {
    smiv2:oid "1.3.6.1.4.1.9.12.3.1.9.21.100";
  }

  smiv2:alias "cevMpsm155t3e3" {
    smiv2:oid "1.3.6.1.4.1.9.12.3.1.9.21.101";
  }

  smiv2:alias "cevMGXSm" {
    smiv2:oid "1.3.6.1.4.1.9.12.3.1.9.21.102";
  }

  smiv2:alias "cevVxsm48t1e1" {
    smiv2:oid "1.3.6.1.4.1.9.12.3.1.9.21.103";
  }

  smiv2:alias "cevVxsm3T3E3" {
    smiv2:oid "1.3.6.1.4.1.9.12.3.1.9.21.104";
  }

  smiv2:alias "cevVxsm6t3e3" {
    smiv2:oid "1.3.6.1.4.1.9.12.3.1.9.21.105";
  }

  smiv2:alias "cevVxsm6t3" {
    smiv2:oid "1.3.6.1.4.1.9.12.3.1.9.21.106";
  }

  smiv2:alias "cevMpsm16t1e1Ppp" {
    smiv2:oid "1.3.6.1.4.1.9.12.3.1.9.21.107";
  }

  smiv2:alias "cevMpsm155t3e3Ppp" {
    smiv2:oid "1.3.6.1.4.1.9.12.3.1.9.21.108";
  }

  smiv2:alias "cevModule38xxType" {
    smiv2:oid "1.3.6.1.4.1.9.12.3.1.9.22";
  }

  smiv2:alias "cevMc3810Vcm3" {
    smiv2:oid "1.3.6.1.4.1.9.12.3.1.9.22.1";
  }

  smiv2:alias "cevMc3810Bvm" {
    smiv2:oid "1.3.6.1.4.1.9.12.3.1.9.22.2";
  }

  smiv2:alias "cevMc3810AvmFxoUk" {
    smiv2:oid "1.3.6.1.4.1.9.12.3.1.9.22.3";
  }

  smiv2:alias "cevMc3810AvmFxoGer" {
    smiv2:oid "1.3.6.1.4.1.9.12.3.1.9.22.4";
  }

  smiv2:alias "cevMc3810Hcm2" {
    smiv2:oid "1.3.6.1.4.1.9.12.3.1.9.22.5";
  }

  smiv2:alias "cevMc3810Hcm6" {
    smiv2:oid "1.3.6.1.4.1.9.12.3.1.9.22.6";
  }

  smiv2:alias "cevMc3810AvmFxoPr3" {
    smiv2:oid "1.3.6.1.4.1.9.12.3.1.9.22.7";
  }

  smiv2:alias "cevMc3810AvmFxoPr2" {
    smiv2:oid "1.3.6.1.4.1.9.12.3.1.9.22.8";
  }

  smiv2:alias "cevMc3810Vdm" {
    smiv2:oid "1.3.6.1.4.1.9.12.3.1.9.22.9";
  }

  smiv2:alias "cevMc3810ApmFxsDid" {
    smiv2:oid "1.3.6.1.4.1.9.12.3.1.9.22.10";
  }

  smiv2:alias "cevMc3810BvmNtTe" {
    smiv2:oid "1.3.6.1.4.1.9.12.3.1.9.22.11";
  }

  smiv2:alias "cevMc3810Hcm1" {
    smiv2:oid "1.3.6.1.4.1.9.12.3.1.9.22.12";
  }

  smiv2:alias "cevMc3810Hcm3" {
    smiv2:oid "1.3.6.1.4.1.9.12.3.1.9.22.13";
  }

  smiv2:alias "cevMc3810Hcm4" {
    smiv2:oid "1.3.6.1.4.1.9.12.3.1.9.22.14";
  }

  smiv2:alias "cevMc3810Hcm5" {
    smiv2:oid "1.3.6.1.4.1.9.12.3.1.9.22.15";
  }

  smiv2:alias "cevSmSre710K9" {
    smiv2:oid "1.3.6.1.4.1.9.12.3.1.9.22.17";
  }

  smiv2:alias "cevSmSre910K9" {
    smiv2:oid "1.3.6.1.4.1.9.12.3.1.9.22.18";
  }

  smiv2:alias "cevPSmSre710K9" {
    smiv2:oid "1.3.6.1.4.1.9.12.3.1.9.22.19";
  }

  smiv2:alias "cevPSmSre910K9" {
    smiv2:oid "1.3.6.1.4.1.9.12.3.1.9.22.20";
  }

  smiv2:alias "cevModuleCat29xxType" {
    smiv2:oid "1.3.6.1.4.1.9.12.3.1.9.23";
  }

  smiv2:alias "cevX2914" {
    smiv2:oid "1.3.6.1.4.1.9.12.3.1.9.23.1";
  }

  smiv2:alias "cevX2922" {
    smiv2:oid "1.3.6.1.4.1.9.12.3.1.9.23.2";
  }

  smiv2:alias "cevX2914V" {
    smiv2:oid "1.3.6.1.4.1.9.12.3.1.9.23.3";
  }

  smiv2:alias "cevX2922V" {
    smiv2:oid "1.3.6.1.4.1.9.12.3.1.9.23.4";
  }

  smiv2:alias "cevX2924V" {
    smiv2:oid "1.3.6.1.4.1.9.12.3.1.9.23.5";
  }

  smiv2:alias "cevX2951" {
    smiv2:oid "1.3.6.1.4.1.9.12.3.1.9.23.6";
  }

  smiv2:alias "cevX2961" {
    smiv2:oid "1.3.6.1.4.1.9.12.3.1.9.23.7";
  }

  smiv2:alias "cevX2971" {
    smiv2:oid "1.3.6.1.4.1.9.12.3.1.9.23.8";
  }

  smiv2:alias "cevX2972" {
    smiv2:oid "1.3.6.1.4.1.9.12.3.1.9.23.9";
  }

  smiv2:alias "cevX2931" {
    smiv2:oid "1.3.6.1.4.1.9.12.3.1.9.23.10";
  }

  smiv2:alias "cevModuleCat297024" {
    smiv2:oid "1.3.6.1.4.1.9.12.3.1.9.23.12";
  }

  smiv2:alias "cevModuleCat297024TS" {
    smiv2:oid "1.3.6.1.4.1.9.12.3.1.9.23.13";
  }

  smiv2:alias "cevModuleCat297048TS" {
    smiv2:oid "1.3.6.1.4.1.9.12.3.1.9.23.14";
  }

  smiv2:alias "cevModuleCat296024" {
    smiv2:oid "1.3.6.1.4.1.9.12.3.1.9.23.15";
  }

  smiv2:alias "cevModuleCat296048" {
    smiv2:oid "1.3.6.1.4.1.9.12.3.1.9.23.16";
  }

  smiv2:alias "cevModuleCat2960G24" {
    smiv2:oid "1.3.6.1.4.1.9.12.3.1.9.23.17";
  }

  smiv2:alias "cevModuleCat2960G48" {
    smiv2:oid "1.3.6.1.4.1.9.12.3.1.9.23.18";
  }

  smiv2:alias "cevModuleCat296024TT" {
    smiv2:oid "1.3.6.1.4.1.9.12.3.1.9.23.19";
  }

  smiv2:alias "cevModuleCat296048TT" {
    smiv2:oid "1.3.6.1.4.1.9.12.3.1.9.23.20";
  }

  smiv2:alias "cevModuleCat29608TC" {
    smiv2:oid "1.3.6.1.4.1.9.12.3.1.9.23.21";
  }

  smiv2:alias "cevModuleCat2960G8TC" {
    smiv2:oid "1.3.6.1.4.1.9.12.3.1.9.23.22";
  }

  smiv2:alias "cevModuleCat296048TCS" {
    smiv2:oid "1.3.6.1.4.1.9.12.3.1.9.23.23";
  }

  smiv2:alias "cevModuleCat296024TCS" {
    smiv2:oid "1.3.6.1.4.1.9.12.3.1.9.23.24";
  }

  smiv2:alias "cevModuleCat296024S" {
    smiv2:oid "1.3.6.1.4.1.9.12.3.1.9.23.25";
  }

  smiv2:alias "cevModuleCat296024PC" {
    smiv2:oid "1.3.6.1.4.1.9.12.3.1.9.23.26";
  }

  smiv2:alias "cevModuleCat296024LT" {
    smiv2:oid "1.3.6.1.4.1.9.12.3.1.9.23.27";
  }

  smiv2:alias "cevModuleCat2960PD8TT" {
    smiv2:oid "1.3.6.1.4.1.9.12.3.1.9.23.28";
  }

  smiv2:alias "cevModuleCat291824TT" {
    smiv2:oid "1.3.6.1.4.1.9.12.3.1.9.23.29";
  }

  smiv2:alias "cevModuleCat291824TC" {
    smiv2:oid "1.3.6.1.4.1.9.12.3.1.9.23.30";
  }

  smiv2:alias "cevModuleCat291848TT" {
    smiv2:oid "1.3.6.1.4.1.9.12.3.1.9.23.31";
  }

  smiv2:alias "cevModuleCat291848TC" {
    smiv2:oid "1.3.6.1.4.1.9.12.3.1.9.23.32";
  }

  smiv2:alias "cevModuleCat296048TTS" {
    smiv2:oid "1.3.6.1.4.1.9.12.3.1.9.23.33";
  }

  smiv2:alias "cevModuleCat29608TCS" {
    smiv2:oid "1.3.6.1.4.1.9.12.3.1.9.23.34";
  }

  smiv2:alias "cevModuleCat296048PSTL" {
    smiv2:oid "1.3.6.1.4.1.9.12.3.1.9.23.35";
  }

  smiv2:alias "cevModuleCat296024LCS" {
    smiv2:oid "1.3.6.1.4.1.9.12.3.1.9.23.36";
  }

  smiv2:alias "cevModuleCat296024PCS" {
    smiv2:oid "1.3.6.1.4.1.9.12.3.1.9.23.37";
  }

  smiv2:alias "cevModuleCat296048PSTS" {
    smiv2:oid "1.3.6.1.4.1.9.12.3.1.9.23.38";
  }

  smiv2:alias "cevModuleWsC2960s48tsS" {
    smiv2:oid "1.3.6.1.4.1.9.12.3.1.9.23.39";
  }

  smiv2:alias "cevModuleWsC2960s24tsS" {
    smiv2:oid "1.3.6.1.4.1.9.12.3.1.9.23.40";
  }

  smiv2:alias "cevModuleWsC2960s48fpdL" {
    smiv2:oid "1.3.6.1.4.1.9.12.3.1.9.23.41";
  }

  smiv2:alias "cevModuleWsC2960s48lpdL" {
    smiv2:oid "1.3.6.1.4.1.9.12.3.1.9.23.42";
  }

  smiv2:alias "cevModuleWsC2960s48tdL" {
    smiv2:oid "1.3.6.1.4.1.9.12.3.1.9.23.43";
  }

  smiv2:alias "cevModuleWsC2960s24pdL" {
    smiv2:oid "1.3.6.1.4.1.9.12.3.1.9.23.44";
  }

  smiv2:alias "cevModuleWsC2960s24tdL" {
    smiv2:oid "1.3.6.1.4.1.9.12.3.1.9.23.45";
  }

  smiv2:alias "cevModuleWsC2960s48fpsL" {
    smiv2:oid "1.3.6.1.4.1.9.12.3.1.9.23.46";
  }

  smiv2:alias "cevModuleWsC2960s48lpsL" {
    smiv2:oid "1.3.6.1.4.1.9.12.3.1.9.23.47";
  }

  smiv2:alias "cevModuleWsC2960s24psL" {
    smiv2:oid "1.3.6.1.4.1.9.12.3.1.9.23.48";
  }

  smiv2:alias "cevModuleWsC2960s48tsL" {
    smiv2:oid "1.3.6.1.4.1.9.12.3.1.9.23.49";
  }

  smiv2:alias "cevModuleWsC2960S24tsL" {
    smiv2:oid "1.3.6.1.4.1.9.12.3.1.9.23.50";
  }

  smiv2:alias "cevModuleCat2960cPD8TT" {
    smiv2:oid "1.3.6.1.4.1.9.12.3.1.9.23.51";
  }

  smiv2:alias "cevModuleCat2960cG8TC" {
    smiv2:oid "1.3.6.1.4.1.9.12.3.1.9.23.53";
  }

  smiv2:alias "cevModuleCat292824TCC" {
    smiv2:oid "1.3.6.1.4.1.9.12.3.1.9.23.54";
  }

  smiv2:alias "cevModuleCat292824LTC" {
    smiv2:oid "1.3.6.1.4.1.9.12.3.1.9.23.55";
  }

  smiv2:alias "cevModuleCat292848TCC" {
    smiv2:oid "1.3.6.1.4.1.9.12.3.1.9.23.56";
  }

  smiv2:alias "cevModuleWsC2960C8tcS" {
    smiv2:oid "1.3.6.1.4.1.9.12.3.1.9.23.57";
  }

  smiv2:alias "cevModuleWsC2960C8tcL" {
    smiv2:oid "1.3.6.1.4.1.9.12.3.1.9.23.58";
  }

  smiv2:alias "cevModuleWsC2960C8pcL" {
    smiv2:oid "1.3.6.1.4.1.9.12.3.1.9.23.59";
  }

  smiv2:alias "cevModuleWsC2960C12pcL" {
    smiv2:oid "1.3.6.1.4.1.9.12.3.1.9.23.60";
  }

  smiv2:alias "cevModuleWsC2960x48fpdL" {
    smiv2:oid "1.3.6.1.4.1.9.12.3.1.9.23.68";
  }

  smiv2:alias "cevModuleWsC2960x48lpdL" {
    smiv2:oid "1.3.6.1.4.1.9.12.3.1.9.23.69";
  }

  smiv2:alias "cevModuleWsC2960x48tdL" {
    smiv2:oid "1.3.6.1.4.1.9.12.3.1.9.23.70";
  }

  smiv2:alias "cevModuleWsC2960x24pdL" {
    smiv2:oid "1.3.6.1.4.1.9.12.3.1.9.23.71";
  }

  smiv2:alias "cevModuleWsC2960x24tdL" {
    smiv2:oid "1.3.6.1.4.1.9.12.3.1.9.23.72";
  }

  smiv2:alias "cevModuleWsC2960x48fpsL" {
    smiv2:oid "1.3.6.1.4.1.9.12.3.1.9.23.73";
  }

  smiv2:alias "cevModuleWsC2960x48lpsL" {
    smiv2:oid "1.3.6.1.4.1.9.12.3.1.9.23.74";
  }

  smiv2:alias "cevModuleWsC2960x24psL" {
    smiv2:oid "1.3.6.1.4.1.9.12.3.1.9.23.75";
  }

  smiv2:alias "cevModuleWsC2960x48tsL" {
    smiv2:oid "1.3.6.1.4.1.9.12.3.1.9.23.76";
  }

  smiv2:alias "cevModuleWsC2960x24tsL" {
    smiv2:oid "1.3.6.1.4.1.9.12.3.1.9.23.77";
  }

  smiv2:alias "cevModuleWsC2960x24psqL" {
    smiv2:oid "1.3.6.1.4.1.9.12.3.1.9.23.78";
  }

  smiv2:alias "cevModuleWsC2960x48lpsS" {
    smiv2:oid "1.3.6.1.4.1.9.12.3.1.9.23.79";
  }

  smiv2:alias "cevModuleWsC2960x24psS" {
    smiv2:oid "1.3.6.1.4.1.9.12.3.1.9.23.80";
  }

  smiv2:alias "cevModuleWsC2960x48tsLL" {
    smiv2:oid "1.3.6.1.4.1.9.12.3.1.9.23.81";
  }

  smiv2:alias "cevModuleWsC2960x24tsLL" {
    smiv2:oid "1.3.6.1.4.1.9.12.3.1.9.23.82";
  }

  smiv2:alias "cevModuleC2960XStack" {
    smiv2:oid "1.3.6.1.4.1.9.12.3.1.9.23.83";
  }

  smiv2:alias "cevModuleC2960XFex" {
    smiv2:oid "1.3.6.1.4.1.9.12.3.1.9.23.84";
  }

  smiv2:alias "cevModuleC2960XFexStack" {
    smiv2:oid "1.3.6.1.4.1.9.12.3.1.9.23.85";
  }

  smiv2:alias "cevModuleWsC2960P48PstL" {
    smiv2:oid "1.3.6.1.4.1.9.12.3.1.9.23.86";
  }

  smiv2:alias "cevModuleWsC2960P24PcL" {
    smiv2:oid "1.3.6.1.4.1.9.12.3.1.9.23.87";
  }

  smiv2:alias "cevModuleWsC2960P24LcL" {
    smiv2:oid "1.3.6.1.4.1.9.12.3.1.9.23.88";
  }

  smiv2:alias "cevModuleWsC2960P48TcL" {
    smiv2:oid "1.3.6.1.4.1.9.12.3.1.9.23.89";
  }

  smiv2:alias "cevModuleWsC2960P24TcL" {
    smiv2:oid "1.3.6.1.4.1.9.12.3.1.9.23.90";
  }

  smiv2:alias "cevModuleWsC2960P48PstS" {
    smiv2:oid "1.3.6.1.4.1.9.12.3.1.9.23.91";
  }

  smiv2:alias "cevModuleWsC2960P24PcS" {
    smiv2:oid "1.3.6.1.4.1.9.12.3.1.9.23.92";
  }

  smiv2:alias "cevModuleWsC2960P24LcS" {
    smiv2:oid "1.3.6.1.4.1.9.12.3.1.9.23.93";
  }

  smiv2:alias "cevModuleWsC2960P48TcS" {
    smiv2:oid "1.3.6.1.4.1.9.12.3.1.9.23.94";
  }

  smiv2:alias "cevModuleWsC2960P24TcS" {
    smiv2:oid "1.3.6.1.4.1.9.12.3.1.9.23.95";
  }

  smiv2:alias "cevModuleOscillatorType" {
    smiv2:oid "1.3.6.1.4.1.9.12.3.1.9.24";
  }

  smiv2:alias "cevStratum3" {
    smiv2:oid "1.3.6.1.4.1.9.12.3.1.9.24.1";
  }

  smiv2:alias "cevStratum4" {
    smiv2:oid "1.3.6.1.4.1.9.12.3.1.9.24.2";
  }

  smiv2:alias "cevModuleDslamType" {
    smiv2:oid "1.3.6.1.4.1.9.12.3.1.9.25";
  }

  smiv2:alias "cevNi2WanOc3mmSubOc3mm" {
    smiv2:oid "1.3.6.1.4.1.9.12.3.1.9.25.1";
  }

  smiv2:alias "cevNi2WanDs3Sub2Ds3" {
    smiv2:oid "1.3.6.1.4.1.9.12.3.1.9.25.2";
  }

  smiv2:alias "cevAtuc1p2Cap" {
    smiv2:oid "1.3.6.1.4.1.9.12.3.1.9.25.3";
  }

  smiv2:alias "cevAtuc1p2Dmt" {
    smiv2:oid "1.3.6.1.4.1.9.12.3.1.9.25.4";
  }

  smiv2:alias "cevAtuc1p4Dmt" {
    smiv2:oid "1.3.6.1.4.1.9.12.3.1.9.25.5";
  }

  smiv2:alias "cevLim" {
    smiv2:oid "1.3.6.1.4.1.9.12.3.1.9.25.6";
  }

  smiv2:alias "cevNi2WanOc3smSubOc3sm" {
    smiv2:oid "1.3.6.1.4.1.9.12.3.1.9.25.7";
  }

  smiv2:alias "cevNi2WanE3Sub2E3" {
    smiv2:oid "1.3.6.1.4.1.9.12.3.1.9.25.8";
  }

  smiv2:alias "cevNi2WanDs3Sub8Ds1Ima" {
    smiv2:oid "1.3.6.1.4.1.9.12.3.1.9.25.9";
  }

  smiv2:alias "cevAtuc1p4Cap" {
    smiv2:oid "1.3.6.1.4.1.9.12.3.1.9.25.10";
  }

  smiv2:alias "cevStuc1p4" {
    smiv2:oid "1.3.6.1.4.1.9.12.3.1.9.25.11";
  }

  smiv2:alias "cevAtuc1p4FlexiDmt" {
    smiv2:oid "1.3.6.1.4.1.9.12.3.1.9.25.13";
  }

  smiv2:alias "cevAtuc1p4FlexiCap" {
    smiv2:oid "1.3.6.1.4.1.9.12.3.1.9.25.14";
  }

  smiv2:alias "cevAtuc1p4Flexi" {
    smiv2:oid "1.3.6.1.4.1.9.12.3.1.9.25.15";
  }

  smiv2:alias "cevAtuc1p4DmtIsdn" {
    smiv2:oid "1.3.6.1.4.1.9.12.3.1.9.25.16";
  }

  smiv2:alias "cevNi2WanOc3smSub2Ds3" {
    smiv2:oid "1.3.6.1.4.1.9.12.3.1.9.25.17";
  }

  smiv2:alias "cevNi2WanOc3mmSub2Ds3" {
    smiv2:oid "1.3.6.1.4.1.9.12.3.1.9.25.18";
  }

  smiv2:alias "cevAtuc1p8DmtItemp" {
    smiv2:oid "1.3.6.1.4.1.9.12.3.1.9.25.21";
  }

  smiv2:alias "cevStuc1p8Itemp" {
    smiv2:oid "1.3.6.1.4.1.9.12.3.1.9.25.22";
  }

  smiv2:alias "cevNi2WanDs3Sub2Ds3Rev2" {
    smiv2:oid "1.3.6.1.4.1.9.12.3.1.9.25.35";
  }

  smiv2:alias "cevNi2WanOc3smSubOc3smRev2" {
    smiv2:oid "1.3.6.1.4.1.9.12.3.1.9.25.36";
  }

  smiv2:alias "cevNi2WanOc3mmSubOc3mmRev2" {
    smiv2:oid "1.3.6.1.4.1.9.12.3.1.9.25.37";
  }

  smiv2:alias "cevNi2WanOc3smSub2Ds3Rev2" {
    smiv2:oid "1.3.6.1.4.1.9.12.3.1.9.25.38";
  }

  smiv2:alias "cevNi2WanOc3mmSub2Ds3Rev2" {
    smiv2:oid "1.3.6.1.4.1.9.12.3.1.9.25.39";
  }

  smiv2:alias "cevNi2WanOc3smSubOc3smItemp" {
    smiv2:oid "1.3.6.1.4.1.9.12.3.1.9.25.40";
  }

  smiv2:alias "cevIo6100DS3" {
    smiv2:oid "1.3.6.1.4.1.9.12.3.1.9.25.43";
  }

  smiv2:alias "cevIo6160DS3" {
    smiv2:oid "1.3.6.1.4.1.9.12.3.1.9.25.44";
  }

  smiv2:alias "cevIo6260OC3" {
    smiv2:oid "1.3.6.1.4.1.9.12.3.1.9.25.45";
  }

  smiv2:alias "cevIo6260Ds3T1" {
    smiv2:oid "1.3.6.1.4.1.9.12.3.1.9.25.46";
  }

  smiv2:alias "cevModuleWASBackCards" {
    smiv2:oid "1.3.6.1.4.1.9.12.3.1.9.26";
  }

  smiv2:alias "cevLmBnc2t3" {
    smiv2:oid "1.3.6.1.4.1.9.12.3.1.9.26.1";
  }

  smiv2:alias "cevLmBnc2e3" {
    smiv2:oid "1.3.6.1.4.1.9.12.3.1.9.26.2";
  }

  smiv2:alias "cevLmDb154x21" {
    smiv2:oid "1.3.6.1.4.1.9.12.3.1.9.26.3";
  }

  smiv2:alias "cevLmScsi22hssi" {
    smiv2:oid "1.3.6.1.4.1.9.12.3.1.9.26.4";
  }

  smiv2:alias "cevLmRj488t1" {
    smiv2:oid "1.3.6.1.4.1.9.12.3.1.9.26.5";
  }

  smiv2:alias "cevLmRj488t1R" {
    smiv2:oid "1.3.6.1.4.1.9.12.3.1.9.26.6";
  }

  smiv2:alias "cevLmRj488e1" {
    smiv2:oid "1.3.6.1.4.1.9.12.3.1.9.26.7";
  }

  smiv2:alias "cevLmRj488e1R" {
    smiv2:oid "1.3.6.1.4.1.9.12.3.1.9.26.8";
  }

  smiv2:alias "cevLmSmb8e1" {
    smiv2:oid "1.3.6.1.4.1.9.12.3.1.9.26.9";
  }

  smiv2:alias "cevLmSmb8e1R" {
    smiv2:oid "1.3.6.1.4.1.9.12.3.1.9.26.10";
  }

  smiv2:alias "cevLmPsmUI" {
    smiv2:oid "1.3.6.1.4.1.9.12.3.1.9.26.11";
  }

  smiv2:alias "cevLmMmf4oc3" {
    smiv2:oid "1.3.6.1.4.1.9.12.3.1.9.26.12";
  }

  smiv2:alias "cevLmSmfIr4oc3" {
    smiv2:oid "1.3.6.1.4.1.9.12.3.1.9.26.13";
  }

  smiv2:alias "cevLmSmfLr4oc3" {
    smiv2:oid "1.3.6.1.4.1.9.12.3.1.9.26.14";
  }

  smiv2:alias "cevLmSmfIr1oc12" {
    smiv2:oid "1.3.6.1.4.1.9.12.3.1.9.26.15";
  }

  smiv2:alias "cevLmSmfLr1oc12" {
    smiv2:oid "1.3.6.1.4.1.9.12.3.1.9.26.16";
  }

  smiv2:alias "cevLmS3Ui" {
    smiv2:oid "1.3.6.1.4.1.9.12.3.1.9.26.17";
  }

  smiv2:alias "cevLm1feTx" {
    smiv2:oid "1.3.6.1.4.1.9.12.3.1.9.26.18";
  }

  smiv2:alias "cevLm1feFx" {
    smiv2:oid "1.3.6.1.4.1.9.12.3.1.9.26.19";
  }

  smiv2:alias "cevLm1mmfFddi" {
    smiv2:oid "1.3.6.1.4.1.9.12.3.1.9.26.20";
  }

  smiv2:alias "cevLm1smfFddi" {
    smiv2:oid "1.3.6.1.4.1.9.12.3.1.9.26.21";
  }

  smiv2:alias "cevLmRj454e" {
    smiv2:oid "1.3.6.1.4.1.9.12.3.1.9.26.22";
  }

  smiv2:alias "cevLmMmf8oc3" {
    smiv2:oid "1.3.6.1.4.1.9.12.3.1.9.26.23";
  }

  smiv2:alias "cevLmSmfIr8oc3" {
    smiv2:oid "1.3.6.1.4.1.9.12.3.1.9.26.24";
  }

  smiv2:alias "cevLmSmfLr8oc3" {
    smiv2:oid "1.3.6.1.4.1.9.12.3.1.9.26.25";
  }

  smiv2:alias "cevLmSmfIr1oc48" {
    smiv2:oid "1.3.6.1.4.1.9.12.3.1.9.26.26";
  }

  smiv2:alias "cevLmSmfLr1oc48" {
    smiv2:oid "1.3.6.1.4.1.9.12.3.1.9.26.27";
  }

  smiv2:alias "cevLmPsmHD" {
    smiv2:oid "1.3.6.1.4.1.9.12.3.1.9.26.28";
  }

  smiv2:alias "cevLmSmb8t3" {
    smiv2:oid "1.3.6.1.4.1.9.12.3.1.9.26.29";
  }

  smiv2:alias "cevLmSmb8e3" {
    smiv2:oid "1.3.6.1.4.1.9.12.3.1.9.26.30";
  }

  smiv2:alias "cevLmSmb4stm1" {
    smiv2:oid "1.3.6.1.4.1.9.12.3.1.9.26.31";
  }

  smiv2:alias "cevLmSmfIr2oc12" {
    smiv2:oid "1.3.6.1.4.1.9.12.3.1.9.26.32";
  }

  smiv2:alias "cevLmSmfLr2oc12" {
    smiv2:oid "1.3.6.1.4.1.9.12.3.1.9.26.33";
  }

  smiv2:alias "cevLmSmfSr1oc48" {
    smiv2:oid "1.3.6.1.4.1.9.12.3.1.9.26.34";
  }

  smiv2:alias "cevLmSmfXlr1oc48" {
    smiv2:oid "1.3.6.1.4.1.9.12.3.1.9.26.35";
  }

  smiv2:alias "cevLmBnc3t3" {
    smiv2:oid "1.3.6.1.4.1.9.12.3.1.9.26.36";
  }

  smiv2:alias "cevLmSmfIr1Oc48B" {
    smiv2:oid "1.3.6.1.4.1.9.12.3.1.9.26.37";
  }

  smiv2:alias "cevLmSmfLr1Oc48B" {
    smiv2:oid "1.3.6.1.4.1.9.12.3.1.9.26.38";
  }

  smiv2:alias "cevLmSmfSr1Oc48B" {
    smiv2:oid "1.3.6.1.4.1.9.12.3.1.9.26.39";
  }

  smiv2:alias "cevLmSmfIr2Oc12B" {
    smiv2:oid "1.3.6.1.4.1.9.12.3.1.9.26.40";
  }

  smiv2:alias "cevLmSmfLr2Oc12B" {
    smiv2:oid "1.3.6.1.4.1.9.12.3.1.9.26.41";
  }

  smiv2:alias "cevLmSmfIr1Oc12C" {
    smiv2:oid "1.3.6.1.4.1.9.12.3.1.9.26.42";
  }

  smiv2:alias "cevLmSmfLr1Oc12C" {
    smiv2:oid "1.3.6.1.4.1.9.12.3.1.9.26.43";
  }

  smiv2:alias "cevLmMmf4Oc3C" {
    smiv2:oid "1.3.6.1.4.1.9.12.3.1.9.26.44";
  }

  smiv2:alias "cevLmSmfIr4Oc3C" {
    smiv2:oid "1.3.6.1.4.1.9.12.3.1.9.26.45";
  }

  smiv2:alias "cevLmSmfLr4Oc3C" {
    smiv2:oid "1.3.6.1.4.1.9.12.3.1.9.26.46";
  }

  smiv2:alias "cevLmSmfXlr1Oc48B" {
    smiv2:oid "1.3.6.1.4.1.9.12.3.1.9.26.51";
  }

  smiv2:alias "cevLm1feTxcp" {
    smiv2:oid "1.3.6.1.4.1.9.12.3.1.9.26.55";
  }

  smiv2:alias "cevLmSmfIr8Oc3C" {
    smiv2:oid "1.3.6.1.4.1.9.12.3.1.9.26.58";
  }

  smiv2:alias "cevLmSmfLr8Oc3C" {
    smiv2:oid "1.3.6.1.4.1.9.12.3.1.9.26.59";
  }

  smiv2:alias "cevLmMmf8Oc3C" {
    smiv2:oid "1.3.6.1.4.1.9.12.3.1.9.26.60";
  }

  smiv2:alias "cevLmSmfIr1Oc3" {
    smiv2:oid "1.3.6.1.4.1.9.12.3.1.9.26.61";
  }

  smiv2:alias "cevLmSmfLr1Oc3" {
    smiv2:oid "1.3.6.1.4.1.9.12.3.1.9.26.62";
  }

  smiv2:alias "cevLmSmb1Stm1" {
    smiv2:oid "1.3.6.1.4.1.9.12.3.1.9.26.63";
  }

  smiv2:alias "cevLmScsi2B2hssi" {
    smiv2:oid "1.3.6.1.4.1.9.12.3.1.9.26.64";
  }

  smiv2:alias "cevLm12In18s" {
    smiv2:oid "1.3.6.1.4.1.9.12.3.1.9.26.65";
  }

  smiv2:alias "cevLmSmb6e3" {
    smiv2:oid "1.3.6.1.4.1.9.12.3.1.9.26.66";
  }

  smiv2:alias "cevLmComboT3E3Oc3" {
    smiv2:oid "1.3.6.1.4.1.9.12.3.1.9.26.67";
  }

  smiv2:alias "cevLmRj488t1e1" {
    smiv2:oid "1.3.6.1.4.1.9.12.3.1.9.26.68";
  }

  smiv2:alias "cevLmMcc16e1" {
    smiv2:oid "1.3.6.1.4.1.9.12.3.1.9.26.69";
  }

  smiv2:alias "cevLmRj4816t1e1" {
    smiv2:oid "1.3.6.1.4.1.9.12.3.1.9.26.70";
  }

  smiv2:alias "cevLmSmfIr2Oc12c" {
    smiv2:oid "1.3.6.1.4.1.9.12.3.1.9.26.71";
  }

  smiv2:alias "cevLmSmfLr2Oc12c" {
    smiv2:oid "1.3.6.1.4.1.9.12.3.1.9.26.72";
  }

  smiv2:alias "cevLmSmb8Stm1" {
    smiv2:oid "1.3.6.1.4.1.9.12.3.1.9.26.82";
  }

  smiv2:alias "cevLmSmf8Oc3Sfp" {
    smiv2:oid "1.3.6.1.4.1.9.12.3.1.9.26.83";
  }

  smiv2:alias "cevLmRbbn16t1e1" {
    smiv2:oid "1.3.6.1.4.1.9.12.3.1.9.26.84";
  }

  smiv2:alias "cevLmSmfSr1Oc192" {
    smiv2:oid "1.3.6.1.4.1.9.12.3.1.9.26.85";
  }

  smiv2:alias "cevLmSmfIr1Oc192" {
    smiv2:oid "1.3.6.1.4.1.9.12.3.1.9.26.86";
  }

  smiv2:alias "cevLmSmfLr1Oc192" {
    smiv2:oid "1.3.6.1.4.1.9.12.3.1.9.26.87";
  }

  smiv2:alias "cevLmSmfXlr1Oc192" {
    smiv2:oid "1.3.6.1.4.1.9.12.3.1.9.26.88";
  }

  smiv2:alias "cevLmMcc8oc3" {
    smiv2:oid "1.3.6.1.4.1.9.12.3.1.9.26.89";
  }

  smiv2:alias "cevLmRbbn16t1e11N" {
    smiv2:oid "1.3.6.1.4.1.9.12.3.1.9.26.92";
  }

  smiv2:alias "cevLmMcc16e11N" {
    smiv2:oid "1.3.6.1.4.1.9.12.3.1.9.26.93";
  }

  smiv2:alias "cevLmRed16t1e1" {
    smiv2:oid "1.3.6.1.4.1.9.12.3.1.9.26.94";
  }

  smiv2:alias "cevLmSfp2Oc3" {
    smiv2:oid "1.3.6.1.4.1.9.12.3.1.9.26.95";
  }

  smiv2:alias "cevLmSmb2Oc3EL" {
    smiv2:oid "1.3.6.1.4.1.9.12.3.1.9.26.96";
  }

  smiv2:alias "cevLmBnc3t3e3" {
    smiv2:oid "1.3.6.1.4.1.9.12.3.1.9.26.97";
  }

  smiv2:alias "cevLmRed2Oc3" {
    smiv2:oid "1.3.6.1.4.1.9.12.3.1.9.26.98";
  }

  smiv2:alias "cevLmRed3t3e3" {
    smiv2:oid "1.3.6.1.4.1.9.12.3.1.9.26.99";
  }

  smiv2:alias "cevLmSmf4Oc12" {
    smiv2:oid "1.3.6.1.4.1.9.12.3.1.9.26.100";
  }

  smiv2:alias "cevLmChamp24t1e1" {
    smiv2:oid "1.3.6.1.4.1.9.12.3.1.9.26.101";
  }

  smiv2:alias "cevLmSmb3t3e3" {
    smiv2:oid "1.3.6.1.4.1.9.12.3.1.9.26.102";
  }

  smiv2:alias "cevLmVxsmSmfIr4Oc3" {
    smiv2:oid "1.3.6.1.4.1.9.12.3.1.9.26.103";
  }

  smiv2:alias "cevLmVxsmSmfLr4Oc3" {
    smiv2:oid "1.3.6.1.4.1.9.12.3.1.9.26.104";
  }

  smiv2:alias "cevLmVxsm4Oc3R" {
    smiv2:oid "1.3.6.1.4.1.9.12.3.1.9.26.105";
  }

  smiv2:alias "cevLmVxsmMmf4Oc3" {
    smiv2:oid "1.3.6.1.4.1.9.12.3.1.9.26.106";
  }

  smiv2:alias "cevLm4V35" {
    smiv2:oid "1.3.6.1.4.1.9.12.3.1.9.26.107";
  }

  smiv2:alias "cevLm4X21" {
    smiv2:oid "1.3.6.1.4.1.9.12.3.1.9.26.108";
  }

  smiv2:alias "cevLmMgxXfUIB" {
    smiv2:oid "1.3.6.1.4.1.9.12.3.1.9.26.109";
  }

  smiv2:alias "cevLm5efegeTx" {
    smiv2:oid "1.3.6.1.4.1.9.12.3.1.9.26.110";
  }

  smiv2:alias "cevLmPsmHDV" {
    smiv2:oid "1.3.6.1.4.1.9.12.3.1.9.26.111";
  }

  smiv2:alias "cevModuleUbrType" {
    smiv2:oid "1.3.6.1.4.1.9.12.3.1.9.27";
  }

  smiv2:alias "cevUbrMc16s" {
    smiv2:oid "1.3.6.1.4.1.9.12.3.1.9.27.2";
  }

  smiv2:alias "cevUbrMc11" {
    smiv2:oid "1.3.6.1.4.1.9.12.3.1.9.27.3";
  }

  smiv2:alias "cevUbrMc11c" {
    smiv2:oid "1.3.6.1.4.1.9.12.3.1.9.27.4";
  }

  smiv2:alias "cevUbrMc12c" {
    smiv2:oid "1.3.6.1.4.1.9.12.3.1.9.27.5";
  }

  smiv2:alias "cevUbrMc14c" {
    smiv2:oid "1.3.6.1.4.1.9.12.3.1.9.27.6";
  }

  smiv2:alias "cevUbrMc16a" {
    smiv2:oid "1.3.6.1.4.1.9.12.3.1.9.27.7";
  }

  smiv2:alias "cevUbrMc16b" {
    smiv2:oid "1.3.6.1.4.1.9.12.3.1.9.27.8";
  }

  smiv2:alias "cevUbrMc16c" {
    smiv2:oid "1.3.6.1.4.1.9.12.3.1.9.27.9";
  }

  smiv2:alias "cevUbrMc16e" {
    smiv2:oid "1.3.6.1.4.1.9.12.3.1.9.27.10";
  }

  smiv2:alias "cevUbrMc28c" {
    smiv2:oid "1.3.6.1.4.1.9.12.3.1.9.27.11";
  }

  smiv2:alias "cevUbrMc26" {
    smiv2:oid "1.3.6.1.4.1.9.12.3.1.9.27.12";
  }

  smiv2:alias "cevUbr912C" {
    smiv2:oid "1.3.6.1.4.1.9.12.3.1.9.27.13";
  }

  smiv2:alias "cevUbr912S" {
    smiv2:oid "1.3.6.1.4.1.9.12.3.1.9.27.14";
  }

  smiv2:alias "cevUbr914R" {
    smiv2:oid "1.3.6.1.4.1.9.12.3.1.9.27.15";
  }

  smiv2:alias "cevUbrClk" {
    smiv2:oid "1.3.6.1.4.1.9.12.3.1.9.27.16";
  }

  smiv2:alias "cevUbr925" {
    smiv2:oid "1.3.6.1.4.1.9.12.3.1.9.27.17";
  }

  smiv2:alias "cevUbrMc26c" {
    smiv2:oid "1.3.6.1.4.1.9.12.3.1.9.27.18";
  }

  smiv2:alias "cevUbrMc28cf" {
    smiv2:oid "1.3.6.1.4.1.9.12.3.1.9.27.21";
  }

  smiv2:alias "cevUbrMc28cBnc" {
    smiv2:oid "1.3.6.1.4.1.9.12.3.1.9.27.22";
  }

  smiv2:alias "cevUbrMc26cf" {
    smiv2:oid "1.3.6.1.4.1.9.12.3.1.9.27.23";
  }

  smiv2:alias "cevUbrMc26cBnc" {
    smiv2:oid "1.3.6.1.4.1.9.12.3.1.9.27.24";
  }

  smiv2:alias "cevUbrDlc24" {
    smiv2:oid "1.3.6.1.4.1.9.12.3.1.9.27.26";
  }

  smiv2:alias "cevUbrMc28j" {
    smiv2:oid "1.3.6.1.4.1.9.12.3.1.9.27.33";
  }

  smiv2:alias "cevUbrMc28u" {
    smiv2:oid "1.3.6.1.4.1.9.12.3.1.9.27.34";
  }

  smiv2:alias "cevUbrMc16u" {
    smiv2:oid "1.3.6.1.4.1.9.12.3.1.9.27.35";
  }

  smiv2:alias "cevUbrMc28x" {
    smiv2:oid "1.3.6.1.4.1.9.12.3.1.9.27.36";
  }

  smiv2:alias "cevUbrMc16x" {
    smiv2:oid "1.3.6.1.4.1.9.12.3.1.9.27.37";
  }

  smiv2:alias "cevUbrMc520uD" {
    smiv2:oid "1.3.6.1.4.1.9.12.3.1.9.27.38";
  }

  smiv2:alias "cevUbrMc520uF" {
    smiv2:oid "1.3.6.1.4.1.9.12.3.1.9.27.39";
  }

  smiv2:alias "cevUbrTccPlus" {
    smiv2:oid "1.3.6.1.4.1.9.12.3.1.9.27.41";
  }

  smiv2:alias "cevUbrMc16uE" {
    smiv2:oid "1.3.6.1.4.1.9.12.3.1.9.27.42";
  }

  smiv2:alias "cevUbrMc28uE" {
    smiv2:oid "1.3.6.1.4.1.9.12.3.1.9.27.43";
  }

  smiv2:alias "cevUbrDtcc" {
    smiv2:oid "1.3.6.1.4.1.9.12.3.1.9.27.44";
  }

  smiv2:alias "cevUbrMc88v" {
    smiv2:oid "1.3.6.1.4.1.9.12.3.1.9.27.46";
  }

  smiv2:alias "cevUbrmc2020" {
    smiv2:oid "1.3.6.1.4.1.9.12.3.1.9.27.47";
  }

  smiv2:alias "cevUbrMc3g60Mha" {
    smiv2:oid "1.3.6.1.4.1.9.12.3.1.9.27.48";
  }

  smiv2:alias "cevModuleCmccType" {
    smiv2:oid "1.3.6.1.4.1.9.12.3.1.9.28";
  }

  smiv2:alias "cevCmccCip" {
    smiv2:oid "1.3.6.1.4.1.9.12.3.1.9.28.1";
  }

  smiv2:alias "cevCmccCip2" {
    smiv2:oid "1.3.6.1.4.1.9.12.3.1.9.28.2";
  }

  smiv2:alias "cevCmccPa1ec" {
    smiv2:oid "1.3.6.1.4.1.9.12.3.1.9.28.3";
  }

  smiv2:alias "cevCmccPa1pc" {
    smiv2:oid "1.3.6.1.4.1.9.12.3.1.9.28.4";
  }

  smiv2:alias "cevCmccPa1ec4" {
    smiv2:oid "1.3.6.1.4.1.9.12.3.1.9.28.5";
  }

  smiv2:alias "cevModuleCat6000Type" {
    smiv2:oid "1.3.6.1.4.1.9.12.3.1.9.29";
  }

  smiv2:alias "cevCat6kWsxSup12ge" {
    smiv2:oid "1.3.6.1.4.1.9.12.3.1.9.29.2";
  }

  smiv2:alias "cevCat6kWsx6408Gbic" {
    smiv2:oid "1.3.6.1.4.1.9.12.3.1.9.29.3";
  }

  smiv2:alias "cevCat6kWsx6224Fx100Mt" {
    smiv2:oid "1.3.6.1.4.1.9.12.3.1.9.29.4";
  }

  smiv2:alias "cevCat6kWsx6248Rj45" {
    smiv2:oid "1.3.6.1.4.1.9.12.3.1.9.29.5";
  }

  smiv2:alias "cevCat6kWsx6248Tel" {
    smiv2:oid "1.3.6.1.4.1.9.12.3.1.9.29.6";
  }

  smiv2:alias "cevCat6kWsx6302Msm" {
    smiv2:oid "1.3.6.1.4.1.9.12.3.1.9.29.7";
  }

  smiv2:alias "cevCat6kWsx6024Mtrj" {
    smiv2:oid "1.3.6.1.4.1.9.12.3.1.9.29.9";
  }

  smiv2:alias "cevCat6kMsfc2" {
    smiv2:oid "1.3.6.1.4.1.9.12.3.1.9.29.10";
  }

  smiv2:alias "cevCat6kWsx6316GeTx" {
    smiv2:oid "1.3.6.1.4.1.9.12.3.1.9.29.11";
  }

  smiv2:alias "cevCat6kWsx6416Gbic" {
    smiv2:oid "1.3.6.1.4.1.9.12.3.1.9.29.12";
  }

  smiv2:alias "cevCat6kWsx6324100Fx" {
    smiv2:oid "1.3.6.1.4.1.9.12.3.1.9.29.13";
  }

  smiv2:alias "cevCat6kWsx6348Rj45" {
    smiv2:oid "1.3.6.1.4.1.9.12.3.1.9.29.14";
  }

  smiv2:alias "cevCat6kWsx650210ge" {
    smiv2:oid "1.3.6.1.4.1.9.12.3.1.9.29.15";
  }

  smiv2:alias "cevCat6kWsx6066SlbApc" {
    smiv2:oid "1.3.6.1.4.1.9.12.3.1.9.29.16";
  }

  smiv2:alias "cevCat6kWsx6548Rj45" {
    smiv2:oid "1.3.6.1.4.1.9.12.3.1.9.29.18";
  }

  smiv2:alias "cevCat6kWsx6248aTel" {
    smiv2:oid "1.3.6.1.4.1.9.12.3.1.9.29.19";
  }

  smiv2:alias "cevCat6kWsxSup22ge" {
    smiv2:oid "1.3.6.1.4.1.9.12.3.1.9.29.20";
  }

  smiv2:alias "cevCat6kWsc6500SFM" {
    smiv2:oid "1.3.6.1.4.1.9.12.3.1.9.29.21";
  }

  smiv2:alias "cevCat6kWsc6500SFM2" {
    smiv2:oid "1.3.6.1.4.1.9.12.3.1.9.29.22";
  }

  smiv2:alias "cevCat6kWsx6816GBIC" {
    smiv2:oid "1.3.6.1.4.1.9.12.3.1.9.29.23";
  }

  smiv2:alias "cevCat6kWsx6600Audio" {
    smiv2:oid "1.3.6.1.4.1.9.12.3.1.9.29.27";
  }

  smiv2:alias "cevCat6kWsx6348RJ21" {
    smiv2:oid "1.3.6.1.4.1.9.12.3.1.9.29.28";
  }

  smiv2:alias "cevCat6kWsx6516GBIC" {
    smiv2:oid "1.3.6.1.4.1.9.12.3.1.9.29.29";
  }

  smiv2:alias "cevCat6kWsxSup1a2ge" {
    smiv2:oid "1.3.6.1.4.1.9.12.3.1.9.29.30";
  }

  smiv2:alias "cevCat6kWsx6548RJ21" {
    smiv2:oid "1.3.6.1.4.1.9.12.3.1.9.29.31";
  }

  smiv2:alias "cevCat6kWsx6416GEMT" {
    smiv2:oid "1.3.6.1.4.1.9.12.3.1.9.29.32";
  }

  smiv2:alias "cevCat6kWsx6380NAM" {
    smiv2:oid "1.3.6.1.4.1.9.12.3.1.9.29.33";
  }

  smiv2:alias "cevCat6kWsx6248aRJ45" {
    smiv2:oid "1.3.6.1.4.1.9.12.3.1.9.29.34";
  }

  smiv2:alias "cevCat6kWsx6408aGbic" {
    smiv2:oid "1.3.6.1.4.1.9.12.3.1.9.29.35";
  }

  smiv2:alias "cevCat6kWsx6381IDS" {
    smiv2:oid "1.3.6.1.4.1.9.12.3.1.9.29.36";
  }

  smiv2:alias "cevCat6kWsx6524MmMT" {
    smiv2:oid "1.3.6.1.4.1.9.12.3.1.9.29.37";
  }

  smiv2:alias "cevCat6kWsx6516GeTx" {
    smiv2:oid "1.3.6.1.4.1.9.12.3.1.9.29.38";
  }

  smiv2:alias "cevCat6kWsx650110Gex4" {
    smiv2:oid "1.3.6.1.4.1.9.12.3.1.9.29.39";
  }

  smiv2:alias "cevCat6kWsx6816Oc3Mm" {
    smiv2:oid "1.3.6.1.4.1.9.12.3.1.9.29.40";
  }

  smiv2:alias "cevCat6kWsf6kVpwr" {
    smiv2:oid "1.3.6.1.4.1.9.12.3.1.9.29.41";
  }

  smiv2:alias "cevCat6kWsSvcNam1" {
    smiv2:oid "1.3.6.1.4.1.9.12.3.1.9.29.42";
  }

  smiv2:alias "cevCat6kWsSvcNam2" {
    smiv2:oid "1.3.6.1.4.1.9.12.3.1.9.29.43";
  }

  smiv2:alias "cevCat6kWsSvcFwm1" {
    smiv2:oid "1.3.6.1.4.1.9.12.3.1.9.29.44";
  }

  smiv2:alias "cevCat6kWsSvcSsl1" {
    smiv2:oid "1.3.6.1.4.1.9.12.3.1.9.29.45";
  }

  smiv2:alias "cevCat6kWsx6516aGBIC" {
    smiv2:oid "1.3.6.1.4.1.9.12.3.1.9.29.46";
  }

  smiv2:alias "cevCat6kIpSecVPNSm" {
    smiv2:oid "1.3.6.1.4.1.9.12.3.1.9.29.49";
  }

  smiv2:alias "cevCat6kWsSup720" {
    smiv2:oid "1.3.6.1.4.1.9.12.3.1.9.29.50";
  }

  smiv2:alias "cevCat6kWsSup720Base" {
    smiv2:oid "1.3.6.1.4.1.9.12.3.1.9.29.51";
  }

  smiv2:alias "cevCat6kWsx680210Ge" {
    smiv2:oid "1.3.6.1.4.1.9.12.3.1.9.29.52";
  }

  smiv2:alias "cevCat6kWsx6832Sfp" {
    smiv2:oid "1.3.6.1.4.1.9.12.3.1.9.29.53";
  }

  smiv2:alias "cevCat6kWsx6748GeTx" {
    smiv2:oid "1.3.6.1.4.1.9.12.3.1.9.29.54";
  }

  smiv2:alias "cevCat6kWsx670410Ge" {
    smiv2:oid "1.3.6.1.4.1.9.12.3.1.9.29.55";
  }

  smiv2:alias "cevCat6kWsx6748Sfp" {
    smiv2:oid "1.3.6.1.4.1.9.12.3.1.9.29.56";
  }

  smiv2:alias "cevCat6kWsx6724Sfp" {
    smiv2:oid "1.3.6.1.4.1.9.12.3.1.9.29.57";
  }

  smiv2:alias "cevCat6kWsf6kPfc" {
    smiv2:oid "1.3.6.1.4.1.9.12.3.1.9.29.58";
  }

  smiv2:alias "cevCat6kWsf6kPfc2" {
    smiv2:oid "1.3.6.1.4.1.9.12.3.1.9.29.59";
  }

  smiv2:alias "cevCat6kWsf6kDfc" {
    smiv2:oid "1.3.6.1.4.1.9.12.3.1.9.29.60";
  }

  smiv2:alias "cevCat6kWsf6kPfc3a" {
    smiv2:oid "1.3.6.1.4.1.9.12.3.1.9.29.61";
  }

  smiv2:alias "cevCat6kWsf6kDfc3a" {
    smiv2:oid "1.3.6.1.4.1.9.12.3.1.9.29.62";
  }

  smiv2:alias "cevCat6kWsx6148GeTx" {
    smiv2:oid "1.3.6.1.4.1.9.12.3.1.9.29.63";
  }

  smiv2:alias "cevCat6kWsx6148Rj21" {
    smiv2:oid "1.3.6.1.4.1.9.12.3.1.9.29.64";
  }

  smiv2:alias "cevCat6kWsx6148Rj45" {
    smiv2:oid "1.3.6.1.4.1.9.12.3.1.9.29.65";
  }

  smiv2:alias "cevCat6kMWAMBlade" {
    smiv2:oid "1.3.6.1.4.1.9.12.3.1.9.29.66";
  }

  smiv2:alias "cevCat6kWsx6548GeTx" {
    smiv2:oid "1.3.6.1.4.1.9.12.3.1.9.29.67";
  }

  smiv2:alias "cevCat6kWsf6700dfc3a" {
    smiv2:oid "1.3.6.1.4.1.9.12.3.1.9.29.68";
  }

  smiv2:alias "cevCat6kWsx6324100FxSm" {
    smiv2:oid "1.3.6.1.4.1.9.12.3.1.9.29.69";
  }

  smiv2:alias "cevCat6kWsc6000cl" {
    smiv2:oid "1.3.6.1.4.1.9.12.3.1.9.29.70";
  }

  smiv2:alias "cevCat6kWsc6513cl" {
    smiv2:oid "1.3.6.1.4.1.9.12.3.1.9.29.71";
  }

  smiv2:alias "cevClk7600" {
    smiv2:oid "1.3.6.1.4.1.9.12.3.1.9.29.72";
  }

  smiv2:alias "cevCat6kWsc6kvtt" {
    smiv2:oid "1.3.6.1.4.1.9.12.3.1.9.29.73";
  }

  smiv2:alias "cevCat6kWsx6302aMsm" {
    smiv2:oid "1.3.6.1.4.1.9.12.3.1.9.29.74";
  }

  smiv2:alias "cevCat6kMemC6kAta164M" {
    smiv2:oid "1.3.6.1.4.1.9.12.3.1.9.29.75";
  }

  smiv2:alias "cevCat6kMemC6kCptfl64M" {
    smiv2:oid "1.3.6.1.4.1.9.12.3.1.9.29.76";
  }

  smiv2:alias "cevCat6kMemC6kCptfl128M" {
    smiv2:oid "1.3.6.1.4.1.9.12.3.1.9.29.77";
  }

  smiv2:alias "cevCat6kMemC6kCptfl256M" {
    smiv2:oid "1.3.6.1.4.1.9.12.3.1.9.29.78";
  }

  smiv2:alias "cevCat6kMemC6kFlc16M" {
    smiv2:oid "1.3.6.1.4.1.9.12.3.1.9.29.79";
  }

  smiv2:alias "cevCat6kMemC6kFlc24M" {
    smiv2:oid "1.3.6.1.4.1.9.12.3.1.9.29.80";
  }

  smiv2:alias "cevCat6kWsSvcIdsm2" {
    smiv2:oid "1.3.6.1.4.1.9.12.3.1.9.29.81";
  }

  smiv2:alias "cevCat6kWssvcidsupg" {
    smiv2:oid "1.3.6.1.4.1.9.12.3.1.9.29.82";
  }

  smiv2:alias "cevCat6kWsx6148x2Rj45" {
    smiv2:oid "1.3.6.1.4.1.9.12.3.1.9.29.83";
  }

  smiv2:alias "cevCat6kWsf6kFe48x2Af" {
    smiv2:oid "1.3.6.1.4.1.9.12.3.1.9.29.84";
  }

  smiv2:alias "cevCat6kWsf6kFe48Af" {
    smiv2:oid "1.3.6.1.4.1.9.12.3.1.9.29.85";
  }

  smiv2:alias "cevCat6kWsf6kGe48Af" {
    smiv2:oid "1.3.6.1.4.1.9.12.3.1.9.29.86";
  }

  smiv2:alias "cevCat6kWsf6kVpwrGe" {
    smiv2:oid "1.3.6.1.4.1.9.12.3.1.9.29.87";
  }

  smiv2:alias "cevCat6kWsf6700cfc" {
    smiv2:oid "1.3.6.1.4.1.9.12.3.1.9.29.88";
  }

  smiv2:alias "cevCat6kWsSvcWlan1K9" {
    smiv2:oid "1.3.6.1.4.1.9.12.3.1.9.29.89";
  }

  smiv2:alias "cevCat6kWsx6624Fxs" {
    smiv2:oid "1.3.6.1.4.1.9.12.3.1.9.29.90";
  }

  smiv2:alias "cevCat6kWsSvcAon1" {
    smiv2:oid "1.3.6.1.4.1.9.12.3.1.9.29.91";
  }

  smiv2:alias "cevCat6kWsSup32ge" {
    smiv2:oid "1.3.6.1.4.1.9.12.3.1.9.29.92";
  }

  smiv2:alias "cevCat6kWsSup3210ge" {
    smiv2:oid "1.3.6.1.4.1.9.12.3.1.9.29.93";
  }

  smiv2:alias "cevCat6kPSDBlade" {
    smiv2:oid "1.3.6.1.4.1.9.12.3.1.9.29.94";
  }

  smiv2:alias "cevCat6kWsc6kvtte" {
    smiv2:oid "1.3.6.1.4.1.9.12.3.1.9.29.95";
  }

  smiv2:alias "cevCat6kWsx6066SlbsK9" {
    smiv2:oid "1.3.6.1.4.1.9.12.3.1.9.29.98";
  }

  smiv2:alias "cevCat6kWsf6kpfc3b" {
    smiv2:oid "1.3.6.1.4.1.9.12.3.1.9.29.99";
  }

  smiv2:alias "cevCat6kWsf6kdfc3b" {
    smiv2:oid "1.3.6.1.4.1.9.12.3.1.9.29.100";
  }

  smiv2:alias "cevCat6kWsf6700dfc3b" {
    smiv2:oid "1.3.6.1.4.1.9.12.3.1.9.29.101";
  }

  smiv2:alias "cevCat6kWsf6kpfc3bxl" {
    smiv2:oid "1.3.6.1.4.1.9.12.3.1.9.29.102";
  }

  smiv2:alias "cevCat6kWsf6kdfc3bxl" {
    smiv2:oid "1.3.6.1.4.1.9.12.3.1.9.29.103";
  }

  smiv2:alias "cevCat6kWsf6700dfc3bxl" {
    smiv2:oid "1.3.6.1.4.1.9.12.3.1.9.29.104";
  }

  smiv2:alias "cevCat6kCsg" {
    smiv2:oid "1.3.6.1.4.1.9.12.3.1.9.29.105";
  }

  smiv2:alias "cevCat6kMsfc2a" {
    smiv2:oid "1.3.6.1.4.1.9.12.3.1.9.29.106";
  }

  smiv2:alias "cevCat6kWs6340Sup" {
    smiv2:oid "1.3.6.1.4.1.9.12.3.1.9.29.107";
  }

  smiv2:alias "cevCat6kWs6340LcA" {
    smiv2:oid "1.3.6.1.4.1.9.12.3.1.9.29.108";
  }

  smiv2:alias "cevCat6kWs6340LcB" {
    smiv2:oid "1.3.6.1.4.1.9.12.3.1.9.29.109";
  }

  smiv2:alias "cevCat6kMec6524gs8s" {
    smiv2:oid "1.3.6.1.4.1.9.12.3.1.9.29.110";
  }

  smiv2:alias "cevCat6kMec6524gt8s" {
    smiv2:oid "1.3.6.1.4.1.9.12.3.1.9.29.111";
  }

  smiv2:alias "cevCat6kMec6524Msfc2a" {
    smiv2:oid "1.3.6.1.4.1.9.12.3.1.9.29.114";
  }

  smiv2:alias "cevCat6kMec6524Pfc3c" {
    smiv2:oid "1.3.6.1.4.1.9.12.3.1.9.29.115";
  }

  smiv2:alias "cevCat6kWsx6196Rj21" {
    smiv2:oid "1.3.6.1.4.1.9.12.3.1.9.29.116";
  }

  smiv2:alias "cevCat6kWsx6148FeSfp" {
    smiv2:oid "1.3.6.1.4.1.9.12.3.1.9.29.117";
  }

  smiv2:alias "cevCat6kWsx6148aGeTx" {
    smiv2:oid "1.3.6.1.4.1.9.12.3.1.9.29.118";
  }

  smiv2:alias "cevCat6kWsx6148aRj45" {
    smiv2:oid "1.3.6.1.4.1.9.12.3.1.9.29.119";
  }

  smiv2:alias "cevCat6kAce10K9" {
    smiv2:oid "1.3.6.1.4.1.9.12.3.1.9.29.120";
  }

  smiv2:alias "cevCat6kWsg6483" {
    smiv2:oid "1.3.6.1.4.1.9.12.3.1.9.29.122";
  }

  smiv2:alias "cevCat6kWsg6485" {
    smiv2:oid "1.3.6.1.4.1.9.12.3.1.9.29.123";
  }

  smiv2:alias "cevCat6kWsg6488" {
    smiv2:oid "1.3.6.1.4.1.9.12.3.1.9.29.124";
  }

  smiv2:alias "cevCat6kWsg6489" {
    smiv2:oid "1.3.6.1.4.1.9.12.3.1.9.29.125";
  }

  smiv2:alias "cevCat6kWsSvcWebVpnK9" {
    smiv2:oid "1.3.6.1.4.1.9.12.3.1.9.29.126";
  }

  smiv2:alias "cevCat6kSAMIBB" {
    smiv2:oid "1.3.6.1.4.1.9.12.3.1.9.29.127";
  }

  smiv2:alias "cevCat6kWsx6708a10ge" {
    smiv2:oid "1.3.6.1.4.1.9.12.3.1.9.29.128";
  }

  smiv2:alias "cevCat6kWsx670810ge" {
    smiv2:oid "1.3.6.1.4.1.9.12.3.1.9.29.129";
  }

  smiv2:alias "cevCat6kWsf6700Dfc3c" {
    smiv2:oid "1.3.6.1.4.1.9.12.3.1.9.29.131";
  }

  smiv2:alias "cevCat6kWsf6700Dfc3cxl" {
    smiv2:oid "1.3.6.1.4.1.9.12.3.1.9.29.132";
  }

  smiv2:alias "cevCat6kVsS72010G" {
    smiv2:oid "1.3.6.1.4.1.9.12.3.1.9.29.133";
  }

  smiv2:alias "cevCat6kVsf6kPfc3c" {
    smiv2:oid "1.3.6.1.4.1.9.12.3.1.9.29.134";
  }

  smiv2:alias "cevCat6kVsf6kPfc3cxl" {
    smiv2:oid "1.3.6.1.4.1.9.12.3.1.9.29.135";
  }

  smiv2:alias "cevCat6kVsF6kMsfc3" {
    smiv2:oid "1.3.6.1.4.1.9.12.3.1.9.29.136";
  }

  smiv2:alias "cevCat6kWsF6kPisa" {
    smiv2:oid "1.3.6.1.4.1.9.12.3.1.9.29.137";
  }

  smiv2:alias "cevCat6kVsF6kPfc4xl" {
    smiv2:oid "1.3.6.1.4.1.9.12.3.1.9.29.138";
  }

  smiv2:alias "cevCat6kWsF6kDfc4exl" {
    smiv2:oid "1.3.6.1.4.1.9.12.3.1.9.29.139";
  }

  smiv2:alias "cevCat6kWsx671610Ge" {
    smiv2:oid "1.3.6.1.4.1.9.12.3.1.9.29.142";
  }

  smiv2:alias "cevCat6kVsF6kPfc4" {
    smiv2:oid "1.3.6.1.4.1.9.12.3.1.9.29.143";
  }

  smiv2:alias "cevCat6kWsF6kDfc4e" {
    smiv2:oid "1.3.6.1.4.1.9.12.3.1.9.29.144";
  }

  smiv2:alias "cevCat6kWsSup32Pge" {
    smiv2:oid "1.3.6.1.4.1.9.12.3.1.9.29.145";
  }

  smiv2:alias "cevCat6kWsSup32P10ge" {
    smiv2:oid "1.3.6.1.4.1.9.12.3.1.9.29.146";
  }

  smiv2:alias "cevCat6kWsx690810g" {
    smiv2:oid "1.3.6.1.4.1.9.12.3.1.9.29.148";
  }

  smiv2:alias "cevCat6kWsc6513Ecl" {
    smiv2:oid "1.3.6.1.4.1.9.12.3.1.9.29.155";
  }

  smiv2:alias "cevCat6kWsSvcWism" {
    smiv2:oid "1.3.6.1.4.1.9.12.3.1.9.29.156";
  }

  smiv2:alias "cevCat6kWsSvcNam1S250" {
    smiv2:oid "1.3.6.1.4.1.9.12.3.1.9.29.157";
  }

  smiv2:alias "cevCat6kWsSvcNam2S250" {
    smiv2:oid "1.3.6.1.4.1.9.12.3.1.9.29.158";
  }

  smiv2:alias "cevCat6kWsF6kDfc4a" {
    smiv2:oid "1.3.6.1.4.1.9.12.3.1.9.29.159";
  }

  smiv2:alias "cevCat6kWsF6kDfc4axl" {
    smiv2:oid "1.3.6.1.4.1.9.12.3.1.9.29.160";
  }

  smiv2:alias "cevCat6kVsSup2t10g" {
    smiv2:oid "1.3.6.1.4.1.9.12.3.1.9.29.163";
  }

  smiv2:alias "cevCat6kVsF6kMsfc5" {
    smiv2:oid "1.3.6.1.4.1.9.12.3.1.9.29.164";
  }

  smiv2:alias "cevCat6kWsf6k48At" {
    smiv2:oid "1.3.6.1.4.1.9.12.3.1.9.29.166";
  }

  smiv2:alias "cevCat6kWsx6148eGe45At" {
    smiv2:oid "1.3.6.1.4.1.9.12.3.1.9.29.167";
  }

  smiv2:alias "cevCat6kWsx671610T" {
    smiv2:oid "1.3.6.1.4.1.9.12.3.1.9.29.168";
  }

  smiv2:alias "cevCat6kWsSvcAsaSm1" {
    smiv2:oid "1.3.6.1.4.1.9.12.3.1.9.29.169";
  }

  smiv2:alias "cevCat6kWsx6148eGeTx" {
    smiv2:oid "1.3.6.1.4.1.9.12.3.1.9.29.172";
  }

  smiv2:alias "cevCat6kWsx690440g" {
    smiv2:oid "1.3.6.1.4.1.9.12.3.1.9.29.174";
  }

  smiv2:alias "cevCat6kWsSvcNam3K9" {
    smiv2:oid "1.3.6.1.4.1.9.12.3.1.9.29.175";
  }

  smiv2:alias "cevCat6kWsx6848Tx" {
    smiv2:oid "1.3.6.1.4.1.9.12.3.1.9.29.176";
  }

  smiv2:alias "cevCat6kWsx6848sfp" {
    smiv2:oid "1.3.6.1.4.1.9.12.3.1.9.29.178";
  }

  smiv2:alias "cevCat6kWsx6824sfp" {
    smiv2:oid "1.3.6.1.4.1.9.12.3.1.9.29.179";
  }

  smiv2:alias "cevCat6kWsx681610ge" {
    smiv2:oid "1.3.6.1.4.1.9.12.3.1.9.29.181";
  }

  smiv2:alias "cevCat6kWsx681610t" {
    smiv2:oid "1.3.6.1.4.1.9.12.3.1.9.29.182";
  }

  smiv2:alias "cevCat6kACE20K9" {
    smiv2:oid "1.3.6.1.4.1.9.12.3.1.9.29.184";
  }

  smiv2:alias "cevCat6kWsSvcWism2" {
    smiv2:oid "1.3.6.1.4.1.9.12.3.1.9.29.185";
  }

  smiv2:alias "cevCat6kWsSvcAsaSm1K7" {
    smiv2:oid "1.3.6.1.4.1.9.12.3.1.9.29.186";
  }

  smiv2:alias "cevCat6kC6880xSup" {
    smiv2:oid "1.3.6.1.4.1.9.12.3.1.9.29.189";
  }

  smiv2:alias "cevCat6kC6880xleSup" {
    smiv2:oid "1.3.6.1.4.1.9.12.3.1.9.29.190";
  }

  smiv2:alias "cevCat6kC6800xl33vCon" {
    smiv2:oid "1.3.6.1.4.1.9.12.3.1.9.29.195";
  }

  smiv2:alias "cevModuleCat5000Type" {
    smiv2:oid "1.3.6.1.4.1.9.12.3.1.9.30";
  }

  smiv2:alias "cevCat5kRsfc" {
    smiv2:oid "1.3.6.1.4.1.9.12.3.1.9.30.1";
  }

  smiv2:alias "cevModule7100Type" {
    smiv2:oid "1.3.6.1.4.1.9.12.3.1.9.31";
  }

  smiv2:alias "cevIo2feTxIsl" {
    smiv2:oid "1.3.6.1.4.1.9.12.3.1.9.31.1";
  }

  smiv2:alias "cevIsmIpsecMppe" {
    smiv2:oid "1.3.6.1.4.1.9.12.3.1.9.31.2";
  }

  smiv2:alias "cev7100VPNAccelerator" {
    smiv2:oid "1.3.6.1.4.1.9.12.3.1.9.31.3";
  }

  smiv2:alias "cev7100VPNAcceleratorModule2" {
    smiv2:oid "1.3.6.1.4.1.9.12.3.1.9.31.4";
  }

  smiv2:alias "cev7100VPNAcceleratorAES" {
    smiv2:oid "1.3.6.1.4.1.9.12.3.1.9.31.5";
  }

  smiv2:alias "cev7100VPNAM2Plus" {
    smiv2:oid "1.3.6.1.4.1.9.12.3.1.9.31.6";
  }

  smiv2:alias "cevModule10000Type" {
    smiv2:oid "1.3.6.1.4.1.9.12.3.1.9.32";
  }

  smiv2:alias "cevPos1oc12" {
    smiv2:oid "1.3.6.1.4.1.9.12.3.1.9.32.1";
  }

  smiv2:alias "cevP6Ct3" {
    smiv2:oid "1.3.6.1.4.1.9.12.3.1.9.32.2";
  }

  smiv2:alias "cevGe" {
    smiv2:oid "1.3.6.1.4.1.9.12.3.1.9.32.3";
  }

  smiv2:alias "cevAtm1Oc12" {
    smiv2:oid "1.3.6.1.4.1.9.12.3.1.9.32.4";
  }

  smiv2:alias "cevP1COc12" {
    smiv2:oid "1.3.6.1.4.1.9.12.3.1.9.32.5";
  }

  smiv2:alias "cevP4Chstm1" {
    smiv2:oid "1.3.6.1.4.1.9.12.3.1.9.32.6";
  }

  smiv2:alias "cev24feTx" {
    smiv2:oid "1.3.6.1.4.1.9.12.3.1.9.32.8";
  }

  smiv2:alias "cev24feFxMm" {
    smiv2:oid "1.3.6.1.4.1.9.12.3.1.9.32.9";
  }

  smiv2:alias "cev24feFxSm" {
    smiv2:oid "1.3.6.1.4.1.9.12.3.1.9.32.10";
  }

  smiv2:alias "cevSrpOc48SmSr" {
    smiv2:oid "1.3.6.1.4.1.9.12.3.1.9.32.11";
  }

  smiv2:alias "cevSrpOc48SmIr" {
    smiv2:oid "1.3.6.1.4.1.9.12.3.1.9.32.12";
  }

  smiv2:alias "cevPos6oc3" {
    smiv2:oid "1.3.6.1.4.1.9.12.3.1.9.32.13";
  }

  smiv2:alias "cevAtm4oc3" {
    smiv2:oid "1.3.6.1.4.1.9.12.3.1.9.32.14";
  }

  smiv2:alias "cevP8E3Ds3" {
    smiv2:oid "1.3.6.1.4.1.9.12.3.1.9.32.15";
  }

  smiv2:alias "cevSrpPos1oc48SmSr" {
    smiv2:oid "1.3.6.1.4.1.9.12.3.1.9.32.16";
  }

  smiv2:alias "cevSrpPos1oc48SmLr" {
    smiv2:oid "1.3.6.1.4.1.9.12.3.1.9.32.17";
  }

  smiv2:alias "cevC10K48MbFlashCard" {
    smiv2:oid "1.3.6.1.4.1.9.12.3.1.9.32.18";
  }

  smiv2:alias "cevC10K128MbFlashCard" {
    smiv2:oid "1.3.6.1.4.1.9.12.3.1.9.32.19";
  }

  smiv2:alias "cevP24ChE1T1" {
    smiv2:oid "1.3.6.1.4.1.9.12.3.1.9.32.22";
  }

  smiv2:alias "cev4Ge8FeTx" {
    smiv2:oid "1.3.6.1.4.1.9.12.3.1.9.32.23";
  }

  smiv2:alias "cev4Ge8FeFxMm" {
    smiv2:oid "1.3.6.1.4.1.9.12.3.1.9.32.24";
  }

  smiv2:alias "cev4Ge8FeFxSm" {
    smiv2:oid "1.3.6.1.4.1.9.12.3.1.9.32.25";
  }

  smiv2:alias "cevSrpOc48SmLr1" {
    smiv2:oid "1.3.6.1.4.1.9.12.3.1.9.32.26";
  }

  smiv2:alias "cevSrpOc48SmLr2" {
    smiv2:oid "1.3.6.1.4.1.9.12.3.1.9.32.27";
  }

  smiv2:alias "cevP8Fe" {
    smiv2:oid "1.3.6.1.4.1.9.12.3.1.9.32.30";
  }

  smiv2:alias "cevP8Ds3E3Atm" {
    smiv2:oid "1.3.6.1.4.1.9.12.3.1.9.32.31";
  }

  smiv2:alias "cevC10720Mnt" {
    smiv2:oid "1.3.6.1.4.1.9.12.3.1.9.32.32";
  }

  smiv2:alias "cevPosSrpOc48SmSr" {
    smiv2:oid "1.3.6.1.4.1.9.12.3.1.9.32.34";
  }

  smiv2:alias "cevPosSrpOc48SmIr" {
    smiv2:oid "1.3.6.1.4.1.9.12.3.1.9.32.35";
  }

  smiv2:alias "cevPosSrpOc48SmLr1" {
    smiv2:oid "1.3.6.1.4.1.9.12.3.1.9.32.36";
  }

  smiv2:alias "cevPosSrpOc48SmLr2" {
    smiv2:oid "1.3.6.1.4.1.9.12.3.1.9.32.37";
  }

  smiv2:alias "cevC10KJacket" {
    smiv2:oid "1.3.6.1.4.1.9.12.3.1.9.32.38";
  }

  smiv2:alias "cev24feTxB" {
    smiv2:oid "1.3.6.1.4.1.9.12.3.1.9.32.39";
  }

  smiv2:alias "cev4Ge8FeTxB" {
    smiv2:oid "1.3.6.1.4.1.9.12.3.1.9.32.40";
  }

  smiv2:alias "cevRprSrpOc48" {
    smiv2:oid "1.3.6.1.4.1.9.12.3.1.9.32.41";
  }

  smiv2:alias "cevP4Ct3" {
    smiv2:oid "1.3.6.1.4.1.9.12.3.1.9.32.42";
  }

  smiv2:alias "cevAtm4oc3stm1Lr" {
    smiv2:oid "1.3.6.1.4.1.9.12.3.1.9.32.43";
  }

  smiv2:alias "cevModuleAs5400Type" {
    smiv2:oid "1.3.6.1.4.1.9.12.3.1.9.33";
  }

  smiv2:alias "cevAs5400DfcCarrier" {
    smiv2:oid "1.3.6.1.4.1.9.12.3.1.9.33.1";
  }

  smiv2:alias "cevAs5400DfcNp348" {
    smiv2:oid "1.3.6.1.4.1.9.12.3.1.9.33.2";
  }

  smiv2:alias "cevAs5400DfcNp192" {
    smiv2:oid "1.3.6.1.4.1.9.12.3.1.9.33.3";
  }

  smiv2:alias "cevAs5400XMDfcCarrier" {
    smiv2:oid "1.3.6.1.4.1.9.12.3.1.9.33.4";
  }

  smiv2:alias "cevAs5400XMVFC" {
    smiv2:oid "1.3.6.1.4.1.9.12.3.1.9.33.5";
  }

  smiv2:alias "cevModuleCat4000Type" {
    smiv2:oid "1.3.6.1.4.1.9.12.3.1.9.35";
  }

  smiv2:alias "cevCat4232L3" {
    smiv2:oid "1.3.6.1.4.1.9.12.3.1.9.35.1";
  }

  smiv2:alias "cevCat4kGateway" {
    smiv2:oid "1.3.6.1.4.1.9.12.3.1.9.35.2";
  }

  smiv2:alias "cevCat4kWsx4014" {
    smiv2:oid "1.3.6.1.4.1.9.12.3.1.9.35.3";
  }

  smiv2:alias "cevCat4kWsx4124FxMt" {
    smiv2:oid "1.3.6.1.4.1.9.12.3.1.9.35.4";
  }

  smiv2:alias "cevCat4kWsx4148FxMt" {
    smiv2:oid "1.3.6.1.4.1.9.12.3.1.9.35.5";
  }

  smiv2:alias "cevCat4kWsx4148Rj" {
    smiv2:oid "1.3.6.1.4.1.9.12.3.1.9.35.6";
  }

  smiv2:alias "cevCat4kWsx4148Rj21" {
    smiv2:oid "1.3.6.1.4.1.9.12.3.1.9.35.7";
  }

  smiv2:alias "cevCat4kWsx4148Rj45V" {
    smiv2:oid "1.3.6.1.4.1.9.12.3.1.9.35.8";
  }

  smiv2:alias "cevCat4kWsx4232GbRj" {
    smiv2:oid "1.3.6.1.4.1.9.12.3.1.9.35.9";
  }

  smiv2:alias "cevCat4kWsx4232RjXx" {
    smiv2:oid "1.3.6.1.4.1.9.12.3.1.9.35.10";
  }

  smiv2:alias "cevCat4kWsx4306Gb" {
    smiv2:oid "1.3.6.1.4.1.9.12.3.1.9.35.11";
  }

  smiv2:alias "cevCat4kWsx4418Gb" {
    smiv2:oid "1.3.6.1.4.1.9.12.3.1.9.35.12";
  }

  smiv2:alias "cevCat4kWsx44122GbTx" {
    smiv2:oid "1.3.6.1.4.1.9.12.3.1.9.35.13";
  }

  smiv2:alias "cevCat4kWsx4424GbRj45" {
    smiv2:oid "1.3.6.1.4.1.9.12.3.1.9.35.14";
  }

  smiv2:alias "cevCat4kWsx4448GbLx" {
    smiv2:oid "1.3.6.1.4.1.9.12.3.1.9.35.15";
  }

  smiv2:alias "cevCat4kWsx4448GbRj45" {
    smiv2:oid "1.3.6.1.4.1.9.12.3.1.9.35.16";
  }

  smiv2:alias "cevCat4kPEM" {
    smiv2:oid "1.3.6.1.4.1.9.12.3.1.9.35.17";
  }

  smiv2:alias "cevCat4kWsx4515" {
    smiv2:oid "1.3.6.1.4.1.9.12.3.1.9.35.18";
  }

  smiv2:alias "cevCat4kWsx4148LxMt" {
    smiv2:oid "1.3.6.1.4.1.9.12.3.1.9.35.19";
  }

  smiv2:alias "cevCat4kWsx4248Rj45V" {
    smiv2:oid "1.3.6.1.4.1.9.12.3.1.9.35.20";
  }

  smiv2:alias "cevCat4kWsx4516" {
    smiv2:oid "1.3.6.1.4.1.9.12.3.1.9.35.21";
  }

  smiv2:alias "cevCat4kWsx4013Plus" {
    smiv2:oid "1.3.6.1.4.1.9.12.3.1.9.35.22";
  }

  smiv2:alias "cevCat4kWsx4248Rj21V" {
    smiv2:oid "1.3.6.1.4.1.9.12.3.1.9.35.23";
  }

  smiv2:alias "cevCat4kWsx4302Gb" {
    smiv2:oid "1.3.6.1.4.1.9.12.3.1.9.35.24";
  }

  smiv2:alias "cevCat4kWsx4548GbRj45V" {
    smiv2:oid "1.3.6.1.4.1.9.12.3.1.9.35.25";
  }

  smiv2:alias "cevCat4kWsx4548GbRj45" {
    smiv2:oid "1.3.6.1.4.1.9.12.3.1.9.35.26";
  }

  smiv2:alias "cevCat4kWsx4712Qam24B" {
    smiv2:oid "1.3.6.1.4.1.9.12.3.1.9.35.27";
  }

  smiv2:alias "cevCat4kWsx4148FeBdLc" {
    smiv2:oid "1.3.6.1.4.1.9.12.3.1.9.35.28";
  }

  smiv2:alias "cevCat4kWsx4124Rj" {
    smiv2:oid "1.3.6.1.4.1.9.12.3.1.9.35.29";
  }

  smiv2:alias "cevCat4kWsx4224Rj45V" {
    smiv2:oid "1.3.6.1.4.1.9.12.3.1.9.35.30";
  }

  smiv2:alias "cevCat4kWsx4524GbRj45V" {
    smiv2:oid "1.3.6.1.4.1.9.12.3.1.9.35.31";
  }

  smiv2:alias "cevCat4kWsx4506GBT" {
    smiv2:oid "1.3.6.1.4.1.9.12.3.1.9.35.32";
  }

  smiv2:alias "cevCat4kWsxSvcNam" {
    smiv2:oid "1.3.6.1.4.1.9.12.3.1.9.35.33";
  }

  smiv2:alias "cevCat4kWsx4448GbSfp" {
    smiv2:oid "1.3.6.1.4.1.9.12.3.1.9.35.34";
  }

  smiv2:alias "cevCat4kWsX4013PlusTS" {
    smiv2:oid "1.3.6.1.4.1.9.12.3.1.9.35.35";
  }

  smiv2:alias "cevCat4kWsx4kClock" {
    smiv2:oid "1.3.6.1.4.1.9.12.3.1.9.35.36";
  }

  smiv2:alias "cevCat4kWsx4948" {
    smiv2:oid "1.3.6.1.4.1.9.12.3.1.9.35.37";
  }

  smiv2:alias "cevCat4kWsx451610GE" {
    smiv2:oid "1.3.6.1.4.1.9.12.3.1.9.35.38";
  }

  smiv2:alias "cevCat4kWsx4013Plus10GE" {
    smiv2:oid "1.3.6.1.4.1.9.12.3.1.9.35.40";
  }

  smiv2:alias "cevCat4kWsx494810GE" {
    smiv2:oid "1.3.6.1.4.1.9.12.3.1.9.35.42";
  }

  smiv2:alias "cevCat4kWsx4kMux" {
    smiv2:oid "1.3.6.1.4.1.9.12.3.1.9.35.43";
  }

  smiv2:alias "cevCat4kWsx490410ge" {
    smiv2:oid "1.3.6.1.4.1.9.12.3.1.9.35.44";
  }

  smiv2:alias "cevCat4kWsx4900M" {
    smiv2:oid "1.3.6.1.4.1.9.12.3.1.9.35.45";
  }

  smiv2:alias "cevCat4kWsx490810ge" {
    smiv2:oid "1.3.6.1.4.1.9.12.3.1.9.35.46";
  }

  smiv2:alias "cevCat4kWsx4920Gbrj45" {
    smiv2:oid "1.3.6.1.4.1.9.12.3.1.9.35.47";
  }

  smiv2:alias "cevCat4kWsx4590" {
    smiv2:oid "1.3.6.1.4.1.9.12.3.1.9.35.48";
  }

  smiv2:alias "cevCatWsx4624SfpE" {
    smiv2:oid "1.3.6.1.4.1.9.12.3.1.9.35.49";
  }

  smiv2:alias "cevCat4kWsx492810GE" {
    smiv2:oid "1.3.6.1.4.1.9.12.3.1.9.35.50";
  }

  smiv2:alias "cevCat4kWsx4548GbRj45VPlus" {
    smiv2:oid "1.3.6.1.4.1.9.12.3.1.9.35.51";
  }

  smiv2:alias "cevCat4kWsx490810GRj45" {
    smiv2:oid "1.3.6.1.4.1.9.12.3.1.9.35.52";
  }

  smiv2:alias "cevCat4kWsx4948ef10GE" {
    smiv2:oid "1.3.6.1.4.1.9.12.3.1.9.35.54";
  }

  smiv2:alias "cevCat4kC4kxNm8" {
    smiv2:oid "1.3.6.1.4.1.9.12.3.1.9.35.55";
  }

  smiv2:alias "cevCat4kWsx4500x16" {
    smiv2:oid "1.3.6.1.4.1.9.12.3.1.9.35.56";
  }

  smiv2:alias "cevCat4kWsx4500x32" {
    smiv2:oid "1.3.6.1.4.1.9.12.3.1.9.35.57";
  }

  smiv2:alias "cevModuleCVAType" {
    smiv2:oid "1.3.6.1.4.1.9.12.3.1.9.36";
  }

  smiv2:alias "cevCVA122" {
    smiv2:oid "1.3.6.1.4.1.9.12.3.1.9.36.1";
  }

  smiv2:alias "cevCVA124" {
    smiv2:oid "1.3.6.1.4.1.9.12.3.1.9.36.2";
  }

  smiv2:alias "cevCVA122E" {
    smiv2:oid "1.3.6.1.4.1.9.12.3.1.9.36.3";
  }

  smiv2:alias "cevCVA124E" {
    smiv2:oid "1.3.6.1.4.1.9.12.3.1.9.36.4";
  }

  smiv2:alias "cevModuleAs5850Type" {
    smiv2:oid "1.3.6.1.4.1.9.12.3.1.9.37";
  }

  smiv2:alias "cevAs5850EPM2Ge" {
    smiv2:oid "1.3.6.1.4.1.9.12.3.1.9.37.1";
  }

  smiv2:alias "cevAs5850Ct3Up216" {
    smiv2:oid "1.3.6.1.4.1.9.12.3.1.9.37.2";
  }

  smiv2:alias "cevAs58508Ce1Up216" {
    smiv2:oid "1.3.6.1.4.1.9.12.3.1.9.37.3";
  }

  smiv2:alias "cevAs58xxUp324" {
    smiv2:oid "1.3.6.1.4.1.9.12.3.1.9.37.4";
  }

  smiv2:alias "cevAs585024E1" {
    smiv2:oid "1.3.6.1.4.1.9.12.3.1.9.37.5";
  }

  smiv2:alias "cevAs585024T1" {
    smiv2:oid "1.3.6.1.4.1.9.12.3.1.9.37.6";
  }

  smiv2:alias "cevModuleAs5350Type" {
    smiv2:oid "1.3.6.1.4.1.9.12.3.1.9.38";
  }

  smiv2:alias "cevAs5350XMDfcCarrier" {
    smiv2:oid "1.3.6.1.4.1.9.12.3.1.9.38.2";
  }

  smiv2:alias "cevModule24xxType" {
    smiv2:oid "1.3.6.1.4.1.9.12.3.1.9.39";
  }

  smiv2:alias "cevIad2420Vm8fxs" {
    smiv2:oid "1.3.6.1.4.1.9.12.3.1.9.39.1";
  }

  smiv2:alias "cevIad242016fxs" {
    smiv2:oid "1.3.6.1.4.1.9.12.3.1.9.39.2";
  }

  smiv2:alias "cevIad2420VmPwr" {
    smiv2:oid "1.3.6.1.4.1.9.12.3.1.9.39.3";
  }

  smiv2:alias "cevIad2420Adsl" {
    smiv2:oid "1.3.6.1.4.1.9.12.3.1.9.39.4";
  }

  smiv2:alias "cevIad2420Hcm1" {
    smiv2:oid "1.3.6.1.4.1.9.12.3.1.9.39.5";
  }

  smiv2:alias "cevIad2420Hcm2" {
    smiv2:oid "1.3.6.1.4.1.9.12.3.1.9.39.6";
  }

  smiv2:alias "cevIad2420Hcm3" {
    smiv2:oid "1.3.6.1.4.1.9.12.3.1.9.39.7";
  }

  smiv2:alias "cevIad2420Hcm4" {
    smiv2:oid "1.3.6.1.4.1.9.12.3.1.9.39.8";
  }

  smiv2:alias "cevIad2420Hcm5" {
    smiv2:oid "1.3.6.1.4.1.9.12.3.1.9.39.9";
  }

  smiv2:alias "cevIad2420Hcm6" {
    smiv2:oid "1.3.6.1.4.1.9.12.3.1.9.39.10";
  }

  smiv2:alias "cevIad2420Cpu" {
    smiv2:oid "1.3.6.1.4.1.9.12.3.1.9.39.11";
  }

  smiv2:alias "cevIad2420MfmE1Unbalanced" {
    smiv2:oid "1.3.6.1.4.1.9.12.3.1.9.39.12";
  }

  smiv2:alias "cevIad2420MfmE1Dsx1Csu" {
    smiv2:oid "1.3.6.1.4.1.9.12.3.1.9.39.13";
  }

  smiv2:alias "cevIad2420MfmT1Dsx1Csu" {
    smiv2:oid "1.3.6.1.4.1.9.12.3.1.9.39.14";
  }

  smiv2:alias "cevIad24208fxo" {
    smiv2:oid "1.3.6.1.4.1.9.12.3.1.9.39.15";
  }

  smiv2:alias "cevIad242016fxsOffPremise" {
    smiv2:oid "1.3.6.1.4.1.9.12.3.1.9.39.18";
  }

  smiv2:alias "cevIad2430Ob8Fxs" {
    smiv2:oid "1.3.6.1.4.1.9.12.3.1.9.39.19";
  }

  smiv2:alias "cevIad2430Ob16Fxs" {
    smiv2:oid "1.3.6.1.4.1.9.12.3.1.9.39.20";
  }

  smiv2:alias "cevIad2430Ob24Fxs" {
    smiv2:oid "1.3.6.1.4.1.9.12.3.1.9.39.21";
  }

  smiv2:alias "cevIad2430ObT1E1" {
    smiv2:oid "1.3.6.1.4.1.9.12.3.1.9.39.22";
  }

  smiv2:alias "cevIad2435ObT1E1" {
    smiv2:oid "1.3.6.1.4.1.9.12.3.1.9.39.23";
  }

  smiv2:alias "cevIad2435Ob8Fxs" {
    smiv2:oid "1.3.6.1.4.1.9.12.3.1.9.39.24";
  }

  smiv2:alias "cevVG204Ob4Fxs" {
    smiv2:oid "1.3.6.1.4.1.9.12.3.1.9.39.25";
  }

  smiv2:alias "cevVG202Ob2Fxs" {
    smiv2:oid "1.3.6.1.4.1.9.12.3.1.9.39.26";
  }

  smiv2:alias "cevVg202xmOb2fxs" {
    smiv2:oid "1.3.6.1.4.1.9.12.3.1.9.39.27";
  }

  smiv2:alias "cevVg204xmOb4fxs" {
    smiv2:oid "1.3.6.1.4.1.9.12.3.1.9.39.28";
  }

  smiv2:alias "cevVg3x0ob24fxs" {
    smiv2:oid "1.3.6.1.4.1.9.12.3.1.9.39.29";
  }

  smiv2:alias "cevModule10000Bases" {
    smiv2:oid "1.3.6.1.4.1.9.12.3.1.9.40";
  }

  smiv2:alias "cevM10000BaseLX4" {
    smiv2:oid "1.3.6.1.4.1.9.12.3.1.9.40.2";
  }

  smiv2:alias "cevM10000BaseEX4" {
    smiv2:oid "1.3.6.1.4.1.9.12.3.1.9.40.3";
  }

  smiv2:alias "cevM10000BaseLR" {
    smiv2:oid "1.3.6.1.4.1.9.12.3.1.9.40.4";
  }

  smiv2:alias "cevM10000BaseER" {
    smiv2:oid "1.3.6.1.4.1.9.12.3.1.9.40.5";
  }

  smiv2:alias "cevM10000BaseSX4" {
    smiv2:oid "1.3.6.1.4.1.9.12.3.1.9.40.6";
  }

  smiv2:alias "cevM10000BaseSR" {
    smiv2:oid "1.3.6.1.4.1.9.12.3.1.9.40.7";
  }

  smiv2:alias "cevM10000BaseCX4" {
    smiv2:oid "1.3.6.1.4.1.9.12.3.1.9.40.8";
  }

  smiv2:alias "cevM10000BaseZR" {
    smiv2:oid "1.3.6.1.4.1.9.12.3.1.9.40.9";
  }

  smiv2:alias "cev10GBaseLW" {
    smiv2:oid "1.3.6.1.4.1.9.12.3.1.9.40.10";
  }

  smiv2:alias "cev10GBaseEW" {
    smiv2:oid "1.3.6.1.4.1.9.12.3.1.9.40.11";
  }

  smiv2:alias "cev10GBaseSW" {
    smiv2:oid "1.3.6.1.4.1.9.12.3.1.9.40.12";
  }

  smiv2:alias "cev10GBaseEdc1310" {
    smiv2:oid "1.3.6.1.4.1.9.12.3.1.9.40.13";
  }

  smiv2:alias "cev10GBaseDwdm3033" {
    smiv2:oid "1.3.6.1.4.1.9.12.3.1.9.40.14";
  }

  smiv2:alias "cev10GBaseDwdm3112" {
    smiv2:oid "1.3.6.1.4.1.9.12.3.1.9.40.15";
  }

  smiv2:alias "cev10GBaseDwdm3190" {
    smiv2:oid "1.3.6.1.4.1.9.12.3.1.9.40.16";
  }

  smiv2:alias "cev10GBaseDwdm3268" {
    smiv2:oid "1.3.6.1.4.1.9.12.3.1.9.40.17";
  }

  smiv2:alias "cev10GBaseDwdm3425" {
    smiv2:oid "1.3.6.1.4.1.9.12.3.1.9.40.18";
  }

  smiv2:alias "cev10GBaseDwdm3504" {
    smiv2:oid "1.3.6.1.4.1.9.12.3.1.9.40.19";
  }

  smiv2:alias "cev10GBaseDwdm3582" {
    smiv2:oid "1.3.6.1.4.1.9.12.3.1.9.40.20";
  }

  smiv2:alias "cev10GBaseDwdm3661" {
    smiv2:oid "1.3.6.1.4.1.9.12.3.1.9.40.21";
  }

  smiv2:alias "cev10GBaseDwdm3819" {
    smiv2:oid "1.3.6.1.4.1.9.12.3.1.9.40.22";
  }

  smiv2:alias "cev10GBaseDwdm3898" {
    smiv2:oid "1.3.6.1.4.1.9.12.3.1.9.40.23";
  }

  smiv2:alias "cev10GBaseDwdm3977" {
    smiv2:oid "1.3.6.1.4.1.9.12.3.1.9.40.24";
  }

  smiv2:alias "cev10GBaseDwdm4056" {
    smiv2:oid "1.3.6.1.4.1.9.12.3.1.9.40.25";
  }

  smiv2:alias "cev10GBaseDwdm4214" {
    smiv2:oid "1.3.6.1.4.1.9.12.3.1.9.40.26";
  }

  smiv2:alias "cev10GBaseDwdm4294" {
    smiv2:oid "1.3.6.1.4.1.9.12.3.1.9.40.27";
  }

  smiv2:alias "cev10GBaseDwdm4373" {
    smiv2:oid "1.3.6.1.4.1.9.12.3.1.9.40.28";
  }

  smiv2:alias "cev10GBaseDwdm4453" {
    smiv2:oid "1.3.6.1.4.1.9.12.3.1.9.40.29";
  }

  smiv2:alias "cev10GBaseDwdm4612" {
    smiv2:oid "1.3.6.1.4.1.9.12.3.1.9.40.30";
  }

  smiv2:alias "cev10GBaseDwdm4692" {
    smiv2:oid "1.3.6.1.4.1.9.12.3.1.9.40.31";
  }

  smiv2:alias "cev10GBaseDwdm4772" {
    smiv2:oid "1.3.6.1.4.1.9.12.3.1.9.40.32";
  }

  smiv2:alias "cev10GBaseDwdm4851" {
    smiv2:oid "1.3.6.1.4.1.9.12.3.1.9.40.33";
  }

  smiv2:alias "cev10GBaseDwdm5012" {
    smiv2:oid "1.3.6.1.4.1.9.12.3.1.9.40.34";
  }

  smiv2:alias "cev10GBaseDwdm5092" {
    smiv2:oid "1.3.6.1.4.1.9.12.3.1.9.40.35";
  }

  smiv2:alias "cev10GBaseDwdm5172" {
    smiv2:oid "1.3.6.1.4.1.9.12.3.1.9.40.36";
  }

  smiv2:alias "cev10GBaseDwdm5252" {
    smiv2:oid "1.3.6.1.4.1.9.12.3.1.9.40.37";
  }

  smiv2:alias "cev10GBaseDwdm5413" {
    smiv2:oid "1.3.6.1.4.1.9.12.3.1.9.40.38";
  }

  smiv2:alias "cev10GBaseDwdm5494" {
    smiv2:oid "1.3.6.1.4.1.9.12.3.1.9.40.39";
  }

  smiv2:alias "cev10GBaseDwdm5575" {
    smiv2:oid "1.3.6.1.4.1.9.12.3.1.9.40.40";
  }

  smiv2:alias "cev10GBaseDwdm5655" {
    smiv2:oid "1.3.6.1.4.1.9.12.3.1.9.40.41";
  }

  smiv2:alias "cev10GBaseDwdm5817" {
    smiv2:oid "1.3.6.1.4.1.9.12.3.1.9.40.42";
  }

  smiv2:alias "cev10GBaseDwdm5898" {
    smiv2:oid "1.3.6.1.4.1.9.12.3.1.9.40.43";
  }

  smiv2:alias "cev10GBaseDwdm5979" {
    smiv2:oid "1.3.6.1.4.1.9.12.3.1.9.40.44";
  }

  smiv2:alias "cev10GBaseDwdm6061" {
    smiv2:oid "1.3.6.1.4.1.9.12.3.1.9.40.45";
  }

  smiv2:alias "cev10GBaseRec" {
    smiv2:oid "1.3.6.1.4.1.9.12.3.1.9.40.46";
  }

  smiv2:alias "cevModuleONS15540Type" {
    smiv2:oid "1.3.6.1.4.1.9.12.3.1.9.42";
  }

  smiv2:alias "cevONS15540LCMBTspProtect" {
    smiv2:oid "1.3.6.1.4.1.9.12.3.1.9.42.1";
  }

  smiv2:alias "cevONS15540LCMBTspEast" {
    smiv2:oid "1.3.6.1.4.1.9.12.3.1.9.42.2";
  }

  smiv2:alias "cevONS15540LCMBTspWest" {
    smiv2:oid "1.3.6.1.4.1.9.12.3.1.9.42.3";
  }

  smiv2:alias "cevONS15540MDXMBOSC" {
    smiv2:oid "1.3.6.1.4.1.9.12.3.1.9.42.4";
  }

  smiv2:alias "cevONS15540MDXMB" {
    smiv2:oid "1.3.6.1.4.1.9.12.3.1.9.42.5";
  }

  smiv2:alias "cevONS15540Tsp1Ch0102MmSc" {
    smiv2:oid "1.3.6.1.4.1.9.12.3.1.9.42.6";
  }

  smiv2:alias "cevONS15540Tsp1Ch0304MmSc" {
    smiv2:oid "1.3.6.1.4.1.9.12.3.1.9.42.7";
  }

  smiv2:alias "cevONS15540Tsp1Ch0506MmSc" {
    smiv2:oid "1.3.6.1.4.1.9.12.3.1.9.42.8";
  }

  smiv2:alias "cevONS15540Tsp1Ch0708MmSc" {
    smiv2:oid "1.3.6.1.4.1.9.12.3.1.9.42.9";
  }

  smiv2:alias "cevONS15540Tsp1Ch0910MmSc" {
    smiv2:oid "1.3.6.1.4.1.9.12.3.1.9.42.10";
  }

  smiv2:alias "cevONS15540Tsp1Ch1112MmSc" {
    smiv2:oid "1.3.6.1.4.1.9.12.3.1.9.42.11";
  }

  smiv2:alias "cevONS15540Tsp1Ch1314MmSc" {
    smiv2:oid "1.3.6.1.4.1.9.12.3.1.9.42.12";
  }

  smiv2:alias "cevONS15540Tsp1Ch1516MmSc" {
    smiv2:oid "1.3.6.1.4.1.9.12.3.1.9.42.13";
  }

  smiv2:alias "cevONS15540Tsp1Ch1718MmSc" {
    smiv2:oid "1.3.6.1.4.1.9.12.3.1.9.42.14";
  }

  smiv2:alias "cevONS15540Tsp1Ch1920MmSc" {
    smiv2:oid "1.3.6.1.4.1.9.12.3.1.9.42.15";
  }

  smiv2:alias "cevONS15540Tsp1Ch2122MmSc" {
    smiv2:oid "1.3.6.1.4.1.9.12.3.1.9.42.16";
  }

  smiv2:alias "cevONS15540Tsp1Ch2324MmSc" {
    smiv2:oid "1.3.6.1.4.1.9.12.3.1.9.42.17";
  }

  smiv2:alias "cevONS15540Tsp1Ch2526MmSc" {
    smiv2:oid "1.3.6.1.4.1.9.12.3.1.9.42.18";
  }

  smiv2:alias "cevONS15540Tsp1Ch2728MmSc" {
    smiv2:oid "1.3.6.1.4.1.9.12.3.1.9.42.19";
  }

  smiv2:alias "cevONS15540Tsp1Ch2930MmSc" {
    smiv2:oid "1.3.6.1.4.1.9.12.3.1.9.42.20";
  }

  smiv2:alias "cevONS15540Tsp1Ch3132MmSc" {
    smiv2:oid "1.3.6.1.4.1.9.12.3.1.9.42.21";
  }

  smiv2:alias "cevONS15540Tsp1Ch0102SmSc" {
    smiv2:oid "1.3.6.1.4.1.9.12.3.1.9.42.22";
  }

  smiv2:alias "cevONS15540Tsp1Ch0304SmSc" {
    smiv2:oid "1.3.6.1.4.1.9.12.3.1.9.42.23";
  }

  smiv2:alias "cevONS15540Tsp1Ch0506SmSc" {
    smiv2:oid "1.3.6.1.4.1.9.12.3.1.9.42.24";
  }

  smiv2:alias "cevONS15540Tsp1Ch0708SmSc" {
    smiv2:oid "1.3.6.1.4.1.9.12.3.1.9.42.25";
  }

  smiv2:alias "cevONS15540Tsp1Ch0910SmSc" {
    smiv2:oid "1.3.6.1.4.1.9.12.3.1.9.42.26";
  }

  smiv2:alias "cevONS15540Tsp1Ch1112SmSc" {
    smiv2:oid "1.3.6.1.4.1.9.12.3.1.9.42.27";
  }

  smiv2:alias "cevONS15540Tsp1Ch1314SmSc" {
    smiv2:oid "1.3.6.1.4.1.9.12.3.1.9.42.28";
  }

  smiv2:alias "cevONS15540Tsp1Ch1516SmSc" {
    smiv2:oid "1.3.6.1.4.1.9.12.3.1.9.42.29";
  }

  smiv2:alias "cevONS15540Tsp1Ch1718SmSc" {
    smiv2:oid "1.3.6.1.4.1.9.12.3.1.9.42.30";
  }

  smiv2:alias "cevONS15540Tsp1Ch1920SmSc" {
    smiv2:oid "1.3.6.1.4.1.9.12.3.1.9.42.31";
  }

  smiv2:alias "cevONS15540Tsp1Ch2122SmSc" {
    smiv2:oid "1.3.6.1.4.1.9.12.3.1.9.42.32";
  }

  smiv2:alias "cevONS15540Tsp1Ch2324SmSc" {
    smiv2:oid "1.3.6.1.4.1.9.12.3.1.9.42.33";
  }

  smiv2:alias "cevONS15540Tsp1Ch2526SmSc" {
    smiv2:oid "1.3.6.1.4.1.9.12.3.1.9.42.34";
  }

  smiv2:alias "cevONS15540Tsp1Ch2728SmSc" {
    smiv2:oid "1.3.6.1.4.1.9.12.3.1.9.42.35";
  }

  smiv2:alias "cevONS15540Tsp1Ch2930SmSc" {
    smiv2:oid "1.3.6.1.4.1.9.12.3.1.9.42.36";
  }

  smiv2:alias "cevONS15540Tsp1Ch3132SmSc" {
    smiv2:oid "1.3.6.1.4.1.9.12.3.1.9.42.37";
  }

  smiv2:alias "cevONS15540MDX4ChA" {
    smiv2:oid "1.3.6.1.4.1.9.12.3.1.9.42.38";
  }

  smiv2:alias "cevONS15540MDX4ChB" {
    smiv2:oid "1.3.6.1.4.1.9.12.3.1.9.42.39";
  }

  smiv2:alias "cevONS15540MDX4ChC" {
    smiv2:oid "1.3.6.1.4.1.9.12.3.1.9.42.40";
  }

  smiv2:alias "cevONS15540MDX4ChD" {
    smiv2:oid "1.3.6.1.4.1.9.12.3.1.9.42.41";
  }

  smiv2:alias "cevONS15540MDX4ChE" {
    smiv2:oid "1.3.6.1.4.1.9.12.3.1.9.42.42";
  }

  smiv2:alias "cevONS15540MDX4ChF" {
    smiv2:oid "1.3.6.1.4.1.9.12.3.1.9.42.43";
  }

  smiv2:alias "cevONS15540MDX4ChG" {
    smiv2:oid "1.3.6.1.4.1.9.12.3.1.9.42.44";
  }

  smiv2:alias "cevONS15540MDX4ChH" {
    smiv2:oid "1.3.6.1.4.1.9.12.3.1.9.42.45";
  }

  smiv2:alias "cevONS15540MDX8ChAB" {
    smiv2:oid "1.3.6.1.4.1.9.12.3.1.9.42.46";
  }

  smiv2:alias "cevONS15540MDX8ChCD" {
    smiv2:oid "1.3.6.1.4.1.9.12.3.1.9.42.47";
  }

  smiv2:alias "cevONS15540MDX8ChEF" {
    smiv2:oid "1.3.6.1.4.1.9.12.3.1.9.42.48";
  }

  smiv2:alias "cevONS15540MDX8ChGH" {
    smiv2:oid "1.3.6.1.4.1.9.12.3.1.9.42.49";
  }

  smiv2:alias "cevONS15540MDX4ChAOSC" {
    smiv2:oid "1.3.6.1.4.1.9.12.3.1.9.42.50";
  }

  smiv2:alias "cevONS15540MDX4ChBOSC" {
    smiv2:oid "1.3.6.1.4.1.9.12.3.1.9.42.51";
  }

  smiv2:alias "cevONS15540MDX4ChCOSC" {
    smiv2:oid "1.3.6.1.4.1.9.12.3.1.9.42.52";
  }

  smiv2:alias "cevONS15540MDX4ChDOSC" {
    smiv2:oid "1.3.6.1.4.1.9.12.3.1.9.42.53";
  }

  smiv2:alias "cevONS15540MDX4ChEOSC" {
    smiv2:oid "1.3.6.1.4.1.9.12.3.1.9.42.54";
  }

  smiv2:alias "cevONS15540MDX4ChFOSC" {
    smiv2:oid "1.3.6.1.4.1.9.12.3.1.9.42.55";
  }

  smiv2:alias "cevONS15540MDX4ChGOSC" {
    smiv2:oid "1.3.6.1.4.1.9.12.3.1.9.42.56";
  }

  smiv2:alias "cevONS15540MDX4ChHOSC" {
    smiv2:oid "1.3.6.1.4.1.9.12.3.1.9.42.57";
  }

  smiv2:alias "cevONS15540MDX8ChABOSC" {
    smiv2:oid "1.3.6.1.4.1.9.12.3.1.9.42.58";
  }

  smiv2:alias "cevONS15540MDX8ChCDOSC" {
    smiv2:oid "1.3.6.1.4.1.9.12.3.1.9.42.59";
  }

  smiv2:alias "cevONS15540MDX8ChEFOSC" {
    smiv2:oid "1.3.6.1.4.1.9.12.3.1.9.42.60";
  }

  smiv2:alias "cevONS15540MDX8ChGHOSC" {
    smiv2:oid "1.3.6.1.4.1.9.12.3.1.9.42.61";
  }

  smiv2:alias "cevONS15540MDX16ChADOSC" {
    smiv2:oid "1.3.6.1.4.1.9.12.3.1.9.42.62";
  }

  smiv2:alias "cevONS15540MDX16ChEH" {
    smiv2:oid "1.3.6.1.4.1.9.12.3.1.9.42.63";
  }

  smiv2:alias "cevONS15540Tsp2Ch0102" {
    smiv2:oid "1.3.6.1.4.1.9.12.3.1.9.42.64";
  }

  smiv2:alias "cevONS15540Tsp2Ch0304" {
    smiv2:oid "1.3.6.1.4.1.9.12.3.1.9.42.65";
  }

  smiv2:alias "cevONS15540Tsp2Ch0506" {
    smiv2:oid "1.3.6.1.4.1.9.12.3.1.9.42.66";
  }

  smiv2:alias "cevONS15540Tsp2Ch0708" {
    smiv2:oid "1.3.6.1.4.1.9.12.3.1.9.42.67";
  }

  smiv2:alias "cevONS15540Tsp2Ch0910" {
    smiv2:oid "1.3.6.1.4.1.9.12.3.1.9.42.68";
  }

  smiv2:alias "cevONS15540Tsp2Ch1112" {
    smiv2:oid "1.3.6.1.4.1.9.12.3.1.9.42.69";
  }

  smiv2:alias "cevONS15540Tsp2Ch1314" {
    smiv2:oid "1.3.6.1.4.1.9.12.3.1.9.42.70";
  }

  smiv2:alias "cevONS15540Tsp2Ch1516" {
    smiv2:oid "1.3.6.1.4.1.9.12.3.1.9.42.71";
  }

  smiv2:alias "cevONS15540Tsp2Ch1718" {
    smiv2:oid "1.3.6.1.4.1.9.12.3.1.9.42.72";
  }

  smiv2:alias "cevONS15540Tsp2Ch1920" {
    smiv2:oid "1.3.6.1.4.1.9.12.3.1.9.42.73";
  }

  smiv2:alias "cevONS15540Tsp2Ch2122" {
    smiv2:oid "1.3.6.1.4.1.9.12.3.1.9.42.74";
  }

  smiv2:alias "cevONS15540Tsp2Ch2324" {
    smiv2:oid "1.3.6.1.4.1.9.12.3.1.9.42.75";
  }

  smiv2:alias "cevONS15540Tsp2Ch2526" {
    smiv2:oid "1.3.6.1.4.1.9.12.3.1.9.42.76";
  }

  smiv2:alias "cevONS15540Tsp2Ch2728" {
    smiv2:oid "1.3.6.1.4.1.9.12.3.1.9.42.77";
  }

  smiv2:alias "cevONS15540Tsp2Ch2930" {
    smiv2:oid "1.3.6.1.4.1.9.12.3.1.9.42.78";
  }

  smiv2:alias "cevONS15540Tsp2Ch3132" {
    smiv2:oid "1.3.6.1.4.1.9.12.3.1.9.42.79";
  }

  smiv2:alias "cevONS15540LCMB10GOC192c" {
    smiv2:oid "1.3.6.1.4.1.9.12.3.1.9.42.80";
  }

  smiv2:alias "cevONS15540ESPxLCMBTspSp" {
    smiv2:oid "1.3.6.1.4.1.9.12.3.1.9.42.81";
  }

  smiv2:alias "cevONS15540ESPxLCMBTsp" {
    smiv2:oid "1.3.6.1.4.1.9.12.3.1.9.42.82";
  }

  smiv2:alias "cevONS15540ESPxLCMB10GOC192cSp" {
    smiv2:oid "1.3.6.1.4.1.9.12.3.1.9.42.83";
  }

  smiv2:alias "cevONS15540ESPxLCMB10GOC192c" {
    smiv2:oid "1.3.6.1.4.1.9.12.3.1.9.42.84";
  }

  smiv2:alias "cevONS15540LCDC10G" {
    smiv2:oid "1.3.6.1.4.1.9.12.3.1.9.42.85";
  }

  smiv2:alias "cevONS15540ESPxMDXMBOsc" {
    smiv2:oid "1.3.6.1.4.1.9.12.3.1.9.42.86";
  }

  smiv2:alias "cevONS15540ESPxMDXMB" {
    smiv2:oid "1.3.6.1.4.1.9.12.3.1.9.42.87";
  }

  smiv2:alias "cevONS15540ESPxMDXMBOscESP" {
    smiv2:oid "1.3.6.1.4.1.9.12.3.1.9.42.88";
  }

  smiv2:alias "cevONS15540ESPxMDXMBESP" {
    smiv2:oid "1.3.6.1.4.1.9.12.3.1.9.42.89";
  }

  smiv2:alias "cevONS1554010GigITUCh01" {
    smiv2:oid "1.3.6.1.4.1.9.12.3.1.9.42.90";
  }

  smiv2:alias "cevONS1554010GigITUCh02" {
    smiv2:oid "1.3.6.1.4.1.9.12.3.1.9.42.91";
  }

  smiv2:alias "cevONS1554010GigITUCh03" {
    smiv2:oid "1.3.6.1.4.1.9.12.3.1.9.42.92";
  }

  smiv2:alias "cevONS1554010GigITUCh04" {
    smiv2:oid "1.3.6.1.4.1.9.12.3.1.9.42.93";
  }

  smiv2:alias "cevONS1554010GigITUCh05" {
    smiv2:oid "1.3.6.1.4.1.9.12.3.1.9.42.94";
  }

  smiv2:alias "cevONS1554010GigITUCh06" {
    smiv2:oid "1.3.6.1.4.1.9.12.3.1.9.42.95";
  }

  smiv2:alias "cevONS1554010GigITUCh07" {
    smiv2:oid "1.3.6.1.4.1.9.12.3.1.9.42.96";
  }

  smiv2:alias "cevONS1554010GigITUCh08" {
    smiv2:oid "1.3.6.1.4.1.9.12.3.1.9.42.97";
  }

  smiv2:alias "cevONS1554010GigITUCh09" {
    smiv2:oid "1.3.6.1.4.1.9.12.3.1.9.42.98";
  }

  smiv2:alias "cevONS1554010GigITUCh10" {
    smiv2:oid "1.3.6.1.4.1.9.12.3.1.9.42.99";
  }

  smiv2:alias "cevONS1554010GigITUCh11" {
    smiv2:oid "1.3.6.1.4.1.9.12.3.1.9.42.100";
  }

  smiv2:alias "cevONS1554010GigITUCh12" {
    smiv2:oid "1.3.6.1.4.1.9.12.3.1.9.42.101";
  }

  smiv2:alias "cevONS1554010GigITUCh13" {
    smiv2:oid "1.3.6.1.4.1.9.12.3.1.9.42.102";
  }

  smiv2:alias "cevONS1554010GigITUCh14" {
    smiv2:oid "1.3.6.1.4.1.9.12.3.1.9.42.103";
  }

  smiv2:alias "cevONS1554010GigITUCh15" {
    smiv2:oid "1.3.6.1.4.1.9.12.3.1.9.42.104";
  }

  smiv2:alias "cevONS1554010GigITUCh16" {
    smiv2:oid "1.3.6.1.4.1.9.12.3.1.9.42.105";
  }

  smiv2:alias "cevONS1554010GigITUCh17" {
    smiv2:oid "1.3.6.1.4.1.9.12.3.1.9.42.106";
  }

  smiv2:alias "cevONS1554010GigITUCh18" {
    smiv2:oid "1.3.6.1.4.1.9.12.3.1.9.42.107";
  }

  smiv2:alias "cevONS1554010GigITUCh19" {
    smiv2:oid "1.3.6.1.4.1.9.12.3.1.9.42.108";
  }

  smiv2:alias "cevONS1554010GigITUCh20" {
    smiv2:oid "1.3.6.1.4.1.9.12.3.1.9.42.109";
  }

  smiv2:alias "cevONS1554010GigITUCh21" {
    smiv2:oid "1.3.6.1.4.1.9.12.3.1.9.42.110";
  }

  smiv2:alias "cevONS1554010GigITUCh22" {
    smiv2:oid "1.3.6.1.4.1.9.12.3.1.9.42.111";
  }

  smiv2:alias "cevONS1554010GigITUCh23" {
    smiv2:oid "1.3.6.1.4.1.9.12.3.1.9.42.112";
  }

  smiv2:alias "cevONS1554010GigITUCh24" {
    smiv2:oid "1.3.6.1.4.1.9.12.3.1.9.42.113";
  }

  smiv2:alias "cevONS1554010GigITUCh25" {
    smiv2:oid "1.3.6.1.4.1.9.12.3.1.9.42.114";
  }

  smiv2:alias "cevONS1554010GigITUCh26" {
    smiv2:oid "1.3.6.1.4.1.9.12.3.1.9.42.115";
  }

  smiv2:alias "cevONS1554010GigITUCh27" {
    smiv2:oid "1.3.6.1.4.1.9.12.3.1.9.42.116";
  }

  smiv2:alias "cevONS1554010GigITUCh28" {
    smiv2:oid "1.3.6.1.4.1.9.12.3.1.9.42.117";
  }

  smiv2:alias "cevONS1554010GigITUCh29" {
    smiv2:oid "1.3.6.1.4.1.9.12.3.1.9.42.118";
  }

  smiv2:alias "cevONS1554010GigITUCh30" {
    smiv2:oid "1.3.6.1.4.1.9.12.3.1.9.42.119";
  }

  smiv2:alias "cevONS1554010GigITUCh31" {
    smiv2:oid "1.3.6.1.4.1.9.12.3.1.9.42.120";
  }

  smiv2:alias "cevONS1554010GigITUCh32" {
    smiv2:oid "1.3.6.1.4.1.9.12.3.1.9.42.121";
  }

  smiv2:alias "cevONS15540OC192cITUCh01" {
    smiv2:oid "1.3.6.1.4.1.9.12.3.1.9.42.122";
  }

  smiv2:alias "cevONS15540OC192cITUCh02" {
    smiv2:oid "1.3.6.1.4.1.9.12.3.1.9.42.123";
  }

  smiv2:alias "cevONS15540OC192cITUCh03" {
    smiv2:oid "1.3.6.1.4.1.9.12.3.1.9.42.124";
  }

  smiv2:alias "cevONS15540OC192cITUCh04" {
    smiv2:oid "1.3.6.1.4.1.9.12.3.1.9.42.125";
  }

  smiv2:alias "cevONS15540OC192cITUCh05" {
    smiv2:oid "1.3.6.1.4.1.9.12.3.1.9.42.126";
  }

  smiv2:alias "cevONS15540OC192cITUCh06" {
    smiv2:oid "1.3.6.1.4.1.9.12.3.1.9.42.127";
  }

  smiv2:alias "cevONS15540OC192cITUCh07" {
    smiv2:oid "1.3.6.1.4.1.9.12.3.1.9.42.128";
  }

  smiv2:alias "cevONS15540OC192cITUCh08" {
    smiv2:oid "1.3.6.1.4.1.9.12.3.1.9.42.129";
  }

  smiv2:alias "cevONS15540OC192cITUCh09" {
    smiv2:oid "1.3.6.1.4.1.9.12.3.1.9.42.130";
  }

  smiv2:alias "cevONS15540OC192cITUCh10" {
    smiv2:oid "1.3.6.1.4.1.9.12.3.1.9.42.131";
  }

  smiv2:alias "cevONS15540OC192cITUCh11" {
    smiv2:oid "1.3.6.1.4.1.9.12.3.1.9.42.132";
  }

  smiv2:alias "cevONS15540OC192cITUCh12" {
    smiv2:oid "1.3.6.1.4.1.9.12.3.1.9.42.133";
  }

  smiv2:alias "cevONS15540OC192cITUCh13" {
    smiv2:oid "1.3.6.1.4.1.9.12.3.1.9.42.134";
  }

  smiv2:alias "cevONS15540OC192cITUCh14" {
    smiv2:oid "1.3.6.1.4.1.9.12.3.1.9.42.135";
  }

  smiv2:alias "cevONS15540OC192cITUCh15" {
    smiv2:oid "1.3.6.1.4.1.9.12.3.1.9.42.136";
  }

  smiv2:alias "cevONS15540OC192cITUCh16" {
    smiv2:oid "1.3.6.1.4.1.9.12.3.1.9.42.137";
  }

  smiv2:alias "cevONS15540OC192cITUCh17" {
    smiv2:oid "1.3.6.1.4.1.9.12.3.1.9.42.138";
  }

  smiv2:alias "cevONS15540OC192cITUCh18" {
    smiv2:oid "1.3.6.1.4.1.9.12.3.1.9.42.139";
  }

  smiv2:alias "cevONS15540OC192cITUCh19" {
    smiv2:oid "1.3.6.1.4.1.9.12.3.1.9.42.140";
  }

  smiv2:alias "cevONS15540OC192cITUCh20" {
    smiv2:oid "1.3.6.1.4.1.9.12.3.1.9.42.141";
  }

  smiv2:alias "cevONS15540OC192cITUCh21" {
    smiv2:oid "1.3.6.1.4.1.9.12.3.1.9.42.142";
  }

  smiv2:alias "cevONS15540OC192cITUCh22" {
    smiv2:oid "1.3.6.1.4.1.9.12.3.1.9.42.143";
  }

  smiv2:alias "cevONS15540OC192cITUCh23" {
    smiv2:oid "1.3.6.1.4.1.9.12.3.1.9.42.144";
  }

  smiv2:alias "cevONS15540OC192cITUCh24" {
    smiv2:oid "1.3.6.1.4.1.9.12.3.1.9.42.145";
  }

  smiv2:alias "cevONS15540OC192cITUCh25" {
    smiv2:oid "1.3.6.1.4.1.9.12.3.1.9.42.146";
  }

  smiv2:alias "cevONS15540OC192cITUCh26" {
    smiv2:oid "1.3.6.1.4.1.9.12.3.1.9.42.147";
  }

  smiv2:alias "cevONS15540OC192cITUCh27" {
    smiv2:oid "1.3.6.1.4.1.9.12.3.1.9.42.148";
  }

  smiv2:alias "cevONS15540OC192cITUCh28" {
    smiv2:oid "1.3.6.1.4.1.9.12.3.1.9.42.149";
  }

  smiv2:alias "cevONS15540OC192cITUCh29" {
    smiv2:oid "1.3.6.1.4.1.9.12.3.1.9.42.150";
  }

  smiv2:alias "cevONS15540OC192cITUCh30" {
    smiv2:oid "1.3.6.1.4.1.9.12.3.1.9.42.151";
  }

  smiv2:alias "cevONS15540OC192cITUCh31" {
    smiv2:oid "1.3.6.1.4.1.9.12.3.1.9.42.152";
  }

  smiv2:alias "cevONS15540OC192cITUCh32" {
    smiv2:oid "1.3.6.1.4.1.9.12.3.1.9.42.153";
  }

  smiv2:alias "cevONS15540ESPxMDX4ChA" {
    smiv2:oid "1.3.6.1.4.1.9.12.3.1.9.42.154";
  }

  smiv2:alias "cevONS15540ESPxMDX4ChB" {
    smiv2:oid "1.3.6.1.4.1.9.12.3.1.9.42.155";
  }

  smiv2:alias "cevONS15540ESPxMDX4ChC" {
    smiv2:oid "1.3.6.1.4.1.9.12.3.1.9.42.156";
  }

  smiv2:alias "cevONS15540ESPxMDX4ChD" {
    smiv2:oid "1.3.6.1.4.1.9.12.3.1.9.42.157";
  }

  smiv2:alias "cevONS15540ESPxMDX4ChE" {
    smiv2:oid "1.3.6.1.4.1.9.12.3.1.9.42.158";
  }

  smiv2:alias "cevONS15540ESPxMDX4ChF" {
    smiv2:oid "1.3.6.1.4.1.9.12.3.1.9.42.159";
  }

  smiv2:alias "cevONS15540ESPxMDX4ChG" {
    smiv2:oid "1.3.6.1.4.1.9.12.3.1.9.42.160";
  }

  smiv2:alias "cevONS15540ESPxMDX4ChH" {
    smiv2:oid "1.3.6.1.4.1.9.12.3.1.9.42.161";
  }

  smiv2:alias "cevONS15540ESPxMDX8ChAB" {
    smiv2:oid "1.3.6.1.4.1.9.12.3.1.9.42.162";
  }

  smiv2:alias "cevONS15540ESPxMDX8ChCD" {
    smiv2:oid "1.3.6.1.4.1.9.12.3.1.9.42.163";
  }

  smiv2:alias "cevONS15540ESPxMDX8ChEF" {
    smiv2:oid "1.3.6.1.4.1.9.12.3.1.9.42.164";
  }

  smiv2:alias "cevONS15540ESPxMDX8ChGH" {
    smiv2:oid "1.3.6.1.4.1.9.12.3.1.9.42.165";
  }

  smiv2:alias "cevONS15540ESPxMDX16ChEH" {
    smiv2:oid "1.3.6.1.4.1.9.12.3.1.9.42.166";
  }

  smiv2:alias "cevONS15540ESPxMDX4ChAOSC" {
    smiv2:oid "1.3.6.1.4.1.9.12.3.1.9.42.167";
  }

  smiv2:alias "cevONS15540ESPxMDX4ChBOSC" {
    smiv2:oid "1.3.6.1.4.1.9.12.3.1.9.42.168";
  }

  smiv2:alias "cevONS15540ESPxMDX4ChCOSC" {
    smiv2:oid "1.3.6.1.4.1.9.12.3.1.9.42.169";
  }

  smiv2:alias "cevONS15540ESPxMDX4ChDOSC" {
    smiv2:oid "1.3.6.1.4.1.9.12.3.1.9.42.170";
  }

  smiv2:alias "cevONS15540ESPxMDX4ChEOSC" {
    smiv2:oid "1.3.6.1.4.1.9.12.3.1.9.42.171";
  }

  smiv2:alias "cevONS15540ESPxMDX4ChFOSC" {
    smiv2:oid "1.3.6.1.4.1.9.12.3.1.9.42.172";
  }

  smiv2:alias "cevONS15540ESPxMDX4ChGOSC" {
    smiv2:oid "1.3.6.1.4.1.9.12.3.1.9.42.173";
  }

  smiv2:alias "cevONS15540ESPxMDX4ChHOSC" {
    smiv2:oid "1.3.6.1.4.1.9.12.3.1.9.42.174";
  }

  smiv2:alias "cevONS15540ESPxMDX8ChABOSC" {
    smiv2:oid "1.3.6.1.4.1.9.12.3.1.9.42.175";
  }

  smiv2:alias "cevONS15540ESPxMDX8ChCDOSC" {
    smiv2:oid "1.3.6.1.4.1.9.12.3.1.9.42.176";
  }

  smiv2:alias "cevONS15540ESPxMDX8ChEFOSC" {
    smiv2:oid "1.3.6.1.4.1.9.12.3.1.9.42.177";
  }

  smiv2:alias "cevONS15540ESPxMDX8ChGHOSC" {
    smiv2:oid "1.3.6.1.4.1.9.12.3.1.9.42.178";
  }

  smiv2:alias "cevONS15540ESPxMDX16ChADOSC" {
    smiv2:oid "1.3.6.1.4.1.9.12.3.1.9.42.179";
  }

  smiv2:alias "cevONS15540ESPxMDX32ChOSC" {
    smiv2:oid "1.3.6.1.4.1.9.12.3.1.9.42.180";
  }

  smiv2:alias "cevONS15540EspPxPSM" {
    smiv2:oid "1.3.6.1.4.1.9.12.3.1.9.42.181";
  }

  smiv2:alias "cevONS15540ESPxVOA1ITUCh1" {
    smiv2:oid "1.3.6.1.4.1.9.12.3.1.9.42.182";
  }

  smiv2:alias "cevONS15540ESPxVOA1ITUCh2" {
    smiv2:oid "1.3.6.1.4.1.9.12.3.1.9.42.183";
  }

  smiv2:alias "cevONS15540ESPxVOA1ITUCh3" {
    smiv2:oid "1.3.6.1.4.1.9.12.3.1.9.42.184";
  }

  smiv2:alias "cevONS15540ESPxVOA1ITUCh4" {
    smiv2:oid "1.3.6.1.4.1.9.12.3.1.9.42.185";
  }

  smiv2:alias "cevONS15540ESPxVOA1ITUCh5" {
    smiv2:oid "1.3.6.1.4.1.9.12.3.1.9.42.186";
  }

  smiv2:alias "cevONS15540ESPxVOA1ITUCh6" {
    smiv2:oid "1.3.6.1.4.1.9.12.3.1.9.42.187";
  }

  smiv2:alias "cevONS15540ESPxVOA1ITUCh7" {
    smiv2:oid "1.3.6.1.4.1.9.12.3.1.9.42.188";
  }

  smiv2:alias "cevONS15540ESPxVOA1ITUCh8" {
    smiv2:oid "1.3.6.1.4.1.9.12.3.1.9.42.189";
  }

  smiv2:alias "cevONS15540ESPxVOA1ITUCh9" {
    smiv2:oid "1.3.6.1.4.1.9.12.3.1.9.42.190";
  }

  smiv2:alias "cevONS15540ESPxVOA1ITUCh10" {
    smiv2:oid "1.3.6.1.4.1.9.12.3.1.9.42.191";
  }

  smiv2:alias "cevONS15540ESPxVOA1ITUCh11" {
    smiv2:oid "1.3.6.1.4.1.9.12.3.1.9.42.192";
  }

  smiv2:alias "cevONS15540ESPxVOA1ITUCh12" {
    smiv2:oid "1.3.6.1.4.1.9.12.3.1.9.42.193";
  }

  smiv2:alias "cevONS15540ESPxVOA1ITUCh13" {
    smiv2:oid "1.3.6.1.4.1.9.12.3.1.9.42.194";
  }

  smiv2:alias "cevONS15540ESPxVOA1ITUCh14" {
    smiv2:oid "1.3.6.1.4.1.9.12.3.1.9.42.195";
  }

  smiv2:alias "cevONS15540ESPxVOA1ITUCh15" {
    smiv2:oid "1.3.6.1.4.1.9.12.3.1.9.42.196";
  }

  smiv2:alias "cevONS15540ESPxVOA1ITUCh16" {
    smiv2:oid "1.3.6.1.4.1.9.12.3.1.9.42.197";
  }

  smiv2:alias "cevONS15540ESPxVOA1ITUCh17" {
    smiv2:oid "1.3.6.1.4.1.9.12.3.1.9.42.198";
  }

  smiv2:alias "cevONS15540ESPxVOA1ITUCh18" {
    smiv2:oid "1.3.6.1.4.1.9.12.3.1.9.42.199";
  }

  smiv2:alias "cevONS15540ESPxVOA1ITUCh19" {
    smiv2:oid "1.3.6.1.4.1.9.12.3.1.9.42.200";
  }

  smiv2:alias "cevONS15540ESPxVOA1ITUCh20" {
    smiv2:oid "1.3.6.1.4.1.9.12.3.1.9.42.201";
  }

  smiv2:alias "cevONS15540ESPxVOA1ITUCh21" {
    smiv2:oid "1.3.6.1.4.1.9.12.3.1.9.42.202";
  }

  smiv2:alias "cevONS15540ESPxVOA1ITUCh22" {
    smiv2:oid "1.3.6.1.4.1.9.12.3.1.9.42.203";
  }

  smiv2:alias "cevONS15540ESPxVOA1ITUCh23" {
    smiv2:oid "1.3.6.1.4.1.9.12.3.1.9.42.204";
  }

  smiv2:alias "cevONS15540ESPxVOA1ITUCh24" {
    smiv2:oid "1.3.6.1.4.1.9.12.3.1.9.42.205";
  }

  smiv2:alias "cevONS15540ESPxVOA1ITUCh25" {
    smiv2:oid "1.3.6.1.4.1.9.12.3.1.9.42.206";
  }

  smiv2:alias "cevONS15540ESPxVOA1ITUCh26" {
    smiv2:oid "1.3.6.1.4.1.9.12.3.1.9.42.207";
  }

  smiv2:alias "cevONS15540ESPxVOA1ITUCh27" {
    smiv2:oid "1.3.6.1.4.1.9.12.3.1.9.42.208";
  }

  smiv2:alias "cevONS15540ESPxVOA1ITUCh28" {
    smiv2:oid "1.3.6.1.4.1.9.12.3.1.9.42.209";
  }

  smiv2:alias "cevONS15540ESPxVOA1ITUCh29" {
    smiv2:oid "1.3.6.1.4.1.9.12.3.1.9.42.210";
  }

  smiv2:alias "cevONS15540ESPxVOA1ITUCh30" {
    smiv2:oid "1.3.6.1.4.1.9.12.3.1.9.42.211";
  }

  smiv2:alias "cevONS15540ESPxVOA1ITUCh31" {
    smiv2:oid "1.3.6.1.4.1.9.12.3.1.9.42.212";
  }

  smiv2:alias "cevONS15540ESPxVOA1ITUCh32" {
    smiv2:oid "1.3.6.1.4.1.9.12.3.1.9.42.213";
  }

  smiv2:alias "cevONS15540ESPxVOA1ITUCh33" {
    smiv2:oid "1.3.6.1.4.1.9.12.3.1.9.42.214";
  }

  smiv2:alias "cevONS15540ESPxVOA2ITUCh0102" {
    smiv2:oid "1.3.6.1.4.1.9.12.3.1.9.42.215";
  }

  smiv2:alias "cevONS15540ESPxVOA2ITUCh0304" {
    smiv2:oid "1.3.6.1.4.1.9.12.3.1.9.42.216";
  }

  smiv2:alias "cevONS15540ESPxVOA2ITUCh0506" {
    smiv2:oid "1.3.6.1.4.1.9.12.3.1.9.42.217";
  }

  smiv2:alias "cevONS15540ESPxVOA2ITUCh0708" {
    smiv2:oid "1.3.6.1.4.1.9.12.3.1.9.42.218";
  }

  smiv2:alias "cevONS15540ESPxVOA2ITUCh0910" {
    smiv2:oid "1.3.6.1.4.1.9.12.3.1.9.42.219";
  }

  smiv2:alias "cevONS15540ESPxVOA2ITUCh1112" {
    smiv2:oid "1.3.6.1.4.1.9.12.3.1.9.42.220";
  }

  smiv2:alias "cevONS15540ESPxVOA2ITUCh1314" {
    smiv2:oid "1.3.6.1.4.1.9.12.3.1.9.42.221";
  }

  smiv2:alias "cevONS15540ESPxVOA2ITUCh1516" {
    smiv2:oid "1.3.6.1.4.1.9.12.3.1.9.42.222";
  }

  smiv2:alias "cevONS15540ESPxVOA2ITUCh1718" {
    smiv2:oid "1.3.6.1.4.1.9.12.3.1.9.42.223";
  }

  smiv2:alias "cevONS15540ESPxVOA2ITUCh1920" {
    smiv2:oid "1.3.6.1.4.1.9.12.3.1.9.42.224";
  }

  smiv2:alias "cevONS15540ESPxVOA2ITUCh2122" {
    smiv2:oid "1.3.6.1.4.1.9.12.3.1.9.42.225";
  }

  smiv2:alias "cevONS15540ESPxVOA2ITUCh2324" {
    smiv2:oid "1.3.6.1.4.1.9.12.3.1.9.42.226";
  }

  smiv2:alias "cevONS15540ESPxVOA2ITUCh2526" {
    smiv2:oid "1.3.6.1.4.1.9.12.3.1.9.42.227";
  }

  smiv2:alias "cevONS15540ESPxVOA2ITUCh2728" {
    smiv2:oid "1.3.6.1.4.1.9.12.3.1.9.42.228";
  }

  smiv2:alias "cevONS15540ESPxVOA2ITUCh2930" {
    smiv2:oid "1.3.6.1.4.1.9.12.3.1.9.42.229";
  }

  smiv2:alias "cevONS15540ESPxVOA2ITUCh3132" {
    smiv2:oid "1.3.6.1.4.1.9.12.3.1.9.42.230";
  }

  smiv2:alias "cevONS15540ESPxVOA4" {
    smiv2:oid "1.3.6.1.4.1.9.12.3.1.9.42.231";
  }

  smiv2:alias "cevModuleGsrPortAdapterType" {
    smiv2:oid "1.3.6.1.4.1.9.12.3.1.9.43";
  }

  smiv2:alias "cevGsrPaUnknown" {
    smiv2:oid "1.3.6.1.4.1.9.12.3.1.9.43.1";
  }

  smiv2:alias "cevGsrPa1Ge" {
    smiv2:oid "1.3.6.1.4.1.9.12.3.1.9.43.2";
  }

  smiv2:alias "cevGsrPa3Ge" {
    smiv2:oid "1.3.6.1.4.1.9.12.3.1.9.43.3";
  }

  smiv2:alias "cevGsrPa24Fe" {
    smiv2:oid "1.3.6.1.4.1.9.12.3.1.9.43.4";
  }

  smiv2:alias "cevModuleONS15530Type" {
    smiv2:oid "1.3.6.1.4.1.9.12.3.1.9.44";
  }

  smiv2:alias "cevONS15530LCMBOsc" {
    smiv2:oid "1.3.6.1.4.1.9.12.3.1.9.44.1";
  }

  smiv2:alias "cevONS15530Osc" {
    smiv2:oid "1.3.6.1.4.1.9.12.3.1.9.44.2";
  }

  smiv2:alias "cevONS15530MDX4ChA" {
    smiv2:oid "1.3.6.1.4.1.9.12.3.1.9.44.3";
  }

  smiv2:alias "cevONS15530MDX4ChB" {
    smiv2:oid "1.3.6.1.4.1.9.12.3.1.9.44.4";
  }

  smiv2:alias "cevONS15530MDX4ChC" {
    smiv2:oid "1.3.6.1.4.1.9.12.3.1.9.44.5";
  }

  smiv2:alias "cevONS15530MDX4ChD" {
    smiv2:oid "1.3.6.1.4.1.9.12.3.1.9.44.6";
  }

  smiv2:alias "cevONS15530MDX4ChE" {
    smiv2:oid "1.3.6.1.4.1.9.12.3.1.9.44.7";
  }

  smiv2:alias "cevONS15530MDX4ChF" {
    smiv2:oid "1.3.6.1.4.1.9.12.3.1.9.44.8";
  }

  smiv2:alias "cevONS15530MDX4ChG" {
    smiv2:oid "1.3.6.1.4.1.9.12.3.1.9.44.9";
  }

  smiv2:alias "cevONS15530MDX4ChH" {
    smiv2:oid "1.3.6.1.4.1.9.12.3.1.9.44.10";
  }

  smiv2:alias "cevONS15530MDX4ChAOsc" {
    smiv2:oid "1.3.6.1.4.1.9.12.3.1.9.44.11";
  }

  smiv2:alias "cevONS15530MDX4ChBOsc" {
    smiv2:oid "1.3.6.1.4.1.9.12.3.1.9.44.12";
  }

  smiv2:alias "cevONS15530MDX4ChCOsc" {
    smiv2:oid "1.3.6.1.4.1.9.12.3.1.9.44.13";
  }

  smiv2:alias "cevONS15530MDX4ChDOsc" {
    smiv2:oid "1.3.6.1.4.1.9.12.3.1.9.44.14";
  }

  smiv2:alias "cevONS15530MDX4ChEOsc" {
    smiv2:oid "1.3.6.1.4.1.9.12.3.1.9.44.15";
  }

  smiv2:alias "cevONS15530MDX4ChFOsc" {
    smiv2:oid "1.3.6.1.4.1.9.12.3.1.9.44.16";
  }

  smiv2:alias "cevONS15530MDX4ChGOsc" {
    smiv2:oid "1.3.6.1.4.1.9.12.3.1.9.44.17";
  }

  smiv2:alias "cevONS15530MDX4ChHOsc" {
    smiv2:oid "1.3.6.1.4.1.9.12.3.1.9.44.18";
  }

  smiv2:alias "cevONS15530Tsp1Ch0102MmScSp" {
    smiv2:oid "1.3.6.1.4.1.9.12.3.1.9.44.19";
  }

  smiv2:alias "cevONS15530Tsp1Ch0304MmScSp" {
    smiv2:oid "1.3.6.1.4.1.9.12.3.1.9.44.20";
  }

  smiv2:alias "cevONS15530Tsp1Ch0506MmScSp" {
    smiv2:oid "1.3.6.1.4.1.9.12.3.1.9.44.21";
  }

  smiv2:alias "cevONS15530Tsp1Ch0708MmScSp" {
    smiv2:oid "1.3.6.1.4.1.9.12.3.1.9.44.22";
  }

  smiv2:alias "cevONS15530Tsp1Ch0910MmScSp" {
    smiv2:oid "1.3.6.1.4.1.9.12.3.1.9.44.23";
  }

  smiv2:alias "cevONS15530Tsp1Ch1112MmScSp" {
    smiv2:oid "1.3.6.1.4.1.9.12.3.1.9.44.24";
  }

  smiv2:alias "cevONS15530Tsp1Ch1314MmScSp" {
    smiv2:oid "1.3.6.1.4.1.9.12.3.1.9.44.25";
  }

  smiv2:alias "cevONS15530Tsp1Ch1516MmScSp" {
    smiv2:oid "1.3.6.1.4.1.9.12.3.1.9.44.26";
  }

  smiv2:alias "cevONS15530Tsp1Ch1718MmScSp" {
    smiv2:oid "1.3.6.1.4.1.9.12.3.1.9.44.27";
  }

  smiv2:alias "cevONS15530Tsp1Ch1920MmScSp" {
    smiv2:oid "1.3.6.1.4.1.9.12.3.1.9.44.28";
  }

  smiv2:alias "cevONS15530Tsp1Ch2122MmScSp" {
    smiv2:oid "1.3.6.1.4.1.9.12.3.1.9.44.29";
  }

  smiv2:alias "cevONS15530Tsp1Ch2324MmScSp" {
    smiv2:oid "1.3.6.1.4.1.9.12.3.1.9.44.30";
  }

  smiv2:alias "cevONS15530Tsp1Ch2526MmScSp" {
    smiv2:oid "1.3.6.1.4.1.9.12.3.1.9.44.31";
  }

  smiv2:alias "cevONS15530Tsp1Ch2728MmScSp" {
    smiv2:oid "1.3.6.1.4.1.9.12.3.1.9.44.32";
  }

  smiv2:alias "cevONS15530Tsp1Ch2930MmScSp" {
    smiv2:oid "1.3.6.1.4.1.9.12.3.1.9.44.33";
  }

  smiv2:alias "cevONS15530Tsp1Ch3132MmScSp" {
    smiv2:oid "1.3.6.1.4.1.9.12.3.1.9.44.34";
  }

  smiv2:alias "cevONS15530Tsp1Ch0102SmScSp" {
    smiv2:oid "1.3.6.1.4.1.9.12.3.1.9.44.35";
  }

  smiv2:alias "cevONS15530Tsp1Ch0304SmScSp" {
    smiv2:oid "1.3.6.1.4.1.9.12.3.1.9.44.36";
  }

  smiv2:alias "cevONS15530Tsp1Ch0506SmScSp" {
    smiv2:oid "1.3.6.1.4.1.9.12.3.1.9.44.37";
  }

  smiv2:alias "cevONS15530Tsp1Ch0708SmScSp" {
    smiv2:oid "1.3.6.1.4.1.9.12.3.1.9.44.38";
  }

  smiv2:alias "cevONS15530Tsp1Ch0910SmScSp" {
    smiv2:oid "1.3.6.1.4.1.9.12.3.1.9.44.39";
  }

  smiv2:alias "cevONS15530Tsp1Ch1112SmScSp" {
    smiv2:oid "1.3.6.1.4.1.9.12.3.1.9.44.40";
  }

  smiv2:alias "cevONS15530Tsp1Ch1314SmScSp" {
    smiv2:oid "1.3.6.1.4.1.9.12.3.1.9.44.41";
  }

  smiv2:alias "cevONS15530Tsp1Ch1516SmScSp" {
    smiv2:oid "1.3.6.1.4.1.9.12.3.1.9.44.42";
  }

  smiv2:alias "cevONS15530Tsp1Ch1718SmScSp" {
    smiv2:oid "1.3.6.1.4.1.9.12.3.1.9.44.43";
  }

  smiv2:alias "cevONS15530Tsp1Ch1920SmScSp" {
    smiv2:oid "1.3.6.1.4.1.9.12.3.1.9.44.44";
  }

  smiv2:alias "cevONS15530Tsp1Ch2122SmScSp" {
    smiv2:oid "1.3.6.1.4.1.9.12.3.1.9.44.45";
  }

  smiv2:alias "cevONS15530Tsp1Ch2324SmScSp" {
    smiv2:oid "1.3.6.1.4.1.9.12.3.1.9.44.46";
  }

  smiv2:alias "cevONS15530Tsp1Ch2526SmScSp" {
    smiv2:oid "1.3.6.1.4.1.9.12.3.1.9.44.47";
  }

  smiv2:alias "cevONS15530Tsp1Ch2728SmScSp" {
    smiv2:oid "1.3.6.1.4.1.9.12.3.1.9.44.48";
  }

  smiv2:alias "cevONS15530Tsp1Ch2930SmScSp" {
    smiv2:oid "1.3.6.1.4.1.9.12.3.1.9.44.49";
  }

  smiv2:alias "cevONS15530Tsp1Ch3132SmScSp" {
    smiv2:oid "1.3.6.1.4.1.9.12.3.1.9.44.50";
  }

  smiv2:alias "cevONS15530Tsp1Ch0102MmSc" {
    smiv2:oid "1.3.6.1.4.1.9.12.3.1.9.44.51";
  }

  smiv2:alias "cevONS15530Tsp1Ch0304MmSc" {
    smiv2:oid "1.3.6.1.4.1.9.12.3.1.9.44.52";
  }

  smiv2:alias "cevONS15530Tsp1Ch0506MmSc" {
    smiv2:oid "1.3.6.1.4.1.9.12.3.1.9.44.53";
  }

  smiv2:alias "cevONS15530Tsp1Ch0708MmSc" {
    smiv2:oid "1.3.6.1.4.1.9.12.3.1.9.44.54";
  }

  smiv2:alias "cevONS15530Tsp1Ch0910MmSc" {
    smiv2:oid "1.3.6.1.4.1.9.12.3.1.9.44.55";
  }

  smiv2:alias "cevONS15530Tsp1Ch1112MmSc" {
    smiv2:oid "1.3.6.1.4.1.9.12.3.1.9.44.56";
  }

  smiv2:alias "cevONS15530Tsp1Ch1314MmSc" {
    smiv2:oid "1.3.6.1.4.1.9.12.3.1.9.44.57";
  }

  smiv2:alias "cevONS15530Tsp1Ch1516MmSc" {
    smiv2:oid "1.3.6.1.4.1.9.12.3.1.9.44.58";
  }

  smiv2:alias "cevONS15530Tsp1Ch1718MmSc" {
    smiv2:oid "1.3.6.1.4.1.9.12.3.1.9.44.59";
  }

  smiv2:alias "cevONS15530Tsp1Ch1920MmSc" {
    smiv2:oid "1.3.6.1.4.1.9.12.3.1.9.44.60";
  }

  smiv2:alias "cevONS15530Tsp1Ch2122MmSc" {
    smiv2:oid "1.3.6.1.4.1.9.12.3.1.9.44.61";
  }

  smiv2:alias "cevONS15530Tsp1Ch2324MmSc" {
    smiv2:oid "1.3.6.1.4.1.9.12.3.1.9.44.62";
  }

  smiv2:alias "cevONS15530Tsp1Ch2526MmSc" {
    smiv2:oid "1.3.6.1.4.1.9.12.3.1.9.44.63";
  }

  smiv2:alias "cevONS15530Tsp1Ch2728MmSc" {
    smiv2:oid "1.3.6.1.4.1.9.12.3.1.9.44.64";
  }

  smiv2:alias "cevONS15530Tsp1Ch2930MmSc" {
    smiv2:oid "1.3.6.1.4.1.9.12.3.1.9.44.65";
  }

  smiv2:alias "cevONS15530Tsp1Ch3132MmSc" {
    smiv2:oid "1.3.6.1.4.1.9.12.3.1.9.44.66";
  }

  smiv2:alias "cevONS15530Tsp1Ch0102SmSc" {
    smiv2:oid "1.3.6.1.4.1.9.12.3.1.9.44.67";
  }

  smiv2:alias "cevONS15530Tsp1Ch0304SmSc" {
    smiv2:oid "1.3.6.1.4.1.9.12.3.1.9.44.68";
  }

  smiv2:alias "cevONS15530Tsp1Ch0506SmSc" {
    smiv2:oid "1.3.6.1.4.1.9.12.3.1.9.44.69";
  }

  smiv2:alias "cevONS15530Tsp1Ch0708SmSc" {
    smiv2:oid "1.3.6.1.4.1.9.12.3.1.9.44.70";
  }

  smiv2:alias "cevONS15530Tsp1Ch0910SmSc" {
    smiv2:oid "1.3.6.1.4.1.9.12.3.1.9.44.71";
  }

  smiv2:alias "cevONS15530Tsp1Ch1112SmSc" {
    smiv2:oid "1.3.6.1.4.1.9.12.3.1.9.44.72";
  }

  smiv2:alias "cevONS15530Tsp1Ch1314SmSc" {
    smiv2:oid "1.3.6.1.4.1.9.12.3.1.9.44.73";
  }

  smiv2:alias "cevONS15530Tsp1Ch1516SmSc" {
    smiv2:oid "1.3.6.1.4.1.9.12.3.1.9.44.74";
  }

  smiv2:alias "cevONS15530Tsp1Ch1718SmSc" {
    smiv2:oid "1.3.6.1.4.1.9.12.3.1.9.44.75";
  }

  smiv2:alias "cevONS15530Tsp1Ch1920SmSc" {
    smiv2:oid "1.3.6.1.4.1.9.12.3.1.9.44.76";
  }

  smiv2:alias "cevONS15530Tsp1Ch2122SmSc" {
    smiv2:oid "1.3.6.1.4.1.9.12.3.1.9.44.77";
  }

  smiv2:alias "cevONS15530Tsp1Ch2324SmSc" {
    smiv2:oid "1.3.6.1.4.1.9.12.3.1.9.44.78";
  }

  smiv2:alias "cevONS15530Tsp1Ch2526SmSc" {
    smiv2:oid "1.3.6.1.4.1.9.12.3.1.9.44.79";
  }

  smiv2:alias "cevONS15530Tsp1Ch2728SmSc" {
    smiv2:oid "1.3.6.1.4.1.9.12.3.1.9.44.80";
  }

  smiv2:alias "cevONS15530Tsp1Ch2930SmSc" {
    smiv2:oid "1.3.6.1.4.1.9.12.3.1.9.44.81";
  }

  smiv2:alias "cevONS15530Tsp1Ch3132SmSc" {
    smiv2:oid "1.3.6.1.4.1.9.12.3.1.9.44.82";
  }

  smiv2:alias "cevONS15530LCEscon10" {
    smiv2:oid "1.3.6.1.4.1.9.12.3.1.9.44.83";
  }

  smiv2:alias "cevONS15500XvrEscon1310MmMTRJ" {
    smiv2:oid "1.3.6.1.4.1.9.12.3.1.9.44.84";
  }

  smiv2:alias "cevONS15530LC10GESmSc" {
    smiv2:oid "1.3.6.1.4.1.9.12.3.1.9.44.85";
  }

  smiv2:alias "cevONS1553010GCh01Sp" {
    smiv2:oid "1.3.6.1.4.1.9.12.3.1.9.44.86";
  }

  smiv2:alias "cevONS1553010GCh02Sp" {
    smiv2:oid "1.3.6.1.4.1.9.12.3.1.9.44.87";
  }

  smiv2:alias "cevONS1553010GCh03Sp" {
    smiv2:oid "1.3.6.1.4.1.9.12.3.1.9.44.88";
  }

  smiv2:alias "cevONS1553010GCh04Sp" {
    smiv2:oid "1.3.6.1.4.1.9.12.3.1.9.44.89";
  }

  smiv2:alias "cevONS1553010GCh05Sp" {
    smiv2:oid "1.3.6.1.4.1.9.12.3.1.9.44.90";
  }

  smiv2:alias "cevONS1553010GCh06Sp" {
    smiv2:oid "1.3.6.1.4.1.9.12.3.1.9.44.91";
  }

  smiv2:alias "cevONS1553010GCh07Sp" {
    smiv2:oid "1.3.6.1.4.1.9.12.3.1.9.44.92";
  }

  smiv2:alias "cevONS1553010GCh08Sp" {
    smiv2:oid "1.3.6.1.4.1.9.12.3.1.9.44.93";
  }

  smiv2:alias "cevONS1553010GCh09Sp" {
    smiv2:oid "1.3.6.1.4.1.9.12.3.1.9.44.94";
  }

  smiv2:alias "cevONS1553010GCh10Sp" {
    smiv2:oid "1.3.6.1.4.1.9.12.3.1.9.44.95";
  }

  smiv2:alias "cevONS1553010GCh11Sp" {
    smiv2:oid "1.3.6.1.4.1.9.12.3.1.9.44.96";
  }

  smiv2:alias "cevONS1553010GCh12Sp" {
    smiv2:oid "1.3.6.1.4.1.9.12.3.1.9.44.97";
  }

  smiv2:alias "cevONS1553010GCh13Sp" {
    smiv2:oid "1.3.6.1.4.1.9.12.3.1.9.44.98";
  }

  smiv2:alias "cevONS1553010GCh14Sp" {
    smiv2:oid "1.3.6.1.4.1.9.12.3.1.9.44.99";
  }

  smiv2:alias "cevONS1553010GCh15Sp" {
    smiv2:oid "1.3.6.1.4.1.9.12.3.1.9.44.100";
  }

  smiv2:alias "cevONS1553010GCh16Sp" {
    smiv2:oid "1.3.6.1.4.1.9.12.3.1.9.44.101";
  }

  smiv2:alias "cevONS1553010GCh17Sp" {
    smiv2:oid "1.3.6.1.4.1.9.12.3.1.9.44.102";
  }

  smiv2:alias "cevONS1553010GCh18Sp" {
    smiv2:oid "1.3.6.1.4.1.9.12.3.1.9.44.103";
  }

  smiv2:alias "cevONS1553010GCh19Sp" {
    smiv2:oid "1.3.6.1.4.1.9.12.3.1.9.44.104";
  }

  smiv2:alias "cevONS1553010GCh20Sp" {
    smiv2:oid "1.3.6.1.4.1.9.12.3.1.9.44.105";
  }

  smiv2:alias "cevONS1553010GCh21Sp" {
    smiv2:oid "1.3.6.1.4.1.9.12.3.1.9.44.106";
  }

  smiv2:alias "cevONS1553010GCh22Sp" {
    smiv2:oid "1.3.6.1.4.1.9.12.3.1.9.44.107";
  }

  smiv2:alias "cevONS1553010GCh23Sp" {
    smiv2:oid "1.3.6.1.4.1.9.12.3.1.9.44.108";
  }

  smiv2:alias "cevONS1553010GCh24Sp" {
    smiv2:oid "1.3.6.1.4.1.9.12.3.1.9.44.109";
  }

  smiv2:alias "cevONS1553010GCh25Sp" {
    smiv2:oid "1.3.6.1.4.1.9.12.3.1.9.44.110";
  }

  smiv2:alias "cevONS1553010GCh26Sp" {
    smiv2:oid "1.3.6.1.4.1.9.12.3.1.9.44.111";
  }

  smiv2:alias "cevONS1553010GCh27Sp" {
    smiv2:oid "1.3.6.1.4.1.9.12.3.1.9.44.112";
  }

  smiv2:alias "cevONS1553010GCh28Sp" {
    smiv2:oid "1.3.6.1.4.1.9.12.3.1.9.44.113";
  }

  smiv2:alias "cevONS1553010GCh29Sp" {
    smiv2:oid "1.3.6.1.4.1.9.12.3.1.9.44.114";
  }

  smiv2:alias "cevONS1553010GCh30Sp" {
    smiv2:oid "1.3.6.1.4.1.9.12.3.1.9.44.115";
  }

  smiv2:alias "cevONS1553010GCh31Sp" {
    smiv2:oid "1.3.6.1.4.1.9.12.3.1.9.44.116";
  }

  smiv2:alias "cevONS1553010GCh32Sp" {
    smiv2:oid "1.3.6.1.4.1.9.12.3.1.9.44.117";
  }

  smiv2:alias "cevONS1553010GCh01" {
    smiv2:oid "1.3.6.1.4.1.9.12.3.1.9.44.118";
  }

  smiv2:alias "cevONS1553010GCh02" {
    smiv2:oid "1.3.6.1.4.1.9.12.3.1.9.44.119";
  }

  smiv2:alias "cevONS1553010GCh03" {
    smiv2:oid "1.3.6.1.4.1.9.12.3.1.9.44.120";
  }

  smiv2:alias "cevONS1553010GCh04" {
    smiv2:oid "1.3.6.1.4.1.9.12.3.1.9.44.121";
  }

  smiv2:alias "cevONS1553010GCh05" {
    smiv2:oid "1.3.6.1.4.1.9.12.3.1.9.44.122";
  }

  smiv2:alias "cevONS1553010GCh06" {
    smiv2:oid "1.3.6.1.4.1.9.12.3.1.9.44.123";
  }

  smiv2:alias "cevONS1553010GCh07" {
    smiv2:oid "1.3.6.1.4.1.9.12.3.1.9.44.124";
  }

  smiv2:alias "cevONS1553010GCh08" {
    smiv2:oid "1.3.6.1.4.1.9.12.3.1.9.44.125";
  }

  smiv2:alias "cevONS1553010GCh09" {
    smiv2:oid "1.3.6.1.4.1.9.12.3.1.9.44.126";
  }

  smiv2:alias "cevONS1553010GCh10" {
    smiv2:oid "1.3.6.1.4.1.9.12.3.1.9.44.127";
  }

  smiv2:alias "cevONS1553010GCh11" {
    smiv2:oid "1.3.6.1.4.1.9.12.3.1.9.44.128";
  }

  smiv2:alias "cevONS1553010GCh12" {
    smiv2:oid "1.3.6.1.4.1.9.12.3.1.9.44.129";
  }

  smiv2:alias "cevONS1553010GCh13" {
    smiv2:oid "1.3.6.1.4.1.9.12.3.1.9.44.130";
  }

  smiv2:alias "cevONS1553010GCh14" {
    smiv2:oid "1.3.6.1.4.1.9.12.3.1.9.44.131";
  }

  smiv2:alias "cevONS1553010GCh15" {
    smiv2:oid "1.3.6.1.4.1.9.12.3.1.9.44.132";
  }

  smiv2:alias "cevONS1553010GCh16" {
    smiv2:oid "1.3.6.1.4.1.9.12.3.1.9.44.133";
  }

  smiv2:alias "cevONS1553010GCh17" {
    smiv2:oid "1.3.6.1.4.1.9.12.3.1.9.44.134";
  }

  smiv2:alias "cevONS1553010GCh18" {
    smiv2:oid "1.3.6.1.4.1.9.12.3.1.9.44.135";
  }

  smiv2:alias "cevONS1553010GCh19" {
    smiv2:oid "1.3.6.1.4.1.9.12.3.1.9.44.136";
  }

  smiv2:alias "cevONS1553010GCh20" {
    smiv2:oid "1.3.6.1.4.1.9.12.3.1.9.44.137";
  }

  smiv2:alias "cevONS1553010GCh21" {
    smiv2:oid "1.3.6.1.4.1.9.12.3.1.9.44.138";
  }

  smiv2:alias "cevONS1553010GCh22" {
    smiv2:oid "1.3.6.1.4.1.9.12.3.1.9.44.139";
  }

  smiv2:alias "cevONS1553010GCh23" {
    smiv2:oid "1.3.6.1.4.1.9.12.3.1.9.44.140";
  }

  smiv2:alias "cevONS1553010GCh24" {
    smiv2:oid "1.3.6.1.4.1.9.12.3.1.9.44.141";
  }

  smiv2:alias "cevONS1553010GCh25" {
    smiv2:oid "1.3.6.1.4.1.9.12.3.1.9.44.142";
  }

  smiv2:alias "cevONS1553010GCh26" {
    smiv2:oid "1.3.6.1.4.1.9.12.3.1.9.44.143";
  }

  smiv2:alias "cevONS1553010GCh27" {
    smiv2:oid "1.3.6.1.4.1.9.12.3.1.9.44.144";
  }

  smiv2:alias "cevONS1553010GCh28" {
    smiv2:oid "1.3.6.1.4.1.9.12.3.1.9.44.145";
  }

  smiv2:alias "cevONS1553010GCh29" {
    smiv2:oid "1.3.6.1.4.1.9.12.3.1.9.44.146";
  }

  smiv2:alias "cevONS1553010GCh30" {
    smiv2:oid "1.3.6.1.4.1.9.12.3.1.9.44.147";
  }

  smiv2:alias "cevONS1553010GCh31" {
    smiv2:oid "1.3.6.1.4.1.9.12.3.1.9.44.148";
  }

  smiv2:alias "cevONS1553010GCh32" {
    smiv2:oid "1.3.6.1.4.1.9.12.3.1.9.44.149";
  }

  smiv2:alias "cevONS15530FCGE8P" {
    smiv2:oid "1.3.6.1.4.1.9.12.3.1.9.44.150";
  }

  smiv2:alias "cevONS155302p5GCh0102Sp" {
    smiv2:oid "1.3.6.1.4.1.9.12.3.1.9.44.151";
  }

  smiv2:alias "cevONS155302p5GCh0304Sp" {
    smiv2:oid "1.3.6.1.4.1.9.12.3.1.9.44.152";
  }

  smiv2:alias "cevONS155302p5GCh0506Sp" {
    smiv2:oid "1.3.6.1.4.1.9.12.3.1.9.44.153";
  }

  smiv2:alias "cevONS155302p5GCh0708Sp" {
    smiv2:oid "1.3.6.1.4.1.9.12.3.1.9.44.154";
  }

  smiv2:alias "cevONS155302p5GCh0910Sp" {
    smiv2:oid "1.3.6.1.4.1.9.12.3.1.9.44.155";
  }

  smiv2:alias "cevONS155302p5GCh1112Sp" {
    smiv2:oid "1.3.6.1.4.1.9.12.3.1.9.44.156";
  }

  smiv2:alias "cevONS155302p5GCh1314Sp" {
    smiv2:oid "1.3.6.1.4.1.9.12.3.1.9.44.157";
  }

  smiv2:alias "cevONS155302p5GCh1516Sp" {
    smiv2:oid "1.3.6.1.4.1.9.12.3.1.9.44.158";
  }

  smiv2:alias "cevONS155302p5GCh1718Sp" {
    smiv2:oid "1.3.6.1.4.1.9.12.3.1.9.44.159";
  }

  smiv2:alias "cevONS155302p5GCh1920Sp" {
    smiv2:oid "1.3.6.1.4.1.9.12.3.1.9.44.160";
  }

  smiv2:alias "cevONS155302p5GCh2122Sp" {
    smiv2:oid "1.3.6.1.4.1.9.12.3.1.9.44.161";
  }

  smiv2:alias "cevONS155302p5GCh2324Sp" {
    smiv2:oid "1.3.6.1.4.1.9.12.3.1.9.44.162";
  }

  smiv2:alias "cevONS155302p5GCh2526Sp" {
    smiv2:oid "1.3.6.1.4.1.9.12.3.1.9.44.163";
  }

  smiv2:alias "cevONS155302p5GCh2728Sp" {
    smiv2:oid "1.3.6.1.4.1.9.12.3.1.9.44.164";
  }

  smiv2:alias "cevONS155302p5GCh2930Sp" {
    smiv2:oid "1.3.6.1.4.1.9.12.3.1.9.44.165";
  }

  smiv2:alias "cevONS155302p5GCh3132Sp" {
    smiv2:oid "1.3.6.1.4.1.9.12.3.1.9.44.166";
  }

  smiv2:alias "cevONS155302p5GCh0102" {
    smiv2:oid "1.3.6.1.4.1.9.12.3.1.9.44.167";
  }

  smiv2:alias "cevONS155302p5GCh0304" {
    smiv2:oid "1.3.6.1.4.1.9.12.3.1.9.44.168";
  }

  smiv2:alias "cevONS155302p5GCh0506" {
    smiv2:oid "1.3.6.1.4.1.9.12.3.1.9.44.169";
  }

  smiv2:alias "cevONS155302p5GCh0708" {
    smiv2:oid "1.3.6.1.4.1.9.12.3.1.9.44.170";
  }

  smiv2:alias "cevONS155302p5GCh0910" {
    smiv2:oid "1.3.6.1.4.1.9.12.3.1.9.44.171";
  }

  smiv2:alias "cevONS155302p5GCh1112" {
    smiv2:oid "1.3.6.1.4.1.9.12.3.1.9.44.172";
  }

  smiv2:alias "cevONS155302p5GCh1314" {
    smiv2:oid "1.3.6.1.4.1.9.12.3.1.9.44.173";
  }

  smiv2:alias "cevONS155302p5GCh1516" {
    smiv2:oid "1.3.6.1.4.1.9.12.3.1.9.44.174";
  }

  smiv2:alias "cevONS155302p5GCh1718" {
    smiv2:oid "1.3.6.1.4.1.9.12.3.1.9.44.175";
  }

  smiv2:alias "cevONS155302p5GCh1920" {
    smiv2:oid "1.3.6.1.4.1.9.12.3.1.9.44.176";
  }

  smiv2:alias "cevONS155302p5GCh2122" {
    smiv2:oid "1.3.6.1.4.1.9.12.3.1.9.44.177";
  }

  smiv2:alias "cevONS155302p5GCh2324" {
    smiv2:oid "1.3.6.1.4.1.9.12.3.1.9.44.178";
  }

  smiv2:alias "cevONS155302p5GCh2526" {
    smiv2:oid "1.3.6.1.4.1.9.12.3.1.9.44.179";
  }

  smiv2:alias "cevONS155302p5GCh2728" {
    smiv2:oid "1.3.6.1.4.1.9.12.3.1.9.44.180";
  }

  smiv2:alias "cevONS155302p5GCh2930" {
    smiv2:oid "1.3.6.1.4.1.9.12.3.1.9.44.181";
  }

  smiv2:alias "cevONS155302p5GCh3132" {
    smiv2:oid "1.3.6.1.4.1.9.12.3.1.9.44.182";
  }

  smiv2:alias "cevONS15530PSM" {
    smiv2:oid "1.3.6.1.4.1.9.12.3.1.9.44.183";
  }

  smiv2:alias "cevONS15530LC2xFC4P" {
    smiv2:oid "1.3.6.1.4.1.9.12.3.1.9.44.184";
  }

  smiv2:alias "cevONS15530MRC8PCh0102Sp" {
    smiv2:oid "1.3.6.1.4.1.9.12.3.1.9.44.185";
  }

  smiv2:alias "cevONS15530MRC8PCh0304Sp" {
    smiv2:oid "1.3.6.1.4.1.9.12.3.1.9.44.186";
  }

  smiv2:alias "cevONS15530MRC8PCh0506Sp" {
    smiv2:oid "1.3.6.1.4.1.9.12.3.1.9.44.187";
  }

  smiv2:alias "cevONS15530MRC8PCh0708Sp" {
    smiv2:oid "1.3.6.1.4.1.9.12.3.1.9.44.188";
  }

  smiv2:alias "cevONS15530MRC8PCh0910Sp" {
    smiv2:oid "1.3.6.1.4.1.9.12.3.1.9.44.189";
  }

  smiv2:alias "cevONS15530MRC8PCh1112Sp" {
    smiv2:oid "1.3.6.1.4.1.9.12.3.1.9.44.190";
  }

  smiv2:alias "cevONS15530MRC8PCh1314Sp" {
    smiv2:oid "1.3.6.1.4.1.9.12.3.1.9.44.191";
  }

  smiv2:alias "cevONS15530MRC8PCh1516Sp" {
    smiv2:oid "1.3.6.1.4.1.9.12.3.1.9.44.192";
  }

  smiv2:alias "cevONS15530MRC8PCh1718Sp" {
    smiv2:oid "1.3.6.1.4.1.9.12.3.1.9.44.193";
  }

  smiv2:alias "cevONS15530MRC8PCh1920Sp" {
    smiv2:oid "1.3.6.1.4.1.9.12.3.1.9.44.194";
  }

  smiv2:alias "cevONS15530MRC8PCh2122Sp" {
    smiv2:oid "1.3.6.1.4.1.9.12.3.1.9.44.195";
  }

  smiv2:alias "cevONS15530MRC8PCh2324Sp" {
    smiv2:oid "1.3.6.1.4.1.9.12.3.1.9.44.196";
  }

  smiv2:alias "cevONS15530MRC8PCh2526Sp" {
    smiv2:oid "1.3.6.1.4.1.9.12.3.1.9.44.197";
  }

  smiv2:alias "cevONS15530MRC8PCh2728Sp" {
    smiv2:oid "1.3.6.1.4.1.9.12.3.1.9.44.198";
  }

  smiv2:alias "cevONS15530MRC8PCh2930Sp" {
    smiv2:oid "1.3.6.1.4.1.9.12.3.1.9.44.199";
  }

  smiv2:alias "cevONS15530MRC8PCh3132Sp" {
    smiv2:oid "1.3.6.1.4.1.9.12.3.1.9.44.200";
  }

  smiv2:alias "cevONS15530MRC8PCh0102" {
    smiv2:oid "1.3.6.1.4.1.9.12.3.1.9.44.201";
  }

  smiv2:alias "cevONS15530MRC8PCh0304" {
    smiv2:oid "1.3.6.1.4.1.9.12.3.1.9.44.202";
  }

  smiv2:alias "cevONS15530MRC8PCh0506" {
    smiv2:oid "1.3.6.1.4.1.9.12.3.1.9.44.203";
  }

  smiv2:alias "cevONS15530MRC8PCh0708" {
    smiv2:oid "1.3.6.1.4.1.9.12.3.1.9.44.204";
  }

  smiv2:alias "cevONS15530MRC8PCh0910" {
    smiv2:oid "1.3.6.1.4.1.9.12.3.1.9.44.205";
  }

  smiv2:alias "cevONS15530MRC8PCh1112" {
    smiv2:oid "1.3.6.1.4.1.9.12.3.1.9.44.206";
  }

  smiv2:alias "cevONS15530MRC8PCh1314" {
    smiv2:oid "1.3.6.1.4.1.9.12.3.1.9.44.207";
  }

  smiv2:alias "cevONS15530MRC8PCh1516" {
    smiv2:oid "1.3.6.1.4.1.9.12.3.1.9.44.208";
  }

  smiv2:alias "cevONS15530MRC8PCh1718" {
    smiv2:oid "1.3.6.1.4.1.9.12.3.1.9.44.209";
  }

  smiv2:alias "cevONS15530MRC8PCh1920" {
    smiv2:oid "1.3.6.1.4.1.9.12.3.1.9.44.210";
  }

  smiv2:alias "cevONS15530MRC8PCh2122" {
    smiv2:oid "1.3.6.1.4.1.9.12.3.1.9.44.211";
  }

  smiv2:alias "cevONS15530MRC8PCh2324" {
    smiv2:oid "1.3.6.1.4.1.9.12.3.1.9.44.212";
  }

  smiv2:alias "cevONS15530MRC8PCh2526" {
    smiv2:oid "1.3.6.1.4.1.9.12.3.1.9.44.213";
  }

  smiv2:alias "cevONS15530MRC8PCh2728" {
    smiv2:oid "1.3.6.1.4.1.9.12.3.1.9.44.214";
  }

  smiv2:alias "cevONS15530MRC8PCh2930" {
    smiv2:oid "1.3.6.1.4.1.9.12.3.1.9.44.215";
  }

  smiv2:alias "cevONS15530MRC8PCh3132" {
    smiv2:oid "1.3.6.1.4.1.9.12.3.1.9.44.216";
  }

  smiv2:alias "cevONS1553010G4ChASp" {
    smiv2:oid "1.3.6.1.4.1.9.12.3.1.9.44.217";
  }

  smiv2:alias "cevONS1553010G4ChBSp" {
    smiv2:oid "1.3.6.1.4.1.9.12.3.1.9.44.218";
  }

  smiv2:alias "cevONS1553010G4ChCSp" {
    smiv2:oid "1.3.6.1.4.1.9.12.3.1.9.44.219";
  }

  smiv2:alias "cevONS1553010G4ChDSp" {
    smiv2:oid "1.3.6.1.4.1.9.12.3.1.9.44.220";
  }

  smiv2:alias "cevONS1553010G4ChESp" {
    smiv2:oid "1.3.6.1.4.1.9.12.3.1.9.44.221";
  }

  smiv2:alias "cevONS1553010G4ChFSp" {
    smiv2:oid "1.3.6.1.4.1.9.12.3.1.9.44.222";
  }

  smiv2:alias "cevONS1553010G4ChGSp" {
    smiv2:oid "1.3.6.1.4.1.9.12.3.1.9.44.223";
  }

  smiv2:alias "cevONS1553010G4ChHSp" {
    smiv2:oid "1.3.6.1.4.1.9.12.3.1.9.44.224";
  }

  smiv2:alias "cevONS1553010G4ChA" {
    smiv2:oid "1.3.6.1.4.1.9.12.3.1.9.44.225";
  }

  smiv2:alias "cevONS1553010G4ChB" {
    smiv2:oid "1.3.6.1.4.1.9.12.3.1.9.44.226";
  }

  smiv2:alias "cevONS1553010G4ChC" {
    smiv2:oid "1.3.6.1.4.1.9.12.3.1.9.44.227";
  }

  smiv2:alias "cevONS1553010G4ChD" {
    smiv2:oid "1.3.6.1.4.1.9.12.3.1.9.44.228";
  }

  smiv2:alias "cevONS1553010G4ChE" {
    smiv2:oid "1.3.6.1.4.1.9.12.3.1.9.44.229";
  }

  smiv2:alias "cevONS1553010G4ChF" {
    smiv2:oid "1.3.6.1.4.1.9.12.3.1.9.44.230";
  }

  smiv2:alias "cevONS1553010G4ChG" {
    smiv2:oid "1.3.6.1.4.1.9.12.3.1.9.44.231";
  }

  smiv2:alias "cevONS1553010G4ChH" {
    smiv2:oid "1.3.6.1.4.1.9.12.3.1.9.44.232";
  }

  smiv2:alias "cevONS1553010G32ChSp" {
    smiv2:oid "1.3.6.1.4.1.9.12.3.1.9.44.233";
  }

  smiv2:alias "cevONS1553010G32Ch" {
    smiv2:oid "1.3.6.1.4.1.9.12.3.1.9.44.234";
  }

  smiv2:alias "cevModuleONS15500Type" {
    smiv2:oid "1.3.6.1.4.1.9.12.3.1.9.46";
  }

  smiv2:alias "cevONS15500PEQ01A" {
    smiv2:oid "1.3.6.1.4.1.9.12.3.1.9.46.1";
  }

  smiv2:alias "cevONS15500PEQ01B" {
    smiv2:oid "1.3.6.1.4.1.9.12.3.1.9.46.2";
  }

  smiv2:alias "cevONS15500PEQ01C" {
    smiv2:oid "1.3.6.1.4.1.9.12.3.1.9.46.3";
  }

  smiv2:alias "cevONS15500PEQ01D" {
    smiv2:oid "1.3.6.1.4.1.9.12.3.1.9.46.4";
  }

  smiv2:alias "cevONS15500PEQ01E" {
    smiv2:oid "1.3.6.1.4.1.9.12.3.1.9.46.5";
  }

  smiv2:alias "cevONS15500PEQ01F" {
    smiv2:oid "1.3.6.1.4.1.9.12.3.1.9.46.6";
  }

  smiv2:alias "cevONS15500PEQ01G" {
    smiv2:oid "1.3.6.1.4.1.9.12.3.1.9.46.7";
  }

  smiv2:alias "cevONS15500PEQ01H" {
    smiv2:oid "1.3.6.1.4.1.9.12.3.1.9.46.8";
  }

  smiv2:alias "cevONS15500PEQ02AB" {
    smiv2:oid "1.3.6.1.4.1.9.12.3.1.9.46.9";
  }

  smiv2:alias "cevONS15500PEQ02CD" {
    smiv2:oid "1.3.6.1.4.1.9.12.3.1.9.46.10";
  }

  smiv2:alias "cevONS15500PEQ02EF" {
    smiv2:oid "1.3.6.1.4.1.9.12.3.1.9.46.11";
  }

  smiv2:alias "cevONS15500PEQ02GH" {
    smiv2:oid "1.3.6.1.4.1.9.12.3.1.9.46.12";
  }

  smiv2:alias "cevONS15500VOA01" {
    smiv2:oid "1.3.6.1.4.1.9.12.3.1.9.46.13";
  }

  smiv2:alias "cevONS15500VOA02" {
    smiv2:oid "1.3.6.1.4.1.9.12.3.1.9.46.14";
  }

  smiv2:alias "cevONS15500XvrEscon1310MTRJ" {
    smiv2:oid "1.3.6.1.4.1.9.12.3.1.9.46.15";
  }

  smiv2:alias "cevONS15500XvrEscon1310LC" {
    smiv2:oid "1.3.6.1.4.1.9.12.3.1.9.46.16";
  }

  smiv2:alias "cevONS15500XvrFC850LC" {
    smiv2:oid "1.3.6.1.4.1.9.12.3.1.9.46.17";
  }

  smiv2:alias "cevONS15500XvrFC850MTRJ" {
    smiv2:oid "1.3.6.1.4.1.9.12.3.1.9.46.18";
  }

  smiv2:alias "cevONS15500XvrFC1310LC" {
    smiv2:oid "1.3.6.1.4.1.9.12.3.1.9.46.19";
  }

  smiv2:alias "cevONS15500XvrFC1310MTRJ" {
    smiv2:oid "1.3.6.1.4.1.9.12.3.1.9.46.20";
  }

  smiv2:alias "cevONS15500XvrGE850LC" {
    smiv2:oid "1.3.6.1.4.1.9.12.3.1.9.46.21";
  }

  smiv2:alias "cevONS15500XvrGE850MTRJ" {
    smiv2:oid "1.3.6.1.4.1.9.12.3.1.9.46.22";
  }

  smiv2:alias "cevONS15500XvrGE1310LC" {
    smiv2:oid "1.3.6.1.4.1.9.12.3.1.9.46.23";
  }

  smiv2:alias "cevONS15500XvrGE1310MTRJ" {
    smiv2:oid "1.3.6.1.4.1.9.12.3.1.9.46.24";
  }

  smiv2:alias "cevONS15500XvrGEFC850LC" {
    smiv2:oid "1.3.6.1.4.1.9.12.3.1.9.46.25";
  }

  smiv2:alias "cevONS15500XvrGEFC850MTRJ" {
    smiv2:oid "1.3.6.1.4.1.9.12.3.1.9.46.26";
  }

  smiv2:alias "cevONS15500XvrGEFC1310LC" {
    smiv2:oid "1.3.6.1.4.1.9.12.3.1.9.46.27";
  }

  smiv2:alias "cevONS15500XvrGEFC1310MTRJ" {
    smiv2:oid "1.3.6.1.4.1.9.12.3.1.9.46.28";
  }

  smiv2:alias "cevONS15500XvrOC3Son1310MTRJ" {
    smiv2:oid "1.3.6.1.4.1.9.12.3.1.9.46.29";
  }

  smiv2:alias "cevONS15500XvrOC3Son1310LC" {
    smiv2:oid "1.3.6.1.4.1.9.12.3.1.9.46.30";
  }

  smiv2:alias "cevONS15500XvrOC12Son1310MTRJ" {
    smiv2:oid "1.3.6.1.4.1.9.12.3.1.9.46.31";
  }

  smiv2:alias "cevONS15500XvrOC12Son1310LC" {
    smiv2:oid "1.3.6.1.4.1.9.12.3.1.9.46.32";
  }

  smiv2:alias "cevONS15500XvrOC48Son1310MTRJ" {
    smiv2:oid "1.3.6.1.4.1.9.12.3.1.9.46.33";
  }

  smiv2:alias "cevONS15500XvrOC48Son1310LC" {
    smiv2:oid "1.3.6.1.4.1.9.12.3.1.9.46.34";
  }

  smiv2:alias "cevONS15500XvrLowMM1310LC" {
    smiv2:oid "1.3.6.1.4.1.9.12.3.1.9.46.35";
  }

  smiv2:alias "cevONS15500XvrLowSM1310LC" {
    smiv2:oid "1.3.6.1.4.1.9.12.3.1.9.46.36";
  }

  smiv2:alias "cevONS15500XvrMidMM1310LC" {
    smiv2:oid "1.3.6.1.4.1.9.12.3.1.9.46.37";
  }

  smiv2:alias "cevONS15500XvrMidSM1310LC" {
    smiv2:oid "1.3.6.1.4.1.9.12.3.1.9.46.38";
  }

  smiv2:alias "cevONS15500XvrHighSM1310LC" {
    smiv2:oid "1.3.6.1.4.1.9.12.3.1.9.46.39";
  }

  smiv2:alias "cevONS15500XvrT1" {
    smiv2:oid "1.3.6.1.4.1.9.12.3.1.9.46.40";
  }

  smiv2:alias "cevONS15500XvrE1" {
    smiv2:oid "1.3.6.1.4.1.9.12.3.1.9.46.41";
  }

  smiv2:alias "cevONS15500XvrDV" {
    smiv2:oid "1.3.6.1.4.1.9.12.3.1.9.46.42";
  }

  smiv2:alias "cevModuleC4224Type" {
    smiv2:oid "1.3.6.1.4.1.9.12.3.1.9.47";
  }

  smiv2:alias "cevC42241FeTx" {
    smiv2:oid "1.3.6.1.4.1.9.12.3.1.9.47.1";
  }

  smiv2:alias "cevC422424FeTx" {
    smiv2:oid "1.3.6.1.4.1.9.12.3.1.9.47.2";
  }

  smiv2:alias "cevModuleONS15454Type" {
    smiv2:oid "1.3.6.1.4.1.9.12.3.1.9.48";
  }

  smiv2:alias "cevONS15454FeCE100" {
    smiv2:oid "1.3.6.1.4.1.9.12.3.1.9.48.3";
  }

  smiv2:alias "cevONS15454Ge10ML2" {
    smiv2:oid "1.3.6.1.4.1.9.12.3.1.9.48.4";
  }

  smiv2:alias "cevONS15454Ge10CE2" {
    smiv2:oid "1.3.6.1.4.1.9.12.3.1.9.48.5";
  }

  smiv2:alias "cevONS15454cptPtf25610GX4" {
    smiv2:oid "1.3.6.1.4.1.9.12.3.1.9.48.9";
  }

  smiv2:alias "cevModuleCat37xxType" {
    smiv2:oid "1.3.6.1.4.1.9.12.3.1.9.50";
  }

  smiv2:alias "cevModuleCat375024" {
    smiv2:oid "1.3.6.1.4.1.9.12.3.1.9.50.1";
  }

  smiv2:alias "cevModuleCat375048" {
    smiv2:oid "1.3.6.1.4.1.9.12.3.1.9.50.2";
  }

  smiv2:alias "cevModuleCat375024TS" {
    smiv2:oid "1.3.6.1.4.1.9.12.3.1.9.50.3";
  }

  smiv2:alias "cevModuleCat375024T" {
    smiv2:oid "1.3.6.1.4.1.9.12.3.1.9.50.4";
  }

  smiv2:alias "cevModuleCat3750Ge12Sfp" {
    smiv2:oid "1.3.6.1.4.1.9.12.3.1.9.50.6";
  }

  smiv2:alias "cevModuleCat375048PS" {
    smiv2:oid "1.3.6.1.4.1.9.12.3.1.9.50.7";
  }

  smiv2:alias "cevModuleCat375024PS" {
    smiv2:oid "1.3.6.1.4.1.9.12.3.1.9.50.8";
  }

  smiv2:alias "cevModuleCat375024ME" {
    smiv2:oid "1.3.6.1.4.1.9.12.3.1.9.50.9";
  }

  smiv2:alias "cevModuleCat3750G16TD" {
    smiv2:oid "1.3.6.1.4.1.9.12.3.1.9.50.10";
  }

  smiv2:alias "cevModuleCat3750G24PS" {
    smiv2:oid "1.3.6.1.4.1.9.12.3.1.9.50.11";
  }

  smiv2:alias "cevModuleCat3750G48PS" {
    smiv2:oid "1.3.6.1.4.1.9.12.3.1.9.50.12";
  }

  smiv2:alias "cevModuleCat3750G48TS" {
    smiv2:oid "1.3.6.1.4.1.9.12.3.1.9.50.13";
  }

  smiv2:alias "cevModuleCat3750G24TS1U" {
    smiv2:oid "1.3.6.1.4.1.9.12.3.1.9.50.14";
  }

  smiv2:alias "cevModuleCat375024FS" {
    smiv2:oid "1.3.6.1.4.1.9.12.3.1.9.50.16";
  }

  smiv2:alias "cevModuleCat3750Ge12SfpDc" {
    smiv2:oid "1.3.6.1.4.1.9.12.3.1.9.50.17";
  }

  smiv2:alias "cevModuleCat3750G24WS" {
    smiv2:oid "1.3.6.1.4.1.9.12.3.1.9.50.18";
  }

  smiv2:alias "cevModuleCat3750E24TD" {
    smiv2:oid "1.3.6.1.4.1.9.12.3.1.9.50.19";
  }

  smiv2:alias "cevModuleCat3750E48TD" {
    smiv2:oid "1.3.6.1.4.1.9.12.3.1.9.50.20";
  }

  smiv2:alias "cevModuleCat3750E48PD" {
    smiv2:oid "1.3.6.1.4.1.9.12.3.1.9.50.21";
  }

  smiv2:alias "cevModuleCat3750E24PD" {
    smiv2:oid "1.3.6.1.4.1.9.12.3.1.9.50.22";
  }

  smiv2:alias "cevModuleCat3750v248ps" {
    smiv2:oid "1.3.6.1.4.1.9.12.3.1.9.50.23";
  }

  smiv2:alias "cevModuleCat3750v248ts" {
    smiv2:oid "1.3.6.1.4.1.9.12.3.1.9.50.24";
  }

  smiv2:alias "cevModuleCat3750v224ps" {
    smiv2:oid "1.3.6.1.4.1.9.12.3.1.9.50.25";
  }

  smiv2:alias "cevModuleCat3750v224ts" {
    smiv2:oid "1.3.6.1.4.1.9.12.3.1.9.50.26";
  }

  smiv2:alias "cevModuleCat3750x24" {
    smiv2:oid "1.3.6.1.4.1.9.12.3.1.9.50.27";
  }

  smiv2:alias "cevModuleCat3750x48" {
    smiv2:oid "1.3.6.1.4.1.9.12.3.1.9.50.28";
  }

  smiv2:alias "cevModuleCat3750x24P" {
    smiv2:oid "1.3.6.1.4.1.9.12.3.1.9.50.29";
  }

  smiv2:alias "cevModuleCat3750x48P" {
    smiv2:oid "1.3.6.1.4.1.9.12.3.1.9.50.30";
  }

  smiv2:alias "cevModuleSFPType" {
    smiv2:oid "1.3.6.1.4.1.9.12.3.1.9.51";
  }

  smiv2:alias "cevSFPOc3mm" {
    smiv2:oid "1.3.6.1.4.1.9.12.3.1.9.51.1";
  }

  smiv2:alias "cevSFPOc12mm" {
    smiv2:oid "1.3.6.1.4.1.9.12.3.1.9.51.2";
  }

  smiv2:alias "cevSFPOc48" {
    smiv2:oid "1.3.6.1.4.1.9.12.3.1.9.51.3";
  }

  smiv2:alias "cevSFPOc3Oc12" {
    smiv2:oid "1.3.6.1.4.1.9.12.3.1.9.51.4";
  }

  smiv2:alias "cevSFPOc3Oc12Oc48" {
    smiv2:oid "1.3.6.1.4.1.9.12.3.1.9.51.5";
  }

  smiv2:alias "cevSFP1000BaseSx" {
    smiv2:oid "1.3.6.1.4.1.9.12.3.1.9.51.6";
  }

  smiv2:alias "cevSFP1000BaseLx" {
    smiv2:oid "1.3.6.1.4.1.9.12.3.1.9.51.7";
  }

  smiv2:alias "cevSFP1000BaseT" {
    smiv2:oid "1.3.6.1.4.1.9.12.3.1.9.51.8";
  }

  smiv2:alias "cevSFP1000BaseZx" {
    smiv2:oid "1.3.6.1.4.1.9.12.3.1.9.51.9";
  }

  smiv2:alias "cevSFPCwdm1470" {
    smiv2:oid "1.3.6.1.4.1.9.12.3.1.9.51.10";
  }

  smiv2:alias "cevSFPCwdm1490" {
    smiv2:oid "1.3.6.1.4.1.9.12.3.1.9.51.11";
  }

  smiv2:alias "cevSFPCwdm1510" {
    smiv2:oid "1.3.6.1.4.1.9.12.3.1.9.51.12";
  }

  smiv2:alias "cevSFPCwdm1530" {
    smiv2:oid "1.3.6.1.4.1.9.12.3.1.9.51.13";
  }

  smiv2:alias "cevSFPCwdm1550" {
    smiv2:oid "1.3.6.1.4.1.9.12.3.1.9.51.14";
  }

  smiv2:alias "cevSFPCwdm1570" {
    smiv2:oid "1.3.6.1.4.1.9.12.3.1.9.51.15";
  }

  smiv2:alias "cevSFPCwdm1590" {
    smiv2:oid "1.3.6.1.4.1.9.12.3.1.9.51.16";
  }

  smiv2:alias "cevSFPCwdm1610" {
    smiv2:oid "1.3.6.1.4.1.9.12.3.1.9.51.17";
  }

  smiv2:alias "cevSFP1000BaseLh" {
    smiv2:oid "1.3.6.1.4.1.9.12.3.1.9.51.18";
  }

  smiv2:alias "cevSFP1000BaseCx" {
    smiv2:oid "1.3.6.1.4.1.9.12.3.1.9.51.19";
  }

  smiv2:alias "cevSFPOc3smir" {
    smiv2:oid "1.3.6.1.4.1.9.12.3.1.9.51.20";
  }

  smiv2:alias "cevSFPOc3smlr" {
    smiv2:oid "1.3.6.1.4.1.9.12.3.1.9.51.21";
  }

  smiv2:alias "cevSFPOc12smir" {
    smiv2:oid "1.3.6.1.4.1.9.12.3.1.9.51.22";
  }

  smiv2:alias "cevSFPOc12smlr" {
    smiv2:oid "1.3.6.1.4.1.9.12.3.1.9.51.23";
  }

  smiv2:alias "cevSFPOc48smsr" {
    smiv2:oid "1.3.6.1.4.1.9.12.3.1.9.51.24";
  }

  smiv2:alias "cevSFPOc48smir" {
    smiv2:oid "1.3.6.1.4.1.9.12.3.1.9.51.25";
  }

  smiv2:alias "cevSFPOc48smlr" {
    smiv2:oid "1.3.6.1.4.1.9.12.3.1.9.51.26";
  }

  smiv2:alias "cevXFPOc192smsr1" {
    smiv2:oid "1.3.6.1.4.1.9.12.3.1.9.51.27";
  }

  smiv2:alias "cevXFPOc192smir2" {
    smiv2:oid "1.3.6.1.4.1.9.12.3.1.9.51.28";
  }

  smiv2:alias "cevXFPOc192smlr2" {
    smiv2:oid "1.3.6.1.4.1.9.12.3.1.9.51.29";
  }

  smiv2:alias "cevSFPCable50cm" {
    smiv2:oid "1.3.6.1.4.1.9.12.3.1.9.51.30";
  }

  smiv2:alias "cevSFPOc48smlr2" {
    smiv2:oid "1.3.6.1.4.1.9.12.3.1.9.51.33";
  }

  smiv2:alias "cevSFPOc3smsr" {
    smiv2:oid "1.3.6.1.4.1.9.12.3.1.9.51.34";
  }

  smiv2:alias "cevSFPOc12smsr" {
    smiv2:oid "1.3.6.1.4.1.9.12.3.1.9.51.35";
  }

  smiv2:alias "cevSFPOc48mm" {
    smiv2:oid "1.3.6.1.4.1.9.12.3.1.9.51.36";
  }

  smiv2:alias "cevSFPDwdm3033" {
    smiv2:oid "1.3.6.1.4.1.9.12.3.1.9.51.37";
  }

  smiv2:alias "cevSFPDwdm3112" {
    smiv2:oid "1.3.6.1.4.1.9.12.3.1.9.51.38";
  }

  smiv2:alias "cevSFPDwdm3190" {
    smiv2:oid "1.3.6.1.4.1.9.12.3.1.9.51.39";
  }

  smiv2:alias "cevSFPDwdm3268" {
    smiv2:oid "1.3.6.1.4.1.9.12.3.1.9.51.40";
  }

  smiv2:alias "cevSFPDwdm3425" {
    smiv2:oid "1.3.6.1.4.1.9.12.3.1.9.51.41";
  }

  smiv2:alias "cevSFPDwdm3504" {
    smiv2:oid "1.3.6.1.4.1.9.12.3.1.9.51.42";
  }

  smiv2:alias "cevSFPDwdm3582" {
    smiv2:oid "1.3.6.1.4.1.9.12.3.1.9.51.43";
  }

  smiv2:alias "cevSFPDwdm3661" {
    smiv2:oid "1.3.6.1.4.1.9.12.3.1.9.51.44";
  }

  smiv2:alias "cevSFPDwdm3819" {
    smiv2:oid "1.3.6.1.4.1.9.12.3.1.9.51.45";
  }

  smiv2:alias "cevSFPDwdm3898" {
    smiv2:oid "1.3.6.1.4.1.9.12.3.1.9.51.46";
  }

  smiv2:alias "cevSFPDwdm3977" {
    smiv2:oid "1.3.6.1.4.1.9.12.3.1.9.51.47";
  }

  smiv2:alias "cevSFPDwdm4056" {
    smiv2:oid "1.3.6.1.4.1.9.12.3.1.9.51.48";
  }

  smiv2:alias "cevSFPDwdm4214" {
    smiv2:oid "1.3.6.1.4.1.9.12.3.1.9.51.49";
  }

  smiv2:alias "cevSFPDwdm4294" {
    smiv2:oid "1.3.6.1.4.1.9.12.3.1.9.51.50";
  }

  smiv2:alias "cevSFPDwdm4373" {
    smiv2:oid "1.3.6.1.4.1.9.12.3.1.9.51.51";
  }

  smiv2:alias "cevSFPDwdm4453" {
    smiv2:oid "1.3.6.1.4.1.9.12.3.1.9.51.52";
  }

  smiv2:alias "cevSFPDwdm4612" {
    smiv2:oid "1.3.6.1.4.1.9.12.3.1.9.51.53";
  }

  smiv2:alias "cevSFPDwdm4692" {
    smiv2:oid "1.3.6.1.4.1.9.12.3.1.9.51.54";
  }

  smiv2:alias "cevSFPDwdm4772" {
    smiv2:oid "1.3.6.1.4.1.9.12.3.1.9.51.55";
  }

  smiv2:alias "cevSFPDwdm4851" {
    smiv2:oid "1.3.6.1.4.1.9.12.3.1.9.51.56";
  }

  smiv2:alias "cevSFPDwdm5012" {
    smiv2:oid "1.3.6.1.4.1.9.12.3.1.9.51.57";
  }

  smiv2:alias "cevSFPDwdm5092" {
    smiv2:oid "1.3.6.1.4.1.9.12.3.1.9.51.58";
  }

  smiv2:alias "cevSFPDwdm5172" {
    smiv2:oid "1.3.6.1.4.1.9.12.3.1.9.51.59";
  }

  smiv2:alias "cevSFPDwdm5252" {
    smiv2:oid "1.3.6.1.4.1.9.12.3.1.9.51.60";
  }

  smiv2:alias "cevSFPDwdm5413" {
    smiv2:oid "1.3.6.1.4.1.9.12.3.1.9.51.61";
  }

  smiv2:alias "cevSFPDwdm5494" {
    smiv2:oid "1.3.6.1.4.1.9.12.3.1.9.51.62";
  }

  smiv2:alias "cevSFPDwdm5575" {
    smiv2:oid "1.3.6.1.4.1.9.12.3.1.9.51.63";
  }

  smiv2:alias "cevSFPDwdm5655" {
    smiv2:oid "1.3.6.1.4.1.9.12.3.1.9.51.64";
  }

  smiv2:alias "cevSFPDwdm5817" {
    smiv2:oid "1.3.6.1.4.1.9.12.3.1.9.51.65";
  }

  smiv2:alias "cevSFPDwdm5898" {
    smiv2:oid "1.3.6.1.4.1.9.12.3.1.9.51.66";
  }

  smiv2:alias "cevSFPDwdm5979" {
    smiv2:oid "1.3.6.1.4.1.9.12.3.1.9.51.67";
  }

  smiv2:alias "cevSFPDwdm6061" {
    smiv2:oid "1.3.6.1.4.1.9.12.3.1.9.51.68";
  }

  smiv2:alias "cevSFP1000BaseBX10D" {
    smiv2:oid "1.3.6.1.4.1.9.12.3.1.9.51.69";
  }

  smiv2:alias "cevSFP1000BaseBX10U" {
    smiv2:oid "1.3.6.1.4.1.9.12.3.1.9.51.70";
  }

  smiv2:alias "cevSFP100BaseFX" {
    smiv2:oid "1.3.6.1.4.1.9.12.3.1.9.51.71";
  }

  smiv2:alias "cevSFP100BaseLX" {
    smiv2:oid "1.3.6.1.4.1.9.12.3.1.9.51.72";
  }

  smiv2:alias "cevSFP100BaseSX" {
    smiv2:oid "1.3.6.1.4.1.9.12.3.1.9.51.73";
  }

  smiv2:alias "cevSFP100BaseZX" {
    smiv2:oid "1.3.6.1.4.1.9.12.3.1.9.51.74";
  }

  smiv2:alias "cevSFP100BaseEX" {
    smiv2:oid "1.3.6.1.4.1.9.12.3.1.9.51.75";
  }

  smiv2:alias "cevSFP100BaseBX10D" {
    smiv2:oid "1.3.6.1.4.1.9.12.3.1.9.51.76";
  }

  smiv2:alias "cevSFP100BaseBX10U" {
    smiv2:oid "1.3.6.1.4.1.9.12.3.1.9.51.77";
  }

  smiv2:alias "cevSFPDwdmXFP6061" {
    smiv2:oid "1.3.6.1.4.1.9.12.3.1.9.51.78";
  }

  smiv2:alias "cevSFPDwdmXFP5979" {
    smiv2:oid "1.3.6.1.4.1.9.12.3.1.9.51.79";
  }

  smiv2:alias "cevSFPDwdmXFP5898" {
    smiv2:oid "1.3.6.1.4.1.9.12.3.1.9.51.80";
  }

  smiv2:alias "cevSFPDwdmXFP5817" {
    smiv2:oid "1.3.6.1.4.1.9.12.3.1.9.51.81";
  }

  smiv2:alias "cevSFPDwdmXFP5655" {
    smiv2:oid "1.3.6.1.4.1.9.12.3.1.9.51.82";
  }

  smiv2:alias "cevSFPDwdmXFP5575" {
    smiv2:oid "1.3.6.1.4.1.9.12.3.1.9.51.83";
  }

  smiv2:alias "cevSFPDwdmXFP5494" {
    smiv2:oid "1.3.6.1.4.1.9.12.3.1.9.51.84";
  }

  smiv2:alias "cevSFPDwdmXFP5413" {
    smiv2:oid "1.3.6.1.4.1.9.12.3.1.9.51.85";
  }

  smiv2:alias "cevSFPDwdmXFP5252" {
    smiv2:oid "1.3.6.1.4.1.9.12.3.1.9.51.86";
  }

  smiv2:alias "cevSFPDwdmXFP5172" {
    smiv2:oid "1.3.6.1.4.1.9.12.3.1.9.51.87";
  }

  smiv2:alias "cevSFPDwdmXFP5092" {
    smiv2:oid "1.3.6.1.4.1.9.12.3.1.9.51.88";
  }

  smiv2:alias "cevSFPDwdmXFP5012" {
    smiv2:oid "1.3.6.1.4.1.9.12.3.1.9.51.89";
  }

  smiv2:alias "cevSFPDwdmXFP4851" {
    smiv2:oid "1.3.6.1.4.1.9.12.3.1.9.51.90";
  }

  smiv2:alias "cevSFPDwdmXFP4772" {
    smiv2:oid "1.3.6.1.4.1.9.12.3.1.9.51.91";
  }

  smiv2:alias "cevSFPDwdmXFP4692" {
    smiv2:oid "1.3.6.1.4.1.9.12.3.1.9.51.92";
  }

  smiv2:alias "cevSFPDwdmXFP4612" {
    smiv2:oid "1.3.6.1.4.1.9.12.3.1.9.51.93";
  }

  smiv2:alias "cevSFPDwdmXFP4453" {
    smiv2:oid "1.3.6.1.4.1.9.12.3.1.9.51.94";
  }

  smiv2:alias "cevSFPDwdmXFP4373" {
    smiv2:oid "1.3.6.1.4.1.9.12.3.1.9.51.95";
  }

  smiv2:alias "cevSFPDwdmXFP4294" {
    smiv2:oid "1.3.6.1.4.1.9.12.3.1.9.51.96";
  }

  smiv2:alias "cevSFPDwdmXFP4214" {
    smiv2:oid "1.3.6.1.4.1.9.12.3.1.9.51.97";
  }

  smiv2:alias "cevSFPDwdmXFP4056" {
    smiv2:oid "1.3.6.1.4.1.9.12.3.1.9.51.98";
  }

  smiv2:alias "cevSFPDwdmXFP3977" {
    smiv2:oid "1.3.6.1.4.1.9.12.3.1.9.51.99";
  }

  smiv2:alias "cevSFPDwdmXFP3898" {
    smiv2:oid "1.3.6.1.4.1.9.12.3.1.9.51.100";
  }

  smiv2:alias "cevSFPDwdmXFP3819" {
    smiv2:oid "1.3.6.1.4.1.9.12.3.1.9.51.101";
  }

  smiv2:alias "cevSFPDwdmXFP3661" {
    smiv2:oid "1.3.6.1.4.1.9.12.3.1.9.51.102";
  }

  smiv2:alias "cevSFPDwdmXFP3582" {
    smiv2:oid "1.3.6.1.4.1.9.12.3.1.9.51.103";
  }

  smiv2:alias "cevSFPDwdmXFP3504" {
    smiv2:oid "1.3.6.1.4.1.9.12.3.1.9.51.104";
  }

  smiv2:alias "cevSFPDwdmXFP3425" {
    smiv2:oid "1.3.6.1.4.1.9.12.3.1.9.51.105";
  }

  smiv2:alias "cevSFPDwdmXFP3268" {
    smiv2:oid "1.3.6.1.4.1.9.12.3.1.9.51.106";
  }

  smiv2:alias "cevSFPDwdmXFP3190" {
    smiv2:oid "1.3.6.1.4.1.9.12.3.1.9.51.107";
  }

  smiv2:alias "cevSFPDwdmXFP3112" {
    smiv2:oid "1.3.6.1.4.1.9.12.3.1.9.51.108";
  }

  smiv2:alias "cevSFPDwdmXFP3033" {
    smiv2:oid "1.3.6.1.4.1.9.12.3.1.9.51.109";
  }

  smiv2:alias "cevSFPDwdm6141" {
    smiv2:oid "1.3.6.1.4.1.9.12.3.1.9.51.110";
  }

  smiv2:alias "cevSFPDwdm5736" {
    smiv2:oid "1.3.6.1.4.1.9.12.3.1.9.51.111";
  }

  smiv2:alias "cevSFPDwdm5332" {
    smiv2:oid "1.3.6.1.4.1.9.12.3.1.9.51.112";
  }

  smiv2:alias "cevSFPDwdm4931" {
    smiv2:oid "1.3.6.1.4.1.9.12.3.1.9.51.113";
  }

  smiv2:alias "cevSFPDwdm4532" {
    smiv2:oid "1.3.6.1.4.1.9.12.3.1.9.51.114";
  }

  smiv2:alias "cevSFPDwdm4134" {
    smiv2:oid "1.3.6.1.4.1.9.12.3.1.9.51.115";
  }

  smiv2:alias "cevSFPDwdm3739" {
    smiv2:oid "1.3.6.1.4.1.9.12.3.1.9.51.116";
  }

  smiv2:alias "cevSFPDwdm3346" {
    smiv2:oid "1.3.6.1.4.1.9.12.3.1.9.51.117";
  }

  smiv2:alias "cevSFPUnknown" {
    smiv2:oid "1.3.6.1.4.1.9.12.3.1.9.51.118";
  }

  smiv2:alias "cevXFPUnknown" {
    smiv2:oid "1.3.6.1.4.1.9.12.3.1.9.51.119";
  }

  smiv2:alias "cevSFPStm1E" {
    smiv2:oid "1.3.6.1.4.1.9.12.3.1.9.51.120";
  }

  smiv2:alias "cevXFPmmsr" {
    smiv2:oid "1.3.6.1.4.1.9.12.3.1.9.51.121";
  }

  smiv2:alias "cevXFR10gMMSR" {
    smiv2:oid "1.3.6.1.4.1.9.12.3.1.9.51.122";
  }

  smiv2:alias "cevSFPTDwdmXfp" {
    smiv2:oid "1.3.6.1.4.1.9.12.3.1.9.51.123";
  }

  smiv2:alias "cevXFP10GLR192SRL" {
    smiv2:oid "1.3.6.1.4.1.9.12.3.1.9.51.124";
  }

  smiv2:alias "cevXFP10GER192IRL" {
    smiv2:oid "1.3.6.1.4.1.9.12.3.1.9.51.125";
  }

  smiv2:alias "cevSFPCiscoSfpT3Ge" {
    smiv2:oid "1.3.6.1.4.1.9.12.3.1.9.51.126";
  }

  smiv2:alias "cevSFPT1E1Fe" {
    smiv2:oid "1.3.6.1.4.1.9.12.3.1.9.51.127";
  }

  smiv2:alias "cevSFPT3E3Fe" {
    smiv2:oid "1.3.6.1.4.1.9.12.3.1.9.51.128";
  }

  smiv2:alias "cevXFPDWDMXFPC" {
    smiv2:oid "1.3.6.1.4.1.9.12.3.1.9.51.129";
  }

  smiv2:alias "cevXFP10GLROC192" {
    smiv2:oid "1.3.6.1.4.1.9.12.3.1.9.51.130";
  }

  smiv2:alias "cevXFP10GER192IR" {
    smiv2:oid "1.3.6.1.4.1.9.12.3.1.9.51.131";
  }

  smiv2:alias "cevXFP10GZROC192" {
    smiv2:oid "1.3.6.1.4.1.9.12.3.1.9.51.132";
  }

  smiv2:alias "cevXFP10GMMSR" {
    smiv2:oid "1.3.6.1.4.1.9.12.3.1.9.51.133";
  }

  smiv2:alias "cevSFPGLC2BXD" {
    smiv2:oid "1.3.6.1.4.1.9.12.3.1.9.51.134";
  }

  smiv2:alias "cevSFPGLC2BXU" {
    smiv2:oid "1.3.6.1.4.1.9.12.3.1.9.51.135";
  }

  smiv2:alias "cevSFPGLCFE1002BX" {
    smiv2:oid "1.3.6.1.4.1.9.12.3.1.9.51.136";
  }

  smiv2:alias "cevSFPGLCFE1002BXU" {
    smiv2:oid "1.3.6.1.4.1.9.12.3.1.9.51.137";
  }

  smiv2:alias "cevSFPGlcSxMmd" {
    smiv2:oid "1.3.6.1.4.1.9.12.3.1.9.51.138";
  }

  smiv2:alias "cevSFPGlcTe" {
    smiv2:oid "1.3.6.1.4.1.9.12.3.1.9.51.139";
  }

  smiv2:alias "cevSFPGlcZxSmd" {
    smiv2:oid "1.3.6.1.4.1.9.12.3.1.9.51.140";
  }

  smiv2:alias "cevSFPGlcExSmd" {
    smiv2:oid "1.3.6.1.4.1.9.12.3.1.9.51.141";
  }

  smiv2:alias "cevSFPGlcLhSmd" {
    smiv2:oid "1.3.6.1.4.1.9.12.3.1.9.51.142";
  }

  smiv2:alias "cevSFP100BaseF" {
    smiv2:oid "1.3.6.1.4.1.9.12.3.1.9.51.143";
  }

  smiv2:alias "cevSFPDSSFPFC16GSW" {
    smiv2:oid "1.3.6.1.4.1.9.12.3.1.9.51.144";
  }

  smiv2:alias "cevSFDSSFPFC16GLW" {
    smiv2:oid "1.3.6.1.4.1.9.12.3.1.9.51.145";
  }

  smiv2:alias "cevSFPGLCGE100FX" {
    smiv2:oid "1.3.6.1.4.1.9.12.3.1.9.51.146";
  }

  smiv2:alias "cevSFPCwdmXFP1570" {
    smiv2:oid "1.3.6.1.4.1.9.12.3.1.9.51.147";
  }

  smiv2:alias "cevSFPCwdmXFP1470" {
    smiv2:oid "1.3.6.1.4.1.9.12.3.1.9.51.148";
  }

  smiv2:alias "cevSFPCwdmXFP1490" {
    smiv2:oid "1.3.6.1.4.1.9.12.3.1.9.51.149";
  }

  smiv2:alias "cevSFPCwdmXFP1510" {
    smiv2:oid "1.3.6.1.4.1.9.12.3.1.9.51.150";
  }

  smiv2:alias "cevSFPCwdmXFP1530" {
    smiv2:oid "1.3.6.1.4.1.9.12.3.1.9.51.151";
  }

  smiv2:alias "cevSFPCwdmXFP1550" {
    smiv2:oid "1.3.6.1.4.1.9.12.3.1.9.51.152";
  }

  smiv2:alias "cevSFPCwdmXFP1590" {
    smiv2:oid "1.3.6.1.4.1.9.12.3.1.9.51.153";
  }

  smiv2:alias "cevSFPCwdmXFP1610" {
    smiv2:oid "1.3.6.1.4.1.9.12.3.1.9.51.154";
  }

  smiv2:alias "cevSFP1000BaseBX40D" {
    smiv2:oid "1.3.6.1.4.1.9.12.3.1.9.51.155";
  }

  smiv2:alias "cevSFP1000BaseBX40U" {
    smiv2:oid "1.3.6.1.4.1.9.12.3.1.9.51.156";
  }

  smiv2:alias "cevSFP1000BaseBX80D" {
    smiv2:oid "1.3.6.1.4.1.9.12.3.1.9.51.157";
  }

  smiv2:alias "cevSFP1000BaseBX80U" {
    smiv2:oid "1.3.6.1.4.1.9.12.3.1.9.51.158";
  }

  smiv2:alias "cevSFP100BaseGlcExFe" {
    smiv2:oid "1.3.6.1.4.1.9.12.3.1.9.51.159";
  }

  smiv2:alias "cevSFP100BaseGlcZxFe" {
    smiv2:oid "1.3.6.1.4.1.9.12.3.1.9.51.160";
  }

  smiv2:alias "cevSFPONSSIGESX" {
    smiv2:oid "1.3.6.1.4.1.9.12.3.1.9.51.186";
  }

  smiv2:alias "cevSFPONSSIGELX" {
    smiv2:oid "1.3.6.1.4.1.9.12.3.1.9.51.187";
  }

  smiv2:alias "cevSFPONSSIGEZX" {
    smiv2:oid "1.3.6.1.4.1.9.12.3.1.9.51.188";
  }

  smiv2:alias "cevSFPONSSEZEEL" {
    smiv2:oid "1.3.6.1.4.1.9.12.3.1.9.51.189";
  }

  smiv2:alias "cevSFPONSSI2GS1" {
    smiv2:oid "1.3.6.1.4.1.9.12.3.1.9.51.190";
  }

  smiv2:alias "cevSFPONSSI2GL1" {
    smiv2:oid "1.3.6.1.4.1.9.12.3.1.9.51.191";
  }

  smiv2:alias "cevSFPONSSI2GL2" {
    smiv2:oid "1.3.6.1.4.1.9.12.3.1.9.51.192";
  }

  smiv2:alias "cevSFPONSSEZ1" {
    smiv2:oid "1.3.6.1.4.1.9.12.3.1.9.51.193";
  }

  smiv2:alias "cevSSFPOAM1000BaseZX" {
    smiv2:oid "1.3.6.1.4.1.9.12.3.1.9.51.200";
  }

  smiv2:alias "cevSSFPOAM1000BaseLX" {
    smiv2:oid "1.3.6.1.4.1.9.12.3.1.9.51.201";
  }

  smiv2:alias "cevSFPGLCBX40UI" {
    smiv2:oid "1.3.6.1.4.1.9.12.3.1.9.51.202";
  }

  smiv2:alias "cevSFPGLCBX40DI" {
    smiv2:oid "1.3.6.1.4.1.9.12.3.1.9.51.203";
  }

  smiv2:alias "cevSFPGLCBX40DAI" {
    smiv2:oid "1.3.6.1.4.1.9.12.3.1.9.51.204";
  }

  smiv2:alias "cevSFPGLCBX80UI" {
    smiv2:oid "1.3.6.1.4.1.9.12.3.1.9.51.205";
  }

  smiv2:alias "cevSFPGLCBX80DI" {
    smiv2:oid "1.3.6.1.4.1.9.12.3.1.9.51.206";
  }

  smiv2:alias "cevSFP100BaseGlcFeBxU" {
    smiv2:oid "1.3.6.1.4.1.9.12.3.1.9.51.249";
  }

  smiv2:alias "cevSFP100BaseGlcFeBxD" {
    smiv2:oid "1.3.6.1.4.1.9.12.3.1.9.51.250";
  }

  smiv2:alias "cevModuleONS15200Type" {
    smiv2:oid "1.3.6.1.4.1.9.12.3.1.9.52";
  }

  smiv2:alias "cevONS15252Clip" {
    smiv2:oid "1.3.6.1.4.1.9.12.3.1.9.52.1";
  }

  smiv2:alias "cevONS15201Clip" {
    smiv2:oid "1.3.6.1.4.1.9.12.3.1.9.52.2";
  }

  smiv2:alias "cevONS15252Ncb" {
    smiv2:oid "1.3.6.1.4.1.9.12.3.1.9.52.3";
  }

  smiv2:alias "cevModuleMDSType" {
    smiv2:oid "1.3.6.1.4.1.9.12.3.1.9.53";
  }

  smiv2:alias "cevMDSDsX9530Sf1K9" {
    smiv2:oid "1.3.6.1.4.1.9.12.3.1.9.53.1";
  }

  smiv2:alias "cevMDSRedDsX9530Sf1K9" {
    smiv2:oid "1.3.6.1.4.1.9.12.3.1.9.53.2";
  }

  smiv2:alias "cevMDSDsX9016" {
    smiv2:oid "1.3.6.1.4.1.9.12.3.1.9.53.3";
  }

  smiv2:alias "cevMDSDsX9032" {
    smiv2:oid "1.3.6.1.4.1.9.12.3.1.9.53.4";
  }

  smiv2:alias "cevMDSDsX9032Smv" {
    smiv2:oid "1.3.6.1.4.1.9.12.3.1.9.53.5";
  }

  smiv2:alias "cevMDSDsX9308Smip" {
    smiv2:oid "1.3.6.1.4.1.9.12.3.1.9.53.6";
  }

  smiv2:alias "cevMDSDsX9560Smc" {
    smiv2:oid "1.3.6.1.4.1.9.12.3.1.9.53.7";
  }

  smiv2:alias "cevMDSDsSfpFc2Gsw" {
    smiv2:oid "1.3.6.1.4.1.9.12.3.1.9.53.8";
  }

  smiv2:alias "cevMDSDsSfpFc2Glw" {
    smiv2:oid "1.3.6.1.4.1.9.12.3.1.9.53.9";
  }

  smiv2:alias "cevMDSDsSfpGeSw" {
    smiv2:oid "1.3.6.1.4.1.9.12.3.1.9.53.10";
  }

  smiv2:alias "cevMDSDsSfpGeLw" {
    smiv2:oid "1.3.6.1.4.1.9.12.3.1.9.53.11";
  }

  smiv2:alias "cevMDSDsC9500Cl" {
    smiv2:oid "1.3.6.1.4.1.9.12.3.1.9.53.12";
  }

  smiv2:alias "cevMDSDsX9216K9Sup" {
    smiv2:oid "1.3.6.1.4.1.9.12.3.1.9.53.13";
  }

  smiv2:alias "cevMDSMemFld512M" {
    smiv2:oid "1.3.6.1.4.1.9.12.3.1.9.53.14";
  }

  smiv2:alias "cevMDSMemMd1G" {
    smiv2:oid "1.3.6.1.4.1.9.12.3.1.9.53.15";
  }

  smiv2:alias "cevMDSDsC9509Cl" {
    smiv2:oid "1.3.6.1.4.1.9.12.3.1.9.53.16";
  }

  smiv2:alias "cevMDSDsC9506Cl" {
    smiv2:oid "1.3.6.1.4.1.9.12.3.1.9.53.17";
  }

  smiv2:alias "cevMDSDsX9140K9Sup" {
    smiv2:oid "1.3.6.1.4.1.9.12.3.1.9.53.18";
  }

  smiv2:alias "cevMDSDsX9120K9Sup" {
    smiv2:oid "1.3.6.1.4.1.9.12.3.1.9.53.19";
  }

  smiv2:alias "cevMDSDsX9032Sma" {
    smiv2:oid "1.3.6.1.4.1.9.12.3.1.9.53.20";
  }

  smiv2:alias "cevMDSDsX9216Mgt" {
    smiv2:oid "1.3.6.1.4.1.9.12.3.1.9.53.21";
  }

  smiv2:alias "cevMDSDsX930214K9" {
    smiv2:oid "1.3.6.1.4.1.9.12.3.1.9.53.22";
  }

  smiv2:alias "cevMDSDsX9202" {
    smiv2:oid "1.3.6.1.4.1.9.12.3.1.9.53.23";
  }

  smiv2:alias "cevMDSDsX9304Smip" {
    smiv2:oid "1.3.6.1.4.1.9.12.3.1.9.53.24";
  }

  smiv2:alias "cevMDSDsX9132K9Sup" {
    smiv2:oid "1.3.6.1.4.1.9.12.3.1.9.53.25";
  }

  smiv2:alias "cevMDSDsX9116K9Sup" {
    smiv2:oid "1.3.6.1.4.1.9.12.3.1.9.53.26";
  }

  smiv2:alias "cevMDSDsX9216IK9Sup" {
    smiv2:oid "1.3.6.1.4.1.9.12.3.1.9.53.27";
  }

  smiv2:alias "cevMDSDsX9530Sf2K9" {
    smiv2:oid "1.3.6.1.4.1.9.12.3.1.9.53.28";
  }

  smiv2:alias "cevMDSDsX9112" {
    smiv2:oid "1.3.6.1.4.1.9.12.3.1.9.53.29";
  }

  smiv2:alias "cevMDSDsX9124" {
    smiv2:oid "1.3.6.1.4.1.9.12.3.1.9.53.30";
  }

  smiv2:alias "cevMDSDsX9148" {
    smiv2:oid "1.3.6.1.4.1.9.12.3.1.9.53.31";
  }

  smiv2:alias "cevMDSDsX9704" {
    smiv2:oid "1.3.6.1.4.1.9.12.3.1.9.53.32";
  }

  smiv2:alias "cevMDSDs13SltFab1" {
    smiv2:oid "1.3.6.1.4.1.9.12.3.1.9.53.33";
  }

  smiv2:alias "cevMDSDsC9513Cl" {
    smiv2:oid "1.3.6.1.4.1.9.12.3.1.9.53.34";
  }

  smiv2:alias "cevMDSDsX9124S2K9" {
    smiv2:oid "1.3.6.1.4.1.9.12.3.1.9.53.35";
  }

  smiv2:alias "cevMDSDsIBMFC" {
    smiv2:oid "1.3.6.1.4.1.9.12.3.1.9.53.36";
  }

  smiv2:alias "cevMDSDsHPFC" {
    smiv2:oid "1.3.6.1.4.1.9.12.3.1.9.53.37";
  }

  smiv2:alias "cevMDSDsX9222iK9Sup" {
    smiv2:oid "1.3.6.1.4.1.9.12.3.1.9.53.38";
  }

  smiv2:alias "cevMDSDxX930418K9" {
    smiv2:oid "1.3.6.1.4.1.9.12.3.1.9.53.39";
  }

  smiv2:alias "cevMDSDsX9134S2K9" {
    smiv2:oid "1.3.6.1.4.1.9.12.3.1.9.53.40";
  }

  smiv2:alias "cevMdsDSC9222iK9Sup" {
    smiv2:oid "1.3.6.1.4.1.9.12.3.1.9.53.41";
  }

  smiv2:alias "cevMDSDsX9248FC48Gbps" {
    smiv2:oid "1.3.6.1.4.1.9.12.3.1.9.53.42";
  }

  smiv2:alias "cevMDSDsX9248FC96Gbps" {
    smiv2:oid "1.3.6.1.4.1.9.12.3.1.9.53.43";
  }

  smiv2:alias "cevMDSDsX9316SSM" {
    smiv2:oid "1.3.6.1.4.1.9.12.3.1.9.53.44";
  }

  smiv2:alias "cevMDSDs13SltFab2" {
    smiv2:oid "1.3.6.1.4.1.9.12.3.1.9.53.45";
  }

  smiv2:alias "cevMDSDsX922496k9" {
    smiv2:oid "1.3.6.1.4.1.9.12.3.1.9.53.46";
  }

  smiv2:alias "cevMDSDsX9716K9" {
    smiv2:oid "1.3.6.1.4.1.9.12.3.1.9.53.52";
  }

  smiv2:alias "cevMDSDsX9248x256K9" {
    smiv2:oid "1.3.6.1.4.1.9.12.3.1.9.53.53";
  }

  smiv2:alias "cevMDSDsX9232x256K9" {
    smiv2:oid "1.3.6.1.4.1.9.12.3.1.9.53.54";
  }

  smiv2:alias "cevMDSDs13SlotFabricEvia3" {
    smiv2:oid "1.3.6.1.4.1.9.12.3.1.9.53.55";
  }

  smiv2:alias "cevMDSDsX9530Sf2AK9" {
    smiv2:oid "1.3.6.1.4.1.9.12.3.1.9.53.56";
  }

  smiv2:alias "cevMDSDs9708HPK9" {
    smiv2:oid "1.3.6.1.4.1.9.12.3.1.9.53.57";
  }

  smiv2:alias "cevMDSDs9708K9" {
    smiv2:oid "1.3.6.1.4.1.9.12.3.1.9.53.58";
  }

  smiv2:alias "cevMDSDSX9448n768K9" {
    smiv2:oid "1.3.6.1.4.1.9.12.3.1.9.53.61";
  }

  smiv2:alias "cevMDSDSX9848n480K9SM" {
    smiv2:oid "1.3.6.1.4.1.9.12.3.1.9.53.62";
  }

  smiv2:alias "cevMDSDSX97SF1K9SUP" {
    smiv2:oid "1.3.6.1.4.1.9.12.3.1.9.53.63";
  }

  smiv2:alias "cevMDSDSX9710FAB1" {
    smiv2:oid "1.3.6.1.4.1.9.12.3.1.9.53.64";
  }

  smiv2:alias "cevMDS9710FCS" {
    smiv2:oid "1.3.6.1.4.1.9.12.3.1.9.53.65";
  }

  smiv2:alias "cevMDS9250iIFSPS" {
    smiv2:oid "1.3.6.1.4.1.9.12.3.1.9.53.66";
  }

  smiv2:alias "cevMDS9250iIFSDC" {
    smiv2:oid "1.3.6.1.4.1.9.12.3.1.9.53.67";
  }

  smiv2:alias "cevMDSDSC9250i22PK9SUPFS" {
    smiv2:oid "1.3.6.1.4.1.9.12.3.1.9.53.68";
  }

  smiv2:alias "cevMDSDSX9848480K9" {
    smiv2:oid "1.3.6.1.4.1.9.12.3.1.9.53.69";
  }

  smiv2:alias "cevMDSDSX9706FAB1" {
    smiv2:oid "1.3.6.1.4.1.9.12.3.1.9.53.70";
  }

  smiv2:alias "cevMDSDSC9148SK9SUP" {
    smiv2:oid "1.3.6.1.4.1.9.12.3.1.9.53.71";
  }

  smiv2:alias "cevMDSDSC9396SK9SUP" {
    smiv2:oid "1.3.6.1.4.1.9.12.3.1.9.53.72";
  }

  smiv2:alias "cevModuleC3220Type" {
    smiv2:oid "1.3.6.1.4.1.9.12.3.1.9.54";
  }

  smiv2:alias "cevC3220Smic" {
    smiv2:oid "1.3.6.1.4.1.9.12.3.1.9.54.1";
  }

  smiv2:alias "cevC3220Fesmic" {
    smiv2:oid "1.3.6.1.4.1.9.12.3.1.9.54.2";
  }

  smiv2:alias "cevModuleCrs1Type" {
    smiv2:oid "1.3.6.1.4.1.9.12.3.1.9.55";
  }

  smiv2:alias "cevModuleCrs1RP" {
    smiv2:oid "1.3.6.1.4.1.9.12.3.1.9.55.1";
  }

  smiv2:alias "cevModuleCrs1DRP" {
    smiv2:oid "1.3.6.1.4.1.9.12.3.1.9.55.2";
  }

  smiv2:alias "cevModuleCrs18sS123Fabric" {
    smiv2:oid "1.3.6.1.4.1.9.12.3.1.9.55.3";
  }

  smiv2:alias "cevModuleCrs116sS123Fabric" {
    smiv2:oid "1.3.6.1.4.1.9.12.3.1.9.55.4";
  }

  smiv2:alias "cevModuleCrs116dS123TFabric" {
    smiv2:oid "1.3.6.1.4.1.9.12.3.1.9.55.5";
  }

  smiv2:alias "cevModuleCrs116mS13Fabric" {
    smiv2:oid "1.3.6.1.4.1.9.12.3.1.9.55.6";
  }

  smiv2:alias "cevModuleCrs116mS2CCFabric" {
    smiv2:oid "1.3.6.1.4.1.9.12.3.1.9.55.7";
  }

  smiv2:alias "cevModuleCrs116mS2Fabric" {
    smiv2:oid "1.3.6.1.4.1.9.12.3.1.9.55.8";
  }

  smiv2:alias "cevModuleCrs1FanCtrllrLC" {
    smiv2:oid "1.3.6.1.4.1.9.12.3.1.9.55.9";
  }

  smiv2:alias "cevModuleCrs116mS2FanCtrllrFabric" {
    smiv2:oid "1.3.6.1.4.1.9.12.3.1.9.55.10";
  }

  smiv2:alias "cevModuleCrs1Alarm" {
    smiv2:oid "1.3.6.1.4.1.9.12.3.1.9.55.11";
  }

  smiv2:alias "cevModuleCrs116mFabricLED" {
    smiv2:oid "1.3.6.1.4.1.9.12.3.1.9.55.12";
  }

  smiv2:alias "cevModuleCrs1DRPPlim" {
    smiv2:oid "1.3.6.1.4.1.9.12.3.1.9.55.13";
  }

  smiv2:alias "cevModuleCrs116OC48Plim" {
    smiv2:oid "1.3.6.1.4.1.9.12.3.1.9.55.14";
  }

  smiv2:alias "cevModuleCrs14OC192VSRPlim" {
    smiv2:oid "1.3.6.1.4.1.9.12.3.1.9.55.15";
  }

  smiv2:alias "cevModuleCrs14OC192SRPlim" {
    smiv2:oid "1.3.6.1.4.1.9.12.3.1.9.55.16";
  }

  smiv2:alias "cevModulecrs14OC192LRPlim" {
    smiv2:oid "1.3.6.1.4.1.9.12.3.1.9.55.17";
  }

  smiv2:alias "cevModuleCrs1OC768VSRPlim" {
    smiv2:oid "1.3.6.1.4.1.9.12.3.1.9.55.18";
  }

  smiv2:alias "cevModuleCrs1OC768SRPlim" {
    smiv2:oid "1.3.6.1.4.1.9.12.3.1.9.55.19";
  }

  smiv2:alias "cevModuleCrs16x10GePlim" {
    smiv2:oid "1.3.6.1.4.1.9.12.3.1.9.55.20";
  }

  smiv2:alias "cevModuleCrs18x10GePlim" {
    smiv2:oid "1.3.6.1.4.1.9.12.3.1.9.55.21";
  }

  smiv2:alias "cevModuleCrs18RP" {
    smiv2:oid "1.3.6.1.4.1.9.12.3.1.9.55.22";
  }

  smiv2:alias "cevModuleCrs18Fabric" {
    smiv2:oid "1.3.6.1.4.1.9.12.3.1.9.55.23";
  }

  smiv2:alias "cevModuleCrs1FabricShelfController" {
    smiv2:oid "1.3.6.1.4.1.9.12.3.1.9.55.24";
  }

  smiv2:alias "cevModuleCrs1FabricSwitchFabric" {
    smiv2:oid "1.3.6.1.4.1.9.12.3.1.9.55.25";
  }

  smiv2:alias "cevModuleCrs1FabricLEDModule" {
    smiv2:oid "1.3.6.1.4.1.9.12.3.1.9.55.26";
  }

  smiv2:alias "cevModuleCrs1FabricOIMSingleSlot" {
    smiv2:oid "1.3.6.1.4.1.9.12.3.1.9.55.27";
  }

  smiv2:alias "cevModuleCrs1FabricOIMDualSlot" {
    smiv2:oid "1.3.6.1.4.1.9.12.3.1.9.55.28";
  }

  smiv2:alias "cevModuleCrs18dS123Fabric" {
    smiv2:oid "1.3.6.1.4.1.9.12.3.1.9.55.29";
  }

  smiv2:alias "cevModuleCrs18mS123Fabric" {
    smiv2:oid "1.3.6.1.4.1.9.12.3.1.9.55.30";
  }

  smiv2:alias "cevModuleCrs116dS123Fabric" {
    smiv2:oid "1.3.6.1.4.1.9.12.3.1.9.55.31";
  }

  smiv2:alias "cevModuleCrs1FccSc22Ge" {
    smiv2:oid "1.3.6.1.4.1.9.12.3.1.9.55.32";
  }

  smiv2:alias "cevModuleCrs1FccSFEc" {
    smiv2:oid "1.3.6.1.4.1.9.12.3.1.9.55.33";
  }

  smiv2:alias "cevModuleCrs14x10GeCDwdmPlim" {
    smiv2:oid "1.3.6.1.4.1.9.12.3.1.9.55.34";
  }

  smiv2:alias "cevModuleCrs14OC192CDwdmPlim" {
    smiv2:oid "1.3.6.1.4.1.9.12.3.1.9.55.35";
  }

  smiv2:alias "cevModuleCrs1OC768CDwdmPlim" {
    smiv2:oid "1.3.6.1.4.1.9.12.3.1.9.55.36";
  }

  smiv2:alias "cevModuleCrs1DRPBPlim" {
    smiv2:oid "1.3.6.1.4.1.9.12.3.1.9.55.37";
  }

  smiv2:alias "cevModuleCrs1DRPB" {
    smiv2:oid "1.3.6.1.4.1.9.12.3.1.9.55.38";
  }

  smiv2:alias "cevModuleCrs1OC768CDwdmDpskC" {
    smiv2:oid "1.3.6.1.4.1.9.12.3.1.9.55.39";
  }

  smiv2:alias "cevModuleCrs14FabricCard" {
    smiv2:oid "1.3.6.1.4.1.9.12.3.1.9.55.42";
  }

  smiv2:alias "cevModuleCrsASPLIM" {
    smiv2:oid "1.3.6.1.4.1.9.12.3.1.9.55.43";
  }

  smiv2:alias "cevModuleCrs4OC192DptLr" {
    smiv2:oid "1.3.6.1.4.1.9.12.3.1.9.55.44";
  }

  smiv2:alias "cevModuleCrs4OC192DptSr" {
    smiv2:oid "1.3.6.1.4.1.9.12.3.1.9.55.45";
  }

  smiv2:alias "cevModuleCrs4OC192DptVs" {
    smiv2:oid "1.3.6.1.4.1.9.12.3.1.9.55.46";
  }

  smiv2:alias "cevModuleCrs14x10GE" {
    smiv2:oid "1.3.6.1.4.1.9.12.3.1.9.55.47";
  }

  smiv2:alias "cevModuleCrs142x1GE" {
    smiv2:oid "1.3.6.1.4.1.9.12.3.1.9.55.48";
  }

  smiv2:alias "cevModuleCrs120x1GeFl" {
    smiv2:oid "1.3.6.1.4.1.9.12.3.1.9.55.49";
  }

  smiv2:alias "cevModuleCrs12x10GeFl" {
    smiv2:oid "1.3.6.1.4.1.9.12.3.1.9.55.50";
  }

  smiv2:alias "cevModuleCrs116Alarm" {
    smiv2:oid "1.3.6.1.4.1.9.12.3.1.9.55.51";
  }

  smiv2:alias "cevModuleCrs14x10GbeWLXfpPlim" {
    smiv2:oid "1.3.6.1.4.1.9.12.3.1.9.55.52";
  }

  smiv2:alias "cevModuleCrs18x10GbeWLXfpPlim" {
    smiv2:oid "1.3.6.1.4.1.9.12.3.1.9.55.53";
  }

  smiv2:alias "cevModuleCrs1LcB40G" {
    smiv2:oid "1.3.6.1.4.1.9.12.3.1.9.55.54";
  }

  smiv2:alias "cevModuleCrs1Lc40G" {
    smiv2:oid "1.3.6.1.4.1.9.12.3.1.9.55.55";
  }

  smiv2:alias "cevModuleCrs114X10GBEWLXFPPlim" {
    smiv2:oid "1.3.6.1.4.1.9.12.3.1.9.55.56";
  }

  smiv2:alias "cevModuleCrs120X10GBEWLXFPPlim" {
    smiv2:oid "1.3.6.1.4.1.9.12.3.1.9.55.57";
  }

  smiv2:alias "cevModuleCrs11X100GBEPlim" {
    smiv2:oid "1.3.6.1.4.1.9.12.3.1.9.55.58";
  }

  smiv2:alias "cevModuleCrs8Prp12g" {
    smiv2:oid "1.3.6.1.4.1.9.12.3.1.9.55.59";
  }

  smiv2:alias "cevModuleCrs8Prp6g" {
    smiv2:oid "1.3.6.1.4.1.9.12.3.1.9.55.60";
  }

  smiv2:alias "cevModuleCrs16Prp12g" {
    smiv2:oid "1.3.6.1.4.1.9.12.3.1.9.55.61";
  }

  smiv2:alias "cevModuleCrs16Prp6g" {
    smiv2:oid "1.3.6.1.4.1.9.12.3.1.9.55.62";
  }

  smiv2:alias "cevModuleCrs16FanCtB" {
    smiv2:oid "1.3.6.1.4.1.9.12.3.1.9.55.63";
  }

  smiv2:alias "cevModuleCrs16AlarmMB" {
    smiv2:oid "1.3.6.1.4.1.9.12.3.1.9.55.64";
  }

  smiv2:alias "cevModuleCrs16LccFCtB" {
    smiv2:oid "1.3.6.1.4.1.9.12.3.1.9.55.65";
  }

  smiv2:alias "cevModuleCrs114X10GBEDwdmXfpPlim" {
    smiv2:oid "1.3.6.1.4.1.9.12.3.1.9.55.66";
  }

  smiv2:alias "cevModuleCrs120X10GBEDwdmXfpPlim" {
    smiv2:oid "1.3.6.1.4.1.9.12.3.1.9.55.67";
  }

  smiv2:alias "cevModuleCrs14X40GBEOtu3Plim" {
    smiv2:oid "1.3.6.1.4.1.9.12.3.1.9.55.68";
  }

  smiv2:alias "cevModuleCrs11X100GBEDwdmPlim" {
    smiv2:oid "1.3.6.1.4.1.9.12.3.1.9.55.69";
  }

  smiv2:alias "cevModuleCrsCgsePlusPlim" {
    smiv2:oid "1.3.6.1.4.1.9.12.3.1.9.55.72";
  }

  smiv2:alias "cevModuleCrs140X10GEWLOPlim" {
    smiv2:oid "1.3.6.1.4.1.9.12.3.1.9.55.73";
  }

  smiv2:alias "cevModuleCrs14x100GELOPlim" {
    smiv2:oid "1.3.6.1.4.1.9.12.3.1.9.55.74";
  }

  smiv2:alias "cevModuleCrs12X100GELOFlex40Plim" {
    smiv2:oid "1.3.6.1.4.1.9.12.3.1.9.55.75";
  }

  smiv2:alias "cevModuleCat35xxType" {
    smiv2:oid "1.3.6.1.4.1.9.12.3.1.9.56";
  }

  smiv2:alias "cevModuleCat356024PS" {
    smiv2:oid "1.3.6.1.4.1.9.12.3.1.9.56.1";
  }

  smiv2:alias "cevModuleCat356048PS" {
    smiv2:oid "1.3.6.1.4.1.9.12.3.1.9.56.2";
  }

  smiv2:alias "cevModuleCat3560G24PS" {
    smiv2:oid "1.3.6.1.4.1.9.12.3.1.9.56.3";
  }

  smiv2:alias "cevModuleCat3560G24TS" {
    smiv2:oid "1.3.6.1.4.1.9.12.3.1.9.56.4";
  }

  smiv2:alias "cevModuleCat3560G48PS" {
    smiv2:oid "1.3.6.1.4.1.9.12.3.1.9.56.5";
  }

  smiv2:alias "cevModuleCat3560G48TS" {
    smiv2:oid "1.3.6.1.4.1.9.12.3.1.9.56.6";
  }

  smiv2:alias "cevModuleCat356024TS" {
    smiv2:oid "1.3.6.1.4.1.9.12.3.1.9.56.7";
  }

  smiv2:alias "cevModuleCat356048TS" {
    smiv2:oid "1.3.6.1.4.1.9.12.3.1.9.56.8";
  }

  smiv2:alias "cevModuleCat3560E24TD" {
    smiv2:oid "1.3.6.1.4.1.9.12.3.1.9.56.9";
  }

  smiv2:alias "cevModuleCat3560E48TD" {
    smiv2:oid "1.3.6.1.4.1.9.12.3.1.9.56.10";
  }

  smiv2:alias "cevModuleCat3560E24PD" {
    smiv2:oid "1.3.6.1.4.1.9.12.3.1.9.56.11";
  }

  smiv2:alias "cevModuleCat3560E48PD" {
    smiv2:oid "1.3.6.1.4.1.9.12.3.1.9.56.12";
  }

  smiv2:alias "cevModuleCat35608PC" {
    smiv2:oid "1.3.6.1.4.1.9.12.3.1.9.56.13";
  }

  smiv2:alias "cevModuleCat3560e12d" {
    smiv2:oid "1.3.6.1.4.1.9.12.3.1.9.56.14";
  }

  smiv2:alias "cevModuleCat3560E12SD" {
    smiv2:oid "1.3.6.1.4.1.9.12.3.1.9.56.15";
  }

  smiv2:alias "cevModuleCat356012PCS" {
    smiv2:oid "1.3.6.1.4.1.9.12.3.1.9.56.16";
  }

  smiv2:alias "cevModuleCat3560v248ps" {
    smiv2:oid "1.3.6.1.4.1.9.12.3.1.9.56.17";
  }

  smiv2:alias "cevModuleCat3560v248ts" {
    smiv2:oid "1.3.6.1.4.1.9.12.3.1.9.56.18";
  }

  smiv2:alias "cevModuleCat3560v224ps" {
    smiv2:oid "1.3.6.1.4.1.9.12.3.1.9.56.19";
  }

  smiv2:alias "cevModuleCat3560v224ts" {
    smiv2:oid "1.3.6.1.4.1.9.12.3.1.9.56.20";
  }

  smiv2:alias "cevModuleCat3560v224tsD" {
    smiv2:oid "1.3.6.1.4.1.9.12.3.1.9.56.21";
  }

  smiv2:alias "cevModuleCat3560x24" {
    smiv2:oid "1.3.6.1.4.1.9.12.3.1.9.56.22";
  }

  smiv2:alias "cevModuleCat3560x48" {
    smiv2:oid "1.3.6.1.4.1.9.12.3.1.9.56.23";
  }

  smiv2:alias "cevModuleWsC3560CPD8ptS" {
    smiv2:oid "1.3.6.1.4.1.9.12.3.1.9.56.28";
  }

  smiv2:alias "cevModuleWsC3560C12pcS" {
    smiv2:oid "1.3.6.1.4.1.9.12.3.1.9.56.29";
  }

  smiv2:alias "cevModuleWsC3560C8pcS" {
    smiv2:oid "1.3.6.1.4.1.9.12.3.1.9.56.30";
  }

  smiv2:alias "cevModuleASA5523Type" {
    smiv2:oid "1.3.6.1.4.1.9.12.3.1.9.57";
  }

  smiv2:alias "cevMASA5523IsmSsmIds20K9" {
    smiv2:oid "1.3.6.1.4.1.9.12.3.1.9.57.1";
  }

  smiv2:alias "cevMASA5523PmSsmIO4ge" {
    smiv2:oid "1.3.6.1.4.1.9.12.3.1.9.57.2";
  }

  smiv2:alias "cevMASA5523IsmSsmIds10K9" {
    smiv2:oid "1.3.6.1.4.1.9.12.3.1.9.57.3";
  }

  smiv2:alias "cevPmSsmIO4geInc" {
    smiv2:oid "1.3.6.1.4.1.9.12.3.1.9.57.4";
  }

  smiv2:alias "cevMASA5523IsmSsmCsc10" {
    smiv2:oid "1.3.6.1.4.1.9.12.3.1.9.57.5";
  }

  smiv2:alias "cevMASA5523IsmSsmCsc20" {
    smiv2:oid "1.3.6.1.4.1.9.12.3.1.9.57.6";
  }

  smiv2:alias "cevMASA5523IsmSsmIds40K9" {
    smiv2:oid "1.3.6.1.4.1.9.12.3.1.9.57.7";
  }

  smiv2:alias "cevModuleUmg9820Type" {
    smiv2:oid "1.3.6.1.4.1.9.12.3.1.9.58";
  }

  smiv2:alias "cevModuleUmg9820GigEProc" {
    smiv2:oid "1.3.6.1.4.1.9.12.3.1.9.58.1";
  }

  smiv2:alias "cevModuleUmg9820QamCard" {
    smiv2:oid "1.3.6.1.4.1.9.12.3.1.9.58.2";
  }

  smiv2:alias "cevModuleONS15310Type" {
    smiv2:oid "1.3.6.1.4.1.9.12.3.1.9.59";
  }

  smiv2:alias "cevONS15310FeML100" {
    smiv2:oid "1.3.6.1.4.1.9.12.3.1.9.59.1";
  }

  smiv2:alias "cevONS15310FeCE100" {
    smiv2:oid "1.3.6.1.4.1.9.12.3.1.9.59.2";
  }

  smiv2:alias "cevONS15310Ge8CE2" {
    smiv2:oid "1.3.6.1.4.1.9.12.3.1.9.59.3";
  }

  smiv2:alias "cevModuleX2s" {
    smiv2:oid "1.3.6.1.4.1.9.12.3.1.9.60";
  }

  smiv2:alias "cevMX210GBaseSR" {
    smiv2:oid "1.3.6.1.4.1.9.12.3.1.9.60.1";
  }

  smiv2:alias "cevMX210GBaseLR" {
    smiv2:oid "1.3.6.1.4.1.9.12.3.1.9.60.2";
  }

  smiv2:alias "cevMX210GBaseER" {
    smiv2:oid "1.3.6.1.4.1.9.12.3.1.9.60.3";
  }

  smiv2:alias "cevMX210GBaseLX4" {
    smiv2:oid "1.3.6.1.4.1.9.12.3.1.9.60.4";
  }

  smiv2:alias "cevMX210GBaseCX4" {
    smiv2:oid "1.3.6.1.4.1.9.12.3.1.9.60.5";
  }

  smiv2:alias "cevMX210GBaseZR" {
    smiv2:oid "1.3.6.1.4.1.9.12.3.1.9.60.6";
  }

  smiv2:alias "cevMX210GBaseLW" {
    smiv2:oid "1.3.6.1.4.1.9.12.3.1.9.60.7";
  }

  smiv2:alias "cevMX210GBaseLRM" {
    smiv2:oid "1.3.6.1.4.1.9.12.3.1.9.60.8";
  }

  smiv2:alias "cevMX210GBaseT" {
    smiv2:oid "1.3.6.1.4.1.9.12.3.1.9.60.9";
  }

  smiv2:alias "cevMX2s10GBaseWdmRxOnly" {
    smiv2:oid "1.3.6.1.4.1.9.12.3.1.9.60.10";
  }

  smiv2:alias "cevMX2s10GBaseDwdm3033" {
    smiv2:oid "1.3.6.1.4.1.9.12.3.1.9.60.11";
  }

  smiv2:alias "cevMX2s10GBaseDwdm3112" {
    smiv2:oid "1.3.6.1.4.1.9.12.3.1.9.60.13";
  }

  smiv2:alias "cevMX2s10GBaseDwdm3190" {
    smiv2:oid "1.3.6.1.4.1.9.12.3.1.9.60.14";
  }

  smiv2:alias "cevMX2s10GBaseDwdm3268" {
    smiv2:oid "1.3.6.1.4.1.9.12.3.1.9.60.15";
  }

  smiv2:alias "cevMX2s10GBaseDwdm3425" {
    smiv2:oid "1.3.6.1.4.1.9.12.3.1.9.60.16";
  }

  smiv2:alias "cevMX2s10GBaseDwdm3504" {
    smiv2:oid "1.3.6.1.4.1.9.12.3.1.9.60.17";
  }

  smiv2:alias "cevMX2s10GBaseDwdm3582" {
    smiv2:oid "1.3.6.1.4.1.9.12.3.1.9.60.18";
  }

  smiv2:alias "cevMX2s10GBaseDwdm3661" {
    smiv2:oid "1.3.6.1.4.1.9.12.3.1.9.60.19";
  }

  smiv2:alias "cevMX2s10GBaseDwdm3819" {
    smiv2:oid "1.3.6.1.4.1.9.12.3.1.9.60.20";
  }

  smiv2:alias "cevMX2s10GBaseDwdm3898" {
    smiv2:oid "1.3.6.1.4.1.9.12.3.1.9.60.21";
  }

  smiv2:alias "cevMX2s10GBaseDwdm3977" {
    smiv2:oid "1.3.6.1.4.1.9.12.3.1.9.60.22";
  }

  smiv2:alias "cevMX2s10GBaseDwdm4056" {
    smiv2:oid "1.3.6.1.4.1.9.12.3.1.9.60.23";
  }

  smiv2:alias "cevMX2s10GBaseDwdm4214" {
    smiv2:oid "1.3.6.1.4.1.9.12.3.1.9.60.24";
  }

  smiv2:alias "cevMX2s10GBaseDwdm4294" {
    smiv2:oid "1.3.6.1.4.1.9.12.3.1.9.60.25";
  }

  smiv2:alias "cevMX2s10GBaseDwdm4373" {
    smiv2:oid "1.3.6.1.4.1.9.12.3.1.9.60.26";
  }

  smiv2:alias "cevMX2s10GBaseDwdm4453" {
    smiv2:oid "1.3.6.1.4.1.9.12.3.1.9.60.27";
  }

  smiv2:alias "cevMX2s10GBaseDwdm4612" {
    smiv2:oid "1.3.6.1.4.1.9.12.3.1.9.60.28";
  }

  smiv2:alias "cevMX2s10GBaseDwdm4692" {
    smiv2:oid "1.3.6.1.4.1.9.12.3.1.9.60.29";
  }

  smiv2:alias "cevMX2s10GBaseDwdm4772" {
    smiv2:oid "1.3.6.1.4.1.9.12.3.1.9.60.30";
  }

  smiv2:alias "cevMX2s10GBaseDwdm4851" {
    smiv2:oid "1.3.6.1.4.1.9.12.3.1.9.60.31";
  }

  smiv2:alias "cevMX2s10GBaseDwdm5012" {
    smiv2:oid "1.3.6.1.4.1.9.12.3.1.9.60.32";
  }

  smiv2:alias "cevMX2s10GBaseDwdm5092" {
    smiv2:oid "1.3.6.1.4.1.9.12.3.1.9.60.33";
  }

  smiv2:alias "cevMX2s10GBaseDwdm5172" {
    smiv2:oid "1.3.6.1.4.1.9.12.3.1.9.60.34";
  }

  smiv2:alias "cevMX2s10GBaseDwdm5252" {
    smiv2:oid "1.3.6.1.4.1.9.12.3.1.9.60.35";
  }

  smiv2:alias "cevMX2s10GBaseDwdm5413" {
    smiv2:oid "1.3.6.1.4.1.9.12.3.1.9.60.36";
  }

  smiv2:alias "cevMX2s10GBaseDwdm5494" {
    smiv2:oid "1.3.6.1.4.1.9.12.3.1.9.60.37";
  }

  smiv2:alias "cevMX2s10GBaseDwdm5575" {
    smiv2:oid "1.3.6.1.4.1.9.12.3.1.9.60.38";
  }

  smiv2:alias "cevMX2s10GBaseDwdm5655" {
    smiv2:oid "1.3.6.1.4.1.9.12.3.1.9.60.39";
  }

  smiv2:alias "cevMX2s10GBaseDwdm5817" {
    smiv2:oid "1.3.6.1.4.1.9.12.3.1.9.60.40";
  }

  smiv2:alias "cevMX2s10GBaseDwdm5898" {
    smiv2:oid "1.3.6.1.4.1.9.12.3.1.9.60.41";
  }

  smiv2:alias "cevMX2s10GBaseDwdm5979" {
    smiv2:oid "1.3.6.1.4.1.9.12.3.1.9.60.42";
  }

  smiv2:alias "cevMX2s10GBaseDwdm6061" {
    smiv2:oid "1.3.6.1.4.1.9.12.3.1.9.60.43";
  }

  smiv2:alias "cevMX210GEBaseT" {
    smiv2:oid "1.3.6.1.4.1.9.12.3.1.9.60.44";
  }

  smiv2:alias "cevModuleCE5xxType" {
    smiv2:oid "1.3.6.1.4.1.9.12.3.1.9.63";
  }

  smiv2:alias "cevModuleCE50024TT" {
    smiv2:oid "1.3.6.1.4.1.9.12.3.1.9.63.1";
  }

  smiv2:alias "cevModuleCE50024LC" {
    smiv2:oid "1.3.6.1.4.1.9.12.3.1.9.63.2";
  }

  smiv2:alias "cevModuleCE50024PC" {
    smiv2:oid "1.3.6.1.4.1.9.12.3.1.9.63.3";
  }

  smiv2:alias "cevModuleCE500G12TC" {
    smiv2:oid "1.3.6.1.4.1.9.12.3.1.9.63.4";
  }

  smiv2:alias "cevModuleCE5208PC" {
    smiv2:oid "1.3.6.1.4.1.9.12.3.1.9.63.5";
  }

  smiv2:alias "cevModuleCE52024PC" {
    smiv2:oid "1.3.6.1.4.1.9.12.3.1.9.63.6";
  }

  smiv2:alias "cevModuleCE52024TT" {
    smiv2:oid "1.3.6.1.4.1.9.12.3.1.9.63.7";
  }

  smiv2:alias "cevModuleCE52024LC" {
    smiv2:oid "1.3.6.1.4.1.9.12.3.1.9.63.8";
  }

  smiv2:alias "cevModule520G24TC" {
    smiv2:oid "1.3.6.1.4.1.9.12.3.1.9.63.9";
  }

  smiv2:alias "cevModuleMEType" {
    smiv2:oid "1.3.6.1.4.1.9.12.3.1.9.64";
  }

  smiv2:alias "cevModuleME240024TS" {
    smiv2:oid "1.3.6.1.4.1.9.12.3.1.9.64.1";
  }

  smiv2:alias "cevModuleME340024TS" {
    smiv2:oid "1.3.6.1.4.1.9.12.3.1.9.64.2";
  }

  smiv2:alias "cevModuleME3400G12CS" {
    smiv2:oid "1.3.6.1.4.1.9.12.3.1.9.64.3";
  }

  smiv2:alias "cevModuleME3400G2CS" {
    smiv2:oid "1.3.6.1.4.1.9.12.3.1.9.64.4";
  }

  smiv2:alias "cevModuleME492410GE" {
    smiv2:oid "1.3.6.1.4.1.9.12.3.1.9.64.5";
  }

  smiv2:alias "cevModuleME340024FS" {
    smiv2:oid "1.3.6.1.4.1.9.12.3.1.9.64.6";
  }

  smiv2:alias "cevModuleME3400E24TS" {
    smiv2:oid "1.3.6.1.4.1.9.12.3.1.9.64.7";
  }

  smiv2:alias "cevModuleME3400EG12CS" {
    smiv2:oid "1.3.6.1.4.1.9.12.3.1.9.64.8";
  }

  smiv2:alias "cevModuleME3400EG2CS" {
    smiv2:oid "1.3.6.1.4.1.9.12.3.1.9.64.9";
  }

  smiv2:alias "cevModuleME3600X24FS" {
    smiv2:oid "1.3.6.1.4.1.9.12.3.1.9.64.10";
  }

  smiv2:alias "cevModuleME3600X24TS" {
    smiv2:oid "1.3.6.1.4.1.9.12.3.1.9.64.11";
  }

  smiv2:alias "cevModuleME3800X24FS" {
    smiv2:oid "1.3.6.1.4.1.9.12.3.1.9.64.12";
  }

  smiv2:alias "cevModuleCat4000EType" {
    smiv2:oid "1.3.6.1.4.1.9.12.3.1.9.65";
  }

  smiv2:alias "cevCat4kWsx45Sup6e" {
    smiv2:oid "1.3.6.1.4.1.9.12.3.1.9.65.1";
  }

  smiv2:alias "cevCat4kWsx4648Rj45e" {
    smiv2:oid "1.3.6.1.4.1.9.12.3.1.9.65.2";
  }

  smiv2:alias "cevCat4kWsx4648Rj45ve" {
    smiv2:oid "1.3.6.1.4.1.9.12.3.1.9.65.3";
  }

  smiv2:alias "cevCat4kWsx4606X2e" {
    smiv2:oid "1.3.6.1.4.1.9.12.3.1.9.65.4";
  }

  smiv2:alias "cevCat4kWsx4624Sfpe" {
    smiv2:oid "1.3.6.1.4.1.9.12.3.1.9.65.5";
  }

  smiv2:alias "cevCat4kWsx4590E" {
    smiv2:oid "1.3.6.1.4.1.9.12.3.1.9.65.7";
  }

  smiv2:alias "cevCat4kWsx4648Rj45je" {
    smiv2:oid "1.3.6.1.4.1.9.12.3.1.9.65.9";
  }

  smiv2:alias "cevCat4kWsx4648Rj45vPlusE" {
    smiv2:oid "1.3.6.1.4.1.9.12.3.1.9.65.10";
  }

  smiv2:alias "cevCat4kWsx45Sup6LE" {
    smiv2:oid "1.3.6.1.4.1.9.12.3.1.9.65.13";
  }

  smiv2:alias "cevCat4kWsx45Sup7e" {
    smiv2:oid "1.3.6.1.4.1.9.12.3.1.9.65.14";
  }

  smiv2:alias "cevCat4kWsx4748Rj45VPlusE" {
    smiv2:oid "1.3.6.1.4.1.9.12.3.1.9.65.15";
  }

  smiv2:alias "cevCat4kWsx4712SfpPlusE" {
    smiv2:oid "1.3.6.1.4.1.9.12.3.1.9.65.16";
  }

  smiv2:alias "cevCat4kWsx4612SfpE" {
    smiv2:oid "1.3.6.1.4.1.9.12.3.1.9.65.17";
  }

  smiv2:alias "cevCat4kWsx4640CSfpE" {
    smiv2:oid "1.3.6.1.4.1.9.12.3.1.9.65.18";
  }

  smiv2:alias "cevCatWsX4748Rj45E" {
    smiv2:oid "1.3.6.1.4.1.9.12.3.1.9.65.19";
  }

  smiv2:alias "cevCat4kWsX4748NgpoeE" {
    smiv2:oid "1.3.6.1.4.1.9.12.3.1.9.65.20";
  }

  smiv2:alias "cevCat4kWsx4712SfpE" {
    smiv2:oid "1.3.6.1.4.1.9.12.3.1.9.65.21";
  }

  smiv2:alias "cevCat4kWsx4724SfpE" {
    smiv2:oid "1.3.6.1.4.1.9.12.3.1.9.65.22";
  }

  smiv2:alias "cevCat4kWsx4748SfpE" {
    smiv2:oid "1.3.6.1.4.1.9.12.3.1.9.65.23";
  }

  smiv2:alias "cevModuleN7KType" {
    smiv2:oid "1.3.6.1.4.1.9.12.3.1.9.66";
  }

  smiv2:alias "cevN7KSup1" {
    smiv2:oid "1.3.6.1.4.1.9.12.3.1.9.66.1";
  }

  smiv2:alias "cevN7KM148GT04" {
    smiv2:oid "1.3.6.1.4.1.9.12.3.1.9.66.2";
  }

  smiv2:alias "cevN7KM132XP08" {
    smiv2:oid "1.3.6.1.4.1.9.12.3.1.9.66.3";
  }

  smiv2:alias "cevN7Kc7010Fab40" {
    smiv2:oid "1.3.6.1.4.1.9.12.3.1.9.66.4";
  }

  smiv2:alias "cevN7KM148GS11" {
    smiv2:oid "1.3.6.1.4.1.9.12.3.1.9.66.5";
  }

  smiv2:alias "cevN7Kc7018Fab1" {
    smiv2:oid "1.3.6.1.4.1.9.12.3.1.9.66.6";
  }

  smiv2:alias "cevN7KF132Xp15" {
    smiv2:oid "1.3.6.1.4.1.9.12.3.1.9.66.7";
  }

  smiv2:alias "cevN7KM108X212" {
    smiv2:oid "1.3.6.1.4.1.9.12.3.1.9.66.8";
  }

  smiv2:alias "cevN7KM108X212L" {
    smiv2:oid "1.3.6.1.4.1.9.12.3.1.9.66.9";
  }

  smiv2:alias "cevN7KM148GS11L" {
    smiv2:oid "1.3.6.1.4.1.9.12.3.1.9.66.10";
  }

  smiv2:alias "cevN7KM116XP22L" {
    smiv2:oid "1.3.6.1.4.1.9.12.3.1.9.66.11";
  }

  smiv2:alias "cevN7KM108XP22L" {
    smiv2:oid "1.3.6.1.4.1.9.12.3.1.9.66.12";
  }

  smiv2:alias "cevN7KM132XP12L" {
    smiv2:oid "1.3.6.1.4.1.9.12.3.1.9.66.13";
  }

  smiv2:alias "cevN7Kc7009Fab2" {
    smiv2:oid "1.3.6.1.4.1.9.12.3.1.9.66.14";
  }

  smiv2:alias "cevN7Kc7010Fab2" {
    smiv2:oid "1.3.6.1.4.1.9.12.3.1.9.66.16";
  }

  smiv2:alias "cevN7Kc7018Fab2" {
    smiv2:oid "1.3.6.1.4.1.9.12.3.1.9.66.17";
  }

  smiv2:alias "cevN7KF248XP24" {
    smiv2:oid "1.3.6.1.4.1.9.12.3.1.9.66.18";
  }

  smiv2:alias "cevN7KF248XT24" {
    smiv2:oid "1.3.6.1.4.1.9.12.3.1.9.66.19";
  }

  smiv2:alias "cevN7KSUP2" {
    smiv2:oid "1.3.6.1.4.1.9.12.3.1.9.66.20";
  }

  smiv2:alias "cevN7KM202CF22L" {
    smiv2:oid "1.3.6.1.4.1.9.12.3.1.9.66.21";
  }

  smiv2:alias "cevN7KM206FQ23L" {
    smiv2:oid "1.3.6.1.4.1.9.12.3.1.9.66.22";
  }

  smiv2:alias "cevN7KM148GT11L" {
    smiv2:oid "1.3.6.1.4.1.9.12.3.1.9.66.23";
  }

  smiv2:alias "cevN7KSMNAMK9" {
    smiv2:oid "1.3.6.1.4.1.9.12.3.1.9.66.27";
  }

  smiv2:alias "cevN7KFabricExtenderConnectionCable" {
    smiv2:oid "1.3.6.1.4.1.9.12.3.1.9.66.31";
  }

  smiv2:alias "cevN7KM224XP23L" {
    smiv2:oid "1.3.6.1.4.1.9.12.3.1.9.66.32";
  }

  smiv2:alias "cevN7KSUP2E" {
    smiv2:oid "1.3.6.1.4.1.9.12.3.1.9.66.33";
  }

  smiv2:alias "cevN7KForwardingEngine" {
    smiv2:oid "1.3.6.1.4.1.9.12.3.1.9.66.34";
  }

  smiv2:alias "cevN7KF306CK25" {
    smiv2:oid "1.3.6.1.4.1.9.12.3.1.9.66.35";
  }

  smiv2:alias "cevN7KF312FQ25" {
    smiv2:oid "1.3.6.1.4.1.9.12.3.1.9.66.36";
  }

  smiv2:alias "cevN7KF248XT25E" {
    smiv2:oid "1.3.6.1.4.1.9.12.3.1.9.66.45";
  }

  smiv2:alias "cevN7KF248XP25E" {
    smiv2:oid "1.3.6.1.4.1.9.12.3.1.9.66.46";
  }

  smiv2:alias "cevModuleASA5580Type" {
    smiv2:oid "1.3.6.1.4.1.9.12.3.1.9.67";
  }

  smiv2:alias "cevModuleASA5580Pm4x1geCu" {
    smiv2:oid "1.3.6.1.4.1.9.12.3.1.9.67.1";
  }

  smiv2:alias "cevModuleASA5580Pm4x1geFi" {
    smiv2:oid "1.3.6.1.4.1.9.12.3.1.9.67.2";
  }

  smiv2:alias "cevModuleASA5580Pm2x10geFi" {
    smiv2:oid "1.3.6.1.4.1.9.12.3.1.9.67.3";
  }

  smiv2:alias "cevModuleASR1000Type" {
    smiv2:oid "1.3.6.1.4.1.9.12.3.1.9.68";
  }

  smiv2:alias "cevModuleASR1000RP1" {
    smiv2:oid "1.3.6.1.4.1.9.12.3.1.9.68.1";
  }

  smiv2:alias "cevModuleASR1000ESP10" {
    smiv2:oid "1.3.6.1.4.1.9.12.3.1.9.68.2";
  }

  smiv2:alias "cevModuleASR1000SIP10" {
    smiv2:oid "1.3.6.1.4.1.9.12.3.1.9.68.3";
  }

  smiv2:alias "cevModuleASR1000UnknownRP" {
    smiv2:oid "1.3.6.1.4.1.9.12.3.1.9.68.4";
  }

  smiv2:alias "cevModuleASR1000UnknownESP" {
    smiv2:oid "1.3.6.1.4.1.9.12.3.1.9.68.5";
  }

  smiv2:alias "cevModuleASR1000UnknownSIP" {
    smiv2:oid "1.3.6.1.4.1.9.12.3.1.9.68.6";
  }

  smiv2:alias "cevModuleASR1002RP1" {
    smiv2:oid "1.3.6.1.4.1.9.12.3.1.9.68.7";
  }

  smiv2:alias "cevModuleASR1000ESP5" {
    smiv2:oid "1.3.6.1.4.1.9.12.3.1.9.68.8";
  }

  smiv2:alias "cevModuleASR1000ESP20" {
    smiv2:oid "1.3.6.1.4.1.9.12.3.1.9.68.9";
  }

  smiv2:alias "cevModuleASR1002Spa4pGe" {
    smiv2:oid "1.3.6.1.4.1.9.12.3.1.9.68.10";
  }

  smiv2:alias "cevModuleASR1002SIP10" {
    smiv2:oid "1.3.6.1.4.1.9.12.3.1.9.68.11";
  }

  smiv2:alias "cevModuleASR1000SIP40" {
    smiv2:oid "1.3.6.1.4.1.9.12.3.1.9.68.12";
  }

  smiv2:alias "cevModuleASR1000RP2" {
    smiv2:oid "1.3.6.1.4.1.9.12.3.1.9.68.13";
  }

  smiv2:alias "cevModuleASR1000ESP10N" {
    smiv2:oid "1.3.6.1.4.1.9.12.3.1.9.68.14";
  }

  smiv2:alias "cevModuleASR1002FESP" {
    smiv2:oid "1.3.6.1.4.1.9.12.3.1.9.68.15";
  }

  smiv2:alias "cevModuleASR1002FSIP10" {
    smiv2:oid "1.3.6.1.4.1.9.12.3.1.9.68.16";
  }

  smiv2:alias "cevModuleASR1000ESP40" {
    smiv2:oid "1.3.6.1.4.1.9.12.3.1.9.68.17";
  }

  smiv2:alias "cevModuleASR1001RP" {
    smiv2:oid "1.3.6.1.4.1.9.12.3.1.9.68.18";
  }

  smiv2:alias "cevModuleASR1001ESP" {
    smiv2:oid "1.3.6.1.4.1.9.12.3.1.9.68.19";
  }

  smiv2:alias "cevModuleASR1001SIP" {
    smiv2:oid "1.3.6.1.4.1.9.12.3.1.9.68.20";
  }

  smiv2:alias "cevModuleASR1001Spa4pGe" {
    smiv2:oid "1.3.6.1.4.1.9.12.3.1.9.68.21";
  }

  smiv2:alias "cevModuleASR1001IDC2xOc3Pos" {
    smiv2:oid "1.3.6.1.4.1.9.12.3.1.9.68.22";
  }

  smiv2:alias "cevModuleASR1001IDC4xT3" {
    smiv2:oid "1.3.6.1.4.1.9.12.3.1.9.68.23";
  }

  smiv2:alias "cevModuleASR1001IDC8xChT1E1" {
    smiv2:oid "1.3.6.1.4.1.9.12.3.1.9.68.24";
  }

  smiv2:alias "cevModuleASR1001IDC4xGe" {
    smiv2:oid "1.3.6.1.4.1.9.12.3.1.9.68.25";
  }

  smiv2:alias "cevModuleASR1001IDCHDD" {
    smiv2:oid "1.3.6.1.4.1.9.12.3.1.9.68.26";
  }

  smiv2:alias "cevModuleASR1002XRP" {
    smiv2:oid "1.3.6.1.4.1.9.12.3.1.9.68.27";
  }

  smiv2:alias "cevModuleASR1002XESP" {
    smiv2:oid "1.3.6.1.4.1.9.12.3.1.9.68.28";
  }

  smiv2:alias "cevModuleASR1002XSIP" {
    smiv2:oid "1.3.6.1.4.1.9.12.3.1.9.68.29";
  }

  smiv2:alias "cevModuleASR1002X6xGeBuiltIn" {
    smiv2:oid "1.3.6.1.4.1.9.12.3.1.9.68.30";
  }

  smiv2:alias "cevModuleASR1000ESP100" {
    smiv2:oid "1.3.6.1.4.1.9.12.3.1.9.68.31";
  }

  smiv2:alias "cevModuleASR1000ELC2xT20xGe" {
    smiv2:oid "1.3.6.1.4.1.9.12.3.1.9.68.33";
  }

  smiv2:alias "cevModuleASR1000ELC40GModule" {
    smiv2:oid "1.3.6.1.4.1.9.12.3.1.9.68.34";
  }

  smiv2:alias "cevModuleASR1002XCRP" {
    smiv2:oid "1.3.6.1.4.1.9.12.3.1.9.68.35";
  }

  smiv2:alias "cevModuleASR1002XCESP" {
    smiv2:oid "1.3.6.1.4.1.9.12.3.1.9.68.36";
  }

  smiv2:alias "cevModuleASR1002XCSIP" {
    smiv2:oid "1.3.6.1.4.1.9.12.3.1.9.68.37";
  }

  smiv2:alias "cevModuleASR1002XC2xGeBuiltIn" {
    smiv2:oid "1.3.6.1.4.1.9.12.3.1.9.68.38";
  }

  smiv2:alias "cevModuleCatRfgwType" {
    smiv2:oid "1.3.6.1.4.1.9.12.3.1.9.69";
  }

  smiv2:alias "cevRfgwDtcc" {
    smiv2:oid "1.3.6.1.4.1.9.12.3.1.9.69.1";
  }

  smiv2:alias "cevRfgwQam48ABC" {
    smiv2:oid "1.3.6.1.4.1.9.12.3.1.9.69.2";
  }

  smiv2:alias "cevRfgwPort4Qam" {
    smiv2:oid "1.3.6.1.4.1.9.12.3.1.9.69.3";
  }

  smiv2:alias "cevRfgwRfswitch" {
    smiv2:oid "1.3.6.1.4.1.9.12.3.1.9.69.4";
  }

  smiv2:alias "cevRfgwQam384ABC" {
    smiv2:oid "1.3.6.1.4.1.9.12.3.1.9.69.5";
  }

  smiv2:alias "cevModuleVgdType" {
    smiv2:oid "1.3.6.1.4.1.9.12.3.1.9.70";
  }

  smiv2:alias "cevVgdDfcCT3" {
    smiv2:oid "1.3.6.1.4.1.9.12.3.1.9.70.1";
  }

  smiv2:alias "cevVgdDfcVFC" {
    smiv2:oid "1.3.6.1.4.1.9.12.3.1.9.70.2";
  }

  smiv2:alias "cevVgdDfcCarrier" {
    smiv2:oid "1.3.6.1.4.1.9.12.3.1.9.70.3";
  }

  smiv2:alias "cevModuleIEType" {
    smiv2:oid "1.3.6.1.4.1.9.12.3.1.9.71";
  }

  smiv2:alias "cevModuleIE30004TC" {
    smiv2:oid "1.3.6.1.4.1.9.12.3.1.9.71.1";
  }

  smiv2:alias "cevModuleIE30008TC" {
    smiv2:oid "1.3.6.1.4.1.9.12.3.1.9.71.2";
  }

  smiv2:alias "cevModuleIE30008TM" {
    smiv2:oid "1.3.6.1.4.1.9.12.3.1.9.71.3";
  }

  smiv2:alias "cevModuleIE30008FM" {
    smiv2:oid "1.3.6.1.4.1.9.12.3.1.9.71.4";
  }

  smiv2:alias "cevModuleRAIE1783MS06T" {
    smiv2:oid "1.3.6.1.4.1.9.12.3.1.9.71.5";
  }

  smiv2:alias "cevModuleRAIE1783MS10T" {
    smiv2:oid "1.3.6.1.4.1.9.12.3.1.9.71.6";
  }

  smiv2:alias "cevModuleRAIE1783MX08T" {
    smiv2:oid "1.3.6.1.4.1.9.12.3.1.9.71.7";
  }

  smiv2:alias "cevModuleRAIE1783MX08F" {
    smiv2:oid "1.3.6.1.4.1.9.12.3.1.9.71.8";
  }

  smiv2:alias "cevModuleIE301016S8PC" {
    smiv2:oid "1.3.6.1.4.1.9.12.3.1.9.71.9";
  }

  smiv2:alias "cevModuleRAIE1783RMS06T" {
    smiv2:oid "1.3.6.1.4.1.9.12.3.1.9.71.13";
  }

  smiv2:alias "cevModuleRAIE1783RMS10T" {
    smiv2:oid "1.3.6.1.4.1.9.12.3.1.9.71.14";
  }

  smiv2:alias "cevModuleIE20004TS" {
    smiv2:oid "1.3.6.1.4.1.9.12.3.1.9.71.15";
  }

  smiv2:alias "cevModuleIE20004T" {
    smiv2:oid "1.3.6.1.4.1.9.12.3.1.9.71.16";
  }

  smiv2:alias "cevModuleIE20004TSG" {
    smiv2:oid "1.3.6.1.4.1.9.12.3.1.9.71.17";
  }

  smiv2:alias "cevModuleIE20004TG" {
    smiv2:oid "1.3.6.1.4.1.9.12.3.1.9.71.18";
  }

  smiv2:alias "cevModuleIE20008TC" {
    smiv2:oid "1.3.6.1.4.1.9.12.3.1.9.71.19";
  }

  smiv2:alias "cevModuleIE20008TCG" {
    smiv2:oid "1.3.6.1.4.1.9.12.3.1.9.71.20";
  }

  smiv2:alias "cevModuleIE200016TC" {
    smiv2:oid "1.3.6.1.4.1.9.12.3.1.9.71.21";
  }

  smiv2:alias "cevModuleIE200016TCG" {
    smiv2:oid "1.3.6.1.4.1.9.12.3.1.9.71.22";
  }

  smiv2:alias "cevModuleIE200016TCGX" {
    smiv2:oid "1.3.6.1.4.1.9.12.3.1.9.71.23";
  }

  smiv2:alias "cevModuleRAIE1783BMS06SL" {
    smiv2:oid "1.3.6.1.4.1.9.12.3.1.9.71.24";
  }

  smiv2:alias "cevModuleRAIE1783BMS06SA" {
    smiv2:oid "1.3.6.1.4.1.9.12.3.1.9.71.25";
  }

  smiv2:alias "cevModuleRAIE1783BMS06TL" {
    smiv2:oid "1.3.6.1.4.1.9.12.3.1.9.71.26";
  }

  smiv2:alias "cevModuleRAIE1783BMS06TA" {
    smiv2:oid "1.3.6.1.4.1.9.12.3.1.9.71.27";
  }

  smiv2:alias "cevModuleRAIE1783BMS06SGL" {
    smiv2:oid "1.3.6.1.4.1.9.12.3.1.9.71.28";
  }

  smiv2:alias "cevModuleRAIE1783BMS06SGA" {
    smiv2:oid "1.3.6.1.4.1.9.12.3.1.9.71.29";
  }

  smiv2:alias "cevModuleRAIE1783BMS06TGL" {
    smiv2:oid "1.3.6.1.4.1.9.12.3.1.9.71.30";
  }

  smiv2:alias "cevModuleRAIE1783BMS06TGA" {
    smiv2:oid "1.3.6.1.4.1.9.12.3.1.9.71.31";
  }

  smiv2:alias "cevModuleRAIE1783BMS10CL" {
    smiv2:oid "1.3.6.1.4.1.9.12.3.1.9.71.32";
  }

  smiv2:alias "cevModuleRAIE1783BMS10CA" {
    smiv2:oid "1.3.6.1.4.1.9.12.3.1.9.71.33";
  }

  smiv2:alias "cevModuleRAIE1783BMS10CGL" {
    smiv2:oid "1.3.6.1.4.1.9.12.3.1.9.71.34";
  }

  smiv2:alias "cevModuleRAIE1783BMS10CGA" {
    smiv2:oid "1.3.6.1.4.1.9.12.3.1.9.71.35";
  }

  smiv2:alias "cevModuleRAIE1783BMS10CGP" {
    smiv2:oid "1.3.6.1.4.1.9.12.3.1.9.71.36";
  }

  smiv2:alias "cevModuleRAIE1783BMS10CGN" {
    smiv2:oid "1.3.6.1.4.1.9.12.3.1.9.71.37";
  }

  smiv2:alias "cevModuleRAIE1783BMS20CL" {
    smiv2:oid "1.3.6.1.4.1.9.12.3.1.9.71.38";
  }

  smiv2:alias "cevModuleRAIE1783BMS20CA" {
    smiv2:oid "1.3.6.1.4.1.9.12.3.1.9.71.39";
  }

  smiv2:alias "cevModuleRAIE1783BMS20CGL" {
    smiv2:oid "1.3.6.1.4.1.9.12.3.1.9.71.40";
  }

  smiv2:alias "cevModuleRAIE1783BMS20CGP" {
    smiv2:oid "1.3.6.1.4.1.9.12.3.1.9.71.41";
  }

  smiv2:alias "cevModuleRAIE1783BMS20CGPK" {
    smiv2:oid "1.3.6.1.4.1.9.12.3.1.9.71.42";
  }

  smiv2:alias "cevModuleIE200016TCGP" {
    smiv2:oid "1.3.6.1.4.1.9.12.3.1.9.71.52";
  }

  smiv2:alias "cevModuleIE200016TCGEP" {
    smiv2:oid "1.3.6.1.4.1.9.12.3.1.9.71.53";
  }

  smiv2:alias "cevModuleIE200016TCGNXP" {
    smiv2:oid "1.3.6.1.4.1.9.12.3.1.9.71.54";
  }

  smiv2:alias "cevModuleIE30004SM" {
    smiv2:oid "1.3.6.1.4.1.9.12.3.1.9.71.55";
  }

  smiv2:alias "cevModuleIE30008SM" {
    smiv2:oid "1.3.6.1.4.1.9.12.3.1.9.71.56";
  }

  smiv2:alias "cevModuleRAIE1783MX04S" {
    smiv2:oid "1.3.6.1.4.1.9.12.3.1.9.71.57";
  }

  smiv2:alias "cevModuleRAIE1783MX08S" {
    smiv2:oid "1.3.6.1.4.1.9.12.3.1.9.71.58";
  }

  smiv2:alias "cevModuleIE30004PC" {
    smiv2:oid "1.3.6.1.4.1.9.12.3.1.9.71.59";
  }

  smiv2:alias "cevModuleIE30004PC4TC" {
    smiv2:oid "1.3.6.1.4.1.9.12.3.1.9.71.60";
  }

  smiv2:alias "cevModuleRAIE1783MX04E" {
    smiv2:oid "1.3.6.1.4.1.9.12.3.1.9.71.61";
  }

  smiv2:alias "cevModuleRAIE1783MX04T04E" {
    smiv2:oid "1.3.6.1.4.1.9.12.3.1.9.71.62";
  }

  smiv2:alias "cevModuleIE20008TCGN" {
    smiv2:oid "1.3.6.1.4.1.9.12.3.1.9.71.63";
  }

  smiv2:alias "cevModuleIE200016TCGN" {
    smiv2:oid "1.3.6.1.4.1.9.12.3.1.9.71.64";
  }

  smiv2:alias "cevModuleRAIE1783BMS20CGN" {
    smiv2:oid "1.3.6.1.4.1.9.12.3.1.9.71.65";
  }

  smiv2:alias "cevModuleRAIE1783BMS12T4E2CGL" {
    smiv2:oid "1.3.6.1.4.1.9.12.3.1.9.71.66";
  }

  smiv2:alias "cevModuleRAIE1783BMS12T4E2CGP" {
    smiv2:oid "1.3.6.1.4.1.9.12.3.1.9.71.67";
  }

  smiv2:alias "cevModuleRAIE1783BMS12T4E2CGNK" {
    smiv2:oid "1.3.6.1.4.1.9.12.3.1.9.71.68";
  }

  smiv2:alias "cevModuleIem30004Pc" {
    smiv2:oid "1.3.6.1.4.1.9.12.3.1.9.71.69";
  }

  smiv2:alias "cevModuleIem30004Pc4TC" {
    smiv2:oid "1.3.6.1.4.1.9.12.3.1.9.71.70";
  }

  smiv2:alias "cevModule1783MX04E" {
    smiv2:oid "1.3.6.1.4.1.9.12.3.1.9.71.71";
  }

  smiv2:alias "cevModule1783MX04T04E" {
    smiv2:oid "1.3.6.1.4.1.9.12.3.1.9.71.72";
  }

  smiv2:alias "cevModuleIE20008T67B" {
    smiv2:oid "1.3.6.1.4.1.9.12.3.1.9.71.79";
  }

  smiv2:alias "cevModuleIE200016T67B" {
    smiv2:oid "1.3.6.1.4.1.9.12.3.1.9.71.80";
  }

  smiv2:alias "cevModuleIE200024T67B" {
    smiv2:oid "1.3.6.1.4.1.9.12.3.1.9.71.81";
  }

  smiv2:alias "cevModuleIE20008T67PGE" {
    smiv2:oid "1.3.6.1.4.1.9.12.3.1.9.71.82";
  }

  smiv2:alias "cevModuleIE200016T67PGE" {
    smiv2:oid "1.3.6.1.4.1.9.12.3.1.9.71.83";
  }

  smiv2:alias "cevModuleRAIE1783ZMS8TA" {
    smiv2:oid "1.3.6.1.4.1.9.12.3.1.9.71.84";
  }

  smiv2:alias "cevModuleRAIE1783ZMS16TA" {
    smiv2:oid "1.3.6.1.4.1.9.12.3.1.9.71.85";
  }

  smiv2:alias "cevModuleRAIE1783ZMS24TA" {
    smiv2:oid "1.3.6.1.4.1.9.12.3.1.9.71.86";
  }

  smiv2:alias "cevModuleRAIE1783ZMS4T4E2TGP" {
    smiv2:oid "1.3.6.1.4.1.9.12.3.1.9.71.87";
  }

  smiv2:alias "cevModuleRAIE1783ZMS8T8E2TGP" {
    smiv2:oid "1.3.6.1.4.1.9.12.3.1.9.71.88";
  }

  smiv2:alias "cevModuleIE2000U4STSG" {
    smiv2:oid "1.3.6.1.4.1.9.12.3.1.9.71.89";
  }

  smiv2:alias "cevModuleIE2000U16TCGP" {
    smiv2:oid "1.3.6.1.4.1.9.12.3.1.9.71.90";
  }

  smiv2:alias "cevModuleIE2000U4TG" {
    smiv2:oid "1.3.6.1.4.1.9.12.3.1.9.71.91";
  }

  smiv2:alias "cevModuleIE2000U4TSG" {
    smiv2:oid "1.3.6.1.4.1.9.12.3.1.9.71.92";
  }

  smiv2:alias "cevModuleIE2000U8TCG" {
    smiv2:oid "1.3.6.1.4.1.9.12.3.1.9.71.93";
  }

  smiv2:alias "cevModuleIE2000U16TCG" {
    smiv2:oid "1.3.6.1.4.1.9.12.3.1.9.71.94";
  }

  smiv2:alias "cevModuleIE2000U16TCGX" {
    smiv2:oid "1.3.6.1.4.1.9.12.3.1.9.71.95";
  }

  smiv2:alias "cevModuleN5KType" {
    smiv2:oid "1.3.6.1.4.1.9.12.3.1.9.72";
  }

  smiv2:alias "cevN5kM1008" {
    smiv2:oid "1.3.6.1.4.1.9.12.3.1.9.72.1";
  }

  smiv2:alias "cevN5KM1404" {
    smiv2:oid "1.3.6.1.4.1.9.12.3.1.9.72.2";
  }

  smiv2:alias "cevN5kM1Blnk" {
    smiv2:oid "1.3.6.1.4.1.9.12.3.1.9.72.3";
  }

  smiv2:alias "cevN5KM1600" {
    smiv2:oid "1.3.6.1.4.1.9.12.3.1.9.72.4";
  }

  smiv2:alias "cevN5kC5020FixedModule" {
    smiv2:oid "1.3.6.1.4.1.9.12.3.1.9.72.5";
  }

  smiv2:alias "cevN5kC5010FixedModule" {
    smiv2:oid "1.3.6.1.4.1.9.12.3.1.9.72.6";
  }

  smiv2:alias "cevN5kFabricExtenderConnection" {
    smiv2:oid "1.3.6.1.4.1.9.12.3.1.9.72.7";
  }

  smiv2:alias "cevN5kC5548pFixedModule" {
    smiv2:oid "1.3.6.1.4.1.9.12.3.1.9.72.10";
  }

  smiv2:alias "cevN5KN55M16P" {
    smiv2:oid "1.3.6.1.4.1.9.12.3.1.9.72.11";
  }

  smiv2:alias "cevN5KN55M8P8FP" {
    smiv2:oid "1.3.6.1.4.1.9.12.3.1.9.72.12";
  }

  smiv2:alias "cevN5KN55M16UP" {
    smiv2:oid "1.3.6.1.4.1.9.12.3.1.9.72.13";
  }

  smiv2:alias "cevN5KN55DL2" {
    smiv2:oid "1.3.6.1.4.1.9.12.3.1.9.72.14";
  }

  smiv2:alias "cevN5KN55D160L3" {
    smiv2:oid "1.3.6.1.4.1.9.12.3.1.9.72.15";
  }

  smiv2:alias "cevN5KN55M160L3" {
    smiv2:oid "1.3.6.1.4.1.9.12.3.1.9.72.16";
  }

  smiv2:alias "cevN5KC5596UpFixedModule" {
    smiv2:oid "1.3.6.1.4.1.9.12.3.1.9.72.17";
  }

  smiv2:alias "cevN5KN55M16FP" {
    smiv2:oid "1.3.6.1.4.1.9.12.3.1.9.72.18";
  }

  smiv2:alias "cevN5kC5548UPFixedModule" {
    smiv2:oid "1.3.6.1.4.1.9.12.3.1.9.72.19";
  }

  smiv2:alias "cevN5KN55M160L3V2" {
    smiv2:oid "1.3.6.1.4.1.9.12.3.1.9.72.20";
  }

  smiv2:alias "cevN5KN55D160L3V2" {
    smiv2:oid "1.3.6.1.4.1.9.12.3.1.9.72.21";
  }

  smiv2:alias "cevN5kC5596TFAFixedModule" {
    smiv2:oid "1.3.6.1.4.1.9.12.3.1.9.72.22";
  }

  smiv2:alias "cevN5KN55M12T" {
    smiv2:oid "1.3.6.1.4.1.9.12.3.1.9.72.23";
  }

  smiv2:alias "cevN5KN55M4Q" {
    smiv2:oid "1.3.6.1.4.1.9.12.3.1.9.72.24";
  }

  smiv2:alias "cevN5KN56M24UP2Q" {
    smiv2:oid "1.3.6.1.4.1.9.12.3.1.9.72.25";
  }

  smiv2:alias "cevN5KC56128PFixedModule" {
    smiv2:oid "1.3.6.1.4.1.9.12.3.1.9.72.26";
  }

  smiv2:alias "cevN5KC5672UPM6Q" {
    smiv2:oid "1.3.6.1.4.1.9.12.3.1.9.72.27";
  }

  smiv2:alias "cevN5KC5672UPFixedModule" {
    smiv2:oid "1.3.6.1.4.1.9.12.3.1.9.72.28";
  }

  smiv2:alias "cevN5KN5696M12Q" {
    smiv2:oid "1.3.6.1.4.1.9.12.3.1.9.72.35";
  }

  smiv2:alias "cevN5KN5696M4C" {
    smiv2:oid "1.3.6.1.4.1.9.12.3.1.9.72.36";
  }

  smiv2:alias "cevN5KN5696M20UP" {
    smiv2:oid "1.3.6.1.4.1.9.12.3.1.9.72.37";
  }

  smiv2:alias "cevN5KC5696QFixedModule" {
    smiv2:oid "1.3.6.1.4.1.9.12.3.1.9.72.38";
  }

  smiv2:alias "cevModuleASA5505Type" {
    smiv2:oid "1.3.6.1.4.1.9.12.3.1.9.73";
  }

  smiv2:alias "cevMASA5505IsmSscIps5K9" {
    smiv2:oid "1.3.6.1.4.1.9.12.3.1.9.73.1";
  }

  smiv2:alias "cevModuleASR9KType" {
    smiv2:oid "1.3.6.1.4.1.9.12.3.1.9.74";
  }

  smiv2:alias "cevModuleA9K8x10GEB" {
    smiv2:oid "1.3.6.1.4.1.9.12.3.1.9.74.1";
  }

  smiv2:alias "cevModuleA9K8x10GEE" {
    smiv2:oid "1.3.6.1.4.1.9.12.3.1.9.74.2";
  }

  smiv2:alias "cevModuleA9K4x10GEB" {
    smiv2:oid "1.3.6.1.4.1.9.12.3.1.9.74.3";
  }

  smiv2:alias "cevModuleA9K4x10GEE" {
    smiv2:oid "1.3.6.1.4.1.9.12.3.1.9.74.4";
  }

  smiv2:alias "cevModuleA9K40x1GEB" {
    smiv2:oid "1.3.6.1.4.1.9.12.3.1.9.74.5";
  }

  smiv2:alias "cevModuleA9K40x1GEE" {
    smiv2:oid "1.3.6.1.4.1.9.12.3.1.9.74.6";
  }

  smiv2:alias "cevModuleA9KRSP" {
    smiv2:oid "1.3.6.1.4.1.9.12.3.1.9.74.7";
  }

  smiv2:alias "cevModuleA9KRSP4G" {
    smiv2:oid "1.3.6.1.4.1.9.12.3.1.9.74.8";
  }

  smiv2:alias "cevModuleASR9KHost" {
    smiv2:oid "1.3.6.1.4.1.9.12.3.1.9.74.9";
  }

  smiv2:alias "cevModuleA9KServiceAcceleratorModule" {
    smiv2:oid "1.3.6.1.4.1.9.12.3.1.9.74.24";
  }

  smiv2:alias "cevModuleA9KRsp440Se" {
    smiv2:oid "1.3.6.1.4.1.9.12.3.1.9.74.25";
  }

  smiv2:alias "cevModuleA9KRsp440Tr" {
    smiv2:oid "1.3.6.1.4.1.9.12.3.1.9.74.26";
  }

  smiv2:alias "cevModuleA9K1X100GeSe" {
    smiv2:oid "1.3.6.1.4.1.9.12.3.1.9.74.27";
  }

  smiv2:alias "cevModuleA9K1X100GeTr" {
    smiv2:oid "1.3.6.1.4.1.9.12.3.1.9.74.28";
  }

  smiv2:alias "cevModuleA9K36X10GeSe" {
    smiv2:oid "1.3.6.1.4.1.9.12.3.1.9.74.29";
  }

  smiv2:alias "cevModuleA9K36X10GeTr" {
    smiv2:oid "1.3.6.1.4.1.9.12.3.1.9.74.30";
  }

  smiv2:alias "cevModuleA9K2X100GeSe" {
    smiv2:oid "1.3.6.1.4.1.9.12.3.1.9.74.31";
  }

  smiv2:alias "cevModuleA9K2X100GeTr" {
    smiv2:oid "1.3.6.1.4.1.9.12.3.1.9.74.32";
  }

  smiv2:alias "cevModuleA9K24X10GeSe" {
    smiv2:oid "1.3.6.1.4.1.9.12.3.1.9.74.33";
  }

  smiv2:alias "cevModuleA9K24X10GeTr" {
    smiv2:oid "1.3.6.1.4.1.9.12.3.1.9.74.34";
  }

  smiv2:alias "cevModuleA9KMOD80SE" {
    smiv2:oid "1.3.6.1.4.1.9.12.3.1.9.74.35";
  }

  smiv2:alias "cevModuleA9KMOD80TR" {
    smiv2:oid "1.3.6.1.4.1.9.12.3.1.9.74.36";
  }

  smiv2:alias "cevModuleA9KMOD160SE" {
    smiv2:oid "1.3.6.1.4.1.9.12.3.1.9.74.37";
  }

  smiv2:alias "cevModuleA9KMOD160TR" {
    smiv2:oid "1.3.6.1.4.1.9.12.3.1.9.74.38";
  }

  smiv2:alias "cevModuleA9K9922RpSe" {
    smiv2:oid "1.3.6.1.4.1.9.12.3.1.9.74.39";
  }

  smiv2:alias "cevModuleA9K9922RpTr" {
    smiv2:oid "1.3.6.1.4.1.9.12.3.1.9.74.40";
  }

  smiv2:alias "cevModuleA9K9922Sfc110" {
    smiv2:oid "1.3.6.1.4.1.9.12.3.1.9.74.41";
  }

  smiv2:alias "cevModuleA9KVGenericLc" {
    smiv2:oid "1.3.6.1.4.1.9.12.3.1.9.74.42";
  }

  smiv2:alias "cevModuleA9K9912SFC110" {
    smiv2:oid "1.3.6.1.4.1.9.12.3.1.9.74.43";
  }

  smiv2:alias "cevModuleA9K9912RpTr" {
    smiv2:oid "1.3.6.1.4.1.9.12.3.1.9.74.44";
  }

  smiv2:alias "cevModuleA9K9912RpSe" {
    smiv2:oid "1.3.6.1.4.1.9.12.3.1.9.74.45";
  }

  smiv2:alias "cevModuleA9KMODULEv" {
    smiv2:oid "1.3.6.1.4.1.9.12.3.1.9.74.46";
  }

  smiv2:alias "cevModuleA9K9001Lc" {
    smiv2:oid "1.3.6.1.4.1.9.12.3.1.9.74.47";
  }

  smiv2:alias "cevModuleA9K9001Rp" {
    smiv2:oid "1.3.6.1.4.1.9.12.3.1.9.74.48";
  }

  smiv2:alias "cevModuleA9KSip7008G" {
    smiv2:oid "1.3.6.1.4.1.9.12.3.1.9.74.49";
  }

  smiv2:alias "cevModuleA9K9001LcS" {
    smiv2:oid "1.3.6.1.4.1.9.12.3.1.9.74.53";
  }

  smiv2:alias "cevModuleA9KVSM500" {
    smiv2:oid "1.3.6.1.4.1.9.12.3.1.9.74.54";
  }

  smiv2:alias "cevModuleASR14KType" {
    smiv2:oid "1.3.6.1.4.1.9.12.3.1.9.75";
  }

  smiv2:alias "cevModuleASR14K20x1GeFl" {
    smiv2:oid "1.3.6.1.4.1.9.12.3.1.9.75.1";
  }

  smiv2:alias "cevModuleASR14K42x1GE" {
    smiv2:oid "1.3.6.1.4.1.9.12.3.1.9.75.2";
  }

  smiv2:alias "cevModuleASR14K4x10GE" {
    smiv2:oid "1.3.6.1.4.1.9.12.3.1.9.75.3";
  }

  smiv2:alias "cevModuleASR14K4FabricCard" {
    smiv2:oid "1.3.6.1.4.1.9.12.3.1.9.75.4";
  }

  smiv2:alias "cevModuleASR14K8FabricCard" {
    smiv2:oid "1.3.6.1.4.1.9.12.3.1.9.75.5";
  }

  smiv2:alias "cevModuleASR14KRP" {
    smiv2:oid "1.3.6.1.4.1.9.12.3.1.9.75.6";
  }

  smiv2:alias "cevModuleASR14KFP40" {
    smiv2:oid "1.3.6.1.4.1.9.12.3.1.9.75.7";
  }

  smiv2:alias "cevModuleASR14KFPE" {
    smiv2:oid "1.3.6.1.4.1.9.12.3.1.9.75.8";
  }

  smiv2:alias "cevModuleASR14K2x10WLFL" {
    smiv2:oid "1.3.6.1.4.1.9.12.3.1.9.75.9";
  }

  smiv2:alias "cevModuleSFPPlusS" {
    smiv2:oid "1.3.6.1.4.1.9.12.3.1.9.76";
  }

  smiv2:alias "cevSFP10GLR" {
    smiv2:oid "1.3.6.1.4.1.9.12.3.1.9.76.1";
  }

  smiv2:alias "cevSFP10GLRM" {
    smiv2:oid "1.3.6.1.4.1.9.12.3.1.9.76.2";
  }

  smiv2:alias "cevSFP10GSR" {
    smiv2:oid "1.3.6.1.4.1.9.12.3.1.9.76.3";
  }

  smiv2:alias "cevSFP10GUSR" {
    smiv2:oid "1.3.6.1.4.1.9.12.3.1.9.76.4";
  }

  smiv2:alias "cevSFP10GER" {
    smiv2:oid "1.3.6.1.4.1.9.12.3.1.9.76.5";
  }

  smiv2:alias "cevSFP10GLRMSM" {
    smiv2:oid "1.3.6.1.4.1.9.12.3.1.9.76.7";
  }

  smiv2:alias "cevSFP10GZR" {
    smiv2:oid "1.3.6.1.4.1.9.12.3.1.9.76.8";
  }

  smiv2:alias "cevSFP10GCU1M" {
    smiv2:oid "1.3.6.1.4.1.9.12.3.1.9.76.9";
  }

  smiv2:alias "cevSFP10GCU3M" {
    smiv2:oid "1.3.6.1.4.1.9.12.3.1.9.76.10";
  }

  smiv2:alias "cevSFP10GCU5M" {
    smiv2:oid "1.3.6.1.4.1.9.12.3.1.9.76.11";
  }

  smiv2:alias "cevSFP10GACU7M" {
    smiv2:oid "1.3.6.1.4.1.9.12.3.1.9.76.12";
  }

  smiv2:alias "cevSFPH10GbAcu10m" {
    smiv2:oid "1.3.6.1.4.1.9.12.3.1.9.76.13";
  }

  smiv2:alias "cevSFPOe8541" {
    smiv2:oid "1.3.6.1.4.1.9.12.3.1.9.76.14";
  }

  smiv2:alias "cevSFPOe7571" {
    smiv2:oid "1.3.6.1.4.1.9.12.3.1.9.76.15";
  }

  smiv2:alias "cevSFPOe7541" {
    smiv2:oid "1.3.6.1.4.1.9.12.3.1.9.76.16";
  }

  smiv2:alias "cevSFPOe694" {
    smiv2:oid "1.3.6.1.4.1.9.12.3.1.9.76.17";
  }

  smiv2:alias "cevSFPOe594" {
    smiv2:oid "1.3.6.1.4.1.9.12.3.1.9.76.18";
  }

  smiv2:alias "cevSFPOe294" {
    smiv2:oid "1.3.6.1.4.1.9.12.3.1.9.76.19";
  }

  smiv2:alias "cevSFPDwdmSfp10g3190" {
    smiv2:oid "1.3.6.1.4.1.9.12.3.1.9.76.20";
  }

  smiv2:alias "cevSFPDwdmSfp10g3112" {
    smiv2:oid "1.3.6.1.4.1.9.12.3.1.9.76.21";
  }

  smiv2:alias "cevSFPDwdmSfp10g3033" {
    smiv2:oid "1.3.6.1.4.1.9.12.3.1.9.76.22";
  }

  smiv2:alias "cevSFPDwdmSfp10g3582" {
    smiv2:oid "1.3.6.1.4.1.9.12.3.1.9.76.23";
  }

  smiv2:alias "cevSFPDwdmSfp10g3504" {
    smiv2:oid "1.3.6.1.4.1.9.12.3.1.9.76.24";
  }

  smiv2:alias "cevSFPDwdmSfp10g3425" {
    smiv2:oid "1.3.6.1.4.1.9.12.3.1.9.76.25";
  }

  smiv2:alias "cevSFPDwdmSfp10g3347" {
    smiv2:oid "1.3.6.1.4.1.9.12.3.1.9.76.26";
  }

  smiv2:alias "cevSFPDwdmSfp10g3268" {
    smiv2:oid "1.3.6.1.4.1.9.12.3.1.9.76.27";
  }

  smiv2:alias "cevSFPDwdmSfp10g3977" {
    smiv2:oid "1.3.6.1.4.1.9.12.3.1.9.76.28";
  }

  smiv2:alias "cevSFPDwdmSfp10g3898" {
    smiv2:oid "1.3.6.1.4.1.9.12.3.1.9.76.29";
  }

  smiv2:alias "cevSFPDwdmSfp10g3819" {
    smiv2:oid "1.3.6.1.4.1.9.12.3.1.9.76.30";
  }

  smiv2:alias "cevSFPDwdmSfp10g3740" {
    smiv2:oid "1.3.6.1.4.1.9.12.3.1.9.76.31";
  }

  smiv2:alias "cevSFPDwdmSfp10g3661" {
    smiv2:oid "1.3.6.1.4.1.9.12.3.1.9.76.32";
  }

  smiv2:alias "cevSFPDwdmSfp10g4373" {
    smiv2:oid "1.3.6.1.4.1.9.12.3.1.9.76.33";
  }

  smiv2:alias "cevSFPDwdmSfp10g4294" {
    smiv2:oid "1.3.6.1.4.1.9.12.3.1.9.76.34";
  }

  smiv2:alias "cevSFPDwdmSfp10g4214" {
    smiv2:oid "1.3.6.1.4.1.9.12.3.1.9.76.35";
  }

  smiv2:alias "cevSFPDwdmSfp10g4135" {
    smiv2:oid "1.3.6.1.4.1.9.12.3.1.9.76.36";
  }

  smiv2:alias "cevSFPDwdmSfp10g4056" {
    smiv2:oid "1.3.6.1.4.1.9.12.3.1.9.76.37";
  }

  smiv2:alias "cevSFPDwdmSfp10g4772" {
    smiv2:oid "1.3.6.1.4.1.9.12.3.1.9.76.38";
  }

  smiv2:alias "cevSFPDwdmSfp10g4692" {
    smiv2:oid "1.3.6.1.4.1.9.12.3.1.9.76.39";
  }

  smiv2:alias "cevSFPDwdmSfp10g4612" {
    smiv2:oid "1.3.6.1.4.1.9.12.3.1.9.76.40";
  }

  smiv2:alias "cevSFPDwdmSfp10g4532" {
    smiv2:oid "1.3.6.1.4.1.9.12.3.1.9.76.41";
  }

  smiv2:alias "cevSFPDwdmSfp10g5172" {
    smiv2:oid "1.3.6.1.4.1.9.12.3.1.9.76.42";
  }

  smiv2:alias "cevSFPDwdmSfp10g5092" {
    smiv2:oid "1.3.6.1.4.1.9.12.3.1.9.76.43";
  }

  smiv2:alias "cevSFPDwdmSfp10g5012" {
    smiv2:oid "1.3.6.1.4.1.9.12.3.1.9.76.44";
  }

  smiv2:alias "cevSFPDwdmSfp10g4932" {
    smiv2:oid "1.3.6.1.4.1.9.12.3.1.9.76.45";
  }

  smiv2:alias "cevSFPDwdmSfp10g4851" {
    smiv2:oid "1.3.6.1.4.1.9.12.3.1.9.76.46";
  }

  smiv2:alias "cevSFPDwdmSfp10g5575" {
    smiv2:oid "1.3.6.1.4.1.9.12.3.1.9.76.47";
  }

  smiv2:alias "cevSFPDwdmSfp10g5494" {
    smiv2:oid "1.3.6.1.4.1.9.12.3.1.9.76.48";
  }

  smiv2:alias "cevSFPDwdmSfp10g5413" {
    smiv2:oid "1.3.6.1.4.1.9.12.3.1.9.76.49";
  }

  smiv2:alias "cevSFPDwdmSfp10g5333" {
    smiv2:oid "1.3.6.1.4.1.9.12.3.1.9.76.50";
  }

  smiv2:alias "cevSFPDwdmSfp10g5252" {
    smiv2:oid "1.3.6.1.4.1.9.12.3.1.9.76.51";
  }

  smiv2:alias "cevSFPDwdmSfp10g5979" {
    smiv2:oid "1.3.6.1.4.1.9.12.3.1.9.76.52";
  }

  smiv2:alias "cevSFPDwdmSfp10g5898" {
    smiv2:oid "1.3.6.1.4.1.9.12.3.1.9.76.53";
  }

  smiv2:alias "cevSFPDwdmSfp10g5817" {
    smiv2:oid "1.3.6.1.4.1.9.12.3.1.9.76.54";
  }

  smiv2:alias "cevSFPDwdmSfp10g5736" {
    smiv2:oid "1.3.6.1.4.1.9.12.3.1.9.76.55";
  }

  smiv2:alias "cevSFPDwdmSfp10g5655" {
    smiv2:oid "1.3.6.1.4.1.9.12.3.1.9.76.56";
  }

  smiv2:alias "cevSFPDwdmSfp10g6061" {
    smiv2:oid "1.3.6.1.4.1.9.12.3.1.9.76.57";
  }

  smiv2:alias "cevSFPDwdmSfp10g6141" {
    smiv2:oid "1.3.6.1.4.1.9.12.3.1.9.76.58";
  }

  smiv2:alias "cevSFPDwdmSfp10g4453" {
    smiv2:oid "1.3.6.1.4.1.9.12.3.1.9.76.59";
  }

  smiv2:alias "cevSFPFET10G" {
    smiv2:oid "1.3.6.1.4.1.9.12.3.1.9.76.60";
  }

  smiv2:alias "cevSFPSC10GTDwdmC" {
    smiv2:oid "1.3.6.1.4.1.9.12.3.1.9.76.61";
  }

  smiv2:alias "cevSFPSC10GSR" {
    smiv2:oid "1.3.6.1.4.1.9.12.3.1.9.76.62";
  }

  smiv2:alias "cevSFPSC10GER" {
    smiv2:oid "1.3.6.1.4.1.9.12.3.1.9.76.63";
  }

  smiv2:alias "cevSFPSC10GLR" {
    smiv2:oid "1.3.6.1.4.1.9.12.3.1.9.76.64";
  }

  smiv2:alias "cevSFPSC10GZR" {
    smiv2:oid "1.3.6.1.4.1.9.12.3.1.9.76.65";
  }

  smiv2:alias "cevSFPSE10GLR" {
    smiv2:oid "1.3.6.1.4.1.9.12.3.1.9.76.66";
  }

  smiv2:alias "cevSFPSC10G303" {
    smiv2:oid "1.3.6.1.4.1.9.12.3.1.9.76.67";
  }

  smiv2:alias "cevSFPSC10G311" {
    smiv2:oid "1.3.6.1.4.1.9.12.3.1.9.76.68";
  }

  smiv2:alias "cevSFPSC10G319" {
    smiv2:oid "1.3.6.1.4.1.9.12.3.1.9.76.69";
  }

  smiv2:alias "cevSFPSC10G326" {
    smiv2:oid "1.3.6.1.4.1.9.12.3.1.9.76.70";
  }

  smiv2:alias "cevSFPSC10G334" {
    smiv2:oid "1.3.6.1.4.1.9.12.3.1.9.76.71";
  }

  smiv2:alias "cevSFPSC10G342" {
    smiv2:oid "1.3.6.1.4.1.9.12.3.1.9.76.72";
  }

  smiv2:alias "cevSFPSC10G350" {
    smiv2:oid "1.3.6.1.4.1.9.12.3.1.9.76.73";
  }

  smiv2:alias "cevSFPSC10G358" {
    smiv2:oid "1.3.6.1.4.1.9.12.3.1.9.76.74";
  }

  smiv2:alias "cevSFPSC10G366" {
    smiv2:oid "1.3.6.1.4.1.9.12.3.1.9.76.75";
  }

  smiv2:alias "cevSFPSC10G374" {
    smiv2:oid "1.3.6.1.4.1.9.12.3.1.9.76.76";
  }

  smiv2:alias "cevSFPSC10G381" {
    smiv2:oid "1.3.6.1.4.1.9.12.3.1.9.76.77";
  }

  smiv2:alias "cevSFPSC10G389" {
    smiv2:oid "1.3.6.1.4.1.9.12.3.1.9.76.78";
  }

  smiv2:alias "cevSFPSC10G397" {
    smiv2:oid "1.3.6.1.4.1.9.12.3.1.9.76.79";
  }

  smiv2:alias "cevSFPSC10G405" {
    smiv2:oid "1.3.6.1.4.1.9.12.3.1.9.76.80";
  }

  smiv2:alias "cevSFPSC10G415" {
    smiv2:oid "1.3.6.1.4.1.9.12.3.1.9.76.81";
  }

  smiv2:alias "cevSFPSC10G421" {
    smiv2:oid "1.3.6.1.4.1.9.12.3.1.9.76.82";
  }

  smiv2:alias "cevSFPSC10G429" {
    smiv2:oid "1.3.6.1.4.1.9.12.3.1.9.76.83";
  }

  smiv2:alias "cevSFPSC10G437" {
    smiv2:oid "1.3.6.1.4.1.9.12.3.1.9.76.84";
  }

  smiv2:alias "cevSFPSC10G445" {
    smiv2:oid "1.3.6.1.4.1.9.12.3.1.9.76.85";
  }

  smiv2:alias "cevSFPSC10G453" {
    smiv2:oid "1.3.6.1.4.1.9.12.3.1.9.76.86";
  }

  smiv2:alias "cevSFPSC10G461" {
    smiv2:oid "1.3.6.1.4.1.9.12.3.1.9.76.87";
  }

  smiv2:alias "cevSFPSC10G469" {
    smiv2:oid "1.3.6.1.4.1.9.12.3.1.9.76.88";
  }

  smiv2:alias "cevSFPSC10G477" {
    smiv2:oid "1.3.6.1.4.1.9.12.3.1.9.76.89";
  }

  smiv2:alias "cevSFPSC10G485" {
    smiv2:oid "1.3.6.1.4.1.9.12.3.1.9.76.90";
  }

  smiv2:alias "cevSFPSC10G493" {
    smiv2:oid "1.3.6.1.4.1.9.12.3.1.9.76.91";
  }

  smiv2:alias "cevSFPSC10G501" {
    smiv2:oid "1.3.6.1.4.1.9.12.3.1.9.76.92";
  }

  smiv2:alias "cevSFPSC10G509" {
    smiv2:oid "1.3.6.1.4.1.9.12.3.1.9.76.93";
  }

  smiv2:alias "cevSFPSC10G517" {
    smiv2:oid "1.3.6.1.4.1.9.12.3.1.9.76.94";
  }

  smiv2:alias "cevSFPSC10G525" {
    smiv2:oid "1.3.6.1.4.1.9.12.3.1.9.76.95";
  }

  smiv2:alias "cevSFPSC10G533" {
    smiv2:oid "1.3.6.1.4.1.9.12.3.1.9.76.96";
  }

  smiv2:alias "cevSFPSC10G541" {
    smiv2:oid "1.3.6.1.4.1.9.12.3.1.9.76.97";
  }

  smiv2:alias "cevSFPSC10G549" {
    smiv2:oid "1.3.6.1.4.1.9.12.3.1.9.76.98";
  }

  smiv2:alias "cevSFPSC10G557" {
    smiv2:oid "1.3.6.1.4.1.9.12.3.1.9.76.99";
  }

  smiv2:alias "cevSFPSC10G565" {
    smiv2:oid "1.3.6.1.4.1.9.12.3.1.9.76.100";
  }

  smiv2:alias "cevSFPSC10G573" {
    smiv2:oid "1.3.6.1.4.1.9.12.3.1.9.76.101";
  }

  smiv2:alias "cevSFPSC10G581" {
    smiv2:oid "1.3.6.1.4.1.9.12.3.1.9.76.102";
  }

  smiv2:alias "cevSFPSC10G589" {
    smiv2:oid "1.3.6.1.4.1.9.12.3.1.9.76.103";
  }

  smiv2:alias "cevSFPSC10G597" {
    smiv2:oid "1.3.6.1.4.1.9.12.3.1.9.76.104";
  }

  smiv2:alias "cevSFPSC10G606" {
    smiv2:oid "1.3.6.1.4.1.9.12.3.1.9.76.105";
  }

  smiv2:alias "cevSFPSC10G614" {
    smiv2:oid "1.3.6.1.4.1.9.12.3.1.9.76.106";
  }

  smiv2:alias "cevSFPPONSSI2GI1" {
    smiv2:oid "1.3.6.1.4.1.9.12.3.1.9.76.114";
  }

  smiv2:alias "cevSFPPONSSC10GEP618" {
    smiv2:oid "1.3.6.1.4.1.9.12.3.1.9.76.115";
  }

  smiv2:alias "cevSFPPONSSC10GEP614" {
    smiv2:oid "1.3.6.1.4.1.9.12.3.1.9.76.116";
  }

  smiv2:alias "cevSFPPONSSC10GEP610" {
    smiv2:oid "1.3.6.1.4.1.9.12.3.1.9.76.117";
  }

  smiv2:alias "cevSFPPONSSC10GEP606" {
    smiv2:oid "1.3.6.1.4.1.9.12.3.1.9.76.118";
  }

  smiv2:alias "cevSFPPONSSC10GEP602" {
    smiv2:oid "1.3.6.1.4.1.9.12.3.1.9.76.119";
  }

  smiv2:alias "cevSFPPONSSC10GEP597" {
    smiv2:oid "1.3.6.1.4.1.9.12.3.1.9.76.120";
  }

  smiv2:alias "cevSFPPONSSC10GEP593" {
    smiv2:oid "1.3.6.1.4.1.9.12.3.1.9.76.121";
  }

  smiv2:alias "cevSFPPONSSC10GEP589" {
    smiv2:oid "1.3.6.1.4.1.9.12.3.1.9.76.122";
  }

  smiv2:alias "cevSFPPONSSC10GEP585" {
    smiv2:oid "1.3.6.1.4.1.9.12.3.1.9.76.123";
  }

  smiv2:alias "cevSFPPONSSC10GEP581" {
    smiv2:oid "1.3.6.1.4.1.9.12.3.1.9.76.124";
  }

  smiv2:alias "cevSFPPONSSC10GEP577" {
    smiv2:oid "1.3.6.1.4.1.9.12.3.1.9.76.125";
  }

  smiv2:alias "cevSFPPONSSC10GEP573" {
    smiv2:oid "1.3.6.1.4.1.9.12.3.1.9.76.126";
  }

  smiv2:alias "cevSFPPONSSC10GEP569" {
    smiv2:oid "1.3.6.1.4.1.9.12.3.1.9.76.127";
  }

  smiv2:alias "cevSFPPONSSC10GEP565" {
    smiv2:oid "1.3.6.1.4.1.9.12.3.1.9.76.128";
  }

  smiv2:alias "cevSFPPONSSC10GEP561" {
    smiv2:oid "1.3.6.1.4.1.9.12.3.1.9.76.129";
  }

  smiv2:alias "cevSFPPONSSC10GEP557" {
    smiv2:oid "1.3.6.1.4.1.9.12.3.1.9.76.130";
  }

  smiv2:alias "cevSFPPONSSC10GEP553" {
    smiv2:oid "1.3.6.1.4.1.9.12.3.1.9.76.131";
  }

  smiv2:alias "cevSFPPONSSC10GEP549" {
    smiv2:oid "1.3.6.1.4.1.9.12.3.1.9.76.132";
  }

  smiv2:alias "cevSFPPONSSC10GEP545" {
    smiv2:oid "1.3.6.1.4.1.9.12.3.1.9.76.133";
  }

  smiv2:alias "cevSFPPONSSC10GEP541" {
    smiv2:oid "1.3.6.1.4.1.9.12.3.1.9.76.134";
  }

  smiv2:alias "cevSFPPONSSC10GEP537" {
    smiv2:oid "1.3.6.1.4.1.9.12.3.1.9.76.135";
  }

  smiv2:alias "cevSFPPONSSC10GEP533" {
    smiv2:oid "1.3.6.1.4.1.9.12.3.1.9.76.136";
  }

  smiv2:alias "cevSFPPONSSC10GEP529" {
    smiv2:oid "1.3.6.1.4.1.9.12.3.1.9.76.137";
  }

  smiv2:alias "cevSFPPONSSC10GEP525" {
    smiv2:oid "1.3.6.1.4.1.9.12.3.1.9.76.138";
  }

  smiv2:alias "cevSFPPONSSC10GEP521" {
    smiv2:oid "1.3.6.1.4.1.9.12.3.1.9.76.139";
  }

  smiv2:alias "cevSFPPONSSC10GEP517" {
    smiv2:oid "1.3.6.1.4.1.9.12.3.1.9.76.140";
  }

  smiv2:alias "cevSFPPONSSC10GEP513" {
    smiv2:oid "1.3.6.1.4.1.9.12.3.1.9.76.141";
  }

  smiv2:alias "cevSFPPONSSC10GEP509" {
    smiv2:oid "1.3.6.1.4.1.9.12.3.1.9.76.142";
  }

  smiv2:alias "cevSFPPONSSC10GEP505" {
    smiv2:oid "1.3.6.1.4.1.9.12.3.1.9.76.143";
  }

  smiv2:alias "cevSFPPONSSC10GEP501" {
    smiv2:oid "1.3.6.1.4.1.9.12.3.1.9.76.144";
  }

  smiv2:alias "cevSFPPONSSC10GEP497" {
    smiv2:oid "1.3.6.1.4.1.9.12.3.1.9.76.145";
  }

  smiv2:alias "cevSFPPONSSC10GEP493" {
    smiv2:oid "1.3.6.1.4.1.9.12.3.1.9.76.146";
  }

  smiv2:alias "cevSFPPONSSC10GEP489" {
    smiv2:oid "1.3.6.1.4.1.9.12.3.1.9.76.147";
  }

  smiv2:alias "cevSFPPONSSC10GEP485" {
    smiv2:oid "1.3.6.1.4.1.9.12.3.1.9.76.148";
  }

  smiv2:alias "cevSFPPONSSC10GEP481" {
    smiv2:oid "1.3.6.1.4.1.9.12.3.1.9.76.149";
  }

  smiv2:alias "cevSFPPONSSC10GEP477" {
    smiv2:oid "1.3.6.1.4.1.9.12.3.1.9.76.150";
  }

  smiv2:alias "cevSFPPONSSC10GEP473" {
    smiv2:oid "1.3.6.1.4.1.9.12.3.1.9.76.151";
  }

  smiv2:alias "cevSFPPONSSC10GEP469" {
    smiv2:oid "1.3.6.1.4.1.9.12.3.1.9.76.152";
  }

  smiv2:alias "cevSFPPONSSC10GEP465" {
    smiv2:oid "1.3.6.1.4.1.9.12.3.1.9.76.153";
  }

  smiv2:alias "cevSFPPONSSC10GEP461" {
    smiv2:oid "1.3.6.1.4.1.9.12.3.1.9.76.154";
  }

  smiv2:alias "cevSFPPONSSC10GEP457" {
    smiv2:oid "1.3.6.1.4.1.9.12.3.1.9.76.155";
  }

  smiv2:alias "cevSFPPONSSC10GEP453" {
    smiv2:oid "1.3.6.1.4.1.9.12.3.1.9.76.156";
  }

  smiv2:alias "cevSFPPONSSC10GEP449" {
    smiv2:oid "1.3.6.1.4.1.9.12.3.1.9.76.157";
  }

  smiv2:alias "cevSFPPONSSC10GEP445" {
    smiv2:oid "1.3.6.1.4.1.9.12.3.1.9.76.158";
  }

  smiv2:alias "cevSFPPONSSC10GEP441" {
    smiv2:oid "1.3.6.1.4.1.9.12.3.1.9.76.159";
  }

  smiv2:alias "cevSFPPONSSC10GEP437" {
    smiv2:oid "1.3.6.1.4.1.9.12.3.1.9.76.160";
  }

  smiv2:alias "cevSFPPONSSC10GEP433" {
    smiv2:oid "1.3.6.1.4.1.9.12.3.1.9.76.161";
  }

  smiv2:alias "cevSFPPONSSC10GEP429" {
    smiv2:oid "1.3.6.1.4.1.9.12.3.1.9.76.162";
  }

  smiv2:alias "cevSFPPONSSC10GEP425" {
    smiv2:oid "1.3.6.1.4.1.9.12.3.1.9.76.163";
  }

  smiv2:alias "cevSFPPONSSC10GEP421" {
    smiv2:oid "1.3.6.1.4.1.9.12.3.1.9.76.164";
  }

  smiv2:alias "cevSFPPONSSC10GEP417" {
    smiv2:oid "1.3.6.1.4.1.9.12.3.1.9.76.165";
  }

  smiv2:alias "cevSFPPONSSC10GEP413" {
    smiv2:oid "1.3.6.1.4.1.9.12.3.1.9.76.166";
  }

  smiv2:alias "cevSFPPONSSC10GEP409" {
    smiv2:oid "1.3.6.1.4.1.9.12.3.1.9.76.167";
  }

  smiv2:alias "cevSFPPONSSC10GEP405" {
    smiv2:oid "1.3.6.1.4.1.9.12.3.1.9.76.168";
  }

  smiv2:alias "cevSFPPONSSC10GEP401" {
    smiv2:oid "1.3.6.1.4.1.9.12.3.1.9.76.169";
  }

  smiv2:alias "cevSFPPONSSC10GEP397" {
    smiv2:oid "1.3.6.1.4.1.9.12.3.1.9.76.170";
  }

  smiv2:alias "cevSFPPONSSC10GEP393" {
    smiv2:oid "1.3.6.1.4.1.9.12.3.1.9.76.171";
  }

  smiv2:alias "cevSFPPONSSC10GEP389" {
    smiv2:oid "1.3.6.1.4.1.9.12.3.1.9.76.172";
  }

  smiv2:alias "cevSFPPONSSC10GEP385" {
    smiv2:oid "1.3.6.1.4.1.9.12.3.1.9.76.173";
  }

  smiv2:alias "cevSFPPONSSC10GEP381" {
    smiv2:oid "1.3.6.1.4.1.9.12.3.1.9.76.174";
  }

  smiv2:alias "cevSFPPONSSC10GEP377" {
    smiv2:oid "1.3.6.1.4.1.9.12.3.1.9.76.175";
  }

  smiv2:alias "cevSFPPONSSC10GEP374" {
    smiv2:oid "1.3.6.1.4.1.9.12.3.1.9.76.176";
  }

  smiv2:alias "cevSFPPONSSC10GEP370" {
    smiv2:oid "1.3.6.1.4.1.9.12.3.1.9.76.177";
  }

  smiv2:alias "cevSFPPONSSC10GEP366" {
    smiv2:oid "1.3.6.1.4.1.9.12.3.1.9.76.178";
  }

  smiv2:alias "cevSFPPONSSC10GEP362" {
    smiv2:oid "1.3.6.1.4.1.9.12.3.1.9.76.179";
  }

  smiv2:alias "cevSFPPONSSC10GEP358" {
    smiv2:oid "1.3.6.1.4.1.9.12.3.1.9.76.180";
  }

  smiv2:alias "cevSFPPONSSC10GEP354" {
    smiv2:oid "1.3.6.1.4.1.9.12.3.1.9.76.181";
  }

  smiv2:alias "cevSFPPONSSC10GEP350" {
    smiv2:oid "1.3.6.1.4.1.9.12.3.1.9.76.182";
  }

  smiv2:alias "cevSFPPONSSC10GEP346" {
    smiv2:oid "1.3.6.1.4.1.9.12.3.1.9.76.183";
  }

  smiv2:alias "cevSFPPONSSC10GEP342" {
    smiv2:oid "1.3.6.1.4.1.9.12.3.1.9.76.184";
  }

  smiv2:alias "cevSFPPONSSC10GEP338" {
    smiv2:oid "1.3.6.1.4.1.9.12.3.1.9.76.185";
  }

  smiv2:alias "cevSFPPONSSC10GEP334" {
    smiv2:oid "1.3.6.1.4.1.9.12.3.1.9.76.186";
  }

  smiv2:alias "cevSFPPONSSC10GEP330" {
    smiv2:oid "1.3.6.1.4.1.9.12.3.1.9.76.187";
  }

  smiv2:alias "cevSFPPONSSC10GEP326" {
    smiv2:oid "1.3.6.1.4.1.9.12.3.1.9.76.188";
  }

  smiv2:alias "cevSFPPONSSC10GEP322" {
    smiv2:oid "1.3.6.1.4.1.9.12.3.1.9.76.189";
  }

  smiv2:alias "cevSFPPONSSC10GEP319" {
    smiv2:oid "1.3.6.1.4.1.9.12.3.1.9.76.190";
  }

  smiv2:alias "cevSFPPONSSC10GEP315" {
    smiv2:oid "1.3.6.1.4.1.9.12.3.1.9.76.191";
  }

  smiv2:alias "cevSFPPONSSC10GEP311" {
    smiv2:oid "1.3.6.1.4.1.9.12.3.1.9.76.192";
  }

  smiv2:alias "cevSFPPONSSC10GEP307" {
    smiv2:oid "1.3.6.1.4.1.9.12.3.1.9.76.193";
  }

  smiv2:alias "cevSFPPONSSC10GEP303" {
    smiv2:oid "1.3.6.1.4.1.9.12.3.1.9.76.194";
  }

  smiv2:alias "cevSFPPONSSC10GC" {
    smiv2:oid "1.3.6.1.4.1.9.12.3.1.9.76.195";
  }

  smiv2:alias "cevSFPCwdmSfp10g1610" {
    smiv2:oid "1.3.6.1.4.1.9.12.3.1.9.76.196";
  }

  smiv2:alias "cevSFPCwdmSfp10g1590" {
    smiv2:oid "1.3.6.1.4.1.9.12.3.1.9.76.197";
  }

  smiv2:alias "cevSFPCwdmSfp10g1570" {
    smiv2:oid "1.3.6.1.4.1.9.12.3.1.9.76.198";
  }

  smiv2:alias "cevSFPCwdmSfp10g1550" {
    smiv2:oid "1.3.6.1.4.1.9.12.3.1.9.76.199";
  }

  smiv2:alias "cevSFPCwdmSfp10g1530" {
    smiv2:oid "1.3.6.1.4.1.9.12.3.1.9.76.200";
  }

  smiv2:alias "cevSFPCwdmSfp10g1510" {
    smiv2:oid "1.3.6.1.4.1.9.12.3.1.9.76.201";
  }

  smiv2:alias "cevSFPCwdmSfp10g1490" {
    smiv2:oid "1.3.6.1.4.1.9.12.3.1.9.76.202";
  }

  smiv2:alias "cevSFPCwdmSfp10g1470" {
    smiv2:oid "1.3.6.1.4.1.9.12.3.1.9.76.203";
  }

  smiv2:alias "cevSFPQsfpPlusLROpticsMod" {
    smiv2:oid "1.3.6.1.4.1.9.12.3.1.9.76.208";
  }

  smiv2:alias "cevSFPQsfpPlusSROpticsMod" {
    smiv2:oid "1.3.6.1.4.1.9.12.3.1.9.76.209";
  }

  smiv2:alias "cevSFPPDWDMSFP10GC" {
    smiv2:oid "1.3.6.1.4.1.9.12.3.1.9.76.213";
  }

  smiv2:alias "cevDirectAttachCable10Gs" {
    smiv2:oid "1.3.6.1.4.1.9.12.3.1.9.77";
  }

  smiv2:alias "cevSFPH10GBCU1M" {
    smiv2:oid "1.3.6.1.4.1.9.12.3.1.9.77.1";
  }

  smiv2:alias "cevSFPH10GBCU5M" {
    smiv2:oid "1.3.6.1.4.1.9.12.3.1.9.77.2";
  }

  smiv2:alias "cevSFPH10GBCU3M" {
    smiv2:oid "1.3.6.1.4.1.9.12.3.1.9.77.3";
  }

  smiv2:alias "cevSFPH10GBCU7M" {
    smiv2:oid "1.3.6.1.4.1.9.12.3.1.9.77.4";
  }

  smiv2:alias "cevSFPH10GBACU1M" {
    smiv2:oid "1.3.6.1.4.1.9.12.3.1.9.77.9";
  }

  smiv2:alias "cevSFPH10GBACU3M" {
    smiv2:oid "1.3.6.1.4.1.9.12.3.1.9.77.10";
  }

  smiv2:alias "cevSFPH10GBACU5M" {
    smiv2:oid "1.3.6.1.4.1.9.12.3.1.9.77.11";
  }

  smiv2:alias "cevSFPH10GBACU15M" {
    smiv2:oid "1.3.6.1.4.1.9.12.3.1.9.77.12";
  }

  smiv2:alias "cevSFPH10GBACU10M" {
    smiv2:oid "1.3.6.1.4.1.9.12.3.1.9.77.13";
  }

  smiv2:alias "cevSFPH10GBACU7M" {
    smiv2:oid "1.3.6.1.4.1.9.12.3.1.9.77.14";
  }

  smiv2:alias "cevSFPH10GBCU150CM" {
    smiv2:oid "1.3.6.1.4.1.9.12.3.1.9.77.15";
  }

  smiv2:alias "cevSFPH10GBCU250CM" {
    smiv2:oid "1.3.6.1.4.1.9.12.3.1.9.77.16";
  }

  smiv2:alias "cevSFP10GAOC1M" {
    smiv2:oid "1.3.6.1.4.1.9.12.3.1.9.77.17";
  }

  smiv2:alias "cevSFP10GAOC2M" {
    smiv2:oid "1.3.6.1.4.1.9.12.3.1.9.77.18";
  }

  smiv2:alias "cevSFP10GAOC3M" {
    smiv2:oid "1.3.6.1.4.1.9.12.3.1.9.77.19";
  }

  smiv2:alias "cevSFP10GAOC5M" {
    smiv2:oid "1.3.6.1.4.1.9.12.3.1.9.77.20";
  }

  smiv2:alias "cevSFP10GAOC7M" {
    smiv2:oid "1.3.6.1.4.1.9.12.3.1.9.77.21";
  }

  smiv2:alias "cevSFP10GAOC10M" {
    smiv2:oid "1.3.6.1.4.1.9.12.3.1.9.77.22";
  }

  smiv2:alias "cevSFPH10GBCU200CM" {
    smiv2:oid "1.3.6.1.4.1.9.12.3.1.9.77.23";
  }

  smiv2:alias "cevSFPH10GBAOC1M" {
    smiv2:oid "1.3.6.1.4.1.9.12.3.1.9.77.24";
  }

  smiv2:alias "cevSFPH10GBAOC2M" {
    smiv2:oid "1.3.6.1.4.1.9.12.3.1.9.77.25";
  }

  smiv2:alias "cevSFPH10GBAOC3M" {
    smiv2:oid "1.3.6.1.4.1.9.12.3.1.9.77.26";
  }

  smiv2:alias "cevSFPH10GBAOC5M" {
    smiv2:oid "1.3.6.1.4.1.9.12.3.1.9.77.27";
  }

  smiv2:alias "cevSFPH10GBAOC7M" {
    smiv2:oid "1.3.6.1.4.1.9.12.3.1.9.77.28";
  }

  smiv2:alias "cevSFPH10GBAOC10M" {
    smiv2:oid "1.3.6.1.4.1.9.12.3.1.9.77.29";
  }

  smiv2:alias "cevModuleN2KType" {
    smiv2:oid "1.3.6.1.4.1.9.12.3.1.9.78";
  }

  smiv2:alias "cevN2kC2148T1GEFixedModule" {
    smiv2:oid "1.3.6.1.4.1.9.12.3.1.9.78.1";
  }

  smiv2:alias "cevN2kC2232PP10GEFixedModule" {
    smiv2:oid "1.3.6.1.4.1.9.12.3.1.9.78.2";
  }

  smiv2:alias "cevN2kC2248TP1GEFixedModule" {
    smiv2:oid "1.3.6.1.4.1.9.12.3.1.9.78.3";
  }

  smiv2:alias "cevN2kC2224TP1GEFixedModule" {
    smiv2:oid "1.3.6.1.4.1.9.12.3.1.9.78.4";
  }

  smiv2:alias "cevN2kC2232TT10GEFixedModule" {
    smiv2:oid "1.3.6.1.4.1.9.12.3.1.9.78.5";
  }

  smiv2:alias "cevN2kC2232TP10GEFixedModule" {
    smiv2:oid "1.3.6.1.4.1.9.12.3.1.9.78.6";
  }

  smiv2:alias "cevN2kC2248TT1GEFixedModule" {
    smiv2:oid "1.3.6.1.4.1.9.12.3.1.9.78.7";
  }

  smiv2:alias "cevN2kB22HPPFixedModule" {
    smiv2:oid "1.3.6.1.4.1.9.12.3.1.9.78.9";
  }

  smiv2:alias "cevN2kM2800P" {
    smiv2:oid "1.3.6.1.4.1.9.12.3.1.9.78.10";
  }

  smiv2:alias "cevN2kC2232TM10GEFixedModule" {
    smiv2:oid "1.3.6.1.4.1.9.12.3.1.9.78.11";
  }

  smiv2:alias "cevN2kC2232TME10GEFixedModule" {
    smiv2:oid "1.3.6.1.4.1.9.12.3.1.9.78.12";
  }

  smiv2:alias "cevN2kC2248PQ10GEFixedModule" {
    smiv2:oid "1.3.6.1.4.1.9.12.3.1.9.78.13";
  }

  smiv2:alias "cevN2kB22DELLPFixedModule" {
    smiv2:oid "1.3.6.1.4.1.9.12.3.1.9.78.14";
  }

  smiv2:alias "cevN2kB22FTSPFixedModule" {
    smiv2:oid "1.3.6.1.4.1.9.12.3.1.9.78.15";
  }

  smiv2:alias "cevN2kB22IBMPFixedModule" {
    smiv2:oid "1.3.6.1.4.1.9.12.3.1.9.78.16";
  }

  smiv2:alias "cevN2KC2348UPQFixedModule" {
    smiv2:oid "1.3.6.1.4.1.9.12.3.1.9.78.17";
  }

  smiv2:alias "cevN2KC2348TQFixedModule" {
    smiv2:oid "1.3.6.1.4.1.9.12.3.1.9.78.18";
  }

  smiv2:alias "cevModuleN1KVType" {
    smiv2:oid "1.3.6.1.4.1.9.12.3.1.9.79";
  }

  smiv2:alias "cevN1KVVSM" {
    smiv2:oid "1.3.6.1.4.1.9.12.3.1.9.79.1";
  }

  smiv2:alias "cevN1KVVEM" {
    smiv2:oid "1.3.6.1.4.1.9.12.3.1.9.79.2";
  }

  smiv2:alias "cevN1KVVXLANGateway" {
    smiv2:oid "1.3.6.1.4.1.9.12.3.1.9.79.3";
  }

  smiv2:alias "cevN1KVInterCloudExtender" {
    smiv2:oid "1.3.6.1.4.1.9.12.3.1.9.79.4";
  }

  smiv2:alias "cevN1KVInterCloudSwitch" {
    smiv2:oid "1.3.6.1.4.1.9.12.3.1.9.79.5";
  }

  smiv2:alias "cevModuleUCSType" {
    smiv2:oid "1.3.6.1.4.1.9.12.3.1.9.80";
  }

  smiv2:alias "cevUCSN10S6100FixedModule" {
    smiv2:oid "1.3.6.1.4.1.9.12.3.1.9.80.1";
  }

  smiv2:alias "cevUCSN10E0080" {
    smiv2:oid "1.3.6.1.4.1.9.12.3.1.9.80.2";
  }

  smiv2:alias "cevUCSN10E0440" {
    smiv2:oid "1.3.6.1.4.1.9.12.3.1.9.80.3";
  }

  smiv2:alias "cevUCSN10E0600" {
    smiv2:oid "1.3.6.1.4.1.9.12.3.1.9.80.4";
  }

  smiv2:alias "cevUCSFIE16UP" {
    smiv2:oid "1.3.6.1.4.1.9.12.3.1.9.80.7";
  }

  smiv2:alias "cevUCSFI6248UPFixedModule" {
    smiv2:oid "1.3.6.1.4.1.9.12.3.1.9.80.8";
  }

  smiv2:alias "cevUCSFI6296UPFixedModule" {
    smiv2:oid "1.3.6.1.4.1.9.12.3.1.9.80.9";
  }

  smiv2:alias "cevUCSFIDL2" {
    smiv2:oid "1.3.6.1.4.1.9.12.3.1.9.80.10";
  }

  smiv2:alias "cevUCSFIM6324FixedModule" {
    smiv2:oid "1.3.6.1.4.1.9.12.3.1.9.80.171";
  }

  smiv2:alias "cevModuleNexus1010Type" {
    smiv2:oid "1.3.6.1.4.1.9.12.3.1.9.81";
  }

  smiv2:alias "cevNexus1010VSM" {
    smiv2:oid "1.3.6.1.4.1.9.12.3.1.9.81.1";
  }

  smiv2:alias "cevNexusN1KVSANam" {
    smiv2:oid "1.3.6.1.4.1.9.12.3.1.9.81.2";
  }

  smiv2:alias "cevModuleMxeType" {
    smiv2:oid "1.3.6.1.4.1.9.12.3.1.9.82";
  }

  smiv2:alias "cevMxeNpm" {
    smiv2:oid "1.3.6.1.4.1.9.12.3.1.9.82.1";
  }

  smiv2:alias "cevMxeMpm" {
    smiv2:oid "1.3.6.1.4.1.9.12.3.1.9.82.2";
  }

  smiv2:alias "cevMxe5600ShelfManager" {
    smiv2:oid "1.3.6.1.4.1.9.12.3.1.9.82.3";
  }

  smiv2:alias "cevModuleASA5585Type" {
    smiv2:oid "1.3.6.1.4.1.9.12.3.1.9.83";
  }

  smiv2:alias "cevASA5585Ssp10" {
    smiv2:oid "1.3.6.1.4.1.9.12.3.1.9.83.1";
  }

  smiv2:alias "cevASA5585Ssp20" {
    smiv2:oid "1.3.6.1.4.1.9.12.3.1.9.83.2";
  }

  smiv2:alias "cevASA5585Ssp40" {
    smiv2:oid "1.3.6.1.4.1.9.12.3.1.9.83.3";
  }

  smiv2:alias "cevASA5585Ssp60" {
    smiv2:oid "1.3.6.1.4.1.9.12.3.1.9.83.4";
  }

  smiv2:alias "cevASA5585IsmSspIps10" {
    smiv2:oid "1.3.6.1.4.1.9.12.3.1.9.83.5";
  }

  smiv2:alias "cevASA5585IsmSspIps20" {
    smiv2:oid "1.3.6.1.4.1.9.12.3.1.9.83.6";
  }

  smiv2:alias "cevASA5585IsmSspIps40" {
    smiv2:oid "1.3.6.1.4.1.9.12.3.1.9.83.7";
  }

  smiv2:alias "cevASA5585IsmSspIps60" {
    smiv2:oid "1.3.6.1.4.1.9.12.3.1.9.83.8";
  }

  smiv2:alias "cevMASA5585Ssp10K7" {
    smiv2:oid "1.3.6.1.4.1.9.12.3.1.9.83.9";
  }

  smiv2:alias "cevMASA5585Ssp20K7" {
    smiv2:oid "1.3.6.1.4.1.9.12.3.1.9.83.10";
  }

  smiv2:alias "cevMASA5585Ssp40K7" {
    smiv2:oid "1.3.6.1.4.1.9.12.3.1.9.83.11";
  }

  smiv2:alias "cevMASA5585Ssp60K7" {
    smiv2:oid "1.3.6.1.4.1.9.12.3.1.9.83.12";
  }

  smiv2:alias "cevMASA5585IsmSspIps10K7" {
    smiv2:oid "1.3.6.1.4.1.9.12.3.1.9.83.13";
  }

  smiv2:alias "cevMASA5585IsmSspIps20K7" {
    smiv2:oid "1.3.6.1.4.1.9.12.3.1.9.83.14";
  }

  smiv2:alias "cevMASA5585IsmSspIps40K7" {
    smiv2:oid "1.3.6.1.4.1.9.12.3.1.9.83.15";
  }

  smiv2:alias "cevMASA5585IsmSspIps60K7" {
    smiv2:oid "1.3.6.1.4.1.9.12.3.1.9.83.16";
  }

  smiv2:alias "cevMASA5585Nm8x10GE" {
    smiv2:oid "1.3.6.1.4.1.9.12.3.1.9.83.17";
  }

  smiv2:alias "cevMASA5585Nm4x10GE" {
    smiv2:oid "1.3.6.1.4.1.9.12.3.1.9.83.18";
  }

  smiv2:alias "cevMASA5585Nm20x1GE" {
    smiv2:oid "1.3.6.1.4.1.9.12.3.1.9.83.19";
  }

  smiv2:alias "cevMASA5585CxSsp40" {
    smiv2:oid "1.3.6.1.4.1.9.12.3.1.9.83.20";
  }

  smiv2:alias "cevMASA5585CxSsp60" {
    smiv2:oid "1.3.6.1.4.1.9.12.3.1.9.83.21";
  }

  smiv2:alias "cevMASA5585CxSsp10" {
    smiv2:oid "1.3.6.1.4.1.9.12.3.1.9.83.22";
  }

  smiv2:alias "cevMASA5585CxSsp20" {
    smiv2:oid "1.3.6.1.4.1.9.12.3.1.9.83.23";
  }

  smiv2:alias "cevMASA5585SFRSsp10" {
    smiv2:oid "1.3.6.1.4.1.9.12.3.1.9.83.24";
  }

  smiv2:alias "cevMASA5585SFRSsp20" {
    smiv2:oid "1.3.6.1.4.1.9.12.3.1.9.83.25";
  }

  smiv2:alias "cevMASA5585SFRSsp40" {
    smiv2:oid "1.3.6.1.4.1.9.12.3.1.9.83.26";
  }

  smiv2:alias "cevMASA5585SFRSsp60" {
    smiv2:oid "1.3.6.1.4.1.9.12.3.1.9.83.27";
  }

  smiv2:alias "cevModuleCFPs" {
    smiv2:oid "1.3.6.1.4.1.9.12.3.1.9.84";
  }

  smiv2:alias "cevCFP100GLR4" {
    smiv2:oid "1.3.6.1.4.1.9.12.3.1.9.84.1";
  }

  smiv2:alias "cevCFP40GLR4" {
    smiv2:oid "1.3.6.1.4.1.9.12.3.1.9.84.2";
  }

  smiv2:alias "cevCFP40GSR4" {
    smiv2:oid "1.3.6.1.4.1.9.12.3.1.9.84.3";
  }

  smiv2:alias "cevCFP40GFR" {
    smiv2:oid "1.3.6.1.4.1.9.12.3.1.9.84.4";
  }

  smiv2:alias "cevCFP100GSR10" {
    smiv2:oid "1.3.6.1.4.1.9.12.3.1.9.84.5";
  }

  smiv2:alias "cevCFP100GER4" {
    smiv2:oid "1.3.6.1.4.1.9.12.3.1.9.84.6";
  }

  smiv2:alias "cevCFPUnknown" {
    smiv2:oid "1.3.6.1.4.1.9.12.3.1.9.84.7";
  }

  smiv2:alias "cevModuleN3KType" {
    smiv2:oid "1.3.6.1.4.1.9.12.3.1.9.85";
  }

  smiv2:alias "cevN3kC3064PQfixedModule" {
    smiv2:oid "1.3.6.1.4.1.9.12.3.1.9.85.1";
  }

  smiv2:alias "cevN3kC3064PQ10GEFixedModule" {
    smiv2:oid "1.3.6.1.4.1.9.12.3.1.9.85.2";
  }

  smiv2:alias "cevN3kC3048TP1GEFixedModule" {
    smiv2:oid "1.3.6.1.4.1.9.12.3.1.9.85.3";
  }

  smiv2:alias "cevN3kC3016Q40GEFixedModule" {
    smiv2:oid "1.3.6.1.4.1.9.12.3.1.9.85.4";
  }

  smiv2:alias "cevN3kC3064Pq10GXFixedModule" {
    smiv2:oid "1.3.6.1.4.1.9.12.3.1.9.85.5";
  }

  smiv2:alias "cevN3kC3548P10GFixedModule" {
    smiv2:oid "1.3.6.1.4.1.9.12.3.1.9.85.6";
  }

  smiv2:alias "cevN3kC3064TQ10GTFixedModule" {
    smiv2:oid "1.3.6.1.4.1.9.12.3.1.9.85.7";
  }

  smiv2:alias "cevN3KC3172" {
    smiv2:oid "1.3.6.1.4.1.9.12.3.1.9.85.8";
  }

  smiv2:alias "cevN3KC3172TQ" {
    smiv2:oid "1.3.6.1.4.1.9.12.3.1.9.85.9";
  }

  smiv2:alias "cevN3KC3132TQ" {
    smiv2:oid "1.3.6.1.4.1.9.12.3.1.9.85.10";
  }

  smiv2:alias "cevN3KC3132CR" {
    smiv2:oid "1.3.6.1.4.1.9.12.3.1.9.85.11";
  }

  smiv2:alias "cevN3kC3164Q40GEFixedModule" {
    smiv2:oid "1.3.6.1.4.1.9.12.3.1.9.85.12";
  }

  smiv2:alias "cevModuleCGSType" {
    smiv2:oid "1.3.6.1.4.1.9.12.3.1.9.86";
  }

  smiv2:alias "cevModuleCGS252016S8PC" {
    smiv2:oid "1.3.6.1.4.1.9.12.3.1.9.86.1";
  }

  smiv2:alias "cevModuleCGS252024TC" {
    smiv2:oid "1.3.6.1.4.1.9.12.3.1.9.86.2";
  }

  smiv2:alias "cevModuleASR900Type" {
    smiv2:oid "1.3.6.1.4.1.9.12.3.1.9.87";
  }

  smiv2:alias "cevModuleASR903RSP1A" {
    smiv2:oid "1.3.6.1.4.1.9.12.3.1.9.87.1";
  }

  smiv2:alias "cevModuleASR900ESP" {
    smiv2:oid "1.3.6.1.4.1.9.12.3.1.9.87.2";
  }

  smiv2:alias "cevModuleASR903RSP1B" {
    smiv2:oid "1.3.6.1.4.1.9.12.3.1.9.87.3";
  }

  smiv2:alias "cevModuleASR903RSP2A64G" {
    smiv2:oid "1.3.6.1.4.1.9.12.3.1.9.87.4";
  }

  smiv2:alias "cevModuleASR903RSP2A128G" {
    smiv2:oid "1.3.6.1.4.1.9.12.3.1.9.87.5";
  }

  smiv2:alias "cevModuleASR92024SZIM" {
    smiv2:oid "1.3.6.1.4.1.9.12.3.1.9.87.6";
  }

  smiv2:alias "cevModuleASR92024SZM" {
    smiv2:oid "1.3.6.1.4.1.9.12.3.1.9.87.7";
  }

  smiv2:alias "cevModuleASR92024TZM" {
    smiv2:oid "1.3.6.1.4.1.9.12.3.1.9.87.8";
  }

  smiv2:alias "cevModuleASR92012CZA" {
    smiv2:oid "1.3.6.1.4.1.9.12.3.1.9.87.9";
  }

  smiv2:alias "cevModuleASR92012CZD" {
    smiv2:oid "1.3.6.1.4.1.9.12.3.1.9.87.10";
  }

  smiv2:alias "cevModuleASR9204SZA" {
    smiv2:oid "1.3.6.1.4.1.9.12.3.1.9.87.11";
  }

  smiv2:alias "cevModuleASR9204SZD" {
    smiv2:oid "1.3.6.1.4.1.9.12.3.1.9.87.12";
  }

  smiv2:alias "cevModuleASR92010SZPA" {
    smiv2:oid "1.3.6.1.4.1.9.12.3.1.9.87.13";
  }

  smiv2:alias "cevModuleASR92010SZPD" {
    smiv2:oid "1.3.6.1.4.1.9.12.3.1.9.87.14";
  }

  smiv2:alias "cevModuleASR5000Type" {
    smiv2:oid "1.3.6.1.4.1.9.12.3.1.9.88";
  }

  smiv2:alias "cevModuleASR5K01100eK9" {
    smiv2:oid "1.3.6.1.4.1.9.12.3.1.9.88.1";
  }

  smiv2:alias "cevModuleASR5K0110gMmK9" {
    smiv2:oid "1.3.6.1.4.1.9.12.3.1.9.88.2";
  }

  smiv2:alias "cevModuleASR5K0110gSmK9" {
    smiv2:oid "1.3.6.1.4.1.9.12.3.1.9.88.3";
  }

  smiv2:alias "cevModuleASR5K011G2LxK9" {
    smiv2:oid "1.3.6.1.4.1.9.12.3.1.9.88.4";
  }

  smiv2:alias "cevModuleASR5K011G2SxK9" {
    smiv2:oid "1.3.6.1.4.1.9.12.3.1.9.88.5";
  }

  smiv2:alias "cevModuleASR5K011G2TK9" {
    smiv2:oid "1.3.6.1.4.1.9.12.3.1.9.88.6";
  }

  smiv2:alias "cevModuleASR5K011GELxK9" {
    smiv2:oid "1.3.6.1.4.1.9.12.3.1.9.88.7";
  }

  smiv2:alias "cevModuleASR5K011GESxK9" {
    smiv2:oid "1.3.6.1.4.1.9.12.3.1.9.88.8";
  }

  smiv2:alias "cevModuleASR5K011GETK9" {
    smiv2:oid "1.3.6.1.4.1.9.12.3.1.9.88.9";
  }

  smiv2:alias "cevModuleASR5K01OC3MmK9" {
    smiv2:oid "1.3.6.1.4.1.9.12.3.1.9.88.10";
  }

  smiv2:alias "cevModuleASR5K01OC3SmK9" {
    smiv2:oid "1.3.6.1.4.1.9.12.3.1.9.88.11";
  }

  smiv2:alias "cevModuleASR5K041GeLxK9" {
    smiv2:oid "1.3.6.1.4.1.9.12.3.1.9.88.12";
  }

  smiv2:alias "cevModuleASR5K041GeSxK9" {
    smiv2:oid "1.3.6.1.4.1.9.12.3.1.9.88.13";
  }

  smiv2:alias "cevModuleASR5K041GeTK9" {
    smiv2:oid "1.3.6.1.4.1.9.12.3.1.9.88.14";
  }

  smiv2:alias "cevModuleASR5K042GeLxK9" {
    smiv2:oid "1.3.6.1.4.1.9.12.3.1.9.88.15";
  }

  smiv2:alias "cevModuleASR5K042GeSxK9" {
    smiv2:oid "1.3.6.1.4.1.9.12.3.1.9.88.16";
  }

  smiv2:alias "cevModuleASR5K042GeTK9" {
    smiv2:oid "1.3.6.1.4.1.9.12.3.1.9.88.17";
  }

  smiv2:alias "cevModuleASR5K08100eK9" {
    smiv2:oid "1.3.6.1.4.1.9.12.3.1.9.88.18";
  }

  smiv2:alias "cevModuleASR5K4OC3CMmK9" {
    smiv2:oid "1.3.6.1.4.1.9.12.3.1.9.88.19";
  }

  smiv2:alias "cevModuleASR5K4OC3CSmK9" {
    smiv2:oid "1.3.6.1.4.1.9.12.3.1.9.88.20";
  }

  smiv2:alias "cevModuleASR5KC1OC3MnK9" {
    smiv2:oid "1.3.6.1.4.1.9.12.3.1.9.88.21";
  }

  smiv2:alias "cevModuleASR5KC1OC3SmK9" {
    smiv2:oid "1.3.6.1.4.1.9.12.3.1.9.88.22";
  }

  smiv2:alias "cevModuleASR5KC4OC3MmK9" {
    smiv2:oid "1.3.6.1.4.1.9.12.3.1.9.88.23";
  }

  smiv2:alias "cevModuleASR5KC4OC3SmK9" {
    smiv2:oid "1.3.6.1.4.1.9.12.3.1.9.88.24";
  }

  smiv2:alias "cevModuleASR5KppcK9" {
    smiv2:oid "1.3.6.1.4.1.9.12.3.1.9.88.25";
  }

  smiv2:alias "cevModuleASR5Kpsc16gK9" {
    smiv2:oid "1.3.6.1.4.1.9.12.3.1.9.88.26";
  }

  smiv2:alias "cevModuleASR5Kpsc32gK9" {
    smiv2:oid "1.3.6.1.4.1.9.12.3.1.9.88.27";
  }

  smiv2:alias "cevModuleASR5Kpsc64gK9" {
    smiv2:oid "1.3.6.1.4.1.9.12.3.1.9.88.28";
  }

  smiv2:alias "cevModuleASR5KpscK9" {
    smiv2:oid "1.3.6.1.4.1.9.12.3.1.9.88.29";
  }

  smiv2:alias "cevModuleASR5KsmcK9" {
    smiv2:oid "1.3.6.1.4.1.9.12.3.1.9.88.30";
  }

  smiv2:alias "cevModuleASR5KSps3BncK9" {
    smiv2:oid "1.3.6.1.4.1.9.12.3.1.9.88.31";
  }

  smiv2:alias "cevModuleASR5KSps33pnK9" {
    smiv2:oid "1.3.6.1.4.1.9.12.3.1.9.88.32";
  }

  smiv2:alias "cevModuleASR5KSpioBncK9" {
    smiv2:oid "1.3.6.1.4.1.9.12.3.1.9.88.33";
  }

  smiv2:alias "cevModuleASR5KSpio3pnK9" {
    smiv2:oid "1.3.6.1.4.1.9.12.3.1.9.88.34";
  }

  smiv2:alias "cevModuleASR5KRccK9" {
    smiv2:oid "1.3.6.1.4.1.9.12.3.1.9.88.35";
  }

  smiv2:alias "cevModuleASR5500Type" {
    smiv2:oid "1.3.6.1.4.1.9.12.3.1.9.89";
  }

  smiv2:alias "cevModuleASR55DPC" {
    smiv2:oid "1.3.6.1.4.1.9.12.3.1.9.89.1";
  }

  smiv2:alias "cevModuleASR55FSC" {
    smiv2:oid "1.3.6.1.4.1.9.12.3.1.9.89.2";
  }

  smiv2:alias "cevModuleASR55MIO10GL10" {
    smiv2:oid "1.3.6.1.4.1.9.12.3.1.9.89.3";
  }

  smiv2:alias "cevModuleASR55MIO10GL20" {
    smiv2:oid "1.3.6.1.4.1.9.12.3.1.9.89.4";
  }

  smiv2:alias "cevModuleASR55MIO10GS10" {
    smiv2:oid "1.3.6.1.4.1.9.12.3.1.9.89.5";
  }

  smiv2:alias "cevModuleASR55MIO10GS20" {
    smiv2:oid "1.3.6.1.4.1.9.12.3.1.9.89.6";
  }

  smiv2:alias "cevModuleASR55MIOBASE" {
    smiv2:oid "1.3.6.1.4.1.9.12.3.1.9.89.7";
  }

  smiv2:alias "cevModuleASR55SSC" {
    smiv2:oid "1.3.6.1.4.1.9.12.3.1.9.89.8";
  }

  smiv2:alias "cevModuleVSR1000Type" {
    smiv2:oid "1.3.6.1.4.1.9.12.3.1.9.90";
  }

  smiv2:alias "cevModuleVSR1000RP" {
    smiv2:oid "1.3.6.1.4.1.9.12.3.1.9.90.1";
  }

  smiv2:alias "cevModuleVSR1000ESP" {
    smiv2:oid "1.3.6.1.4.1.9.12.3.1.9.90.2";
  }

  smiv2:alias "cevModuleCgrType" {
    smiv2:oid "1.3.6.1.4.1.9.12.3.1.9.91";
  }

  smiv2:alias "cevModuleCGMPlc" {
    smiv2:oid "1.3.6.1.4.1.9.12.3.1.9.91.18";
  }

  smiv2:alias "cevModuleCGMGe" {
    smiv2:oid "1.3.6.1.4.1.9.12.3.1.9.91.19";
  }

  smiv2:alias "cevModuleCGM3gEVDOSE" {
    smiv2:oid "1.3.6.1.4.1.9.12.3.1.9.91.21";
  }

  smiv2:alias "cevModuleCGM3gEVDOVE" {
    smiv2:oid "1.3.6.1.4.1.9.12.3.1.9.91.22";
  }

  smiv2:alias "cevModuleCGM3gHSPAAE" {
    smiv2:oid "1.3.6.1.4.1.9.12.3.1.9.91.23";
  }

  smiv2:alias "cevModuleCGM3gHSPAGE" {
    smiv2:oid "1.3.6.1.4.1.9.12.3.1.9.91.24";
  }

  smiv2:alias "cevModuleCGM3gHspaAbGE" {
    smiv2:oid "1.3.6.1.4.1.9.12.3.1.9.91.25";
  }

  smiv2:alias "cevModuleISR4400Type" {
    smiv2:oid "1.3.6.1.4.1.9.12.3.1.9.92";
  }

  smiv2:alias "cevModuleISR4441RP" {
    smiv2:oid "1.3.6.1.4.1.9.12.3.1.9.92.1";
  }

  smiv2:alias "cevModuleISR4442RP" {
    smiv2:oid "1.3.6.1.4.1.9.12.3.1.9.92.2";
  }

  smiv2:alias "cevModuleISR4451RP" {
    smiv2:oid "1.3.6.1.4.1.9.12.3.1.9.92.3";
  }

  smiv2:alias "cevModuleISR4452RP" {
    smiv2:oid "1.3.6.1.4.1.9.12.3.1.9.92.4";
  }

  smiv2:alias "cevModuleISR4400RP" {
    smiv2:oid "1.3.6.1.4.1.9.12.3.1.9.92.5";
  }

  smiv2:alias "cevModuleISR4441FP" {
    smiv2:oid "1.3.6.1.4.1.9.12.3.1.9.92.6";
  }

  smiv2:alias "cevModuleISR4442FP" {
    smiv2:oid "1.3.6.1.4.1.9.12.3.1.9.92.7";
  }

  smiv2:alias "cevModuleISR4451FP" {
    smiv2:oid "1.3.6.1.4.1.9.12.3.1.9.92.8";
  }

  smiv2:alias "cevModuleISR4452FP" {
    smiv2:oid "1.3.6.1.4.1.9.12.3.1.9.92.9";
  }

  smiv2:alias "cevModuleISR4400FP" {
    smiv2:oid "1.3.6.1.4.1.9.12.3.1.9.92.10";
  }

  smiv2:alias "cevModuleISR4400NIM" {
    smiv2:oid "1.3.6.1.4.1.9.12.3.1.9.92.11";
  }

  smiv2:alias "cevModuleISR4441NIM" {
    smiv2:oid "1.3.6.1.4.1.9.12.3.1.9.92.12";
  }

  smiv2:alias "cevModuleISR4442NIM" {
    smiv2:oid "1.3.6.1.4.1.9.12.3.1.9.92.13";
  }

  smiv2:alias "cevModuleISR4451NIM" {
    smiv2:oid "1.3.6.1.4.1.9.12.3.1.9.92.14";
  }

  smiv2:alias "cevModuleISR4452NIM" {
    smiv2:oid "1.3.6.1.4.1.9.12.3.1.9.92.15";
  }

  smiv2:alias "cevModuleISR4400ESM" {
    smiv2:oid "1.3.6.1.4.1.9.12.3.1.9.92.16";
  }

  smiv2:alias "cevModuleISR4441ESM" {
    smiv2:oid "1.3.6.1.4.1.9.12.3.1.9.92.17";
  }

  smiv2:alias "cevModuleISR4442ESM" {
    smiv2:oid "1.3.6.1.4.1.9.12.3.1.9.92.18";
  }

  smiv2:alias "cevModuleISR4451ESM" {
    smiv2:oid "1.3.6.1.4.1.9.12.3.1.9.92.19";
  }

  smiv2:alias "cevModuleISR4452ESM" {
    smiv2:oid "1.3.6.1.4.1.9.12.3.1.9.92.20";
  }

  smiv2:alias "cevModuleISR44000FP4xGE" {
    smiv2:oid "1.3.6.1.4.1.9.12.3.1.9.92.21";
  }

  smiv2:alias "cevModuleISR4400InternalPOE" {
    smiv2:oid "1.3.6.1.4.1.9.12.3.1.9.92.22";
  }

  smiv2:alias "cevModuleNGWICSerial1T" {
    smiv2:oid "1.3.6.1.4.1.9.12.3.1.9.92.43";
  }

  smiv2:alias "cevModuleNGWICSerial2T" {
    smiv2:oid "1.3.6.1.4.1.9.12.3.1.9.92.44";
  }

  smiv2:alias "cevModuleNGWICSerial4T" {
    smiv2:oid "1.3.6.1.4.1.9.12.3.1.9.92.45";
  }

  smiv2:alias "cevModuleQSFPPlusS" {
    smiv2:oid "1.3.6.1.4.1.9.12.3.1.9.93";
  }

  smiv2:alias "cevQSFP40GLR4" {
    smiv2:oid "1.3.6.1.4.1.9.12.3.1.9.93.1";
  }

  smiv2:alias "cevQSFP40GSR4" {
    smiv2:oid "1.3.6.1.4.1.9.12.3.1.9.93.2";
  }

  smiv2:alias "cevQSFP40GSMSR4" {
    smiv2:oid "1.3.6.1.4.1.9.12.3.1.9.93.3";
  }

  smiv2:alias "cevQSFP40GCR4Active" {
    smiv2:oid "1.3.6.1.4.1.9.12.3.1.9.93.4";
  }

  smiv2:alias "cevQSFP40GCR4Passive" {
    smiv2:oid "1.3.6.1.4.1.9.12.3.1.9.93.5";
  }

  smiv2:alias "cevSFPQSFP40GECSR4" {
    smiv2:oid "1.3.6.1.4.1.9.12.3.1.9.93.6";
  }

  smiv2:alias "cevSFPQSFP40GELR4" {
    smiv2:oid "1.3.6.1.4.1.9.12.3.1.9.93.7";
  }

  smiv2:alias "cevQSFP40GER4" {
    smiv2:oid "1.3.6.1.4.1.9.12.3.1.9.93.9";
  }

  smiv2:alias "cevModuleN6KType" {
    smiv2:oid "1.3.6.1.4.1.9.12.3.1.9.95";
  }

  smiv2:alias "cevN6KN6004XM20UP" {
    smiv2:oid "1.3.6.1.4.1.9.12.3.1.9.95.1";
  }

  smiv2:alias "cevN6KC6004M12Q" {
    smiv2:oid "1.3.6.1.4.1.9.12.3.1.9.95.2";
  }

  smiv2:alias "cevN6KC600496QFixedModule" {
    smiv2:oid "1.3.6.1.4.1.9.12.3.1.9.95.3";
  }

  smiv2:alias "cevN6KC6001M4Q" {
    smiv2:oid "1.3.6.1.4.1.9.12.3.1.9.95.4";
  }

  smiv2:alias "cevN6KC600164PFixedModule" {
    smiv2:oid "1.3.6.1.4.1.9.12.3.1.9.95.5";
  }

  smiv2:alias "cevN6K48P10G" {
    smiv2:oid "1.3.6.1.4.1.9.12.3.1.9.95.6";
  }

  smiv2:alias "cevN6K32Q40G" {
    smiv2:oid "1.3.6.1.4.1.9.12.3.1.9.95.7";
  }

  smiv2:alias "cevN6K24Q40G" {
    smiv2:oid "1.3.6.1.4.1.9.12.3.1.9.95.8";
  }

  smiv2:alias "cevN6KC600164TFixedModule" {
    smiv2:oid "1.3.6.1.4.1.9.12.3.1.9.95.11";
  }

  smiv2:alias "cevN6KN6002M24UP2Q" {
    smiv2:oid "1.3.6.1.4.1.9.12.3.1.9.95.12";
  }

  smiv2:alias "cevN6KC6002128PFixedModule" {
    smiv2:oid "1.3.6.1.4.1.9.12.3.1.9.95.15";
  }

  smiv2:alias "cevN6KC600172UPFixedModule" {
    smiv2:oid "1.3.6.1.4.1.9.12.3.1.9.95.16";
  }

  smiv2:alias "cevN6KN6004M12Q" {
    smiv2:oid "1.3.6.1.4.1.9.12.3.1.9.95.18";
  }

  smiv2:alias "cevN6KC6001M6Q" {
    smiv2:oid "1.3.6.1.4.1.9.12.3.1.9.95.19";
  }

  smiv2:alias "cevModuleISRType" {
    smiv2:oid "1.3.6.1.4.1.9.12.3.1.9.96";
  }

  smiv2:alias "cevModuleISRSM1T3E3" {
    smiv2:oid "1.3.6.1.4.1.9.12.3.1.9.96.1";
  }

  smiv2:alias "cevModuleISRSM6XGE" {
    smiv2:oid "1.3.6.1.4.1.9.12.3.1.9.96.2";
  }

  smiv2:alias "cevModuleISRSM1X10GE4XGE" {
    smiv2:oid "1.3.6.1.4.1.9.12.3.1.9.96.3";
  }

  smiv2:alias "cevModuleISRSmEs3x16P" {
    smiv2:oid "1.3.6.1.4.1.9.12.3.1.9.96.4";
  }

  smiv2:alias "cevModuleISRSmEs3x24P" {
    smiv2:oid "1.3.6.1.4.1.9.12.3.1.9.96.5";
  }

  smiv2:alias "cevModuleISRSmDEs3x48P" {
    smiv2:oid "1.3.6.1.4.1.9.12.3.1.9.96.6";
  }

  smiv2:alias "cevModuleN77Type" {
    smiv2:oid "1.3.6.1.4.1.9.12.3.1.9.97";
  }

  smiv2:alias "cevN77c7718Fab2" {
    smiv2:oid "1.3.6.1.4.1.9.12.3.1.9.97.1";
  }

  smiv2:alias "cevN77c7710Fab2" {
    smiv2:oid "1.3.6.1.4.1.9.12.3.1.9.97.2";
  }

  smiv2:alias "cevN77c7706Fab2" {
    smiv2:oid "1.3.6.1.4.1.9.12.3.1.9.97.3";
  }

  smiv2:alias "cevN77F248XP23E" {
    smiv2:oid "1.3.6.1.4.1.9.12.3.1.9.97.4";
  }

  smiv2:alias "cevN77SUP2E" {
    smiv2:oid "1.3.6.1.4.1.9.12.3.1.9.97.5";
  }

  smiv2:alias "cevN77F324FQ25" {
    smiv2:oid "1.3.6.1.4.1.9.12.3.1.9.97.6";
  }

  smiv2:alias "cevN77F348XP23" {
    smiv2:oid "1.3.6.1.4.1.9.12.3.1.9.97.7";
  }

  smiv2:alias "cevN77F312CK26" {
    smiv2:oid "1.3.6.1.4.1.9.12.3.1.9.97.8";
  }

  smiv2:alias "cevModuleCat3KCAxType" {
    smiv2:oid "1.3.6.1.4.1.9.12.3.1.9.98";
  }

  smiv2:alias "cevModuleCat365048PQ" {
    smiv2:oid "1.3.6.1.4.1.9.12.3.1.9.98.1";
  }

  smiv2:alias "cevModuleCat365048TQ" {
    smiv2:oid "1.3.6.1.4.1.9.12.3.1.9.98.2";
  }

  smiv2:alias "cevModuleCat385024u" {
    smiv2:oid "1.3.6.1.4.1.9.12.3.1.9.98.3";
  }

  smiv2:alias "cevModuleCat385048u" {
    smiv2:oid "1.3.6.1.4.1.9.12.3.1.9.98.4";
  }

  smiv2:alias "cevModuleCat365024TD" {
    smiv2:oid "1.3.6.1.4.1.9.12.3.1.9.98.5";
  }

  smiv2:alias "cevModuleCat365048TD" {
    smiv2:oid "1.3.6.1.4.1.9.12.3.1.9.98.6";
  }

  smiv2:alias "cevModuleCat365024PD" {
    smiv2:oid "1.3.6.1.4.1.9.12.3.1.9.98.7";
  }

  smiv2:alias "cevModuleCat365048PD" {
    smiv2:oid "1.3.6.1.4.1.9.12.3.1.9.98.8";
  }

  smiv2:alias "cevModuleCat365024TS" {
    smiv2:oid "1.3.6.1.4.1.9.12.3.1.9.98.9";
  }

  smiv2:alias "cevModuleCat365048TS" {
    smiv2:oid "1.3.6.1.4.1.9.12.3.1.9.98.10";
  }

  smiv2:alias "cevModuleCat365024PS" {
    smiv2:oid "1.3.6.1.4.1.9.12.3.1.9.98.11";
  }

  smiv2:alias "cevModuleCat365048PS" {
    smiv2:oid "1.3.6.1.4.1.9.12.3.1.9.98.12";
  }

  smiv2:alias "cevModuleCat385024T" {
    smiv2:oid "1.3.6.1.4.1.9.12.3.1.9.98.13";
  }

  smiv2:alias "cevModuleCat385048T" {
    smiv2:oid "1.3.6.1.4.1.9.12.3.1.9.98.14";
  }

  smiv2:alias "cevModuleCat385024P" {
    smiv2:oid "1.3.6.1.4.1.9.12.3.1.9.98.15";
  }

  smiv2:alias "cevModuleCat385048P" {
    smiv2:oid "1.3.6.1.4.1.9.12.3.1.9.98.16";
  }

  smiv2:alias "cevModuleCat385012S" {
    smiv2:oid "1.3.6.1.4.1.9.12.3.1.9.98.17";
  }

  smiv2:alias "cevModuleCat385024S" {
    smiv2:oid "1.3.6.1.4.1.9.12.3.1.9.98.18";
  }

  smiv2:alias "cevModule57xxwlc" {
    smiv2:oid "1.3.6.1.4.1.9.12.3.1.9.99";
  }

  smiv2:alias "cevModuleCat5760wlc" {
    smiv2:oid "1.3.6.1.4.1.9.12.3.1.9.99.2";
  }

  smiv2:alias "cevModuleCat5700wlc" {
    smiv2:oid "1.3.6.1.4.1.9.12.3.1.9.99.3";
  }

  smiv2:alias "cevModuleN95KType" {
    smiv2:oid "1.3.6.1.4.1.9.12.3.1.9.100";
  }

  smiv2:alias "cevN9KSUPA" {
    smiv2:oid "1.3.6.1.4.1.9.12.3.1.9.100.1";
  }

  smiv2:alias "cevN9Kc9508FM" {
    smiv2:oid "1.3.6.1.4.1.9.12.3.1.9.100.2";
  }

  smiv2:alias "cevN9kScA" {
    smiv2:oid "1.3.6.1.4.1.9.12.3.1.9.100.3";
  }

  smiv2:alias "cevN9kX9564PX" {
    smiv2:oid "1.3.6.1.4.1.9.12.3.1.9.100.4";
  }

  smiv2:alias "cevN9kX9564TX" {
    smiv2:oid "1.3.6.1.4.1.9.12.3.1.9.100.5";
  }

  smiv2:alias "cevN9kX9636PQ" {
    smiv2:oid "1.3.6.1.4.1.9.12.3.1.9.100.6";
  }

  smiv2:alias "cevN9KX9464PX" {
    smiv2:oid "1.3.6.1.4.1.9.12.3.1.9.100.18";
  }

  smiv2:alias "cevN9KX9464TX" {
    smiv2:oid "1.3.6.1.4.1.9.12.3.1.9.100.19";
  }

  smiv2:alias "cevN9KX9432PQ" {
    smiv2:oid "1.3.6.1.4.1.9.12.3.1.9.100.20";
  }

  smiv2:alias "cevN9KX9632PC" {
    smiv2:oid "1.3.6.1.4.1.9.12.3.1.9.100.22";
  }

  smiv2:alias "cevN9KX9464TX2" {
    smiv2:oid "1.3.6.1.4.1.9.12.3.1.9.100.23";
  }

  smiv2:alias "cevN9kC9508FM2" {
    smiv2:oid "1.3.6.1.4.1.9.12.3.1.9.100.24";
  }

  smiv2:alias "cevN9kC9504FM2" {
    smiv2:oid "1.3.6.1.4.1.9.12.3.1.9.100.25";
  }

  smiv2:alias "cevModuleCPAKType" {
    smiv2:oid "1.3.6.1.4.1.9.12.3.1.9.101";
  }

  smiv2:alias "cevCPAK100GLR4" {
    smiv2:oid "1.3.6.1.4.1.9.12.3.1.9.101.1";
  }

  smiv2:alias "cevCPAK100GSR10" {
    smiv2:oid "1.3.6.1.4.1.9.12.3.1.9.101.2";
  }

  smiv2:alias "cevCPAK100GLR10" {
    smiv2:oid "1.3.6.1.4.1.9.12.3.1.9.101.3";
  }

  smiv2:alias "cevCPAK100GER4L" {
    smiv2:oid "1.3.6.1.4.1.9.12.3.1.9.101.4";
  }

  smiv2:alias "cevDirectAttachCable40Gs" {
    smiv2:oid "1.3.6.1.4.1.9.12.3.1.9.102";
  }

  smiv2:alias "cevQSFP4SFP10GCU1M" {
    smiv2:oid "1.3.6.1.4.1.9.12.3.1.9.102.1";
  }

  smiv2:alias "cevQSFP4SFP10GCU3M" {
    smiv2:oid "1.3.6.1.4.1.9.12.3.1.9.102.2";
  }

  smiv2:alias "cevQSFP4SFP10GCU5M" {
    smiv2:oid "1.3.6.1.4.1.9.12.3.1.9.102.3";
  }

  smiv2:alias "cevModuleN93KType" {
    smiv2:oid "1.3.6.1.4.1.9.12.3.1.9.103";
  }

  smiv2:alias "cevN9KM6PQ" {
    smiv2:oid "1.3.6.1.4.1.9.12.3.1.9.103.1";
  }

  smiv2:alias "cevN9KM12PQ" {
    smiv2:oid "1.3.6.1.4.1.9.12.3.1.9.103.2";
  }

  smiv2:alias "cevN9KC93128TXfixedModule" {
    smiv2:oid "1.3.6.1.4.1.9.12.3.1.9.103.3";
  }

  smiv2:alias "cevN9KC9396TXfixedModule" {
    smiv2:oid "1.3.6.1.4.1.9.12.3.1.9.103.4";
  }

  smiv2:alias "cevN9KC9396PXfixedModule" {
    smiv2:oid "1.3.6.1.4.1.9.12.3.1.9.103.5";
  }

  smiv2:alias "cevN9KC9372PXfixedModule" {
    smiv2:oid "1.3.6.1.4.1.9.12.3.1.9.103.7";
  }

  smiv2:alias "cevN9KC9372TXfixedModule" {
    smiv2:oid "1.3.6.1.4.1.9.12.3.1.9.103.8";
  }

  smiv2:alias "cevN9KC9332PQfixedModule" {
    smiv2:oid "1.3.6.1.4.1.9.12.3.1.9.103.9";
  }

  smiv2:alias "cevN9KM4PC" {
    smiv2:oid "1.3.6.1.4.1.9.12.3.1.9.103.10";
  }

  smiv2:alias "cevModuleASA5506Type" {
    smiv2:oid "1.3.6.1.4.1.9.12.3.1.9.107";
  }

  smiv2:alias "cevModuleASA5508Type" {
    smiv2:oid "1.3.6.1.4.1.9.12.3.1.9.108";
  }

  smiv2:alias "cevModuleWIMType" {
    smiv2:oid "1.3.6.1.4.1.9.12.3.1.9.110";
  }

  smiv2:alias "cevModuleWIM1T" {
    smiv2:oid "1.3.6.1.4.1.9.12.3.1.9.110.3";
  }

  smiv2:alias "cevModuleWIM3G" {
    smiv2:oid "1.3.6.1.4.1.9.12.3.1.9.110.4";
  }

  smiv2:alias "cevPort" {
    smiv2:oid "1.3.6.1.4.1.9.12.3.1.10";
  }

  smiv2:alias "cevPortUnknown" {
    smiv2:oid "1.3.6.1.4.1.9.12.3.1.10.1";
  }

  smiv2:alias "cevPortMCIEther" {
    smiv2:oid "1.3.6.1.4.1.9.12.3.1.10.2";
  }

  smiv2:alias "cevPortMCISerial" {
    smiv2:oid "1.3.6.1.4.1.9.12.3.1.10.3";
  }

  smiv2:alias "cevPortCBusSerial" {
    smiv2:oid "1.3.6.1.4.1.9.12.3.1.10.4";
  }

  smiv2:alias "cevPortFddi" {
    smiv2:oid "1.3.6.1.4.1.9.12.3.1.10.5";
  }

  smiv2:alias "cevPortFddit" {
    smiv2:oid "1.3.6.1.4.1.9.12.3.1.10.6";
  }

  smiv2:alias "cevPortCBusTR" {
    smiv2:oid "1.3.6.1.4.1.9.12.3.1.10.7";
  }

  smiv2:alias "cevPortAsync" {
    smiv2:oid "1.3.6.1.4.1.9.12.3.1.10.8";
  }

  smiv2:alias "cevPortHSSI" {
    smiv2:oid "1.3.6.1.4.1.9.12.3.1.10.9";
  }

  smiv2:alias "cevPortT1" {
    smiv2:oid "1.3.6.1.4.1.9.12.3.1.10.10";
  }

  smiv2:alias "cevPortE1" {
    smiv2:oid "1.3.6.1.4.1.9.12.3.1.10.11";
  }

  smiv2:alias "cevPortBRI" {
    smiv2:oid "1.3.6.1.4.1.9.12.3.1.10.12";
  }

  smiv2:alias "cevPortAIP" {
    smiv2:oid "1.3.6.1.4.1.9.12.3.1.10.13";
  }

  smiv2:alias "cevPortCIP" {
    smiv2:oid "1.3.6.1.4.1.9.12.3.1.10.14";
  }

  smiv2:alias "cevPortVtyAsync" {
    smiv2:oid "1.3.6.1.4.1.9.12.3.1.10.15";
  }

  smiv2:alias "cevPortFEIP" {
    smiv2:oid "1.3.6.1.4.1.9.12.3.1.10.16";
  }

  smiv2:alias "cevPortAsyncGroup" {
    smiv2:oid "1.3.6.1.4.1.9.12.3.1.10.17";
  }

  smiv2:alias "cevPortVTemplate" {
    smiv2:oid "1.3.6.1.4.1.9.12.3.1.10.18";
  }

  smiv2:alias "cevPortVAccess" {
    smiv2:oid "1.3.6.1.4.1.9.12.3.1.10.19";
  }

  smiv2:alias "cevPortT3" {
    smiv2:oid "1.3.6.1.4.1.9.12.3.1.10.20";
  }

  smiv2:alias "cevPortVGAnyLAN" {
    smiv2:oid "1.3.6.1.4.1.9.12.3.1.10.21";
  }

  smiv2:alias "cevPortLance" {
    smiv2:oid "1.3.6.1.4.1.9.12.3.1.10.22";
  }

  smiv2:alias "cevPortATMS2000" {
    smiv2:oid "1.3.6.1.4.1.9.12.3.1.10.23";
  }

  smiv2:alias "cevPortSALI25" {
    smiv2:oid "1.3.6.1.4.1.9.12.3.1.10.24";
  }

  smiv2:alias "cevPortSonicT" {
    smiv2:oid "1.3.6.1.4.1.9.12.3.1.10.25";
  }

  smiv2:alias "cevPortOC3SUNI" {
    smiv2:oid "1.3.6.1.4.1.9.12.3.1.10.26";
  }

  smiv2:alias "cevPortOC12SUNI" {
    smiv2:oid "1.3.6.1.4.1.9.12.3.1.10.27";
  }

  smiv2:alias "cevPortDS3SUNI" {
    smiv2:oid "1.3.6.1.4.1.9.12.3.1.10.28";
  }

  smiv2:alias "cevPortE3SUNI" {
    smiv2:oid "1.3.6.1.4.1.9.12.3.1.10.29";
  }

  smiv2:alias "cevPortDS3SUNIQUAD" {
    smiv2:oid "1.3.6.1.4.1.9.12.3.1.10.30";
  }

  smiv2:alias "cevPortE3SUNIQUAD" {
    smiv2:oid "1.3.6.1.4.1.9.12.3.1.10.31";
  }

  smiv2:alias "cevPortMK5025" {
    smiv2:oid "1.3.6.1.4.1.9.12.3.1.10.32";
  }

  smiv2:alias "cevPortTMS380" {
    smiv2:oid "1.3.6.1.4.1.9.12.3.1.10.33";
  }

  smiv2:alias "cevPortBSI" {
    smiv2:oid "1.3.6.1.4.1.9.12.3.1.10.34";
  }

  smiv2:alias "cevPortATMZR" {
    smiv2:oid "1.3.6.1.4.1.9.12.3.1.10.35";
  }

  smiv2:alias "cevPortHD64570" {
    smiv2:oid "1.3.6.1.4.1.9.12.3.1.10.36";
  }

  smiv2:alias "cevPortPCBus" {
    smiv2:oid "1.3.6.1.4.1.9.12.3.1.10.37";
  }

  smiv2:alias "cevPortQuiccEther" {
    smiv2:oid "1.3.6.1.4.1.9.12.3.1.10.38";
  }

  smiv2:alias "cevPortQuiccSerial" {
    smiv2:oid "1.3.6.1.4.1.9.12.3.1.10.39";
  }

  smiv2:alias "cevPortAMDP2" {
    smiv2:oid "1.3.6.1.4.1.9.12.3.1.10.40";
  }

  smiv2:alias "cevPortMIF68840" {
    smiv2:oid "1.3.6.1.4.1.9.12.3.1.10.41";
  }

  smiv2:alias "cevPortCYLEPA" {
    smiv2:oid "1.3.6.1.4.1.9.12.3.1.10.42";
  }

  smiv2:alias "cevPortS4T68360" {
    smiv2:oid "1.3.6.1.4.1.9.12.3.1.10.43";
  }

  smiv2:alias "cevPortIBM2692" {
    smiv2:oid "1.3.6.1.4.1.9.12.3.1.10.44";
  }

  smiv2:alias "cevPortMueslix" {
    smiv2:oid "1.3.6.1.4.1.9.12.3.1.10.45";
  }

  smiv2:alias "cevPortCD2430" {
    smiv2:oid "1.3.6.1.4.1.9.12.3.1.10.46";
  }

  smiv2:alias "cevPortILACC" {
    smiv2:oid "1.3.6.1.4.1.9.12.3.1.10.47";
  }

  smiv2:alias "cevPortNIC100" {
    smiv2:oid "1.3.6.1.4.1.9.12.3.1.10.48";
  }

  smiv2:alias "cevPortDCUATM" {
    smiv2:oid "1.3.6.1.4.1.9.12.3.1.10.49";
  }

  smiv2:alias "cevPortDCUATMPort" {
    smiv2:oid "1.3.6.1.4.1.9.12.3.1.10.50";
  }

  smiv2:alias "cevPortTI1570" {
    smiv2:oid "1.3.6.1.4.1.9.12.3.1.10.51";
  }

  smiv2:alias "cevPortPOS" {
    smiv2:oid "1.3.6.1.4.1.9.12.3.1.10.52";
  }

  smiv2:alias "cevPortLoopBack" {
    smiv2:oid "1.3.6.1.4.1.9.12.3.1.10.53";
  }

  smiv2:alias "cevPortLex" {
    smiv2:oid "1.3.6.1.4.1.9.12.3.1.10.54";
  }

  smiv2:alias "cevPortDialer" {
    smiv2:oid "1.3.6.1.4.1.9.12.3.1.10.55";
  }

  smiv2:alias "cevPortCIPLANAdapter" {
    smiv2:oid "1.3.6.1.4.1.9.12.3.1.10.56";
  }

  smiv2:alias "cevPortBVI" {
    smiv2:oid "1.3.6.1.4.1.9.12.3.1.10.57";
  }

  smiv2:alias "cevPortOSPFVL" {
    smiv2:oid "1.3.6.1.4.1.9.12.3.1.10.58";
  }

  smiv2:alias "cevPortRinconSwitch" {
    smiv2:oid "1.3.6.1.4.1.9.12.3.1.10.59";
  }

  smiv2:alias "cevPortSynALCATM" {
    smiv2:oid "1.3.6.1.4.1.9.12.3.1.10.60";
  }

  smiv2:alias "cevPortSynALCBIGA" {
    smiv2:oid "1.3.6.1.4.1.9.12.3.1.10.61";
  }

  smiv2:alias "cevPortSwitchTrunk" {
    smiv2:oid "1.3.6.1.4.1.9.12.3.1.10.62";
  }

  smiv2:alias "cevPortC2KATM" {
    smiv2:oid "1.3.6.1.4.1.9.12.3.1.10.63";
  }

  smiv2:alias "cevPortDec21140A" {
    smiv2:oid "1.3.6.1.4.1.9.12.3.1.10.64";
  }

  smiv2:alias "cevPortC5Ether" {
    smiv2:oid "1.3.6.1.4.1.9.12.3.1.10.65";
  }

  smiv2:alias "cevPortC5TR" {
    smiv2:oid "1.3.6.1.4.1.9.12.3.1.10.66";
  }

  smiv2:alias "cevPortEswitch" {
    smiv2:oid "1.3.6.1.4.1.9.12.3.1.10.69";
  }

  smiv2:alias "cevPortBITS" {
    smiv2:oid "1.3.6.1.4.1.9.12.3.1.10.70";
  }

  smiv2:alias "cevPortAdslCap" {
    smiv2:oid "1.3.6.1.4.1.9.12.3.1.10.71";
  }

  smiv2:alias "cevPortAdslDmt" {
    smiv2:oid "1.3.6.1.4.1.9.12.3.1.10.72";
  }

  smiv2:alias "cevPortSdsl2b1q" {
    smiv2:oid "1.3.6.1.4.1.9.12.3.1.10.73";
  }

  smiv2:alias "cevPortEscon" {
    smiv2:oid "1.3.6.1.4.1.9.12.3.1.10.74";
  }

  smiv2:alias "cevPortParallel" {
    smiv2:oid "1.3.6.1.4.1.9.12.3.1.10.75";
  }

  smiv2:alias "cevPortCipVirtual" {
    smiv2:oid "1.3.6.1.4.1.9.12.3.1.10.76";
  }

  smiv2:alias "cevPortDs3" {
    smiv2:oid "1.3.6.1.4.1.9.12.3.1.10.78";
  }

  smiv2:alias "cevPortE3" {
    smiv2:oid "1.3.6.1.4.1.9.12.3.1.10.79";
  }

  smiv2:alias "cevPortOc3" {
    smiv2:oid "1.3.6.1.4.1.9.12.3.1.10.80";
  }

  smiv2:alias "cevPortHdvDsp" {
    smiv2:oid "1.3.6.1.4.1.9.12.3.1.10.82";
  }

  smiv2:alias "cevPortAdslFlexiDmt" {
    smiv2:oid "1.3.6.1.4.1.9.12.3.1.10.83";
  }

  smiv2:alias "cevPortAdslFlexiCap" {
    smiv2:oid "1.3.6.1.4.1.9.12.3.1.10.84";
  }

  smiv2:alias "cevPortAdslDmtIsdn" {
    smiv2:oid "1.3.6.1.4.1.9.12.3.1.10.85";
  }

  smiv2:alias "cevPortRfMac" {
    smiv2:oid "1.3.6.1.4.1.9.12.3.1.10.86";
  }

  smiv2:alias "cevPortRfUs" {
    smiv2:oid "1.3.6.1.4.1.9.12.3.1.10.87";
  }

  smiv2:alias "cevPortRfDs" {
    smiv2:oid "1.3.6.1.4.1.9.12.3.1.10.88";
  }

  smiv2:alias "cevPortUbrClk" {
    smiv2:oid "1.3.6.1.4.1.9.12.3.1.10.89";
  }

  smiv2:alias "cevPortShdslTcpam" {
    smiv2:oid "1.3.6.1.4.1.9.12.3.1.10.90";
  }

  smiv2:alias "cevPortShdslTcpamOptis" {
    smiv2:oid "1.3.6.1.4.1.9.12.3.1.10.91";
  }

  smiv2:alias "cevPortGEIP" {
    smiv2:oid "1.3.6.1.4.1.9.12.3.1.10.100";
  }

  smiv2:alias "cevPortWDM" {
    smiv2:oid "1.3.6.1.4.1.9.12.3.1.10.101";
  }

  smiv2:alias "cevPortThru" {
    smiv2:oid "1.3.6.1.4.1.9.12.3.1.10.102";
  }

  smiv2:alias "cevPortFilter" {
    smiv2:oid "1.3.6.1.4.1.9.12.3.1.10.103";
  }

  smiv2:alias "cevPortWave" {
    smiv2:oid "1.3.6.1.4.1.9.12.3.1.10.104";
  }

  smiv2:alias "cevPortWavePatch" {
    smiv2:oid "1.3.6.1.4.1.9.12.3.1.10.105";
  }

  smiv2:alias "cevPortTransparent" {
    smiv2:oid "1.3.6.1.4.1.9.12.3.1.10.106";
  }

  smiv2:alias "cevPortDPT" {
    smiv2:oid "1.3.6.1.4.1.9.12.3.1.10.107";
  }

  smiv2:alias "cevPortOc12" {
    smiv2:oid "1.3.6.1.4.1.9.12.3.1.10.108";
  }

  smiv2:alias "cevPortGe" {
    smiv2:oid "1.3.6.1.4.1.9.12.3.1.10.109";
  }

  smiv2:alias "cevPortChOc12" {
    smiv2:oid "1.3.6.1.4.1.9.12.3.1.10.110";
  }

  smiv2:alias "cevPortChOc3Stm1" {
    smiv2:oid "1.3.6.1.4.1.9.12.3.1.10.111";
  }

  smiv2:alias "cevPortFilterGroup" {
    smiv2:oid "1.3.6.1.4.1.9.12.3.1.10.112";
  }

  smiv2:alias "cevPortFilterBand" {
    smiv2:oid "1.3.6.1.4.1.9.12.3.1.10.113";
  }

  smiv2:alias "cevPortChE1T1" {
    smiv2:oid "1.3.6.1.4.1.9.12.3.1.10.114";
  }

  smiv2:alias "cevPortASIMod" {
    smiv2:oid "1.3.6.1.4.1.9.12.3.1.10.115";
  }

  smiv2:alias "cevPortASIIn" {
    smiv2:oid "1.3.6.1.4.1.9.12.3.1.10.116";
  }

  smiv2:alias "cevPortASIOut" {
    smiv2:oid "1.3.6.1.4.1.9.12.3.1.10.117";
  }

  smiv2:alias "cevPortAimDsp" {
    smiv2:oid "1.3.6.1.4.1.9.12.3.1.10.118";
  }

  smiv2:alias "cevPortAtm" {
    smiv2:oid "1.3.6.1.4.1.9.12.3.1.10.119";
  }

  smiv2:alias "cevPortChSonet" {
    smiv2:oid "1.3.6.1.4.1.9.12.3.1.10.120";
  }

  smiv2:alias "cevPortChOcX" {
    smiv2:oid "1.3.6.1.4.1.9.12.3.1.10.121";
  }

  smiv2:alias "cevPortFe" {
    smiv2:oid "1.3.6.1.4.1.9.12.3.1.10.123";
  }

  smiv2:alias "cevPortDs3E3Atm" {
    smiv2:oid "1.3.6.1.4.1.9.12.3.1.10.125";
  }

  smiv2:alias "cevPortFxs" {
    smiv2:oid "1.3.6.1.4.1.9.12.3.1.10.126";
  }

  smiv2:alias "cevPortFxo" {
    smiv2:oid "1.3.6.1.4.1.9.12.3.1.10.127";
  }

  smiv2:alias "cevPortEM" {
    smiv2:oid "1.3.6.1.4.1.9.12.3.1.10.128";
  }

  smiv2:alias "cevPortOc48" {
    smiv2:oid "1.3.6.1.4.1.9.12.3.1.10.129";
  }

  smiv2:alias "cevPortOc192" {
    smiv2:oid "1.3.6.1.4.1.9.12.3.1.10.130";
  }

  smiv2:alias "cevPortFibreChannel" {
    smiv2:oid "1.3.6.1.4.1.9.12.3.1.10.131";
  }

  smiv2:alias "cevPortGigEthernet" {
    smiv2:oid "1.3.6.1.4.1.9.12.3.1.10.132";
  }

  smiv2:alias "cevPortFibreChGigEth" {
    smiv2:oid "1.3.6.1.4.1.9.12.3.1.10.133";
  }

  smiv2:alias "cevPortCatEthernet" {
    smiv2:oid "1.3.6.1.4.1.9.12.3.1.10.134";
  }

  smiv2:alias "cevPortWaveOsc" {
    smiv2:oid "1.3.6.1.4.1.9.12.3.1.10.135";
  }

  smiv2:alias "cevPortWaveEthPhy" {
    smiv2:oid "1.3.6.1.4.1.9.12.3.1.10.136";
  }

  smiv2:alias "cevPort10GigEthPhy" {
    smiv2:oid "1.3.6.1.4.1.9.12.3.1.10.137";
  }

  smiv2:alias "cevPortEsconPhy" {
    smiv2:oid "1.3.6.1.4.1.9.12.3.1.10.138";
  }

  smiv2:alias "cevPortGEFCPhy" {
    smiv2:oid "1.3.6.1.4.1.9.12.3.1.10.139";
  }

  smiv2:alias "cevPortVOAIn" {
    smiv2:oid "1.3.6.1.4.1.9.12.3.1.10.140";
  }

  smiv2:alias "cevPortVOAOut" {
    smiv2:oid "1.3.6.1.4.1.9.12.3.1.10.141";
  }

  smiv2:alias "cevPortVOAFilterIn" {
    smiv2:oid "1.3.6.1.4.1.9.12.3.1.10.142";
  }

  smiv2:alias "cevPortVOAFilterOut" {
    smiv2:oid "1.3.6.1.4.1.9.12.3.1.10.143";
  }

  smiv2:alias "cevPortVOAByPassIn" {
    smiv2:oid "1.3.6.1.4.1.9.12.3.1.10.144";
  }

  smiv2:alias "cevPortVOAByPassOut" {
    smiv2:oid "1.3.6.1.4.1.9.12.3.1.10.145";
  }

  smiv2:alias "cevPortGT96K" {
    smiv2:oid "1.3.6.1.4.1.9.12.3.1.10.146";
  }

  smiv2:alias "cevPortDSCC4" {
    smiv2:oid "1.3.6.1.4.1.9.12.3.1.10.147";
  }

  smiv2:alias "cevPortBaseTEther" {
    smiv2:oid "1.3.6.1.4.1.9.12.3.1.10.150";
  }

  smiv2:alias "cevPortGESFP" {
    smiv2:oid "1.3.6.1.4.1.9.12.3.1.10.151";
  }

  smiv2:alias "cevPortWdmSplit" {
    smiv2:oid "1.3.6.1.4.1.9.12.3.1.10.152";
  }

  smiv2:alias "cevPortWavePassThru" {
    smiv2:oid "1.3.6.1.4.1.9.12.3.1.10.153";
  }

  smiv2:alias "cevPortDspPVDM" {
    smiv2:oid "1.3.6.1.4.1.9.12.3.1.10.154";
  }

  smiv2:alias "cevPortiScsi" {
    smiv2:oid "1.3.6.1.4.1.9.12.3.1.10.155";
  }

  smiv2:alias "cevPortVic2Did" {
    smiv2:oid "1.3.6.1.4.1.9.12.3.1.10.156";
  }

  smiv2:alias "cevPortWic1Adsl" {
    smiv2:oid "1.3.6.1.4.1.9.12.3.1.10.157";
  }

  smiv2:alias "cevPortWic1Shdsl" {
    smiv2:oid "1.3.6.1.4.1.9.12.3.1.10.158";
  }

  smiv2:alias "cevPortWic1Ethernet" {
    smiv2:oid "1.3.6.1.4.1.9.12.3.1.10.159";
  }

  smiv2:alias "cevPort10GigBaseEX4" {
    smiv2:oid "1.3.6.1.4.1.9.12.3.1.10.160";
  }

  smiv2:alias "cevPort10GigBaseLR" {
    smiv2:oid "1.3.6.1.4.1.9.12.3.1.10.161";
  }

  smiv2:alias "cevPort10GigBaseSX4" {
    smiv2:oid "1.3.6.1.4.1.9.12.3.1.10.162";
  }

  smiv2:alias "cevPort10GigBaseER" {
    smiv2:oid "1.3.6.1.4.1.9.12.3.1.10.163";
  }

  smiv2:alias "cevPortGigUnsupported" {
    smiv2:oid "1.3.6.1.4.1.9.12.3.1.10.164";
  }

  smiv2:alias "cevPortGigBaseZX" {
    smiv2:oid "1.3.6.1.4.1.9.12.3.1.10.165";
  }

  smiv2:alias "cevPort10GigBaseCPX" {
    smiv2:oid "1.3.6.1.4.1.9.12.3.1.10.166";
  }

  smiv2:alias "cevPort10GigBaseLX4" {
    smiv2:oid "1.3.6.1.4.1.9.12.3.1.10.167";
  }

  smiv2:alias "cevPortGigBaseLX" {
    smiv2:oid "1.3.6.1.4.1.9.12.3.1.10.168";
  }

  smiv2:alias "cevPortGigBaseSX" {
    smiv2:oid "1.3.6.1.4.1.9.12.3.1.10.169";
  }

  smiv2:alias "cevPortGigBaseCX" {
    smiv2:oid "1.3.6.1.4.1.9.12.3.1.10.170";
  }

  smiv2:alias "cevPortGigBaseLH" {
    smiv2:oid "1.3.6.1.4.1.9.12.3.1.10.171";
  }

  smiv2:alias "cevPortGigBaseT" {
    smiv2:oid "1.3.6.1.4.1.9.12.3.1.10.172";
  }

  smiv2:alias "cevPortDslsar" {
    smiv2:oid "1.3.6.1.4.1.9.12.3.1.10.173";
  }

  smiv2:alias "cevPortAtm25" {
    smiv2:oid "1.3.6.1.4.1.9.12.3.1.10.174";
  }

  smiv2:alias "cevPortAnalogFxs" {
    smiv2:oid "1.3.6.1.4.1.9.12.3.1.10.175";
  }

  smiv2:alias "cevPortE3Atm" {
    smiv2:oid "1.3.6.1.4.1.9.12.3.1.10.176";
  }

  smiv2:alias "cevPortDs3Atm" {
    smiv2:oid "1.3.6.1.4.1.9.12.3.1.10.177";
  }

  smiv2:alias "cevPortNetworkAnalysis" {
    smiv2:oid "1.3.6.1.4.1.9.12.3.1.10.178";
  }

  smiv2:alias "cevPortIntrusionDetect" {
    smiv2:oid "1.3.6.1.4.1.9.12.3.1.10.180";
  }

  smiv2:alias "cevPort10GigBaseLW" {
    smiv2:oid "1.3.6.1.4.1.9.12.3.1.10.181";
  }

  smiv2:alias "cevPort10GigBaseEW" {
    smiv2:oid "1.3.6.1.4.1.9.12.3.1.10.182";
  }

  smiv2:alias "cevPortGigBaseUnknown" {
    smiv2:oid "1.3.6.1.4.1.9.12.3.1.10.183";
  }

  smiv2:alias "cevPort10GigBaseUnknown" {
    smiv2:oid "1.3.6.1.4.1.9.12.3.1.10.184";
  }

  smiv2:alias "cevPort10GigBaseUnapproved" {
    smiv2:oid "1.3.6.1.4.1.9.12.3.1.10.185";
  }

  smiv2:alias "cevPortGigBaseWdmRxOnly" {
    smiv2:oid "1.3.6.1.4.1.9.12.3.1.10.186";
  }

  smiv2:alias "cevPortGigBaseDwdm3033" {
    smiv2:oid "1.3.6.1.4.1.9.12.3.1.10.187";
  }

  smiv2:alias "cevPortGigBaseDwdm3112" {
    smiv2:oid "1.3.6.1.4.1.9.12.3.1.10.188";
  }

  smiv2:alias "cevPortGigBaseDwdm3190" {
    smiv2:oid "1.3.6.1.4.1.9.12.3.1.10.189";
  }

  smiv2:alias "cevPortGigBaseDwdm3268" {
    smiv2:oid "1.3.6.1.4.1.9.12.3.1.10.190";
  }

  smiv2:alias "cevPortGigBaseDwdm3425" {
    smiv2:oid "1.3.6.1.4.1.9.12.3.1.10.191";
  }

  smiv2:alias "cevPortGigBaseDwdm3504" {
    smiv2:oid "1.3.6.1.4.1.9.12.3.1.10.192";
  }

  smiv2:alias "cevPortGigBaseDwdm3582" {
    smiv2:oid "1.3.6.1.4.1.9.12.3.1.10.193";
  }

  smiv2:alias "cevPortGigBaseDwdm3661" {
    smiv2:oid "1.3.6.1.4.1.9.12.3.1.10.194";
  }

  smiv2:alias "cevPortGigBaseDwdm3819" {
    smiv2:oid "1.3.6.1.4.1.9.12.3.1.10.195";
  }

  smiv2:alias "cevPortGigBaseDwdm3898" {
    smiv2:oid "1.3.6.1.4.1.9.12.3.1.10.196";
  }

  smiv2:alias "cevPortGigBaseDwdm3977" {
    smiv2:oid "1.3.6.1.4.1.9.12.3.1.10.197";
  }

  smiv2:alias "cevPortGigBaseDwdm4056" {
    smiv2:oid "1.3.6.1.4.1.9.12.3.1.10.198";
  }

  smiv2:alias "cevPortGigBaseDwdm4214" {
    smiv2:oid "1.3.6.1.4.1.9.12.3.1.10.199";
  }

  smiv2:alias "cevPortGigBaseDwdm4294" {
    smiv2:oid "1.3.6.1.4.1.9.12.3.1.10.200";
  }

  smiv2:alias "cevPortGigBaseDwdm4373" {
    smiv2:oid "1.3.6.1.4.1.9.12.3.1.10.201";
  }

  smiv2:alias "cevPortGigBaseDwdm4453" {
    smiv2:oid "1.3.6.1.4.1.9.12.3.1.10.202";
  }

  smiv2:alias "cevPortGigBaseDwdm4612" {
    smiv2:oid "1.3.6.1.4.1.9.12.3.1.10.203";
  }

  smiv2:alias "cevPortGigBaseDwdm4692" {
    smiv2:oid "1.3.6.1.4.1.9.12.3.1.10.204";
  }

  smiv2:alias "cevPortGigBaseDwdm4772" {
    smiv2:oid "1.3.6.1.4.1.9.12.3.1.10.205";
  }

  smiv2:alias "cevPortGigBaseDwdm4851" {
    smiv2:oid "1.3.6.1.4.1.9.12.3.1.10.206";
  }

  smiv2:alias "cevPortGigBaseDwdm5012" {
    smiv2:oid "1.3.6.1.4.1.9.12.3.1.10.207";
  }

  smiv2:alias "cevPortGigBaseDwdm5092" {
    smiv2:oid "1.3.6.1.4.1.9.12.3.1.10.208";
  }

  smiv2:alias "cevPortGigBaseDwdm5172" {
    smiv2:oid "1.3.6.1.4.1.9.12.3.1.10.209";
  }

  smiv2:alias "cevPortGigBaseDwdm5252" {
    smiv2:oid "1.3.6.1.4.1.9.12.3.1.10.210";
  }

  smiv2:alias "cevPortGigBaseDwdm5413" {
    smiv2:oid "1.3.6.1.4.1.9.12.3.1.10.211";
  }

  smiv2:alias "cevPortGigBaseDwdm5494" {
    smiv2:oid "1.3.6.1.4.1.9.12.3.1.10.212";
  }

  smiv2:alias "cevPortGigBaseDwdm5575" {
    smiv2:oid "1.3.6.1.4.1.9.12.3.1.10.213";
  }

  smiv2:alias "cevPortGigBaseDwdm5655" {
    smiv2:oid "1.3.6.1.4.1.9.12.3.1.10.214";
  }

  smiv2:alias "cevPortGigBaseDwdm5817" {
    smiv2:oid "1.3.6.1.4.1.9.12.3.1.10.215";
  }

  smiv2:alias "cevPortGigBaseDwdm5898" {
    smiv2:oid "1.3.6.1.4.1.9.12.3.1.10.216";
  }

  smiv2:alias "cevPortGigBaseDwdm5979" {
    smiv2:oid "1.3.6.1.4.1.9.12.3.1.10.217";
  }

  smiv2:alias "cevPortGigBaseDwdm6061" {
    smiv2:oid "1.3.6.1.4.1.9.12.3.1.10.218";
  }

  smiv2:alias "cevPort10GigBaseWdmRxOnly" {
    smiv2:oid "1.3.6.1.4.1.9.12.3.1.10.219";
  }

  smiv2:alias "cevPort10GigBaseDwdm3033" {
    smiv2:oid "1.3.6.1.4.1.9.12.3.1.10.220";
  }

  smiv2:alias "cevPort10GigBaseDwdm3112" {
    smiv2:oid "1.3.6.1.4.1.9.12.3.1.10.221";
  }

  smiv2:alias "cevPort10GigBaseDwdm3190" {
    smiv2:oid "1.3.6.1.4.1.9.12.3.1.10.222";
  }

  smiv2:alias "cevPort10GigBaseDwdm3268" {
    smiv2:oid "1.3.6.1.4.1.9.12.3.1.10.223";
  }

  smiv2:alias "cevPort10GigBaseDwdm3425" {
    smiv2:oid "1.3.6.1.4.1.9.12.3.1.10.224";
  }

  smiv2:alias "cevPort10GigBaseDwdm3504" {
    smiv2:oid "1.3.6.1.4.1.9.12.3.1.10.225";
  }

  smiv2:alias "cevPort10GigBaseDwdm3582" {
    smiv2:oid "1.3.6.1.4.1.9.12.3.1.10.226";
  }

  smiv2:alias "cevPort10GigBaseDwdm3661" {
    smiv2:oid "1.3.6.1.4.1.9.12.3.1.10.227";
  }

  smiv2:alias "cevPort10GigBaseDwdm3819" {
    smiv2:oid "1.3.6.1.4.1.9.12.3.1.10.228";
  }

  smiv2:alias "cevPort10GigBaseDwdm3898" {
    smiv2:oid "1.3.6.1.4.1.9.12.3.1.10.229";
  }

  smiv2:alias "cevPort10GigBaseDwdm3977" {
    smiv2:oid "1.3.6.1.4.1.9.12.3.1.10.230";
  }

  smiv2:alias "cevPort10GigBaseDwdm4056" {
    smiv2:oid "1.3.6.1.4.1.9.12.3.1.10.231";
  }

  smiv2:alias "cevPort10GigBaseDwdm4214" {
    smiv2:oid "1.3.6.1.4.1.9.12.3.1.10.232";
  }

  smiv2:alias "cevPort10GigBaseDwdm4294" {
    smiv2:oid "1.3.6.1.4.1.9.12.3.1.10.233";
  }

  smiv2:alias "cevPort10GigBaseDwdm4373" {
    smiv2:oid "1.3.6.1.4.1.9.12.3.1.10.234";
  }

  smiv2:alias "cevPort10GigBaseDwdm4453" {
    smiv2:oid "1.3.6.1.4.1.9.12.3.1.10.235";
  }

  smiv2:alias "cevPort10GigBaseDwdm4612" {
    smiv2:oid "1.3.6.1.4.1.9.12.3.1.10.236";
  }

  smiv2:alias "cevPort10GigBaseDwdm4692" {
    smiv2:oid "1.3.6.1.4.1.9.12.3.1.10.237";
  }

  smiv2:alias "cevPort10GigBaseDwdm4772" {
    smiv2:oid "1.3.6.1.4.1.9.12.3.1.10.238";
  }

  smiv2:alias "cevPort10GigBaseDwdm4851" {
    smiv2:oid "1.3.6.1.4.1.9.12.3.1.10.239";
  }

  smiv2:alias "cevPort10GigBaseDwdm5012" {
    smiv2:oid "1.3.6.1.4.1.9.12.3.1.10.240";
  }

  smiv2:alias "cevPort10GigBaseDwdm5092" {
    smiv2:oid "1.3.6.1.4.1.9.12.3.1.10.241";
  }

  smiv2:alias "cevPort10GigBaseDwdm5172" {
    smiv2:oid "1.3.6.1.4.1.9.12.3.1.10.242";
  }

  smiv2:alias "cevPort10GigBaseDwdm5252" {
    smiv2:oid "1.3.6.1.4.1.9.12.3.1.10.243";
  }

  smiv2:alias "cevPort10GigBaseDwdm5413" {
    smiv2:oid "1.3.6.1.4.1.9.12.3.1.10.244";
  }

  smiv2:alias "cevPort10GigBaseDwdm5494" {
    smiv2:oid "1.3.6.1.4.1.9.12.3.1.10.245";
  }

  smiv2:alias "cevPort10GigBaseDwdm5575" {
    smiv2:oid "1.3.6.1.4.1.9.12.3.1.10.246";
  }

  smiv2:alias "cevPort10GigBaseDwdm5655" {
    smiv2:oid "1.3.6.1.4.1.9.12.3.1.10.247";
  }

  smiv2:alias "cevPort10GigBaseDwdm5817" {
    smiv2:oid "1.3.6.1.4.1.9.12.3.1.10.248";
  }

  smiv2:alias "cevPort10GigBaseDwdm5898" {
    smiv2:oid "1.3.6.1.4.1.9.12.3.1.10.249";
  }

  smiv2:alias "cevPort10GigBaseDwdm5979" {
    smiv2:oid "1.3.6.1.4.1.9.12.3.1.10.250";
  }

  smiv2:alias "cevPort10GigBaseDwdm6061" {
    smiv2:oid "1.3.6.1.4.1.9.12.3.1.10.251";
  }

  smiv2:alias "cevPortGigBaseBX10D" {
    smiv2:oid "1.3.6.1.4.1.9.12.3.1.10.252";
  }

  smiv2:alias "cevPortGigBaseBX10U" {
    smiv2:oid "1.3.6.1.4.1.9.12.3.1.10.253";
  }

  smiv2:alias "cevPortT1E1" {
    smiv2:oid "1.3.6.1.4.1.9.12.3.1.10.254";
  }

  smiv2:alias "cevPort2GFCPhy" {
    smiv2:oid "1.3.6.1.4.1.9.12.3.1.10.255";
  }

  smiv2:alias "cevPortLanWirelessApplication" {
    smiv2:oid "1.3.6.1.4.1.9.12.3.1.10.256";
  }

  smiv2:alias "cevPortSEInternalFE" {
    smiv2:oid "1.3.6.1.4.1.9.12.3.1.10.257";
  }

  smiv2:alias "cevPortCEInternalFE" {
    smiv2:oid "1.3.6.1.4.1.9.12.3.1.10.258";
  }

  smiv2:alias "cevPortIpsecVpn" {
    smiv2:oid "1.3.6.1.4.1.9.12.3.1.10.259";
  }

  smiv2:alias "cevPortSsl" {
    smiv2:oid "1.3.6.1.4.1.9.12.3.1.10.260";
  }

  smiv2:alias "cevPortFirewall" {
    smiv2:oid "1.3.6.1.4.1.9.12.3.1.10.261";
  }

  smiv2:alias "cevPortDsp5441" {
    smiv2:oid "1.3.6.1.4.1.9.12.3.1.10.263";
  }

  smiv2:alias "cevPortDsp6415" {
    smiv2:oid "1.3.6.1.4.1.9.12.3.1.10.264";
  }

  smiv2:alias "cevPortHwicSerial" {
    smiv2:oid "1.3.6.1.4.1.9.12.3.1.10.265";
  }

  smiv2:alias "cevPortAsi" {
    smiv2:oid "1.3.6.1.4.1.9.12.3.1.10.266";
  }

  smiv2:alias "cevPortQam" {
    smiv2:oid "1.3.6.1.4.1.9.12.3.1.10.267";
  }

  smiv2:alias "cevPortGigBaseBT" {
    smiv2:oid "1.3.6.1.4.1.9.12.3.1.10.268";
  }

  smiv2:alias "cevPort100BaseUnknown" {
    smiv2:oid "1.3.6.1.4.1.9.12.3.1.10.269";
  }

  smiv2:alias "cevPort100BaseUnapproved" {
    smiv2:oid "1.3.6.1.4.1.9.12.3.1.10.270";
  }

  smiv2:alias "cevPort100BaseBX10D" {
    smiv2:oid "1.3.6.1.4.1.9.12.3.1.10.271";
  }

  smiv2:alias "cevPort100BaseBX10U" {
    smiv2:oid "1.3.6.1.4.1.9.12.3.1.10.272";
  }

  smiv2:alias "cevPort100BaseFX" {
    smiv2:oid "1.3.6.1.4.1.9.12.3.1.10.273";
  }

  smiv2:alias "cevPort100BaseLX10" {
    smiv2:oid "1.3.6.1.4.1.9.12.3.1.10.274";
  }

  smiv2:alias "cevPort100BaseSX" {
    smiv2:oid "1.3.6.1.4.1.9.12.3.1.10.275";
  }

  smiv2:alias "cevPortSM" {
    smiv2:oid "1.3.6.1.4.1.9.12.3.1.10.276";
  }

  smiv2:alias "cevPortT3E3" {
    smiv2:oid "1.3.6.1.4.1.9.12.3.1.10.277";
  }

  smiv2:alias "cevPortMultiRate" {
    smiv2:oid "1.3.6.1.4.1.9.12.3.1.10.278";
  }

  smiv2:alias "cevPortWaveSonetPhy" {
    smiv2:oid "1.3.6.1.4.1.9.12.3.1.10.279";
  }

  smiv2:alias "cevPortSDCC" {
    smiv2:oid "1.3.6.1.4.1.9.12.3.1.10.280";
  }

  smiv2:alias "cevPortAdslAnnexA" {
    smiv2:oid "1.3.6.1.4.1.9.12.3.1.10.281";
  }

  smiv2:alias "cevPortAdslAnnexB" {
    smiv2:oid "1.3.6.1.4.1.9.12.3.1.10.282";
  }

  smiv2:alias "cevPort10GigBaseZR" {
    smiv2:oid "1.3.6.1.4.1.9.12.3.1.10.285";
  }

  smiv2:alias "cevPort10GigBaseCX4" {
    smiv2:oid "1.3.6.1.4.1.9.12.3.1.10.286";
  }

  smiv2:alias "cevPort10GigBaseSR" {
    smiv2:oid "1.3.6.1.4.1.9.12.3.1.10.287";
  }

  smiv2:alias "cevPortGigBaseCwdm1610" {
    smiv2:oid "1.3.6.1.4.1.9.12.3.1.10.288";
  }

  smiv2:alias "cevPortGigBaseCwdm1590" {
    smiv2:oid "1.3.6.1.4.1.9.12.3.1.10.289";
  }

  smiv2:alias "cevPortGigBaseCwdm1550" {
    smiv2:oid "1.3.6.1.4.1.9.12.3.1.10.290";
  }

  smiv2:alias "cevPortGigBaseCwdm1530" {
    smiv2:oid "1.3.6.1.4.1.9.12.3.1.10.291";
  }

  smiv2:alias "cevPortGigBaseCwdm1510" {
    smiv2:oid "1.3.6.1.4.1.9.12.3.1.10.292";
  }

  smiv2:alias "cevPortGigBaseCwdm1490" {
    smiv2:oid "1.3.6.1.4.1.9.12.3.1.10.293";
  }

  smiv2:alias "cevPortGigBaseCwdm1470" {
    smiv2:oid "1.3.6.1.4.1.9.12.3.1.10.294";
  }

  smiv2:alias "cevPortGigBaseCwdm1570" {
    smiv2:oid "1.3.6.1.4.1.9.12.3.1.10.295";
  }

  smiv2:alias "cevPortUSB" {
    smiv2:oid "1.3.6.1.4.1.9.12.3.1.10.296";
  }

  smiv2:alias "cevPortSslVpn" {
    smiv2:oid "1.3.6.1.4.1.9.12.3.1.10.297";
  }

  smiv2:alias "cevPortCableModem" {
    smiv2:oid "1.3.6.1.4.1.9.12.3.1.10.298";
  }

  smiv2:alias "cevNmeApaPort" {
    smiv2:oid "1.3.6.1.4.1.9.12.3.1.10.299";
  }

  smiv2:alias "cevPort10GigBase" {
    smiv2:oid "1.3.6.1.4.1.9.12.3.1.10.300";
  }

  smiv2:alias "cevPort10GigBaseLRM" {
    smiv2:oid "1.3.6.1.4.1.9.12.3.1.10.301";
  }

  smiv2:alias "cevPortdot11abg" {
    smiv2:oid "1.3.6.1.4.1.9.12.3.1.10.302";
  }

  smiv2:alias "cevPortDti" {
    smiv2:oid "1.3.6.1.4.1.9.12.3.1.10.303";
  }

  smiv2:alias "cevPort10GigSFPPlus" {
    smiv2:oid "1.3.6.1.4.1.9.12.3.1.10.304";
  }

  smiv2:alias "cevPortCscPort" {
    smiv2:oid "1.3.6.1.4.1.9.12.3.1.10.305";
  }

  smiv2:alias "cevPortGEXFP" {
    smiv2:oid "1.3.6.1.4.1.9.12.3.1.10.306";
  }

  smiv2:alias "cevPortGigBaseDwdm6141" {
    smiv2:oid "1.3.6.1.4.1.9.12.3.1.10.307";
  }

  smiv2:alias "cevPortGigBaseDwdm5736" {
    smiv2:oid "1.3.6.1.4.1.9.12.3.1.10.308";
  }

  smiv2:alias "cevPortGigBaseDwdm5332" {
    smiv2:oid "1.3.6.1.4.1.9.12.3.1.10.309";
  }

  smiv2:alias "cevPortGigBaseDwdm4931" {
    smiv2:oid "1.3.6.1.4.1.9.12.3.1.10.310";
  }

  smiv2:alias "cevPortGigBaseDwdm4532" {
    smiv2:oid "1.3.6.1.4.1.9.12.3.1.10.311";
  }

  smiv2:alias "cevPortGigBaseDwdm4134" {
    smiv2:oid "1.3.6.1.4.1.9.12.3.1.10.312";
  }

  smiv2:alias "cevPortGigBaseDwdm3739" {
    smiv2:oid "1.3.6.1.4.1.9.12.3.1.10.313";
  }

  smiv2:alias "cevPortGigBaseDwdm3346" {
    smiv2:oid "1.3.6.1.4.1.9.12.3.1.10.314";
  }

  smiv2:alias "cevPort10GigEthernet" {
    smiv2:oid "1.3.6.1.4.1.9.12.3.1.10.315";
  }

  smiv2:alias "cevPortSEInternal" {
    smiv2:oid "1.3.6.1.4.1.9.12.3.1.10.316";
  }

  smiv2:alias "cevPortGigBaseEX" {
    smiv2:oid "1.3.6.1.4.1.9.12.3.1.10.317";
  }

  smiv2:alias "cevPort40GigEthernet" {
    smiv2:oid "1.3.6.1.4.1.9.12.3.1.10.318";
  }

  smiv2:alias "cevPortAces" {
    smiv2:oid "1.3.6.1.4.1.9.12.3.1.10.319";
  }

  smiv2:alias "cevPort100GigEthernet" {
    smiv2:oid "1.3.6.1.4.1.9.12.3.1.10.320";
  }

  smiv2:alias "cevPort40GigQSFPPlus" {
    smiv2:oid "1.3.6.1.4.1.9.12.3.1.10.321";
  }

  smiv2:alias "cevPort100GECFP" {
    smiv2:oid "1.3.6.1.4.1.9.12.3.1.10.322";
  }

  smiv2:alias "cevPortPlcG" {
    smiv2:oid "1.3.6.1.4.1.9.12.3.1.10.323";
  }

  smiv2:alias "cevPortWimaxG" {
    smiv2:oid "1.3.6.1.4.1.9.12.3.1.10.324";
  }

  smiv2:alias "cevPort3gCdmaG" {
    smiv2:oid "1.3.6.1.4.1.9.12.3.1.10.325";
  }

  smiv2:alias "cevPort3gGsmG" {
    smiv2:oid "1.3.6.1.4.1.9.12.3.1.10.326";
  }

  smiv2:alias "cevPortWpanG" {
    smiv2:oid "1.3.6.1.4.1.9.12.3.1.10.327";
  }

  smiv2:alias "cevPortCXP" {
    smiv2:oid "1.3.6.1.4.1.9.12.3.1.10.331";
  }

  smiv2:alias "cevPortCPAK" {
    smiv2:oid "1.3.6.1.4.1.9.12.3.1.10.332";
  }

  smiv2:alias "cevPortConsole" {
    smiv2:oid "1.3.6.1.4.1.9.12.3.1.10.333";
  }

  smiv2:alias "cevPortAlarmDSUB15" {
    smiv2:oid "1.3.6.1.4.1.9.12.3.1.10.334";
  }

  smiv2:alias "cevPortSseBreakout100GePort" {
    smiv2:oid "1.3.6.1.4.1.9.12.3.1.10.337";
  }

  smiv2:alias "cevPortSseBreakout10GePort" {
    smiv2:oid "1.3.6.1.4.1.9.12.3.1.10.338";
  }

  smiv2:alias "cevPortCisco10GeSFPPlusPOZR" {
    smiv2:oid "1.3.6.1.4.1.9.12.3.1.10.339";
  }

  smiv2:alias "cevPortCisco10GeSFPPlusPOER" {
    smiv2:oid "1.3.6.1.4.1.9.12.3.1.10.340";
  }

  smiv2:alias "cevPortCisco10GeSFPPlusPOSRX" {
    smiv2:oid "1.3.6.1.4.1.9.12.3.1.10.341";
  }

  smiv2:alias "cevPortCisco10GeSFPPlusPOLRX" {
    smiv2:oid "1.3.6.1.4.1.9.12.3.1.10.342";
  }

  smiv2:alias "cevPortCisco10GeSFPPlusPOLR" {
    smiv2:oid "1.3.6.1.4.1.9.12.3.1.10.343";
  }

  smiv2:alias "cevPortCisco10GeSFPPlusPOSR" {
    smiv2:oid "1.3.6.1.4.1.9.12.3.1.10.344";
  }

  smiv2:alias "cevPortPHwicSerial" {
    smiv2:oid "1.3.6.1.4.1.9.12.3.1.10.346";
  }

  smiv2:alias "cevPortPT1E1" {
    smiv2:oid "1.3.6.1.4.1.9.12.3.1.10.347";
  }

  smiv2:alias "cevPortPHdvDsp" {
    smiv2:oid "1.3.6.1.4.1.9.12.3.1.10.348";
  }

  smiv2:alias "cevPortSerial" {
    smiv2:oid "1.3.6.1.4.1.9.12.3.1.10.350";
  }

  smiv2:alias "cevPortCPAKLR10" {
    smiv2:oid "1.3.6.1.4.1.9.12.3.1.10.351";
  }

  smiv2:alias "cevPortAdslAnnexM" {
    smiv2:oid "1.3.6.1.4.1.9.12.3.1.10.352";
  }

  smiv2:alias "cevStack" {
    smiv2:oid "1.3.6.1.4.1.9.12.3.1.11";
  }

  smiv2:alias "cevStackUnknown" {
    smiv2:oid "1.3.6.1.4.1.9.12.3.1.11.1";
  }

  smiv2:alias "cevStackCat37xx" {
    smiv2:oid "1.3.6.1.4.1.9.12.3.1.11.2";
  }

  smiv2:alias "cevCat65xxVirtualSwitch" {
    smiv2:oid "1.3.6.1.4.1.9.12.3.1.11.3";
  }

  smiv2:alias "cevCbs3120Stack" {
    smiv2:oid "1.3.6.1.4.1.9.12.3.1.11.5";
  }

  smiv2:alias "cevC29xxStack" {
    smiv2:oid "1.3.6.1.4.1.9.12.3.1.11.11";
  }

  smiv2:alias "cevStackIosXrMultichassis" {
    smiv2:oid "1.3.6.1.4.1.9.12.3.1.11.12";
  }

  smiv2:alias "cevStackCat4xxxVirtualSwitchStack" {
    smiv2:oid "1.3.6.1.4.1.9.12.3.1.11.13";
  }

  smiv2:alias "cevStackFex" {
    smiv2:oid "1.3.6.1.4.1.9.12.3.1.11.14";
  }

  smiv2:alias "cevStackC68xxVirSwitch" {
    smiv2:oid "1.3.6.1.4.1.9.12.3.1.11.20";
  }

  smiv2:alias "cevMidplane" {
    smiv2:oid "1.3.6.1.4.1.9.12.3.1.12";
  }

  smiv2:alias "cevMidplaneUmg9820" {
    smiv2:oid "1.3.6.1.4.1.9.12.3.1.12.1";
  }

}
