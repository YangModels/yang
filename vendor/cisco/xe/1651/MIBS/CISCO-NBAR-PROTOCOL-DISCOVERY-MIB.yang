/*
 * Generated by confdc --mib2yang-std
 * Source: mgmt/dmi/model/common/mib-source/CISCO-NBAR-PROTOCOL-DISCOVERY-MIB.mib
 */
/*
 * This YANG module has been generated by smidump 0.5.0:
 *
 *      smidump -f yang CISCO-NBAR-PROTOCOL-DISCOVERY-MIB
 *
 * Do not edit. Edit the source file instead!
 */

module CISCO-NBAR-PROTOCOL-DISCOVERY-MIB {

  namespace "urn:ietf:params:xml:ns:yang:smiv2:CISCO-NBAR-PROTOCOL-DISCOVERY-MIB";
  prefix CISCO-NBAR-PROTOCOL-DISCOVERY-MIB;

  import IF-MIB {
    prefix "if-mib";
  }

  import SNMPv2-TC {
    prefix "snmpv2-tc";
  }

  import ietf-yang-smiv2 {
    prefix "smiv2";
  }

  import ietf-yang-types {
    prefix "yang";
  }

  organization
   "Cisco Systems, Inc.";

  contact
   "	 Cisco Systems
    Customer Service
    
    Postal: 170 W. Tasman Drive
    San Jose, CA  95134-1706
    USA
    
    Tel: +1 800 553-NETS
    
    E-mail: cs-cnpd-mib@cisco.com";

  description
   "Cisco NBAR Protocol Discovery MIB 
    
    NBAR - Network Based Application Recognition is
    an intelligent classification engine that recognizes 
    applications that are static (which use fixed TCP or
    UDP port numbers), and stateful (which dynamically 
    assign TCP or UDP port numbers). 
    
    Protocol Discovery - uses NBAR to show you the mix 
    of applications currently running on the network. 
    Key statistics are associated with each protocol. 
    These statistics can be used to define traffic 
    classes and QoS policies.
    
    Functionality:
    1. To enable/disable Protocol Discovery per interface.
    2. Display the protocols/applications which NBAR
       currently recognizes.
    3. To display various Protocol Discovery statistics.
    4. A configurable top N table which lists
       protocols using user defined criteria.
    5. To configure notifications (traps) based 
       on configurable statistic thresholds.
    6. To maintain a history table of all notification 
       events.";

  revision 2002-08-16 {
    description
     "Added comment that cnpdStatusLastUpdateTime becomes 
      zero when PD disabled.
      
      Added comment that during overflow in cnpdAllStatsTable, 
      the 32 bit counter not valid. There is no overflow 
      support for it. One should only use the HC (64 bit) 
      counters to get the stats in cnpdAllStatsTable
      
      Default cnpdTopNConfigStatsSelect changed from 
      'bitRateSum' to 'byteCountSum'.
      
      Added better rowStatus descriptions to TopNConfig and 
      ThresholdConfig tables.
      
      Added comment to explain what TopNSampleTime really does - 
      i.e only changes sample time for bitrate on an interface.
      
      Changed sizes of TopN and Threshold tables according to 
      memory requirements and recommendations from various 
      platforms.
      
      Added following objects to cnpdThresholdHistoryTable:
        cnpdThresholdHistoryValue
        cnpdThresholdHistoryType
        cnpdThresholdHistoryProtocol
        cnpdThresholdHistoryStatsSelect
      
      Changed reported objects in Notification Table to reflect
      changes in cnpdThresholdHistoryTable.";
  }

  revision 2001-12-28 {
    description
     "Initial version of this MIB module";
  }

  typedef CiscoPdProtocolIndex {
    type uint32;
    description
     "An object which represents a unique 
      identifier for a protocol or application 
      which NBAR currently recognizes.
      
      The value of this object is defined in 
      the cnpdSupportedProtocolsTable.";
  }

  typedef CiscoPdProtocolName {
    type binary {
      length "1..255";
    }
    description
     "Name of an application or protocol, 
      which NBAR is capable of recognizing.
      
      For example: ftp, vdolive and citrix.";
  }

  typedef CiscoPdDataType {
    type enumeration {
      enum "bitRateIn" {
        value "1";
      }
      enum "bitRateOut" {
        value "2";
      }
      enum "bitRateSum" {
        value "3";
      }
      enum "byteCountIn" {
        value "4";
      }
      enum "byteCountOut" {
        value "5";
      }
      enum "byteCountSum" {
        value "6";
      }
      enum "packetCountIn" {
        value "7";
      }
      enum "packetCountOut" {
        value "8";
      }
      enum "packetCountSum" {
        value "9";
      }
    }
    description
     "These are the data types which NBAR
      can measure a particular protocol by.
      bitRateIn(1)      - incoming bitrate.
      bitRateOut(2)     - outgoing bitrate.
      bitRateSum(3)     - sum of incoming and 
                          outgoing bitrate.
      byteCountIn(4)    - incoming bytecount.
      byteCountOut(5)   - outgoing bytecount.
      byteCountSum(6)   - sum of incoming and 
                          outgoing bytecount.
      packetCountIn(7)  - incoming packetcount.
      packetCountOut(8) - outgoing packetcount.
      packetCountSum(9) - sum of incoming and 
                          outgoing packetcount.
      UNITS:
      bitrate     - unit is kilo bits per second
      bytecount   - unit is bytes
      packetcount - unit is packets";
  }


  container CISCO-NBAR-PROTOCOL-DISCOVERY-MIB {
    config false;

    container cnpdNotificationsConfig {
      smiv2:oid "1.3.6.1.4.1.9.9.244.1.7";

      leaf cnpdNotificationsEnable {
        type boolean;
        description
         "This object is used to enable or disable 
          Notifications on a global basis. 
          
          If set to 'true' - Notifications are
          enabled.
          If set to 'false' - Notifications are
          disabled.";
        smiv2:defval "false";
        smiv2:max-access "read-write";
        smiv2:oid "1.3.6.1.4.1.9.9.244.1.7.1";
      }
    }

    container cnpdStatusTable {
      description
       "The cnpdStatusTable is used to enable and
        disable Protocol Discovery on an interface.";
      smiv2:oid "1.3.6.1.4.1.9.9.244.1.1.1";

      list cnpdStatusEntry {
        key "ifIndex";
        description
         "An entry in the cnpdStatusTable contains objects
          for enabling or disabling Protocol Discovery on a
          per interface basis.";
        smiv2:oid "1.3.6.1.4.1.9.9.244.1.1.1.1";

        leaf ifIndex {
          type leafref {
            path "/if-mib:IF-MIB/if-mib:ifTable/if-mib:ifEntry/if-mib:ifIndex";
          }
        }

        leaf cnpdStatusPdEnable {
          type boolean;
          description
           "This object is used to enable or disable 
            Protocol Discovery on an interface. 
            
            If set to 'true' - Protocol Discovery is 
            enabled on this Interface. 
            If set to 'false' - Protocol Discovery is 
            disabled on this Interface.";
          smiv2:max-access "read-write";
          smiv2:oid "1.3.6.1.4.1.9.9.244.1.1.1.1.1";
        }

        leaf cnpdStatusLastUpdateTime {
          type yang:timeticks;
          description
           "The value of sysUpTime at the time Protocol 
            Discovery was last enabled  on an interface.
            If the interface does not have Protocol
            Discovery enabled this value is zero.";
          smiv2:max-access "read-only";
          smiv2:oid "1.3.6.1.4.1.9.9.244.1.1.1.1.2";
        }
      }
    }

    container cnpdAllStatsTable {
      description
       "The cnpdAllStatsTable contains all the statistics
        available for all the protocols/applications currently
        recognized by NBAR Protocol Discovery for a particular 
        interface.
        
        In the event of an overflow, the 32 bit counters are not 
        valid. There is no overflow support.";
      smiv2:oid "1.3.6.1.4.1.9.9.244.1.2.1";

      list cnpdAllStatsEntry {
        key "ifIndex cnpdAllStatsProtocolsIndex";
        description
         "An entry in the cnpdAllStatsTable table. This entry 
          contains the statistics collected on all the protocols 
          which NBAR classifies for a particular interface.";
        smiv2:oid "1.3.6.1.4.1.9.9.244.1.2.1.1";

        leaf ifIndex {
          type leafref {
            path "/if-mib:IF-MIB/if-mib:ifTable/if-mib:ifEntry/if-mib:ifIndex";
          }
        }

        leaf cnpdAllStatsProtocolsIndex {
          type CISCO-NBAR-PROTOCOL-DISCOVERY-MIB:CiscoPdProtocolIndex {
            range "1..1024";
          }
          description
           "An object which represents a unique 
            identifier for a protocol or application 
            which NBAR currently recognizes.
            
            This object is an index into the 
            SupportedProtocolsTable where details
            of the protocol can be found.";
          smiv2:max-access "not-accessible";
          smiv2:oid "1.3.6.1.4.1.9.9.244.1.2.1.1.1";
        }

        leaf cnpdAllStatsProtocolName {
          type CISCO-NBAR-PROTOCOL-DISCOVERY-MIB:CiscoPdProtocolName;
          description
           "Name of the application or protocol, a 
            unique textual string, assigned in the
            cnpdSupportedProtocolsTable.";
          smiv2:max-access "read-only";
          smiv2:oid "1.3.6.1.4.1.9.9.244.1.2.1.1.2";
        }

        leaf cnpdAllStatsInPkts {
          type yang:counter32;
          units "packets";
          description
           "The packet count of inbound packets as 
            determined by Protocol Discovery.";
          smiv2:max-access "read-only";
          smiv2:oid "1.3.6.1.4.1.9.9.244.1.2.1.1.3";
        }

        leaf cnpdAllStatsOutPkts {
          type yang:counter32;
          units "packets";
          description
           "The packet count of outbound packets as 
            determined by Protocol Discovery.";
          smiv2:max-access "read-only";
          smiv2:oid "1.3.6.1.4.1.9.9.244.1.2.1.1.4";
        }

        leaf cnpdAllStatsInBytes {
          type yang:counter32;
          units "bytes";
          description
           "The byte count of inbound octets as 
            determined by Protocol Discovery.";
          smiv2:max-access "read-only";
          smiv2:oid "1.3.6.1.4.1.9.9.244.1.2.1.1.5";
        }

        leaf cnpdAllStatsOutBytes {
          type yang:counter32;
          units "bytes";
          description
           "The byte count of outbound octets as
            determined by Protocol Discovery.";
          smiv2:max-access "read-only";
          smiv2:oid "1.3.6.1.4.1.9.9.244.1.2.1.1.6";
        }

        leaf cnpdAllStatsHCInPkts {
          type yang:counter64;
          units "packets";
          description
           "The packet count of inbound packets as 
            determined by Protocol Discovery.
            This is the 64-bit (High Capacity)
            version of cnpdAllStatsInPkts.";
          smiv2:max-access "read-only";
          smiv2:oid "1.3.6.1.4.1.9.9.244.1.2.1.1.7";
        }

        leaf cnpdAllStatsHCOutPkts {
          type yang:counter64;
          units "packets";
          description
           "The packet count of outbound packets as 
            determined by Protocol Discovery.
            This is the 64-bit (High Capacity)
            version of cnpdAllStatsOutPkts.";
          smiv2:max-access "read-only";
          smiv2:oid "1.3.6.1.4.1.9.9.244.1.2.1.1.8";
        }

        leaf cnpdAllStatsHCInBytes {
          type yang:counter64;
          units "bytes";
          description
           "The byte count of inbound octets as 
            determined by Protocol Discovery.
            This is the 64-bit (High Capacity)
            version of cnpdAllStatsInBytes.";
          smiv2:max-access "read-only";
          smiv2:oid "1.3.6.1.4.1.9.9.244.1.2.1.1.9";
        }

        leaf cnpdAllStatsHCOutBytes {
          type yang:counter64;
          units "bytes";
          description
           "The byte count of outbound octets as 
            determined by Protocol Discovery.
            This is the 64-bit (High Capacity)
            version of cnpdAllStatsOutBytes.";
          smiv2:max-access "read-only";
          smiv2:oid "1.3.6.1.4.1.9.9.244.1.2.1.1.10";
        }

        leaf cnpdAllStatsInBitRate {
          type uint32 {
            range "1..4294967295";
          }
          units "kilo bits per second";
          description
           "The inbound bit rate as determined 
            by Protocol Discovery.";
          smiv2:max-access "read-only";
          smiv2:oid "1.3.6.1.4.1.9.9.244.1.2.1.1.11";
        }

        leaf cnpdAllStatsOutBitRate {
          type uint32 {
            range "1..4294967295";
          }
          units "kilo bits per second";
          description
           "The outbound bit rate as determined 
            by Protocol Discovery.";
          smiv2:max-access "read-only";
          smiv2:oid "1.3.6.1.4.1.9.9.244.1.2.1.1.12";
        }
      }
    }

    container cnpdTopNConfigTable {
      description
       "The cnpdTopNConfigTable is used to configure
        cnpdTopNStatsTable's.";
      smiv2:oid "1.3.6.1.4.1.9.9.244.1.3.1";

      list cnpdTopNConfigEntry {
        key "cnpdTopNConfigIndex";
        description
         "This entry provides the objects to configure and thus
          initiate the generation of a cnpdTopNStatsTable..";
        smiv2:oid "1.3.6.1.4.1.9.9.244.1.3.1.1";

        leaf cnpdTopNConfigIndex {
          type uint32 {
            range "1..50";
          }
          description
           "A monotonically increasing integer which
            uniquely identifies a cnpdTopNConfigEntry 
            in the cnpdTopNConfigTable.";
          smiv2:max-access "not-accessible";
          smiv2:oid "1.3.6.1.4.1.9.9.244.1.3.1.1.1";
        }

        leaf cnpdTopNConfigIfIndex {
          type if-mib:InterfaceIndex;
          description
           "This object allows the management station
            to select the interface, which Protocol Discovery
            is running on, to be used to create this 
            cnpdTopNConfigEntry.";
          smiv2:max-access "read-write";
          smiv2:oid "1.3.6.1.4.1.9.9.244.1.3.1.1.2";
        }

        leaf cnpdTopNConfigStatsSelect {
          type CISCO-NBAR-PROTOCOL-DISCOVERY-MIB:CiscoPdDataType;
          description
           "This object allows the management station to
            select the statistic used to base the order
            of the top-n table on.
            
            For example: a cnpdTopNConfigStatsSelect of
            bitRateSum means order this table based
            on each applications/protocols combined
            in and out bitrate.";
          smiv2:defval "byteCountSum";
          smiv2:max-access "read-write";
          smiv2:oid "1.3.6.1.4.1.9.9.244.1.3.1.1.3";
        }

        leaf cnpdTopNConfigSampleTime {
          type uint32 {
            range "1..2048";
          }
          units "seconds";
          description
           "If the cnpdTopNConfigStatsSelect is
            bitRateIn, bitRateOut or bitRateSum, then
            this value is the interval in seconds that 
            the bitrate is sampled.
            
            This has no effect if the cnpdTopNConfigStatsSelect
            is byte or packet based.
            
            When this object is modified by the management 
            station, a new sample period is started regardless
            of whether the original cnpdTopNConfigSampleTime
            was finished.";
          smiv2:defval "10";
          smiv2:max-access "read-write";
          smiv2:oid "1.3.6.1.4.1.9.9.244.1.3.1.1.4";
        }

        leaf cnpdTopNConfigRequestedSize {
          type uint32 {
            range "1..500";
          }
          description
           "The requested size of the associated 
            cnpdTopNStatsTable entry.
            
            For example a cnpdTopNConfigRequestedSize of
            20 indicates the management station wants
            to create an associated  cnpdTopNStatsTable 
            entry of 20 protocol/application's";
          smiv2:defval "10";
          smiv2:max-access "read-write";
          smiv2:oid "1.3.6.1.4.1.9.9.244.1.3.1.1.5";
        }

        leaf cnpdTopNConfigGrantedSize {
          type uint32 {
            range "1..500";
          }
          description
           "The actual size of the associated 	
            cnpdTopNStatsTable entry.
            
            The reason this may differ from 
            cnpdTopNConfigRequestedSize is because a 
            management station may request a number of 
            protocols that is greater than the number of 
            protocols actually found by Protocol Discovery.";
          smiv2:max-access "read-only";
          smiv2:oid "1.3.6.1.4.1.9.9.244.1.3.1.1.6";
        }

        leaf cnpdTopNConfigTime {
          type yang:timeticks;
          description
           "The value of sysUpTime when the associated
            cnpdTopNStatsTable entry was created.";
          smiv2:max-access "read-only";
          smiv2:oid "1.3.6.1.4.1.9.9.244.1.3.1.1.7";
        }

        leaf cnpdTopNConfigStatus {
          type snmpv2-tc:RowStatus;
          description
           "This object is used to create or delete 
            the row entry in cnpdTopNConfigTable.
            
            When creating a row entry the management
            station is required to specify a value
            for cnpdTopNConfigIfIndex only.
            
            'notReady' means that a row exists but 
            either it has no valid IfIndex or it has 
            not been set to createAndGo or active.
            
            'active' means that a createAndGo or active 
            has been issued, AND a valid ifIndex exists. 
            Therefore if a row is 'active' it means a 
            TopNStats entry has been generated.
            
            If you set an 'active' row to createAndWait 
            it will get the status 'notReady'. 
            
            If you set any row to 'notReady' - it will go 
            to the 'notReadystate'.
            
            If you set any row to 'notInService' - it will 
            go to the 'notInService' state and the corresponding 
            TopNStatsEntry will be deleted.
            
            The same TopNConfig entry can be re-used without 
            changes by setting it to 'active'. The corresponding 
            TopStatsTable entry will be regenerated. This can 
            be used by the NMS to poll a particular TopNConfig 
            Entry.
            
            Changes to an existing TopNConfig entry can be made
            by setting the status to 'createAndWait' and changing
            the necessary objects. Setting it to 'createAndGo' or
            'active' will cause the corresponding TopNStats entry
            to be regenerated.";
          smiv2:max-access "read-write";
          smiv2:oid "1.3.6.1.4.1.9.9.244.1.3.1.1.8";
        }
      }
    }

    container cnpdTopNStatsTable {
      description
       "A cnpdTopNStatsTable describes an ordered
        list of protocols.";
      smiv2:oid "1.3.6.1.4.1.9.9.244.1.4.1";

      list cnpdTopNStatsEntry {
        key "cnpdTopNConfigIndex cnpdTopNStatsIndex";
        description
         "This entry is used to store a set of objects which 
          describe a cnpdTopNStatsTable. A cnpdTopNStatsTable 
          is a number of protocols and statistics sorted 
          according to the criteria in the associated
          cnpdTopNConfigEntry.
          
          Therefore a cnpdTopNStatsTable can differ in content 
          and size according to what was configured in the associated
          cnpdTopNConfigTableEntry.";
        smiv2:oid "1.3.6.1.4.1.9.9.244.1.4.1.1";

        leaf cnpdTopNConfigIndex {
          type leafref {
            path "/CISCO-NBAR-PROTOCOL-DISCOVERY-MIB:CISCO-NBAR-PROTOCOL-DISCOVERY-MIB/CISCO-NBAR-PROTOCOL-DISCOVERY-MIB:cnpdTopNConfigTable/CISCO-NBAR-PROTOCOL-DISCOVERY-MIB:cnpdTopNConfigEntry/CISCO-NBAR-PROTOCOL-DISCOVERY-MIB:cnpdTopNConfigIndex";
          }
        }

        leaf cnpdTopNStatsIndex {
          type uint32 {
            range "1..500";
          }
          description
           "A monotonically increasing integer which 
            uniquely identifies a cnpdTopNStatsEntry 
            in the cnpdTopNStatsTable.";
          smiv2:max-access "not-accessible";
          smiv2:oid "1.3.6.1.4.1.9.9.244.1.4.1.1.1";
        }

        leaf cnpdTopNStatsProtocolName {
          type CISCO-NBAR-PROTOCOL-DISCOVERY-MIB:CiscoPdProtocolName;
          description
           "Name of the application or protocol, 
            a unique textual string, assigned in the
            cnpdSupportedProtocolsTable.";
          smiv2:max-access "read-only";
          smiv2:oid "1.3.6.1.4.1.9.9.244.1.4.1.1.2";
        }

        leaf cnpdTopNStatsRate {
          type yang:counter32;
          description
           "The amount of change in the selected statistic
            during this sampling interval. The selected
            statistic is the cnpdTopNConfigStatsSelect
            from the associated cnpdTopNConfigStatsEntry.";
          smiv2:max-access "read-only";
          smiv2:oid "1.3.6.1.4.1.9.9.244.1.4.1.1.3";
        }

        leaf cnpdTopNStatsHCRate {
          type yang:counter64;
          description
           "The amount of change in the selected statistic
            during this sampling interval. The selected
            statistic is the cnpdTopNConfigStatsSelect
            from the associated cnpdTopNConfigStatsEntry.	
            
            This is the 64-bit (High Capacity) version of 
            cnpdTopNStatsRate.";
          smiv2:max-access "read-only";
          smiv2:oid "1.3.6.1.4.1.9.9.244.1.4.1.1.4";
        }
      }
    }

    container cnpdThresholdConfigTable {
      description
       "The cnpdThresholdConfigTable allows the management
        station to create thresholds for the purpose of
        sending notifications if breached, and creating a
        history of breached thresholds.";
      smiv2:oid "1.3.6.1.4.1.9.9.244.1.5.1";

      list cnpdThresholdConfigEntry {
        key "cnpdThresholdConfigIndex";
        description
         "This entry contains configuration information to 
          set thresholds for the purpose of notifications.
          
          The management station is allowed to set thresholds
          on individual statistics for individual protocols
          on an interface. If the threshold is breached by
          the protocol statistic, a new event is written to
          the cnpdThresholdHistoryTable, which in turn will 
          generate a Notification Event.
          
          This function has a hysteresis mechanism to limit
          the generation of events. This mechanism generates
          one event as a threshold is crossed in the
          appropriate direction. No more events are generated
          for that threshold until the opposite threshold is
          crossed. This stops repeated Notification events
          being generated each time the value is sampled,
          when the value is above the threshold. Instead one
          notification is sent when the threshold is breached
          and one notification when the statistic drops below
          the threshold value again.";
        smiv2:oid "1.3.6.1.4.1.9.9.244.1.5.1.1";

        leaf cnpdThresholdConfigIndex {
          type uint32 {
            range "1..100";
          }
          description
           "A monotonically increasing integer which 
            uniquely identifies an entry in the 
            cnpdThresholdConfigTable.";
          smiv2:max-access "not-accessible";
          smiv2:oid "1.3.6.1.4.1.9.9.244.1.5.1.1.1";
        }

        leaf cnpdThresholdConfigIfIndex {
          type if-mib:InterfaceIndex;
          description
           "This object allows the management station to 
            select the interface, which Protocol Discovery is 
            running on, to be used to create this 
            cnpdThresholdConfigTable entry.";
          smiv2:max-access "read-write";
          smiv2:oid "1.3.6.1.4.1.9.9.244.1.5.1.1.2";
        }

        leaf cnpdThresholdConfigInterval {
          type uint32 {
            range "1..2048";
          }
          units "seconds";
          description
           "The interval in seconds over which the data is
            sampled and compared with cnpdThresholdConfigRising
            and cnpdThresholdConfigFalling thresholds.";
          smiv2:defval "10";
          smiv2:max-access "read-write";
          smiv2:oid "1.3.6.1.4.1.9.9.244.1.5.1.1.3";
        }

        leaf cnpdThresholdConfigSampleType {
          type enumeration {
            enum "absoluteValue" {
              value "1";
            }
            enum "deltaValue" {
              value "2";
            }
          }
          description
           "The method of sampling the selected statistic and
            calculating the value to be compared against 
            cnpdThresholdConfigRising or 
            cnpdThresholdConfigFalling thresholds. 
            		
            If the value of this object is absoluteValue(1), 
            the value at the end of the sampling interval 
            cnpdThresholdConfigInterval, will be compared 
            with the cnpdThresholdConfigRising and 
            cnpdThresholdConfigFalling thresholds. 
            
            In this mode, when cnpdThresholdConfigStatsSelect is
            byte or packet based, a maximum of two 
            cnpdThresholdHistory entries will be created per
            application, as these byte and packet counts 
            monotonically increase from zero.
            		
            If the value of this object is deltaValue(2), 
            the difference between the samples at the 
            beginning and end of the cnpdThresholdConfigInterval 
            will be compared with the cnpdThresholdConfigRising 
            and cnpdThresholdConfigFalling thresholds.
            		
            Because the difference in the previous and current
            samples are compared over the sample period
            cnpdThresholdConfigInterval, this mode provides 
            more granularity to the thresholds because the NMS 
            is now provided with the gradient or change in the 
            cnpdThresholdConfigStatsSelect.
            
            Note that even though the sample value is monotonically
            increasing for byte and packet counts, 
            cnpdThresholdConfigSampleType set to deltaValue, can 
            generate falling cnpdThresholdHistory entries, because
            the gradient can be lower than the 
            cnpdThresholdConfigFalling value.";
          smiv2:defval "absoluteValue";
          smiv2:max-access "read-write";
          smiv2:oid "1.3.6.1.4.1.9.9.244.1.5.1.1.4";
        }

        leaf cnpdThresholdConfigProtocol {
          type CISCO-NBAR-PROTOCOL-DISCOVERY-MIB:CiscoPdProtocolIndex {
            range "1..1024";
          }
          description
           "The application or protocol which the
            management station wishes to configure a
            threshold on.
            
            This object is an index into the 
            SupportedProtocolsTable where details
            of the protocol can be found.
            
            If cnpdThresholdConfigProtocolAny is set
            to TRUE this value will be ignored. If it
            is set to FALSE, then cnpdThresholdConfigProtocol
            will be the only protocol that is checked
            to see if it has breached the threshold.";
          smiv2:max-access "read-write";
          smiv2:oid "1.3.6.1.4.1.9.9.244.1.5.1.1.5";
        }

        leaf cnpdThresholdConfigProtocolAny {
          type boolean;
          description
           "If set to 'true' - this threshold is configured
            to check for any protocol which meets the threshold
            criteria. This means that multiple protocols can
            generate ThresholdHistoryTable entries. Each
            protocol is subject to the hysterisis mechanism.
            
            If set to 'false' - this threshold is configured
            to check for the protocol which meets the threshold
            criteria referred to by cnpdThresholdConfigProtocol.";
          smiv2:defval "true";
          smiv2:max-access "read-write";
          smiv2:oid "1.3.6.1.4.1.9.9.244.1.5.1.1.6";
        }

        leaf cnpdThresholdConfigStatsSelect {
          type CISCO-NBAR-PROTOCOL-DISCOVERY-MIB:CiscoPdDataType;
          description
           "This object allows the management station to
            select the statistic used to base the threshold
            on.
            
            For example a cnpdThresholdConfigStatsSelect of
            bitRateSum means cnpdThresholdConfigRising and
            cnpdThresholdConfigFalling are values based on
            the combined value of in and out bitrates.";
          smiv2:defval "bitRateSum";
          smiv2:max-access "read-write";
          smiv2:oid "1.3.6.1.4.1.9.9.244.1.5.1.1.7";
        }

        leaf cnpdThresholdConfigStartup {
          type enumeration {
            enum "rising" {
              value "1";
            }
            enum "falling" {
              value "2";
            }
            enum "risingOrFalling" {
              value "3";
            }
          }
          description
           "This controls the type of notification that is 
            sent when this threshold entry is first enabled. 
            
            Because there is no previous sampling history,
            choosing one of these options determines the type
            of notification generated - Rising or Falling.
            
            If the first sample after this entry is enabled 
            is greater than or equal to cnpdThresholdConfigRising and
            this object is equal to rising(1) or risingOrFalling(3), 
            then a single rising notification will be generated. 
            
            If the first sample after this entry is enabled
            is less than or equal to cnpdThresholdConfigFalling
            and this object is equal to falling(2) or 
            risingOrFalling(3), then a single falling notification 
            will be generated.";
          smiv2:defval "risingOrFalling";
          smiv2:max-access "read-write";
          smiv2:oid "1.3.6.1.4.1.9.9.244.1.5.1.1.8";
        }

        leaf cnpdThresholdConfigRising {
          type uint32 {
            range "1..4294967295";
          }
          description
           "This is the threshold object which the managment
            station sets to determine if it gets breached. It 
            indicates the statistic being sampled was
            rising.
            
            When the current sample is greater than or 
            equal to this object, and the value at the last 
            sampling interval was less than this object (in 
            other words the value is rising), an entry in the 
            cnpdThresholdHistoryTable will be created.
            
            After a rising event is generated, another such 
            event will not be generated until the sampled value
            falls below this threshold and reaches the
            cnpdThresholdConfigFalling value.
            
            This ensures that samples which are taken
            after a cnpdThresholdConfigRising threshold event
            has been created, do not create further thresholds
            and therefore notifications, until the 
            cnpdThresholdConfigFalling threshold has been met.
            
            Thus a very short cnpdThresholdConfigInterval can be
            chosen without risk of multiple notifications for
            the same threshold breach condition.";
          smiv2:max-access "read-write";
          smiv2:oid "1.3.6.1.4.1.9.9.244.1.5.1.1.9";
        }

        leaf cnpdThresholdConfigFalling {
          type uint32 {
            range "1..4294967295";
          }
          description
           "This is the threshold object which the management 
            station sets to determine if it gets breached. It 
            indicates the statistic being sampled was
            falling. 
            
            When current sample is less than or equal 
            to this object, and the value at the last sampling
            interval was greater than this object (in other 
            words the value is falling), an entry in the 
            cnpdThresholdHistoryTable will be created. 
            		
            After a falling event is generated, another 
            such event will not be generated until the sampled 
            value rises above this object and reaches the
            cnpdThresholdConfigRising value.";
          smiv2:max-access "read-write";
          smiv2:oid "1.3.6.1.4.1.9.9.244.1.5.1.1.10";
        }

        leaf cnpdThresholdConfigStatus {
          type snmpv2-tc:RowStatus;
          description
           "This object is used to create or delete 
            the row entry in cnpdThresholdConfigTable.
             
            When creating a row entry the management station 
            is required to specify a value for 
            cnpdThresholdConfigIfIndex, cnpdThresholdConfigRising 
            and cnpdThresholdConfigFalling.
            
            'active' means that a createAndGo or active has 
            been issued, AND a valid ifIndex exists. And therefore 
            if a row is 'active' it means a ThresholdHistory entry 
            may have been generated if the value was breached.
            
            If you set an 'active' row to 'createAndWait' - it will 
            in fact get the status 'notReady'. 
            
            Likewise if you set any row to 'notInService' or 'notReady' 
            it will go to the 'notReady' state.";
          smiv2:max-access "read-write";
          smiv2:oid "1.3.6.1.4.1.9.9.244.1.5.1.1.12";
        }
      }
    }

    container cnpdThresholdHistoryTable {
      description
       "The Threshold History table. Notifications
        are unreliable so this table provides a
        history of the last 5000 threshold breached
        events. A notification can be traced back to
        its cnpdThresholdHistoryEntry.";
      smiv2:oid "1.3.6.1.4.1.9.9.244.1.6.1";

      list cnpdThresholdHistoryEntry {
        key "cnpdThresholdHistoryIndex";
        description
         "This entry is created each time a threshold 
          is breached. 
          
          Thus there is not necessarily a one to one 
          relationship to cnpdThresholdConfigTable 
          as not every Threshold configured will 
          be breached.";
        smiv2:oid "1.3.6.1.4.1.9.9.244.1.6.1.1";

        leaf cnpdThresholdHistoryIndex {
          type uint32 {
            range "1..1000";
          }
          description
           "A monotonically increasing integer
            which uniquely identifies this 
            cnpdThresholdHistoryEntry in the 
            cnpdThresholdHistory table.";
          smiv2:max-access "not-accessible";
          smiv2:oid "1.3.6.1.4.1.9.9.244.1.6.1.1.1";
        }

        leaf cnpdThresholdHistoryConfigIndex {
          type uint32 {
            range "1..1000";
          }
          description
           "The cnpdThresholdConfigTable entry 
            which generated this entry. Using this 
            object the management station can backtrack 
            to the appropriate cnpdThresholdConfigEntry.";
          smiv2:max-access "read-only";
          smiv2:oid "1.3.6.1.4.1.9.9.244.1.6.1.1.2";
        }

        leaf cnpdThresholdHistoryValue {
          type uint32 {
            range "1..4294967295";
          }
          description
           "The actual value of the statistic when 
            the sampling was made.";
          smiv2:max-access "read-only";
          smiv2:oid "1.3.6.1.4.1.9.9.244.1.6.1.1.3";
        }

        leaf cnpdThresholdHistoryType {
          type enumeration {
            enum "risingBreach" {
              value "1";
            }
            enum "fallingBreach" {
              value "2";
            }
          }
          description
           "Describes whether this is an
            event caused by a rising
            or falling threshold breach.";
          smiv2:max-access "read-only";
          smiv2:oid "1.3.6.1.4.1.9.9.244.1.6.1.1.4";
        }

        leaf cnpdThresholdHistoryTime {
          type yang:timeticks;
          description
           "The value of sysUpTime of the running 
            configuration when the event occurred.";
          smiv2:max-access "read-only";
          smiv2:oid "1.3.6.1.4.1.9.9.244.1.6.1.1.5";
        }

        leaf cnpdThresholdHistoryProtocol {
          type CISCO-NBAR-PROTOCOL-DISCOVERY-MIB:CiscoPdProtocolIndex {
            range "1..1024";
          }
          description
           "The application or protocol which the
            management station configured a
            threshold on.
            
            This object is an index into the 
            SupportedProtocolsTable where details
            of the protocol can be found.";
          smiv2:max-access "read-only";
          smiv2:oid "1.3.6.1.4.1.9.9.244.1.6.1.1.6";
        }

        leaf cnpdThresholdHistoryStatsSelect {
          type CISCO-NBAR-PROTOCOL-DISCOVERY-MIB:CiscoPdDataType;
          description
           "This is the statistic used to base the threshold
            on.";
          smiv2:max-access "read-only";
          smiv2:oid "1.3.6.1.4.1.9.9.244.1.6.1.1.7";
        }
      }
    }

    container cnpdSupportedProtocolsTable {
      description
       "The Supported Protocols table lists all the 
        protocols and applications which NBAR is currently
        capable of recognizing.";
      smiv2:oid "1.3.6.1.4.1.9.9.244.1.8.1";

      list cnpdSupportedProtocolsEntry {
        key "cnpdSupportedProtocolsIndex";
        description
         "A entry in the Supported Protocols table reflecting
          key information about a protocol.";
        smiv2:oid "1.3.6.1.4.1.9.9.244.1.8.1.1";

        leaf cnpdSupportedProtocolsIndex {
          type CISCO-NBAR-PROTOCOL-DISCOVERY-MIB:CiscoPdProtocolIndex {
            range "1..1024";
          }
          description
           "A unique identifier of a row in this table.
            
            Thus it also represents a unique identifier for a
            protocol or application which NBAR currently
            recognizes.";
          smiv2:max-access "not-accessible";
          smiv2:oid "1.3.6.1.4.1.9.9.244.1.8.1.1.1";
        }

        leaf cnpdSupportedProtocolsName {
          type CISCO-NBAR-PROTOCOL-DISCOVERY-MIB:CiscoPdProtocolName;
          description
           "This object reflects the valid string of a
            protocol or application which NBAR currently
            recognizes.";
          smiv2:max-access "read-only";
          smiv2:oid "1.3.6.1.4.1.9.9.244.1.8.1.1.2";
        }
      }
    }
  }

  notification cnpdThresholdRisingEvent {
    description
     "A cnpdThresholdRisingEvent is sent whenever 
      a notification entry crosses its rising threshold 
      and generates an event that is added to the
      cnpdThresholdHistoryTable.";
    smiv2:oid "1.3.6.1.4.1.9.9.244.0.1";

    container object-1 {

      leaf cnpdThresholdConfigIndex {
        type leafref {
          path "/CISCO-NBAR-PROTOCOL-DISCOVERY-MIB:CISCO-NBAR-PROTOCOL-DISCOVERY-MIB/CISCO-NBAR-PROTOCOL-DISCOVERY-MIB:cnpdThresholdConfigTable/CISCO-NBAR-PROTOCOL-DISCOVERY-MIB:cnpdThresholdConfigEntry/CISCO-NBAR-PROTOCOL-DISCOVERY-MIB:cnpdThresholdConfigIndex";
        }
      }

      leaf cnpdThresholdConfigIfIndex {
        type leafref {
          path "/CISCO-NBAR-PROTOCOL-DISCOVERY-MIB:CISCO-NBAR-PROTOCOL-DISCOVERY-MIB/CISCO-NBAR-PROTOCOL-DISCOVERY-MIB:cnpdThresholdConfigTable/CISCO-NBAR-PROTOCOL-DISCOVERY-MIB:cnpdThresholdConfigEntry/CISCO-NBAR-PROTOCOL-DISCOVERY-MIB:cnpdThresholdConfigIfIndex";
        }
      }
    }

    container object-2 {

      leaf cnpdThresholdConfigIndex {
        type leafref {
          path "/CISCO-NBAR-PROTOCOL-DISCOVERY-MIB:CISCO-NBAR-PROTOCOL-DISCOVERY-MIB/CISCO-NBAR-PROTOCOL-DISCOVERY-MIB:cnpdThresholdConfigTable/CISCO-NBAR-PROTOCOL-DISCOVERY-MIB:cnpdThresholdConfigEntry/CISCO-NBAR-PROTOCOL-DISCOVERY-MIB:cnpdThresholdConfigIndex";
        }
      }

      leaf cnpdThresholdConfigStatsSelect {
        type leafref {
          path "/CISCO-NBAR-PROTOCOL-DISCOVERY-MIB:CISCO-NBAR-PROTOCOL-DISCOVERY-MIB/CISCO-NBAR-PROTOCOL-DISCOVERY-MIB:cnpdThresholdConfigTable/CISCO-NBAR-PROTOCOL-DISCOVERY-MIB:cnpdThresholdConfigEntry/CISCO-NBAR-PROTOCOL-DISCOVERY-MIB:cnpdThresholdConfigStatsSelect";
        }
      }
    }

    container object-3 {

      leaf cnpdThresholdHistoryIndex {
        type leafref {
          path "/CISCO-NBAR-PROTOCOL-DISCOVERY-MIB:CISCO-NBAR-PROTOCOL-DISCOVERY-MIB/CISCO-NBAR-PROTOCOL-DISCOVERY-MIB:cnpdThresholdHistoryTable/CISCO-NBAR-PROTOCOL-DISCOVERY-MIB:cnpdThresholdHistoryEntry/CISCO-NBAR-PROTOCOL-DISCOVERY-MIB:cnpdThresholdHistoryIndex";
        }
      }

      leaf cnpdThresholdHistoryValue {
        type leafref {
          path "/CISCO-NBAR-PROTOCOL-DISCOVERY-MIB:CISCO-NBAR-PROTOCOL-DISCOVERY-MIB/CISCO-NBAR-PROTOCOL-DISCOVERY-MIB:cnpdThresholdHistoryTable/CISCO-NBAR-PROTOCOL-DISCOVERY-MIB:cnpdThresholdHistoryEntry/CISCO-NBAR-PROTOCOL-DISCOVERY-MIB:cnpdThresholdHistoryValue";
        }
      }
    }

    container object-4 {

      leaf cnpdThresholdConfigIndex {
        type leafref {
          path "/CISCO-NBAR-PROTOCOL-DISCOVERY-MIB:CISCO-NBAR-PROTOCOL-DISCOVERY-MIB/CISCO-NBAR-PROTOCOL-DISCOVERY-MIB:cnpdThresholdConfigTable/CISCO-NBAR-PROTOCOL-DISCOVERY-MIB:cnpdThresholdConfigEntry/CISCO-NBAR-PROTOCOL-DISCOVERY-MIB:cnpdThresholdConfigIndex";
        }
      }

      leaf cnpdThresholdConfigRising {
        type leafref {
          path "/CISCO-NBAR-PROTOCOL-DISCOVERY-MIB:CISCO-NBAR-PROTOCOL-DISCOVERY-MIB/CISCO-NBAR-PROTOCOL-DISCOVERY-MIB:cnpdThresholdConfigTable/CISCO-NBAR-PROTOCOL-DISCOVERY-MIB:cnpdThresholdConfigEntry/CISCO-NBAR-PROTOCOL-DISCOVERY-MIB:cnpdThresholdConfigRising";
        }
      }
    }

    container object-5 {

      leaf cnpdThresholdConfigIndex {
        type leafref {
          path "/CISCO-NBAR-PROTOCOL-DISCOVERY-MIB:CISCO-NBAR-PROTOCOL-DISCOVERY-MIB/CISCO-NBAR-PROTOCOL-DISCOVERY-MIB:cnpdThresholdConfigTable/CISCO-NBAR-PROTOCOL-DISCOVERY-MIB:cnpdThresholdConfigEntry/CISCO-NBAR-PROTOCOL-DISCOVERY-MIB:cnpdThresholdConfigIndex";
        }
      }

      leaf cnpdThresholdConfigProtocol {
        type leafref {
          path "/CISCO-NBAR-PROTOCOL-DISCOVERY-MIB:CISCO-NBAR-PROTOCOL-DISCOVERY-MIB/CISCO-NBAR-PROTOCOL-DISCOVERY-MIB:cnpdThresholdConfigTable/CISCO-NBAR-PROTOCOL-DISCOVERY-MIB:cnpdThresholdConfigEntry/CISCO-NBAR-PROTOCOL-DISCOVERY-MIB:cnpdThresholdConfigProtocol";
        }
      }
    }

    container object-6 {

      leaf cnpdThresholdHistoryIndex {
        type leafref {
          path "/CISCO-NBAR-PROTOCOL-DISCOVERY-MIB:CISCO-NBAR-PROTOCOL-DISCOVERY-MIB/CISCO-NBAR-PROTOCOL-DISCOVERY-MIB:cnpdThresholdHistoryTable/CISCO-NBAR-PROTOCOL-DISCOVERY-MIB:cnpdThresholdHistoryEntry/CISCO-NBAR-PROTOCOL-DISCOVERY-MIB:cnpdThresholdHistoryIndex";
        }
      }

      leaf cnpdThresholdHistoryTime {
        type leafref {
          path "/CISCO-NBAR-PROTOCOL-DISCOVERY-MIB:CISCO-NBAR-PROTOCOL-DISCOVERY-MIB/CISCO-NBAR-PROTOCOL-DISCOVERY-MIB:cnpdThresholdHistoryTable/CISCO-NBAR-PROTOCOL-DISCOVERY-MIB:cnpdThresholdHistoryEntry/CISCO-NBAR-PROTOCOL-DISCOVERY-MIB:cnpdThresholdHistoryTime";
        }
      }
    }
  }

  notification cnpdThresholdFallingEvent {
    description
     "A cnpdThresholdConfigFallingEvent is sent 
      whenever a notification entry crosses its 
      falling threshold and generates an event 
      that is added to the cnpdThresholdHistoryTable.";
    smiv2:oid "1.3.6.1.4.1.9.9.244.0.2";

    container object-1 {

      leaf cnpdThresholdConfigIndex {
        type leafref {
          path "/CISCO-NBAR-PROTOCOL-DISCOVERY-MIB:CISCO-NBAR-PROTOCOL-DISCOVERY-MIB/CISCO-NBAR-PROTOCOL-DISCOVERY-MIB:cnpdThresholdConfigTable/CISCO-NBAR-PROTOCOL-DISCOVERY-MIB:cnpdThresholdConfigEntry/CISCO-NBAR-PROTOCOL-DISCOVERY-MIB:cnpdThresholdConfigIndex";
        }
      }

      leaf cnpdThresholdConfigIfIndex {
        type leafref {
          path "/CISCO-NBAR-PROTOCOL-DISCOVERY-MIB:CISCO-NBAR-PROTOCOL-DISCOVERY-MIB/CISCO-NBAR-PROTOCOL-DISCOVERY-MIB:cnpdThresholdConfigTable/CISCO-NBAR-PROTOCOL-DISCOVERY-MIB:cnpdThresholdConfigEntry/CISCO-NBAR-PROTOCOL-DISCOVERY-MIB:cnpdThresholdConfigIfIndex";
        }
      }
    }

    container object-2 {

      leaf cnpdThresholdConfigIndex {
        type leafref {
          path "/CISCO-NBAR-PROTOCOL-DISCOVERY-MIB:CISCO-NBAR-PROTOCOL-DISCOVERY-MIB/CISCO-NBAR-PROTOCOL-DISCOVERY-MIB:cnpdThresholdConfigTable/CISCO-NBAR-PROTOCOL-DISCOVERY-MIB:cnpdThresholdConfigEntry/CISCO-NBAR-PROTOCOL-DISCOVERY-MIB:cnpdThresholdConfigIndex";
        }
      }

      leaf cnpdThresholdConfigStatsSelect {
        type leafref {
          path "/CISCO-NBAR-PROTOCOL-DISCOVERY-MIB:CISCO-NBAR-PROTOCOL-DISCOVERY-MIB/CISCO-NBAR-PROTOCOL-DISCOVERY-MIB:cnpdThresholdConfigTable/CISCO-NBAR-PROTOCOL-DISCOVERY-MIB:cnpdThresholdConfigEntry/CISCO-NBAR-PROTOCOL-DISCOVERY-MIB:cnpdThresholdConfigStatsSelect";
        }
      }
    }

    container object-3 {

      leaf cnpdThresholdHistoryIndex {
        type leafref {
          path "/CISCO-NBAR-PROTOCOL-DISCOVERY-MIB:CISCO-NBAR-PROTOCOL-DISCOVERY-MIB/CISCO-NBAR-PROTOCOL-DISCOVERY-MIB:cnpdThresholdHistoryTable/CISCO-NBAR-PROTOCOL-DISCOVERY-MIB:cnpdThresholdHistoryEntry/CISCO-NBAR-PROTOCOL-DISCOVERY-MIB:cnpdThresholdHistoryIndex";
        }
      }

      leaf cnpdThresholdHistoryValue {
        type leafref {
          path "/CISCO-NBAR-PROTOCOL-DISCOVERY-MIB:CISCO-NBAR-PROTOCOL-DISCOVERY-MIB/CISCO-NBAR-PROTOCOL-DISCOVERY-MIB:cnpdThresholdHistoryTable/CISCO-NBAR-PROTOCOL-DISCOVERY-MIB:cnpdThresholdHistoryEntry/CISCO-NBAR-PROTOCOL-DISCOVERY-MIB:cnpdThresholdHistoryValue";
        }
      }
    }

    container object-4 {

      leaf cnpdThresholdConfigIndex {
        type leafref {
          path "/CISCO-NBAR-PROTOCOL-DISCOVERY-MIB:CISCO-NBAR-PROTOCOL-DISCOVERY-MIB/CISCO-NBAR-PROTOCOL-DISCOVERY-MIB:cnpdThresholdConfigTable/CISCO-NBAR-PROTOCOL-DISCOVERY-MIB:cnpdThresholdConfigEntry/CISCO-NBAR-PROTOCOL-DISCOVERY-MIB:cnpdThresholdConfigIndex";
        }
      }

      leaf cnpdThresholdConfigFalling {
        type leafref {
          path "/CISCO-NBAR-PROTOCOL-DISCOVERY-MIB:CISCO-NBAR-PROTOCOL-DISCOVERY-MIB/CISCO-NBAR-PROTOCOL-DISCOVERY-MIB:cnpdThresholdConfigTable/CISCO-NBAR-PROTOCOL-DISCOVERY-MIB:cnpdThresholdConfigEntry/CISCO-NBAR-PROTOCOL-DISCOVERY-MIB:cnpdThresholdConfigFalling";
        }
      }
    }

    container object-5 {

      leaf cnpdThresholdConfigIndex {
        type leafref {
          path "/CISCO-NBAR-PROTOCOL-DISCOVERY-MIB:CISCO-NBAR-PROTOCOL-DISCOVERY-MIB/CISCO-NBAR-PROTOCOL-DISCOVERY-MIB:cnpdThresholdConfigTable/CISCO-NBAR-PROTOCOL-DISCOVERY-MIB:cnpdThresholdConfigEntry/CISCO-NBAR-PROTOCOL-DISCOVERY-MIB:cnpdThresholdConfigIndex";
        }
      }

      leaf cnpdThresholdConfigProtocol {
        type leafref {
          path "/CISCO-NBAR-PROTOCOL-DISCOVERY-MIB:CISCO-NBAR-PROTOCOL-DISCOVERY-MIB/CISCO-NBAR-PROTOCOL-DISCOVERY-MIB:cnpdThresholdConfigTable/CISCO-NBAR-PROTOCOL-DISCOVERY-MIB:cnpdThresholdConfigEntry/CISCO-NBAR-PROTOCOL-DISCOVERY-MIB:cnpdThresholdConfigProtocol";
        }
      }
    }

    container object-6 {

      leaf cnpdThresholdHistoryIndex {
        type leafref {
          path "/CISCO-NBAR-PROTOCOL-DISCOVERY-MIB:CISCO-NBAR-PROTOCOL-DISCOVERY-MIB/CISCO-NBAR-PROTOCOL-DISCOVERY-MIB:cnpdThresholdHistoryTable/CISCO-NBAR-PROTOCOL-DISCOVERY-MIB:cnpdThresholdHistoryEntry/CISCO-NBAR-PROTOCOL-DISCOVERY-MIB:cnpdThresholdHistoryIndex";
        }
      }

      leaf cnpdThresholdHistoryTime {
        type leafref {
          path "/CISCO-NBAR-PROTOCOL-DISCOVERY-MIB:CISCO-NBAR-PROTOCOL-DISCOVERY-MIB/CISCO-NBAR-PROTOCOL-DISCOVERY-MIB:cnpdThresholdHistoryTable/CISCO-NBAR-PROTOCOL-DISCOVERY-MIB:cnpdThresholdHistoryEntry/CISCO-NBAR-PROTOCOL-DISCOVERY-MIB:cnpdThresholdHistoryTime";
        }
      }
    }
  }

  smiv2:alias "ciscoNbarProtocolDiscoveryMIB" {
    smiv2:oid "1.3.6.1.4.1.9.9.244";
  }

  smiv2:alias "cnpdMIBNotifications" {
    smiv2:oid "1.3.6.1.4.1.9.9.244.0";
  }

  smiv2:alias "cnpdMIBObjects" {
    smiv2:oid "1.3.6.1.4.1.9.9.244.1";
  }

  smiv2:alias "cnpdStatus" {
    smiv2:oid "1.3.6.1.4.1.9.9.244.1.1";
  }

  smiv2:alias "cnpdAllStats" {
    smiv2:oid "1.3.6.1.4.1.9.9.244.1.2";
  }

  smiv2:alias "cnpdTopNConfig" {
    smiv2:oid "1.3.6.1.4.1.9.9.244.1.3";
  }

  smiv2:alias "cnpdTopNStats" {
    smiv2:oid "1.3.6.1.4.1.9.9.244.1.4";
  }

  smiv2:alias "cnpdThresholdConfig" {
    smiv2:oid "1.3.6.1.4.1.9.9.244.1.5";
  }

  smiv2:alias "cnpdThresholdHistory" {
    smiv2:oid "1.3.6.1.4.1.9.9.244.1.6";
  }

  smiv2:alias "cnpdNotificationsConfig" {
    smiv2:oid "1.3.6.1.4.1.9.9.244.1.7";
  }

  smiv2:alias "cnpdSupportedProtocols" {
    smiv2:oid "1.3.6.1.4.1.9.9.244.1.8";
  }

  smiv2:alias "cnpdMIBConformance" {
    smiv2:oid "1.3.6.1.4.1.9.9.244.2";
  }

  smiv2:alias "cnpdMIBCompliances" {
    smiv2:oid "1.3.6.1.4.1.9.9.244.2.1";
  }

  smiv2:alias "cnpdMIBGroups" {
    smiv2:oid "1.3.6.1.4.1.9.9.244.2.2";
  }

}
