module Cisco-IOS-XE-aaa {
  namespace "http://cisco.com/ns/yang/Cisco-IOS-XE-aaa";
  prefix ios-aaa;

  import ietf-inet-types {
    prefix inet;
  }


  import Cisco-IOS-XE-types {
    prefix ios-types;
  }

  import Cisco-IOS-XE-native {
    prefix ios;
  }

  import Cisco-IOS-XE-interface-common {
    prefix ios-ifc;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Authentication, Authorization and Accouting (AAA) Yang Model.
     Copyright (c) 2016-2017 by Cisco Systems, Inc.
     All rights reserved."; 

  // =========================================================================
  // REVISION 
  // =========================================================================

  revision 2017-02-07 {
    description
      "Initial revision";
  }

  

  grouping aaa-authentication-dot1x-grouping {
    leaf group {
      description
        "Use Server-group";
      type union {
        type string;
        type enumeration {
          enum "radius";
          enum "tacacs+";
        }
      }
    }
  }

  grouping aaa-accounting-grouping {
    choice accounting-choice {
      leaf none {
        description
          "No accounting.";
        type empty;
      }
      container start-stop {
        description
          "Record start and stop without waiting";
        leaf broadcast {
          description
            "Use Broadcast for Accounting";
          type empty;
        }
        leaf group {
          description
            "Use Server-group";
          type union {
            type string;
            type enumeration {
              enum "radius";
              enum "tacacs+";
            }
          }
        }
      }
      container stop-only {
        description
          "Record stop when service terminates.";
        leaf broadcast {
          description
            "Use Broadcast for Accounting";
          type empty;
        }
        leaf group {
          description
            "Use Server-group";
          type union {
            type string;
            type enumeration {
              enum "radius";
              enum "tacacs+";
            }
          }
        }
      }
    }
  }

  grouping config-aaa-grouping {
    leaf new-model {
      description
        "Enable NEW access control commands and functions.(Disables OLD commands.)";
        type empty;
    }
    container group {
      description
        "AAA group definitions";
      container server {
        description
          "AAA Server group definitions";
        list tacacsplus {
          description
            "Tacacs+ server-group definition";
          key "name";
          leaf name {
            type string;
          }
          container server {
            description
              "Specify a TACACS server";
            leaf name {
              description
                "Name of tacacs server";
              type string;
            }
          }
          list server-private {
            description
              "Define a private TACACS server (per group)";
            key "name";
            leaf name {
              type ios-types:host-type;
            }
            leaf timeout {
              description
                "Time to wait for this TACACS server to reply (overrides default)";
              type uint16 {
                range "1..1000";
              }
            }
            container key {
              description
                "per-server encryption key (overrides default)";
              leaf encryption {
                type enumeration {
                  enum "0";
                  enum "7";
                }
              }
              leaf key {
                type string;
              }
            }
            //nat  To send client's post NAT address to tacacs+ server
            //port TCP port for TACACS+ server (default is 49)
            //single-connection Multiplex all packets over a single..
            //..tcp connection to server (for CiscoSecure)
          }
          container ip {
            description
              "Internet Protocol config commands";
            container tacacs {
              description
                "TACACS configuration commands";
              uses config-ip-tacacs-main-grouping;
            }
            container vrf {
              description
                "Set VPN Routing Forwarding to use with the servers";
              leaf forwarding {
                description
                  "Configure forwarding table";
                type string;
              }
            }
          }
        }
        // aaa group server tacacs+
        list tacacs {
          description "Tacacs+ server-group definition";
          key "name";
          leaf name {
            type string;
          }
        }
        // aaa group server radius *
        list radius {
          description
            "Radius server-group definition";
          key "name";
          leaf name {
            type string;
          }
          container server {
            description
              "Specify a RADIUS server";
            list name {
              description
                "Name of radius server";
              key "name";
              leaf name {
                type string;
              }
            }
            list direct {
              key "name";
              leaf name {
                type inet:host;
              }
              leaf auth-port {
                description
                  "UDP port for RADIUS authentication server (default is 1645)";
                type uint16 {
                  range "0..65535";
                }
              }
              leaf acct-port {
                description
                  "UDP port for RADIUS accounting server (default is 1646)";
                type uint16 {
                  range "0..65535";
                }
              }
            }
          }
          container ip {
            description
              "Internet Protocol config commands";
            container radius {
              description
                "RADIUS configuration commands";
              //Leave source-interface in aaa model
              //Main raidus model uses container for source-interface
              leaf source-interface {
                type string;
              }
            }
            container vrf {
              description
                "Set VPN Routing Forwarding to use with the servers";
              leaf forwarding {
                description
                  "Configure forwarding table";
                type string;
              }
            }
          }
          container load-balance {
            description
              "Server group load-balancing options.";
            container method {
              description
                "Method by which the next host will be picked.";
              container least-outstanding {
                description
                  "Pick the server with the least transactions outstanding.";
                leaf batch-size {
                  description
                    "Size of the transaction batch that should be load-balanced.";
                  type uint32 {
                    range "1..2147483647";
                  }
                }
                leaf ignore-preferred-server {
                  description
                    "Should the preferred-server be ignored.";
                  type empty;
                }
              }
            }
          }
          //  server-private Define a private RADIUS server (per group)
          //  subscriber Configures MAC Filtering RADIUS Compatibility mode
          //  throttle Throttle requests to radius server
        }
      }
    }
    // aaa authentication
    container authentication {
      description
        "Authentication configurations parameters.";
       //  arap             Set authentication lists for arap.
      //aaa authentication attempts
      container attempts {
        description
          "Set the maximum number of authentication attempts";
        leaf login {
          description
            "Set the max. number of attempts for login service";
          type uint8 {
            range "1..25";
          }
        }
      }
      //  banner           Message to use when starting login/authentication.
      container banner {
        description "Message to use when starting login/authentication.";
        leaf start-marker {
          type string;
        }
        leaf message {
          type string;
        }
        leaf end-marker {
          type string;
          must ". = ../start-marker" {
          }
        }
      }

      // aaa authentication dot1x
      container dot1x {
        description
          "Set authentication lists for IEEE 802.1x.";
        list dot1x-list {
          key "name";
          leaf name {
            type string;
          }
          uses aaa-authentication-dot1x-grouping;
        }
        container default {
          description
            "The default authentication list.";
          uses aaa-authentication-dot1x-grouping;
        }
      }
      // aaa authentication enable
      container enable {
        description
          "Set authentication list for enable.";
        container default {
          description
            "The default authentication list.";
          leaf group {
            description
              "Use Server-group";
            type union {
              type string;
              type enumeration {
                enum "radius";
                enum "tacacs+";
              }
            }
          }
          leaf enable {
            description
              "Use enable password for authentication.";
            type empty;
          }
          leaf line {
            description
              "Use line password for authentication.";
            type empty;
          }
          leaf none {
            description
              "No authentication.";
            type empty;
          }
        }
      }
      // aaa authentication eou
      container eou {
          description "Set authentication lists for EAPoUDP";
          container default {
              description "The default authentication list";
              container group {
                  description "Use Server-group";
                  leaf radius {
                      description "Use list of all Radius hosts.";
                      type empty;
                  }
              }
          }
      }
      //  eou              Set authentication lists for EAPoUDP
      //  fail-message     Message to use for failed login/authentication.
      container fail-message {
        description "Message to use for failed login/authentication.";
        leaf start-marker {
          type string;
        }
        leaf message {
          type string;
        }
        leaf end-marker {
          type string;
          must ". = ../start-marker" {
          }
        }
      }

      // aaa authentication login *
      list login {
        description
          "Set authentication lists for logins.";
        key "name";
        leaf name {
          type union {
            type enumeration {
              enum "default";
            }
            type string {
              length "1..31";
            }
          }
        }
        container a1 {
          choice auth-login-choice {
            leaf none {
              description
                "NO authentication.";
              type empty;
            }
            leaf krb5 {
              description
                "Use Kerberos 5 authentication.";
              type empty;
            }
            leaf krb5-telnet {
              description
               "Allow logins only if already authenticated via Kerbero";
              type empty;
            }
            leaf line {
              description
                "Use line password for authentication.";
              type empty;
            }
            leaf enable {
              description
                "Use enable password for authentication.";
              type empty;
            }
            leaf local {
              description
                "Use local username authentication.";
              type empty;
            }
            leaf local-case {
              description
                "Use case-sensitive local username authentication.";
              type empty;
            }
            leaf group {
              description
                "Use Server-group";
              type union {
                type string;
                type enumeration {
                  enum "ldap";
                  enum "radius";
                  enum "tacacs+";
                }
              }
            }
            leaf cache {
              description
                "Use Cached-group";
              type union {
                type string;
                type enumeration {
                  enum "ldap";
                  enum "radius";
                  enum "tacacs+";
                }
              }
            }
          }
        }
        container a2 {
          when "not(../a1/none)" {
          }
          choice auth-login-choice {
            leaf group {
              description
                "Use Server-group";
              type union {
                type string;
                type enumeration {
                  enum "ldap";
                  enum "radius";
                  enum "tacacs+";
                }
              }
            }
            leaf cache {
              description
                "Use Cached-group";
              type union {
                type string;
                type enumeration {
                  enum "ldap";
                  enum "radius";
                  enum "tacacs+";
                }
              }
            }
            leaf none {
              description
                "NO authentication.";
              type empty;
            }
            leaf krb5 {
              when "not(../../a1/krb5) and not(../../a1/krb5-telnet)" {
              }
              type empty;
            }
            leaf krb5-telnet {
              when "not(../../a1/krb5) and not(../../a1/krb5-telnet)" {
              }
            type empty;
            }
            leaf line {
              description
                "Use line password for authentication.";
              type empty;
            }
            leaf enable {
              description
                "Use enable password for authentication.";
              type empty;
            }
            leaf local {
              when "not(../../a1/local) and not(../../a1/local-case)" {
              }
              type empty;
            }
            leaf local-case {
              when "not(../../a1/local) and not(../../a1/local-case)" {
              }
              type empty;
            }
          }
        }
        container a3 {
          when "not(../a2/none) and not (../a1/none)" {
          }
          choice auth-login-choice {
            leaf group {
              description
                "Use Server-group";
              type union {
                type string;
                type enumeration {
                  enum "ldap";
                  enum "radius";
                  enum "tacacs+";
                }
              }
            }
            leaf cache {
              description
                "Use Cached-group";
              type union {
                type string;
                type enumeration {
                  enum "ldap";
                  enum "radius";
                  enum "tacacs+";
                }
              }
            }
            leaf none {
              description
                "NO authentication.";
              type empty;
            }
            leaf krb5 {
              when "not(../../a1/krb5) and not(../../a1/krb5-telnet) and not(../../a2/krb5) and not(../../a2/krb5-telnet)" {
              }
              type empty;
            }
            leaf krb5-telnet {
              when "not(../../a1/krb5) and not(../../a1/krb5-telnet) and not(../../a2/krb5) and not(../../a2/krb5-telnet)" {
              }
              type empty;
            }
            leaf line {
              description
                "Use line password for authentication.";
              type empty;
            }
            leaf enable {
              description
                "Use enable password for authentication.";
              type empty;
            }
            leaf local {
              when "not(../../a1/local) and not(../../a1/local-case) and not(../../a2/local) and not(../../a2/local-case)" {
              }
              type empty;
            }
            leaf local-case {
              when "not(../../a1/local) and not(../../a1/local-case) and not(../../a2/local) and not(../../a2/local-case)" {
              }
              type empty;
            }
          }
        }
        container a4 {
          when "not(../a2/none) and not(../a1/none) and not(../a3/none)" {
          }
          choice auth-login-choice {
            leaf group {
              description
                "Use Server-group";
              type union {
                type string;
                type enumeration {
                  enum "ldap";
                  enum "radius";
                  enum "tacacs+";
                }
              }
            }
            leaf cache {
              description
                "Use Cached-group";
              type union {
                type string;
                type enumeration {
                  enum "ldap";
                  enum "radius";
                  enum "tacacs+";
                }
              }
            }
            leaf none {
              description
                "NO authentication.";
              type empty;
            }
            leaf krb5 {
              when "not(../../a1/krb5) and not(../../a1/krb5-telnet) and not(../../a2/krb5) and not(../../a2/krb5-telnet) and not(../../a3/krb5) and not(../../a3/krb5-telnet)" {
              }
              type empty;
            }
            leaf krb5-telnet {
              when "not(../../a1/krb5) and not(../../a1/krb5-telnet) and not(../../a2/krb5) and not(../../a2/krb5-telnet) and not(../../a3/krb5) and not(../../a3/krb5-telnet)" {
              }
              type empty;
            }
            leaf line {
              description
                "Use line password for authentication.";
              type empty;
            }
            leaf enable {
              description
                "Use enable password for authentication.";
              type empty;
            }

            leaf local {
              when "not(../../a1/local) and not(../../a1/local-case) and not(../../a2/local) and not(../../a2/local-case) and not(../../a3/local) and not(../../a3/local-case)" {
              }
              type empty;
            }
            leaf local-case {
              when "not(../../a1/local) and not(../../a1/local-case) and not(../../a2/local) and not(../../a2/local-case) and not(../../a3/local) and not(../../a3/local-case)" {
              }
              type empty;
            }
          }
        }
      }

      // aaa authentication onep *
      container onep {
        description "Set authentication lists for ONEP";
        container default {
          description "The default authentication list.";
          container local {
            description "Use local username authentication.";
            presence true;
          }
        }
      }

      // aaa authentication ppp *
      list ppp {
        description
          "Set authentication lists for ppp.";
        key "id";
        leaf id {
          type string {
            length "1..31";
          }
        }
        container a1 {
          choice auth-choice {
            leaf if-needed {
              description
                "Only authenticate if needed.";
              type empty;
            }
            leaf none {
              description
                "NO authentication.";
              type empty;
            }
            leaf krb5 {
              description
                "Use Kerberos 5 authentication.";
              type empty;
            }
            leaf local {
              description
                "Use local username authentication.";
              type empty;
            }
            leaf local-case {
              description
                "Use case-sensitive local username authentication.";
              type empty;
            }
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
          }
        }
        container a2 {
          when "not(../a1/none)" {
          }
          choice auth-choice {
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
            leaf none {
              description
                "NO authentication.";
              type empty;
            }
            leaf krb5 {
              when "not(../../a1/krb5)" {
              }
              type empty;
            }
            leaf local {
              when "not(../../a1/local) and not(../../a1/local-case)" {
              }
              type empty;
            }
            leaf local-case {
              when "not(../../a1/local) and not(../../a1/local-case)" {
              }
              type empty;
            }
          }
        }
        container a3 {
          when "not(../a2/none) and not (../a1/none)" {
          }
          choice auth-choice {
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
            leaf none {
              description
                "NO authentication.";
              type empty;
            }
            leaf krb5 {
              when "not(../../a1/krb5) and not(../../a2/krb5)" {
              }
              type empty;
            }
            leaf local {
              when "not(../../a1/local) and not(../../a1/local-case) and not(../../a2/local) and not(../../a2/local-case)" {
              }
              type empty;
            }
            leaf local-case {
              when "not(../../a1/local) and not(../../a1/local-case) and not(../../a2/local) and not(../../a2/local-case)" {
              }
              type empty;
            }
          }
        }
        container a4 {
          when "not(../a2/none) and not(../a1/none) and not(../a3/none)" {
          }
          choice auth-choice {
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
            leaf none {
              description
                "NO authentication.";
              type empty;
            }
            leaf krb5 {
              when "not(../../a1/krb5) and not(../../a2/krb5) and not(../../a3/krb5)" {
              }
              type empty;
            }
            leaf local {
              when "not(../../a1/local) and not(../../a1/local-case) and not(../../a2/local) and not(../../a2/local-case) and not(../../a3/local) and not(../../a3/local-case)" {
              }
              type empty;
            }
            leaf local-case {
              when "not(../../a1/local) and not(../../a1/local-case) and not(../../a2/local) and not(../../a2/local-case) and not(../../a3/local) and not(../../a3/local-case)" {
              }
              type empty;
            }
          }
        }
      }
    }
    // aaa authorization
    container authorization {
      description
        "Authorization configurations parameters.";
      container auth-type {
          description "For Authentication Proxy Services";
          container default {
              description "The default authorization list.";
              leaf group {
                  description "Use server-group.";
                  type enumeration {
                      enum "radius";
                  }
              }
          }
      }
      list commands {
        description
          "For exec (shell) commands.";
        key "level list-name";
        leaf level {
          description
            "Enable level";
          type uint8 {
            range "0..15";
          }
        }
        leaf list-name {
          type union {
            type enumeration {
              enum "default";
            }
            type string;
          }
        }
        leaf group {
          description
            "Use server-group.";
          type union {
            type enumeration {
              enum "tacacs+";
            }
            type string;
          }
        }
        leaf if-authenticated {
          description
            "Succeed if user has authenticated.";
          type empty;
        }
        leaf local {
          description
            "Use local database.";
          type empty;
        }
        leaf none {
          description
            "No authorization (always succeeds).";
          type empty;
        }
      }
      leaf console {
        type empty;
      }
      leaf config-commands {
        description
          "For configuration mode commands.";
        type empty;
      }
      //  configuration For downloading configurations from AAA server
      //  console For enabling console authorization
      //  credential-download  For downloading EAP credential
      //                       from Local/RADIUS/LDAP

      // aaa authorization exec *
      list exec {
        description
          "For starting an exec (shell).";
        key "name";
        leaf name {
          type string;
        }
    container a1 {
      choice auth-exec-choice {
        leaf if-authenticated {
      description
        "Succeed if user has authenticated.";
      type empty;
        }
        leaf none {
      description
        "No authorization (always succeeds)";
      type empty;
        }
        leaf krb5-instance {
      description
        "Use Kerberos instance privilege maps";
      type empty;
        }
        leaf local {
      description
        "Use local database";
      type empty;
        }
        leaf group {
      description
        "Use Server-group";
      type union {
        type string;
        type enumeration {
          enum "ldap";
          enum "radius";
          enum "tacacs+";
        }
      }
       }
       leaf cache {
      description
        "Use Cached-group";
      type union {
        type string;
        type enumeration {
          enum "ldap";
          enum "radius";
          enum "tacacs+";
        }
      }
        }
      }
    }
    container a2 {
      when "not(../a1/none) and not(../a1/if-authenticated)" {
      }
      choice auth-exec-choice {
        leaf group {
      description
        "Use Server-group";
      type union {
        type string;
        type enumeration {
          enum "ldap";
          enum "radius";
          enum "tacacs+";
        }
      }
        }
        leaf cache {
      description
        "Use Cached-group";
      type union {
        type string;
        type enumeration {
          enum "ldap";
          enum "radius";
          enum "tacacs+";
        }
      }
        }
            leaf if-authenticated {
      description
        "Succeed if user has authenticated.";
      type empty;
        }
        leaf none {
      description
        "No authorization (always succeeds).";
      type empty;
        }
        leaf krb5-instance {
      when "not (../../a1/krb5-instance)" {
      }
      type empty;
        }
        leaf local {
      when "not(../../a1/local)" {
      }
      type empty;
        }
      }
    }
    container a3 {
      when "not(../a2/none) and not (../a1/none) and not(../a2/if-authenticated) and not(../a1/if-authenticated)" {
      }
      choice auth-exec-choice {
        leaf group {
      description
        "Use Server-group";
      type union {
        type string;
        type enumeration {
          enum "ldap";
          enum "radius";
          enum "tacacs+";
        }
      }
        }
        leaf cache {
      description
        "Use Cached-group";
      type union {
        type string;
        type enumeration {
          enum "ldap";
          enum "radius";
          enum "tacacs+";
        }
      }
        }
        leaf none {
      description
        "No authorization (always succeeds).";
      type empty;
        }
        leaf if-authenticated {
      description
        "Succeed if user has authenticated.";
      type empty;
        }
        leaf krb5-instance {
      when "not (../../a1/krb5-instance) and not (../../a2/krb5-instance)" {
      }
      type empty;
        }
        leaf local {
      when "not(../../a1/local) and not(../../a2/local)" {
      }
      type empty;
        }
      }
    }
    container a4 {
      when "not(../a2/none) and not(../a1/none) and not(../a3/none) and not(../a2/if-authenticated) and not(../a1/if-authenticated) and not(../a3/if-authenticated)" {
      }
      choice auth-exec-choice {
        leaf group {
      description
        "Use Server-group";
      type union {
        type string;
        type enumeration {
          enum "ldap";
          enum "radius";
          enum "tacacs+";
        }
      }
        }
        leaf cache {
      description
        "Use Cached-group";
      type union {
        type string;
        type enumeration {
          enum "ldap";
          enum "radius";
          enum "tacacs+";
        }
      }
        }
        leaf none {
      description
        "No authorization (always succeeds).";
      type empty;
        }
        leaf if-authenticated {
      description
        "Succeed if user has authenticated.";
      type empty;
        }
        leaf krb5-instance {
      when "not (../../a1/krb5-instance) and not (../../a2/krb5-instance) and not (../../a3/krb5-instance)" {
      }
      type empty;
        }
        leaf local {
      when "not(../../a1/local) and not(../../a2/local) and not(../../a3/local)" {
      }
      type empty;
        }
      }
    }
  }
      // aaa authorization eventmanager *
      list eventmanager {
        description
          "For starting an exec (shell).";
        key "name";
        leaf name {
          type string;
        }
        leaf group {
          description
            "Use server-group.";
          type union {
            type string;
            type enumeration {
              enum "ldap";
              enum "radius";
              enum "tacacs";
            }
          }
        }
        leaf local {
          description
            "Use local database.";
          type empty;
        }
        leaf none {
          description
            "No authorization (always succeeds).";
          type empty;
        }
      }
      // aaa authorization network *
      list network {
        description
          "For network services. (PPP, SLIP, ARAP)";
        key "id";
        leaf id {
          type union {
            type enumeration {
              enum "default";
            }
            type string {
              length "1..31";
            }
          }
        }
        container a1 {
          choice auth-choice {
            leaf if-authenticated {
              description
                "Succeed if user has authenticated.";
              type empty;
            }
            leaf none {
              description
                "NO authentication.";
              type empty;
            }
            leaf local {
              description
                "Use local username authentication.";
              type empty;
            }
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
          }
        }
        container a2 {
          when "not(../a1/none) and not(../a1/if-authenticated)" {
          }
          choice auth-choice {
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
            leaf if-authenticated {
              description
                "Succeed if user has authenticated.";
              type empty;
            }
            leaf none {
              description
                "NO authentication.";
              type empty;
            }
            leaf local {
              when "not(../../a1/local)" {
              }
              type empty;
            }
          }
        }
        container a3 {
          when "not(../a2/none) and not (../a1/none) and not(../a2/if-authenticated) and not(../a1/if-authenticated)" {
          }
          choice auth-choice {
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
            leaf none {
              description
                "NO authentication.";
              type empty;
            }
            leaf if-authenticated {
              description
                "Succeed if user has authenticated.";
              type empty;
            }
            leaf local {
              when "not(../../a1/local) and not(../../a2/local)" {
              }
              type empty;
            }
          }
        }
        container a4 {
          when "not(../a2/none) and not(../a1/none) and not(../a3/none) and not(../a2/if-authenticated) and not(../a1/if-authenticated) and not(../a3/if-authenticated)" {
          }
          choice auth-choice {
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
            leaf none {
              description
                "NO authentication.";
              type empty;
            }
            leaf if-authenticated {
              description
                "Succeed if user has authenticated.";
              type empty;
            }
            leaf local {
              when "not(../../a1/local) and not(../../a2/local) and not(../../a3/local)" {
              }
              type empty;
            }
          }
        }
      }
      // aaa authorization auth-proxy
      container auth-proxy {
          description "For Authentication Proxy Services";
          container default {
              description "The default authorization list.";
              container group {
                  description "Use server-group.";
                  leaf radius {
                      description "Use list of all Radius hosts.";
                      type empty;
                  }
          leaf group-name {
                    type string;
                  }
              }
          }
      }
      // aaa authorization onep *
      container onep {
        description "Set authorization lists for ONEP";
        container default {
          description "The default authorization list.";
          container group {
            description "Use Server-group";
            list group-word {
              key "group-word";
              leaf group-word {
                description "Server-group name";
                type string;
              }
            }
          }
        }
      }
    }
    // aaa accounting
    container accounting {
      description
        "Accounting configurations parameters.";
      list commands {
        description
          "For exec (shell) commands.";
        key "level list-name";
        leaf level {
          description
            "Enable level";
          type uint8 {
            range "0..15";
          }
        }
        leaf list-name {
          type union {
            type enumeration {
              enum "default";
            }
            type string {
              length "1..31";
            }
          }
        }
        leaf action-type {
          type enumeration {
            enum "none";
            enum "start-stop";
            enum "stop-only";
          }
        }
        leaf broadcast {
          description
            "Use Broadcast for Accounting";
          type empty;
        }
        leaf group {
          description
            "Use Server-group";
          type union {
            type string;
            type enumeration {
              enum "tacacs+";
            }
          }
        }
      }
      list connection {
        description
          "For outbound connections. (telnet, rlogin)";
        key "name";
        leaf name {
          type string;
        }
        uses aaa-accounting-grouping;
      }
      container delay-start {
        description "Delay PPP Network start record until peer IP address is known.";
        leaf extended-delay {
          description "";
          type uint8 {
            range "1..2";
          }
        }
        leaf all {
          description
            "Delay start records for all vrf and non-vrf users.";
          type empty;
        }
      }
      list dot1x {
        description
          "For dot1x sessions.";
        key "name";
        leaf name {
          type string;
        }
        container start-stop {
          description
            "Record start and stop without waiting";
          leaf broadcast {
            description
              "Use Broadcast for Accounting";
            type empty;
          }
          leaf group {
            description
              "Use Server-group";
            type union {
              type string;
              type enumeration {
                enum "radius";
                enum "tacacs+";
              }
            }
          }
        }
      }
      list exec {
        description
          "For starting an exec (shell).";
        key "name";
        leaf name {
          type string;
        }
        uses aaa-accounting-grouping;
      }
      container exec-submode {
        list exec {
          description
            "For starting an exec (shell).";
          key "name";
          leaf name {
            type string;
          }
          container action-type {
            description
              "Type of action to be performed on accounting records";
            uses aaa-accounting-grouping;
          }
        }
      }
      list network {
        description
          "For network services. (PPP, SLIP, ARAP)";
        key "id";
        leaf id {
          type union {
            type enumeration {
              enum "default";
            }
            type string {
              length "1..31";
            }
          }
        }
        container start-stop {
          description
            "Record start and stop without waiting";

          leaf group {
            description
              "Use Server-group";
            type union {
              type string;
              type enumeration {
                enum "radius";

              }
            }
          }
        }
        choice network-choice {
          case a {
            leaf none {
              description
                "No accounting.";
              type empty;
            }
          }
          case b {
            leaf mode {
              type enumeration {
                enum "start-stop";
                enum "stop-only";
              }
            }
            leaf broadcast {
              description
                "Use Broadcast for Accounting";
              type empty;
            }
            container a1 {
              leaf group {
                description
                  "Use server-group.";
                type union {
                  type string;
                  type enumeration {
                    enum "ldap";
                    enum "radius";
                    enum "tacacs";
                  }
                }
              }
            }
            container a2 {
              leaf group {
                description
                  "Use server-group.";
                type union {
                  type string;
                  type enumeration {
                    enum "ldap";
                    enum "radius";
                    enum "tacacs";
                  }
                }
              }
            }
            container a3 {
              leaf group {
                description
                  "Use server-group.";
                type union {
                  type string;
                  type enumeration {
                    enum "ldap";
                    enum "radius";
                    enum "tacacs";
                  }
                }
              }
            }
            container a4 {
              leaf group {
                description
                  "Use server-group.";
                type union {
                  type string;
                  type enumeration {
                    enum "ldap";
                    enum "radius";
                    enum "tacacs";
                  }
                }
              }
            }
          }
        }
      }
      container send {
        description
          "Send records to accounting server";
        container counters {
          description
            "Enable specific counters in the Stop record";
          leaf ipv6 {
            description
              "Send IPv6 counters in the Stop Record";
            type empty;
          }
        }
        container stop-record {
          description
            "Generate STOP records for a specified event";
          leaf always {
            description
              "Generate STOP records always, even if the START record is not sent";
            type empty;
          }
          container authentication {
            description
              "Generate STOP records for authentication failures";
            container failure {
              description
                "Generate STOP records for authentication failures";
              presence "true";
              leaf vrf {
                description
                  "VPN Routing/Forwarding parameters";
                type string;
              }
            }
            container success {
              description
                "Generate STOP records for authenticated users";
              container remote-server {
                description
                  "Successfully authenticated, through access-accept, by a remote AAA server";
                presence "true";
                leaf vrf {
                  description
                    "VPN Routing/Forwarding parameters";
                  type string;
                }
              }
            }
          }
        }
      }
      container system {
        description
          "For system events.";
        choice default-guarantee-first {
          case default-case {
            container default {
              description
                "The default accounting list.";
              presence "true";
              leaf none {
                description
                  "No accounting.";
                type empty;
              }
              container start-stop {
                description
                  "Record start and stop without waiting";
                leaf broadcast {
                  description
                    "Use Broadcast for Accounting";
                  type empty;
                }
                leaf group {
                  description
                    "Use Server-group";
                  type union {
                    type string;
                    type enumeration {
                      enum "radius";
                      enum "tacacs+";
                    }
                  }
                }
              }
              leaf vrf {
                description
                  "VPN Routing/Forwarding parameters";
                type string;
              }
            }
          }
          case guarantee-first-case {
            leaf guarantee-first {
              description
                "Guarantee system accounting as first record.";
              type boolean;
            }
          }
        }
      }
       container update {
          description "Enable accounting update records";
          leaf periodic {
              description "Periodic intervals to send accounting update records(in minutes)";
              type uint32 {
                  range "1..71582";
              }
          }
      }
      container auth-proxy {
        description
          "For Authentication Proxy Services";
        container default {
          description
            "The default authorization list.";
          container start-stop {
            description
              "Record start and stop without waiting";
            leaf group {
              description
                "Use server-group.";
              type string;
            }
          }
        }
      }
    }
    //aaa server
    container server {
      description
        "Local AAA server";
      container radius {
        description
          "Profile for local radius server";
        container dynamic-author {
          description
            "Local server profile for RFC 3576 support";
      presence true;
          list client {
            description
              "Specify a RADIUS client";
            key ip;
            leaf ip {
              type union {
                type inet:ipv4-address;
                type inet:ipv6-address;
                type string;
              }
            }
            list vrf {
              description
                " Virtual Routing/Forwarding parameters";
              key name;
              leaf name {
                type string;
              }
            }
            container server-key {
              description
                "Specify a RADIUS client server-key";
              leaf key {
                type enumeration {
                  enum "0";
                  enum "6";
                  enum "7";
                }
              }
              leaf string {
                type string;
              }
            }
          }
          container server-key {
            description
              "Specify a RADIUS client server-key";
            leaf key {
              type enumeration {
                enum "0";
                enum "6";
                enum "7";
              }
            }
            leaf string {
              type string;
            }
          }
          container domain {
            description
              "Username domain options";
            leaf delimiter {
              description
                "Domain delimiter, Choose from {@, /, $, %, \, #, -}";
              type string;
            }
            container stripping {
              description
                "Match incoming username left oriented of the @ domain delimiter";
              presence true;
              leaf right-to-left {
                description
                  "Terminate the string at the first delimiter going from right to left";
                type empty;
              }
            }
          }
          leaf auth-type {
            description
              "Specify the server authorization type";
            type enumeration {
              enum all;
              enum any;
              enum session-key;
            }
          }
        }
      }
    }
    // aaa session-id
    leaf session-id {
      description
        "AAA Session ID";
      type enumeration {
        enum "common";
        enum "unique";
      }
    }
  }

  grouping config-radius-grouping {
    list filter {
      description
        "Packet filter configuration";
      key "id";
      leaf id {
        type string;
      }
      leaf match {
        type enumeration {
          enum "match-all";
          enum "match-any";
        }
      }
    }
    list server {
      description
        "Server configuration";
      key "id";
      leaf id {
        type string;
      }
      container address {
        description
          "Specify the radius server address";
        container ipv4 {
          description
            "IPv4 Address";
          leaf host {
            type string;
          }
          leaf auth-port {
            description
              "UDP port for RADIUS authentication server (default is 1645)";
            type uint16 {
              range "0..65535";
            }
          }
          leaf acct-port {
            description
              "UDP port for RADIUS accounting server (default is 1646)";
            type uint16 {
              range "0..65535";
            }
          }
        }
      }
      container backoff {
        description
          "Retry backoff pattern(Default is retransmits with constant delay)";
        container exponential {
          description
            "Exponential retransmit backoff";
          presence "true";
          leaf max-delay {
            description
              "Max delay between retransmits(default is 3 min)";
            type uint8 {
              range "1..120";
            }
          }
          leaf backoff-retry {
            description
              "Exponential backoff retry number(default is 8)";
            type uint8 {
              range "1..50";
            }
          }
        }
      }
      container key {
        description
          "Per-server encryption key";
        leaf encryption {
          type enumeration {
            enum "0";
            enum "5";
          }
        }
        leaf key {
          type string;
        }
      }
      container pac {
        description
          "Protected Access Credential key";
        container key {
          description
            "Per-server encryption key";
          leaf encryption {
            type enumeration {
              enum "0";
              enum "6";
              enum "7";
            }
          }
          leaf key {
            type string;
          }
        }
      }
    }
  }

  grouping config-radius-server-grouping {
    // radius-server attribute           Customize selected radius attributes
    list attribute {
      description
        "Customize selected radius attributes";
      key "number";
      leaf number {
        type uint32;
      }
      leaf-list send-attribute {
        type enumeration {
          enum "on-for-login-auth";
          enum "include-in-access-req";
          enum "support-multiple";
        }
      }
      container access-request {
        description
          "Access-Request packet";
        when "../number = '25'";
        leaf include {
          description
            "Include attribute";
          type empty;
        }
      }
    }
    //  authorization       Authorization processing information
    //  backoff             Retry backoff pattern(Default is retransmits with
    //                      constant delay)
    //  cache               AAA auth cache default server group
    //  challenge-noecho    Data echoing to screen is disabled during
    //                      Access-Challenge
    //  configure-nas       Attempt to upload static routes and IP pools
    //                      at startup
    //  dead-criteria       Set the criteria used to decide when a radius
    // snmp-server dead-criteria       Set the criteria used to decide when a radius
    container dead-criteria {
      description
        "Set the criteria used to decide when a radius server ismarked dead";
      leaf time {
        description
          "The time during which no properly formed response must be recievedfrom the RADIUS server";
        type uint8 {
          range "1..120";
        }
      }
      leaf tries {
        description
          "The number of times the router must fail to recieve a response fromthe radius server to mark it as dead";
        type uint8 {
          range "1..100";
        }
      }
    }
    //                      server is marked dead
    //  deadtime            Time to stop using a server that doesn't respond
    // radius-server deadtime *
    leaf deadtime {
      description
        "Time to stop using a server that doesn't respond";
      type uint32 {
        range "1..1440";
      }
    }
    //  directed-request    Allow user to specify radius server to use
    //                      with `@server'
    //  domain-stripping    Strip the domain from the username
    // radius-server host *
    list host {
      description
        "Specify a RADIUS server";
      key "id";
      leaf id {
        type union {
          type string;
          type inet:ipv4-address;
        }
      }
      // radius-server host * auth-port
      leaf auth-port {
        description
          "UDP port for RADIUS authentication server (default is 1645)";
        type uint16 {
          range "0..65535";
        }
      }
      // radius-server host * acct-port
      leaf acct-port {
        description
          "UDP port for RADIUS accounting server (default is 1646)";
        type uint16 {
          range "0..65535";
        }
      }
      //  alias         1-8 aliases for this server (max. 8)
      //  backoff       Retry backoff pattern (Default is retransmits with
      //                constant delay)
      //  non-standard  Parse attributes that violate the RADIUS standard
      // radius-server host * retransmit
      //  retransmit    Specify the number of retries to active server
      //                (overrides default)
      leaf retransmit {
        description
          "Specify the number of retries to active server";
        type uint8 {
          range "1..100";
        }
      }
      //  test          Configure server automated testing.
      // radius-server host * test
      container test {
        description
          "Configure server automated testing";
        list username {
          description
            "A name (from local database) that should be used to send requests.";
          key "name";
          leaf name {
            type string;
          }
          container key {
            description
              "per-server encryption key (overrides default)";
            leaf encryption {
              type enumeration {
                enum "0";
                enum "7";
              }
            }
            leaf clear-key {
              type string;
            }
          }
        }
      }
      // radius-server host * timeout
      leaf timeout {
        description
          "Time to wait for a RADIUS server to reply (overrides default)";
        type uint16 {
          range "1..1000";
        }
      }
      // radius-server host * key
      leaf key {
        description
          "per-server encryption key (overrides default)";
        type union {
          type enumeration {
            enum "0";
            enum "7";
          }
          type string;
        }
      }
      leaf clear-key {
        when "../key = '0' or ../key = '7'";
        type string;
      }
      //  non-standard  Parse attributes that violate the RADIUS standard
    }
    //  key                 encryption key shared with the radius servers
    container key {
      description
        "encryption key shared with the radius servers";
      leaf encryption {
        type enumeration {
          enum "0";
          enum "7";
        }
      }
      leaf clear-key {
        type string;
      }
    }
    //  load-balance        Radius load-balancing options.
    //  optional-passwords  The first RADIUS request can be made without
    //                      requesting a password
    //  retransmit          Specify the number of retries to active server
    leaf retransmit {
      description
        "Specify the number of retries to active server";
      type uint8 {
        range "1..100";
      }
    }
    //  retry               Specify how the next packet is sent after timeout.
    //  source-ports
    container source-ports {
      description
        "source ports used for sending out RADIUS requests";
      leaf extended {
        description
          "Use 200 source-ports between 21645-21844";
        type empty;
      }
    }
    //  timeout             Time to wait for a RADIUS server to reply
    leaf timeout {
      description
        "Time to wait for a RADIUS server to reply";
      type uint16 {
        range "1..1000";
      }
    }
    //  transaction         Specify per-transaction parameters
    //  unique-ident        Higher order bits of Acct-Session-Id
    // radius-server vsa *                Vendor specific attribute configuration
    container vsa {
      description
        "Vendor specific attribute configuration";
      container disallow {
        description
          "Forbid certain VSA behaviour";
        leaf unknown {
          description
            "Forbid unknown VSAs";
          type empty;
        }
      }
      container send {
        description
          "Send vendor-specific attributes in requests";
        presence "true";
        container accounting {
          description
            "Send in accounting requests";
          presence "true";
          leaf threegpp2 {
            description
              "Send 3GPP2 VSAs in accounting requests";
            type empty;
          }
        }
        container authentication {
          description
            "Send in access requests";
          presence "true";
          leaf threegpp2 {
            description
              "Send 3GPP2 VSAs in accounting requests";
            type empty;
          }
        }
        container cisco-nas-port {
          description
            "Send cisco-nas-port VSA(2)";
          presence "true";
          leaf threegpp2 {
            description
              "Send 3GPP2 VSAs in accounting requests";
            type empty;
          }
        }
      }
    }
  }

  grouping config-ip-radius-grouping {
    container radius {
      description
        "RADIUS configuration commands";
      container source-interface {
        description
          "Specify interface for source address in RADIUS packets";
        uses ios-ifc:interface-grouping;
      }
    }
  }

  grouping config-tacacs-grouping {
    list server {
      description
        "Server configuration";
      key "name";
      leaf name {
        type string;
      }
      container address {
        description
          "Specify ip address for tacacs server";
        leaf ipv4 {
          description
            "Configure ipv4 address for tacacs server";
          type union {
            type string;
            type inet:ipv4-address;
          }
        }
      }
      container key {
        description
          "per-server encryption key (overrides default)";
        leaf encryption {
          type enumeration {
            enum "0";
            enum "7";
          }
        }
        leaf key {
          type string;
        }
      }
    }
  }

  grouping config-tacacs-server-grouping {
    // tacacs-server host *
    list host {
      description
        "Specify a TACACS server";
      key "name";
      leaf name {
        type ios-types:host-type;
      }
      // tacacs-server host * port
      leaf port {
        description
          "TCP port for TACACS+ server (default is 49)";
        type uint16 {
          range "1..65535";
        }
      }
      // tacacs-server host * key
      leaf key {
        description
          "Set TACACS+ encryption key.";
        type union {
          type enumeration {
            enum "0";
            enum "7";
          }
          type string;
        }
      }
      leaf encryption-key {
        when "../key = '0' or ../key = '7'";
        type string;
      }
      // tacacs-server host * timeout
      leaf timeout {
        description
          "Time to wait for this TACACS server to reply (overrides default)";
        type uint16 {
          range "1..1000";
        }
      }
    }
    // tacacs-server timeout
    leaf timeout {
      description
        "Time to wait for a TACACS server to reply";
      type uint16 {
        range "1..1000";
      }
    }
    // tacacs-server directed-request
    container directed-request {
      description
        "Allow user to specify tacacs server to use with `@server'";
      presence "true";
      leaf restricted {
        description
          "restrict queries to directed request servers only";
        type empty;
      }
      leaf no-truncate {
        description
          "Do not truncate the @hostname from username.";
        type empty;
      }
    }
    // tacacs-server key
    container key {
      description
        "Set TACACS+ encryption key.";
      leaf encryption {
        type enumeration {
          enum "0";
          enum "7";
        }
      }
      leaf key {
        type string;
      }
    }
  }

  grouping config-ip-tacacs-main-grouping {
    container source-interface {
      description
        "Specify interface for source address in TACACS packets";
      uses ios-ifc:interface-grouping;
    }
  }

  grouping config-ip-tacacs-grouping {
    container tacacs {
      description
        "TACACS configuration commands";
      uses config-ip-tacacs-main-grouping;
    }
  }

  /////////////////////////////////////////////////////////
  // native / aaa *
  /////////////////////////////////////////////////////////
  augment "/ios:native/ios:aaa" {
      uses config-aaa-grouping;
  }

  /////////////////////////////////////////////////////////
  // native / radius *
  /////////////////////////////////////////////////////////
  augment "/ios:native/ios:radius" {
    uses config-radius-grouping;
  }

  /////////////////////////////////////////////////////////
  // native / radius-server *
  /////////////////////////////////////////////////////////
  augment "/ios:native/ios:radius-server" {
    uses config-radius-server-grouping;
  }

  /////////////////////////////////////////////////////////
  // native / ip / radius *
  /////////////////////////////////////////////////////////
  augment "/ios:native/ios:ip" {
    uses config-ip-radius-grouping;
  }

  /////////////////////////////////////////////////////////
  // native / tacacs *
  /////////////////////////////////////////////////////////
  augment "/ios:native/ios:tacacs" {
    uses config-tacacs-grouping;
  }

  /////////////////////////////////////////////////////////
  // native / tacacs server *
  /////////////////////////////////////////////////////////
  augment "/ios:native/ios:tacacs-server" {
    uses config-tacacs-server-grouping;
  }

  /////////////////////////////////////////////////////////
  // native / ip / tacacs *
  /////////////////////////////////////////////////////////
  augment "/ios:native/ios:ip" {
    uses config-ip-tacacs-grouping;
  }
}
