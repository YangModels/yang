module Cisco-IOS-XE-platform-software-oper {

    yang-version 1;

    namespace "http://cisco.com/ns/yang/Cisco-IOS-XE-platform-software-oper";
    prefix platform-sw-ios-xe-oper;

    organization
    "Cisco Systems, Inc.";

    contact
        "Cisco Systems, Inc. Customer Service Postal: 170 W Tasman Drive
         San Jose, CA 95134 Tel: +1 1800 553-NETS E-mail: cs-yang@cisco.com";
    
    description
       "This module contains a collection of YANG definitions for
        monitoring the platform software in a Network Element."+
        "Copyright (c) 2016-2017 by Cisco Systems, Inc."+
        "All rights reserved."; 

  // =========================================================================
  // REVISION 
  // =========================================================================

  revision 2017-02-07 {
    description
      "Initial revision";
  }
    
    
    grouping min-status {
        leaf condition {
            type string;
            description
               "Need description";
        }

        leaf threshold-status {
            type string;
            description
               "Need description";
        }

        leaf threshold-value {
            type string;
            description
               "Format: Decimal with 2 fraction digits";
        }
    }

    grouping minute {
        leaf number {
            type uint64;
            description
                "The number of minutes the average was calculated on.";
        }
                
        leaf average {
            type string;
            description
                    "Format: Decimal with 2 fraction digits";
        }

        container status {
            uses platform-sw-ios-xe-oper:min-status;
        }                
    }

    grouping load-average-stats {
        leaf load-average-status {
            type string;
        }
    }

    grouping memory-status {
        leaf condition {
            type string;
            description
               "Need description";
        }

        leaf threshold-status {
            type string;
            description
               "Need description";
        }

        leaf threshold-value-percent {
            type uint64;
            description
               "Need description";
        }
    }

    grouping  platform-memory-stats {
        leaf memory-status {
            type string;
            description
                "The status of the memory";
        }
            
        leaf total {
            type uint64;
            description
                "The total number of memory in kb";
        }
            
        leaf used-number {
            type uint64;
            description
                "The number of memory being used in kb";
        }
            
        leaf used-percent {
            type uint64;
            description
                "The percentage of memory being used";
        }
            
        leaf free-number {
            type uint64;
            description
                "The number of free memory in kb";
        }
            
        leaf free-percent {
            type uint64;
            description
                "The percentage of free memory";
        }
        
        leaf available-number {
            type uint64;
            description
                "The number of available memory in kb";
        }

        leaf available-percent {
            type uint64;
            description
               "The percentage of available memory";
        }

        leaf committed-number {
            type uint64;
            description
                "The number of committed memory in kb";
        }
            
        leaf committed-percent {
            type uint8;
            description
                "The percentage of comitted memory";
        }

        container status {
            uses platform-sw-ios-xe-oper:memory-status;
        }
    }

    grouping core {
        leaf name {
            type string;
            description
                "The name of the core";
        }
                
        leaf user {
            type string;
            description
                "The percentage of utilization by user
                                 Format: Decimal with 2 fraction digits";
        }
                
        leaf system {
            type string;
            description
                "The percentage of utilization by the system
                                 Format: Decimal with 2 fraction digits";
        }
                
        leaf nice {
            type string;
            description
                "The percentage of utilization by nice
                                 Format: Decimal with 2 fraction digits";
        }
                
        leaf idle {
            type string;
            description
                "The percentage that is idle
                                 Format: Decimal with 2 fraction digits";
        } 
                
        leaf irq {
            type string;
            description
                "The percentage of utilizaion by irq
                                 Format: Decimal with 2 fraction digits";
        }
                
        leaf sirq {
            type string;

            description
                "The percentage of utilizaion by sirq
                                 Format: Decimal with 2 fraction digits";
        }
                
        leaf io-wait {
            type string;
            description
                "The percentage of utilization by IOwait
                                 Format: Decimal with 2 fraction digits";
        }
    }

    grouping control-process {
        leaf name {
            type string;
            description
                    "Name of the control process";
        }
 
        leaf status {
            type string;
            description
                "Status of the control processer";
        }
        
        leaf updated {
            type uint64;
            description
                "Number of seconds since the data has been updated.";
        }
        
        container load-average-stats {
            description
                "Statistics on the load average.";
                
            uses platform-sw-ios-xe-oper:load-average-stats;
        } 

        container load-avg-minutes {

            list load-avg-minute {
                key "number";
                description
                    "Load average statistics based on a time frame";
                uses platform-sw-ios-xe-oper:minute;
            }
        }
        
        container memory-stats {
            description
                "The statistics on the memory";
                
            uses platform-sw-ios-xe-oper:platform-memory-stats;
        } 

        container per-core-stats {
            description
                "Statistics on each core";
        
            list per-core-stat {
                key "name";
                description
                    "A Core";

                uses platform-sw-ios-xe-oper:core;
            }
        }
    }

    grouping platform-software-status-control-process {
        description
            "Contents of the show platform software status control process cli.";

        container control-processes {
 
            list control-process {
                key "name";
                description
                    "Control process";

                uses platform-sw-ios-xe-oper:control-process;
            }
        }
    }

    grouping interface-xos {
        leaf name {
            type string;
            description
                "DESCRPITION NEEDED";
       }
            
       leaf id {
           type uint64;
           description
               "DESCRPITION NEEDED";
       }
            
       leaf qfp-id {
           type uint64;
           description
               "DESCRPITION NEEDED";
        }
    }

    grouping platform-software-interface-rp-active-brief-forwarding {
        description
            "DESCRIPTION NEEDED";
        
        container xos-interfaces {
            list xos-interface {
                key "name";
                description
                    "DESCRIPTION NEEDED";

                uses platform-sw-ios-xe-oper:interface-xos;
            }
        }
    }

    grouping cisco-platform-software {
        container platform-software-status-control-processes {
            description
                "Contents of the show platform software status control process cli.";

            uses platform-sw-ios-xe-oper:platform-software-status-control-process;
        }

        container platform-software-interface-rp-active-brief-forwarding  {
            description
                "DESCRIPTION NEEDED";
        
            uses platform-sw-ios-xe-oper:platform-software-interface-rp-active-brief-forwarding;
        }
    }

    container cisco-platform-software {
        config false;
 
        uses platform-sw-ios-xe-oper:cisco-platform-software;
    }
}
