module Cisco-IOS-XE-checkpoint-archive-oper {

    yang-version 1;

    namespace "http://cisco.com/ns/yang/Cisco-IOS-XE-checkpoint-archive-oper";
    prefix checkpoint-archive-ios-xe-oper;

    organization
    "Cisco Systems, Inc.";

   contact
       "Cisco Systems, Inc. Customer Service Postal: 170 W Tasman Drive
        San Jose, CA 95134 Tel: +1 1800 553-NETS E-mail: cs-yang@cisco.com";
    
    description
       "This module contains a collection of YANG definitions for
        monitoring the checkpoint archives in a Network Element."+
       "Copyright (c) 2016-2017 by Cisco Systems, Inc."+
       "All rights reserved."; 

  // =========================================================================
  // REVISION 
  // =========================================================================

  revision 2017-02-07 {
    description
      "Initial revision";
  }
    
       

    grouping archive {
        leaf number {
            type uint16;
            description
                "The archive number";
        }
        
        leaf name {
            type string;
            description
                "the name of the archive";
        }
    }

    grouping checkpoint-archive {
        leaf max {
            type uint8;
            description
                "The maxium number of archives";
        }
    
        leaf current {
            type uint8;
            description
                "The current number of archives";
        }
    
        leaf recent {
            type string;
            description
                "The most recent archive";
        }

        container archives {

            list archive {
                key "number";
                description
                    "Archive information";
                uses checkpoint-archive-ios-xe-oper:archive;
            }
        }
    }
  
    container checkpoint-archive {
        config false;
        description
            "Contents of the show archive cli";
        uses checkpoint-archive-ios-xe-oper:checkpoint-archive;
    }
}
