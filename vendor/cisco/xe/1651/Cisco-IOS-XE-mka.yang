module Cisco-IOS-XE-mka {
  namespace "http://cisco.com/ns/yang/Cisco-IOS-XE-mka";
  prefix ios-mka;

  import Cisco-IOS-XE-native {
    prefix ios;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE  Macsec Key Agreement protocol (MKA) Yang Model.
     Copyright (c) 2016 by Cisco Systems, Inc.
     All rights reserved."; 

  // =========================================================================
  // REVISION 
  // =========================================================================

  revision 2017-02-07 {
    description
      "Initial revision";
  }

  grouping config-mka-grouping {
      list policy {
        description "Configure MKA Policy";
        key "name";
        leaf name {
          description "MKA Policy NAME";
          type string;
        }
        container macsec-cipher-suite {
          description "Cipher Suite for SAK derivation";
          leaf gcm-aes-128 {
            description
              "GCM-AES-128 Cipher Suite";
            type empty;
          }
          leaf gcm-aes-256 {
            description
              "GCM-AES-256 Cipher Suite";
            type empty;
          }
        }
      }
  }

  grouping config-interface-mka-grouping {
    container mka {
      description
        "MACsec Key Agreement (MKA) interface configuration";
      container pre-shared-key {
        description
          "Configure MKA Pre-Shared-Key";
        container key-chain {
          description
            "Configure the key-chain name";
          leaf name {
            description
              "Name of key-chain to be used to get keys";
            type string;
          }
        }
      }
    }
  }

  /////////////////////////////////////////////////////////
  // native / mka
  /////////////////////////////////////////////////////////
  augment "/ios:native/ios:mka" {
    uses config-mka-grouping;
  }

  /////////////////////////////////////////////////////////
  // interface * / mka 
  /////////////////////////////////////////////////////////
  augment "/ios:native/ios:interface/ios:FastEthernet" {
    uses config-interface-mka-grouping;
  }

  augment "/ios:native/ios:interface/ios:GigabitEthernet" {
    uses config-interface-mka-grouping;
  }

  augment "/ios:native/ios:interface/ios:TenGigabitEthernet" {
    uses config-interface-mka-grouping;
  }
}
