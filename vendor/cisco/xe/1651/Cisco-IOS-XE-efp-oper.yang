module Cisco-IOS-XE-efp-oper {

    yang-version 1;

    namespace "http://cisco.com/ns/yang/Cisco-IOS-XE-efp-oper";
    prefix efp-stats-ios-xe-oper;

    import ietf-yang-types {
        prefix yang;
    }

    organization
        "Cisco Systems, Inc.";

    contact
         "Cisco Systems, Inc. Customer Service Postal: 170 W Tasman Drive
          San Jose, CA 95134 Tel: +1 1800 553-NETS E-mail: cs-yang@cisco.com";

    description
    "This module contains a collection of YANG definitions for
     service instance (efp) stats"+
        "Copyright (c) 2016-2017 by Cisco Systems, Inc."+
        "All rights reserved."; 

  // =========================================================================
  // REVISION 
  // =========================================================================

  revision 2017-02-07 {
    description
      "Initial revision";
  }
    
 
    grouping efp-key {
        leaf id {
            type uint32;
        }
        leaf interface {
            type string;
        }
    }

    grouping efp-params {
        leaf in-pkts {
            type yang:counter64;
        }
        leaf in-bytes {
            type yang:counter64;
        }
        leaf out-pkts {
            type yang:counter64;
        }
        leaf out-bytes {
            type yang:counter64;
        }
    }
   
    container efp-stats {
        config false;

        description
            "Service instance stats";

        list efp-stat {
            key "id interface";

            uses efp-stats-ios-xe-oper:efp-key;
            uses efp-stats-ios-xe-oper:efp-params;
        }
    }
}
