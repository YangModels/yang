module Cisco-IOS-XE-eem {
  namespace "http://cisco.com/ns/yang/Cisco-IOS-XE-eem";
  prefix ios-eem;

  import ietf-inet-types {
    prefix inet;
  }


  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Embedded Event Manager (EEM) Yang model.
     Copyright (c) 2016 by Cisco Systems, Inc.
     All rights reserved."; 

  // =========================================================================
  // REVISION 
  // =========================================================================

  revision 2017-02-07 {
    description
      "Initial revision";
  }

  typedef operator-type {
    type enumeration {
      enum "eq";
      enum "ge";
      enum "gt";
      enum "le";
      enum "lt";
      enum "ne";
    }
  }

  grouping config-eem-grouping {
    container manager {
      description
        "Event Manager configuration commands";
      // event manager environment *
      list environment {
        description
          "Set an Embedded Event Manager global environment variable";
        key "name";
        leaf name {
          type string;
        }
        leaf value {
          type string;
        }
      }
      // event manager directory
      container directory {
        description
          "Set Embedded Event Manager directory information";
        container user {
          description
            "Set Embedded Event Manager user directory information";
          leaf policy {
            description
              "Set Embedded Event Manager user policy directory";
            type string;
          }
        }
      }
      // event manager session
      container session {
        description
          "Set Embedded Event Manager session attributes";
        container cli {
           description
            "Set Embedded Event Manager session cli attributes";
           container username {
              description
                "Set username used in Embedded Event Manager cli sessions";
              list username_in_word {
                key "username_in_word";
                leaf username_in_word {
                  type string;
                }
                leaf privilege {
                  description
                    "Set user privilege level";
                  type uint8 {
                    range "0..15";
                  }
                }
              }
            }
         }
      }
      // event manager applet *
      list applet {
        description
          "Register an Event Manager applet";
        key "name";
        leaf name {
          type string;
        }
        leaf authorization {
          description
            "Specify an authorization type for the applet";
          type enumeration {
            enum "bypass";
          }
        }
        leaf class {
          description
            "Specify a class for the applet";
          type string {
            pattern "[A-Z]|default";
          }
        }
        leaf trap {
          description
            "Generate an SNMP trap when applet is triggered.";
          type empty;
        }
        container event {
          description
            "Add or modify event information";
          container timer {
            description
              "Timer event";
            container watchdog {
              description
                "Watchdog timer event";
              container name {
                description
                  "Name of the timer";
                list timer-name {
                  key "timer-name";
                  leaf timer-name {
                    type string;
                  }
                  container time {
                    description
                      "Time period for watchdog / countdown / absolute timer";
                    list time-in-seconds {
                      key "time-in-seconds";
                      leaf time-in-seconds {
                        description
                          "Enter seconds[.milliseconds] value";
                        type uint32 {
                          range "1..2085978494";
                        }
                      }
                      container maxrun {
                        description
                          "Maximum runtime of applet";
                        list timer-in-seconds {
                          key "timer-in-seconds";
                          leaf timer-in-seconds {
                            description
                              "Enter seconds[.milliseconds] value";
                            type uint32 {
                              range "0..31536000";
                            }
                          }
                          leaf ratelimit {
                            description 
                              "Limit trigger to once per given time period.
                               Enter seconds[.milliseconds] value";
                            type uint32 {
                               range "0..31536000";
                            }
                          }
                        }
                      }
                    }
                  }
                }
              }
            }
          } 

          container snmp-notification {
            description
              "SNMP Notification Event";
            leaf oid {
              description
                "Object ID of data element";
              type string;
            }
            leaf oid-val {
              description
                "Comparison value";
              type string;
            }
            leaf op {
              description
                "Operator";
              type operator-type;
            }
            leaf src-ip-address {
              description
                "Source ip address";
              type union {
                type inet:ipv4-address;
                type inet:ipv6-address;
              }
            }
            leaf dest-ip-address {
              description
                "Destination ip address";
              type union {
                type inet:ipv4-address;
                type inet:ipv6-address;
              }
            }
          }
          container syslog {
            description
              "Syslog event";
            leaf pattern {
              description
                "Pattern match string for the entire message";
              type string;
            }
          }
        }
        list action {
          description
            "Add or modify an action statement";
          ordered-by user;
          key "name";
          leaf name {
            type string;
          }
          container if {
            description
              "if conditional";
            leaf string-op-1 {
              type string;
            }
            leaf keyword {
              type operator-type;
            }
            leaf string-op-2 {
              type string;
            }
            leaf goto {
              description
                "goto label";
              type string;
            }
          }
          container info {
            description
              "Obtain system specific information";
            container type {
              description
                "Type of information to obtain";
              container snmp {
                description
                  "SNMP information";
                container var {
                  description
                    "Trap variable";
                  leaf variable-name {
                    type string;
                  }
                  leaf oid {
                    description
                      "SNMP object id";
                    type string;
                  }
                  leaf oid-type {
                    type enumeration {
                      enum "counter";
                      enum "gauge";
                      enum "int";
                      enum "ipv4";
                      enum "octet";
                      enum "string";
                      enum "uint";
                    }
                  }
                  leaf oid-type-value {
                    type string;
                  }
                }
                container trap {
                  description
                    "SNMP trap";
                  leaf enterprise-oid {
                    description
                      "Enterprise oid";
                    type string;
                  }
                  leaf generic-trapnum {
                    description
                      "Generic trap number";
                    type uint32;
                  }
                  leaf specific-trapnum {
                    description
                      "Specific trap number";
                    type uint32;
                  }
                  leaf trap-oid {
                    description
                      "Trap oid";
                    type string;
                  }
                  leaf trap-var {
                    description
                      "Trap variable";
                    type string;
                  }
                }
              }
            }
          }
          leaf end {
            description
              "end conditional block";
            type empty;
          }
          container regexp {
            description
              "regular expression match";
            leaf string-pattern {
              type string;
            }
            leaf string-input {
              type string;
            }
            leaf string-match {
              type string;
            }
            leaf string-submatch1 {
              type string;
            }
            leaf string-submatch2 {
              type string;
            }
            leaf string-submatch3 {
              type string;
            }
          }
          container snmp-trap {
            description
              "Send an SNMP trap";
            presence "true";
            leaf intdata1 {
              description
                "SNMP integer data1";
              type int32;
            }
            leaf intdata2 {
              description
                "SNMP integer data2";
              type int32;
            }
            leaf strdata {
              description
                "SNMP trap string";
              type string;
            }
          }
          container string {
            description
              "string commands";
            leaf trim {
              description
                "trim characters from both ends of string";
              type string;
            }
          }
          container syslog {
            description
              "Log a syslog message";
            leaf facility {
              description
                "Facility string";
              type string;
            }
            leaf msg {
              description
                "Syslog message";
              type string;
            }
            leaf priority {
              description
                "Priority of syslog message";
              type ios:logging-level-type;
            }
          }
        }
        leaf description {
          description
            "Add or modify an applet description";
          type string;
        }
        // event manager applet * / trigger
        container trigger {
          description
            "Enter applet trigger configuration submode";
        }
      }
    }
  }

  /////////////////////////////////////////////////////////
  // native / event
  /////////////////////////////////////////////////////////
  augment "/ios:native/ios:event" {
    uses config-eem-grouping;
  }
}
