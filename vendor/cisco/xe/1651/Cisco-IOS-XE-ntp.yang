module Cisco-IOS-XE-ntp {
  namespace "http://cisco.com/ns/yang/Cisco-IOS-XE-ntp";
  prefix ios-ntp;

  import ietf-inet-types {
    prefix inet;
  }


  import Cisco-IOS-XE-types {
    prefix ios-types;
  }

  import Cisco-IOS-XE-native {
    prefix ios;
  }

  import Cisco-IOS-XE-interface-common {
    prefix ios-ifc;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Network Time Protocol (NTP) Yang model.
     Copyright (c) 2016 by Cisco Systems, Inc.
     All rights reserved."; 

  // =========================================================================
  // REVISION 
  // =========================================================================

  revision 2017-02-07 {
    description
      "Initial revision";
  }

  grouping ntp-access-group-kod-grouping {
    leaf acl {
      type ios-types:std-acl-type;
    }
    leaf kod {
      description
        "Send a Kiss-o-Death packet for failing peers";
      type empty;
    }
  }

  grouping ntp-access-group-grouping {
    container peer {
      description
        "Provide full access";
      uses ntp-access-group-kod-grouping;
    }
    //  query-only  Allow only control queries
    container query-only {
      description
        "Provide server and query access";
      uses ntp-access-group-kod-grouping;
    }
    container serve {
      description
        "Provide server and query access";
      uses ntp-access-group-kod-grouping;
    }
    //  serve-only  Provide only server access
    container serve-only {
      description
        "Provide only server access";
      uses ntp-access-group-kod-grouping;
    }
  }

  grouping ntp-peer-server-attr-grouping {
    leaf burst {
      description
        "Send a burst when peer is reachable (Default)";
      type empty;
    }
    leaf iburst {
      description
        "Send a burst when peer is unreachable (Default)";
      type empty;
    }
    leaf key {
      description
        "Configure peer authentication key";
      type uint32;
    }
    leaf maxpoll {
      description
        "Maximum poll interval";
      type uint8 {
        range "4..17";
      }
    }
    leaf minpoll {
      description
        "Minimum poll interval";
      type uint8 {
        range "4..17";
      }
    }
    leaf prefer {
      description
        "Prefer this peer when possible";
      type empty;
    }
    leaf source {
      description
        "Interface for source address";
      type string;
    }
    leaf version {
      description
        "    Configure NTP version";
      type uint8;
    }
  }

  grouping ntp-peer-server-grouping {
    list server-list {
      key "ip-address";
      leaf ip-address {
        type union {
          type inet:ipv4-address;
          type string;
          type inet:ipv6-address;
        }
      }
      uses ntp-peer-server-attr-grouping;
    }
    list ip {
      description
        "Use IP for DNS resolution";
      key "host-name";
      leaf host-name {
        type string;
      }
      uses ntp-peer-server-attr-grouping;
    }
    list ipv6 {
      description
        "Use IPv6 for DNS resolution";
      key "host-name";
      leaf host-name {
        type string;
      }
      uses ntp-peer-server-attr-grouping;
    }
  }

  grouping config-ntp-grouping {
    container access-group {
      description
        "Control NTP access";
      container ipv4 {
        description
          "ipv4 access lists";
        uses ntp-access-group-grouping;
      }
      container ipv6 {
        description
          "ipv6 access lists";
        uses ntp-access-group-grouping;
      }
      uses ntp-access-group-grouping;
    }
    container allow {
      description
        "Allow processing of packets";
      container mode {
        description
          "Allow processing of particular mode packets";
        container control {
          description
            "Allow processing control mode packets";
          presence "true";
          leaf delay {
            description
              "Rate limiting delay (s)";
            type uint8 {
              range "3..15";
            }
          }
        }
        leaf private {
          description
            "Allow processing private mode packets";
          type empty;
        }
      }
    }
    leaf authenticate {
      description
        "Authenticate time sources";
      type empty;
    }
    list authentication-key {
      description
        "Authentication key for trusted time sources";
      key "number";
      leaf number {
        type uint32;
      }
      leaf md5 {
        description
          "MD5 authentication";
        type string;
      }
      leaf encryption-type {
        type uint32;
      }
    }
    leaf broadcastdelay {
      description
        "Estimated round-trip delay in microseconds";
      type uint32 {
        range "1..999999";
      }
    }
    leaf clock-period {
      description
        "Length of hardware clock tick";
      type uint32;
    }
    // authenticate  Authenticate time sources
    // authentication-key Authentication key for trusted time sources
    // broadcastdelay  Estimated round-trip delay

    // should be ignored, stripped by the java code
    // leaf clock-period {
    //   type uint32 {
    //   }
    // }

    // logging Enable NTP message logging
    // ntp logging
    leaf logging {
      description
        "Enable NTP message logging";
      type empty;
    }
    // master Act as NTP master clock
    // ntp master
    container master {
      description
        "Act as NTP master clock";
      presence "true";
      leaf stratum-number {
        type uint8 {
          range "1..15";
        }
      }
    }
    // max-associations Set maximum number of associations
    // ntp max-associations
    leaf max-associations {
      description
        "Set maximum number of associations";
      type uint32;
    }
    leaf maxdistance {
      description
        "Maximum Distance for synchronization";
      type uint8 {
        range "1..16";
      }
    }
    leaf mindistance {
      description
        "Minimum distance to consider for clockhop";
      type uint16 {
        range "1..500";
      }
    }
    //ntp orphan
    leaf orphan {
      description
        "Threshold Stratum for orphan mode";
      type uint8 {
        range "1..16";
      }
    }
    //ntp panic
    container panic {
      description
        "Reject time updates > panic threshold (default 1000Sec)";
      leaf update {
        description
          "Reject time updates > panic threshold (default 1000Sec)";
        type empty;
      }
    }
    //ntp passive
    leaf passive {
      description
        "NTP passive mode";
      type empty;
    }
    //ntp peer
    // peer Configure NTP peer
    container peer {
      description
        "Configure NTP peer";
      uses ntp-peer-server-grouping;
      list vrf {
        description
          "VPN Routing/Forwarding Information";
        key "name";
        leaf name {
          type string;
        }
        uses ntp-peer-server-grouping;
      }
    }
    // ntp server
    container server {
      description
        "Configure NTP server";
      uses ntp-peer-server-grouping;
      list vrf {
        description
          "VPN Routing/Forwarding Information";
        key "name";
        leaf name {
          type string;
        }
        uses ntp-peer-server-grouping;
      }
    }
    // ntp source
    container source {
      description
        "Configure interface for source address";
      uses ios-ifc:interface-grouping;
    }
    // trusted-key Key numbers for trusted time sources
    list trusted-key {
      description
        "Key numbers for trusted time sources";
      key "number";
      leaf number {
        type uint16;
      }
      leaf end-key {
        description
          "End Key";
        type uint16;
      }
    }

    // ntp update-calender
    leaf update-calendar {
      description
        "Periodically update calendar with NTP time";
      type empty;
    }
  }

  /////////////////////////////////////////////////////////
  // native / ntp
  /////////////////////////////////////////////////////////
  augment "/ios:native/ios:ntp" {
    uses config-ntp-grouping;
  }
}
