module Cisco-IOS-XE-segment-routing{
  namespace "http://cisco.com/ns/yang/Cisco-IOS-XE-segment-routing";
  prefix ios-segment-routing;

  import ietf-inet-types {
    prefix inet;
  }


  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Segment Routing Yang model.
     Copyright (c) 2016 by Cisco Systems, Inc.
     All rights reserved."; 

  // =========================================================================
  // REVISION 
  // =========================================================================

  revision 2017-02-07 {
    description
      "Initial revision";
  }

  

  grouping mcfg-srmpls-sidmap {
    container address-family {
      container ipv4 {
        presence "true";
        uses srcfg-srmpls-conn-af;
      }
      container ipv4-strict-spf {
        container ipv4 {
          description
            "Address Family";
          container strict-spf {
            presence true;

            uses srcfg-srmpls-conn-af;
          }
        }
      }
    }
  }

  grouping srcfg-srmpls-attr-af {
    leaf explicit-null {
      type empty;
    }
    leaf sr-label-preferred {
      type empty;
    }
  }

  grouping sr-range {
    leaf range-start {
      type uint32 {
        range "0..1048575";
      }
    }
    leaf range {
      description
        "Range value";
      type uint32 {
        range "1..1048575";
      }
    }
  }

  grouping srcfg-srmpls-conn-af {
    list prefixes {
      key "ipprefix";
      leaf ipprefix {
        type inet:ipv4-prefix;
      }
      container index {

        uses sr-range;

        leaf attach {
          type empty;
        }
      }
      container absolute {
        uses sr-range;
      }
    }
  }

  grouping config-segment-routing-grouping {
    container mpls {
      description
        "Segment Routing MPLS Mode";
      presence "true";

      container connected-prefix-sid-map {
        description
          "Enter Connected Prefix Sid Map  Mode";
        presence true;

        uses mcfg-srmpls-sidmap;
      }
      container global-block {
        description
          "SR Global Block Config";
        leaf range-start {
          description
            "SR GB Label Range Start";
          type uint32 {
            range "16..1048575";
          }
        }
        leaf range-end {
          description
            "SR GB Label Range End";
          type uint32 {
            range "16..1048575";
          }
        }
      }
      container mapping-server {
        description
          "Enter Segment Routing Mapping Server Mode";
        presence true;
        container prefix-sid-map {
          description
            "Enter Mapping Server Sidmap Mode";
          presence true;

          uses mcfg-srmpls-sidmap;
        }
      }
      container set-attributes {
        description
          "Enter SR Set Attributes  Mode";
        presence true;
        container address-family {
          description
            "Enter Address Family command mode";
          container ipv4 {
            description
              "Address Family";
            presence true;

            uses srcfg-srmpls-attr-af;
          }
        }
      }
      leaf shutdown {
        description
          "SR Shutdown";
        type empty;
      }
    }
  }

  /////////////////////////////////////////////////////////
  // native / segment-routing
  /////////////////////////////////////////////////////////
  augment "/ios:native/ios:segment-routing" {
    uses config-segment-routing-grouping;
  }
}
