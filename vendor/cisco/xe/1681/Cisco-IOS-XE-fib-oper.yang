module Cisco-IOS-XE-fib-oper {
  yang-version 1;
  namespace "http://cisco.com/ns/yang/Cisco-IOS-XE-fib-oper";
  prefix fib-ios-xe-oper;

  import ietf-inet-types {
    prefix inet;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for IOS-XE FIB operational data.";

  revision 2017-07-04 {
    description
      "Initial revision";
    reference "1.0.0";
  }

  typedef fib-address-family {
    type enumeration {
      enum "fib-addr-fam-unknown" {
        value 0;
        description
          "Unknown Address Family";
      }
      enum "fib-addr-fam-ipv4" {
        value 1;
        description
          "IPv4 Address Family";
      }
      enum "fib-addr-fam-ipv6" {
        value 2;
        description
          "IPv6 Address Family";
      }
    }
    description
      "FIB Address Family Types";
  }

  typedef encapsulation-header-type {
    type enumeration {
      enum "encap-hdr-type-unknown" {
        value 0;
        description
          "Unknown encapsulation header type";
      }
      enum "encap-hdr-type-gre" {
        value 1;
        description
          "GRE encapsulation header type";
      }
      enum "encap-hdr-type-ipv4" {
        value 2;
        description
          "IPv4 encapsulation header type";
      }
      enum "encap-hdr-type-ipv6" {
        value 3;
        description
          "IPv6 encapsulation header type";
      }
      enum "encap-hdr-type-mpls" {
        value 4;
        description
          "MPLS encapsulation header type";
      }
    }
    description
      "Types of header for packet encapsulation";
  }

  typedef fib-path-type {
    type enumeration {
      enum "fib-path-type-unknown" {
        value 0;
        description
          "Unknown FIB path type";
      }
      enum "fib-path-type-receive" {
        value 1;
        description
          "Receive FIB path type";
      }
      enum "fib-path-type-connected" {
        value 2;
        description
          "Connected FIB path type";
      }
      enum "fib-path-type-attached-prefix" {
        value 3;
        description
          "Attached Prefix FIB path type";
      }
      enum "fib-path-type-attached-host" {
        value 4;
        description
          "Attached Host FIB path type";
      }
      enum "fib-path-type-attached-nexthop" {
        value 5;
        description
          "Attached Nexthop FIB path type";
      }
      enum "fib-path-type-recursive" {
        value 6;
        description
          "Recursive FIB path type";
      }
      enum "fib-path-type-adjacency-prefix" {
        value 7;
        description
          "Adjacency Prefix FIB path type";
      }
      enum "fib-path-type-special-prefix" {
        value 8;
        description
          "Special Prefix FIB path type";
      }
    }
    description
      "Type of FIB path used";
  }

  grouping fib-nexthop-entry {
    description
      "FIB Next-hop Entry";
    leaf nh-addr {
      type inet:ip-prefix;
      description
        "IP Address";
    }
    leaf index {
      type uint32;
      description
        "Unique Next-hop Path Index";
    }
    leaf af {
      type fib-ios-xe-oper:fib-address-family;
      description
        "Address Family";
    }
    leaf ifname {
      type string;
      description
        "Output Interface Name";
    }
    leaf path-type {
      type fib-ios-xe-oper:fib-path-type;
      description
        "FIB path type";
    }
    leaf path-id {
      type uint32;
      description
        "Unique Next-hop Path Index";
    }
    leaf weight {
      type uint8;
      description
        "Next-hop weight";
    }
    leaf encap {
      type fib-ios-xe-oper:encapsulation-header-type;
      description
        "Encap Header Type";
    }
    leaf decap {
      type fib-ios-xe-oper:encapsulation-header-type;
      description
        "Decap Header Type";
    }
  }

  grouping fib-entry {
    description
      "FIB Entry";
    leaf ip-addr {
      type inet:ip-prefix;
      description
        "IP address";
    }
    leaf instance-name {
      type string;
      description
        "Instance Name";
    }
    leaf af {
      type fib-ios-xe-oper:fib-address-family;
      description
        "Address Family";
    }
    leaf num-paths {
      type uint8;
      description
        "Number of Paths available";
    }
    leaf packets-forwarded {
      type uint64;
      description
        "Packets forwarded through this entry";
    }
    leaf octets-forwarded {
      type uint64;
      description
        "Octets forwarded through this entry";
    }
    list fib-nexthop-entries {
      key "nh-addr";
      description
        "List of FIB next-hop entries";
      uses fib-ios-xe-oper:fib-nexthop-entry;
    }
  }

  grouping fib-ni-entry {
    description
      "FIB Network Instance Entry";
    leaf instance-name {
      type string;
      description
        "Instance Name";
    }
    leaf af {
      type fib-ios-xe-oper:fib-address-family;
      description
        "Address Family";
    }
    leaf num-pfx {
      type uint32;
      description
        "Number of prefixes";
    }
    leaf num-pfx-fwd {
      type uint32;
      description
        "Number of forwarding prefixes";
    }
    leaf num-pfx-non-fwd {
      type uint32;
      description
        "Number of non-forwarding prefixes";
    }
    list fib-entries {
      key "ip-addr";
      description
        "List of FIB entries";
      uses fib-ios-xe-oper:fib-entry;
    }
  }

  container fib-oper-data {
    config false;
    description
      "This module contains a collection of YANG definitions for
       monitoring the operation of IOS-XE CEF.
       Copyright (c) 2016-2017 by Cisco Systems, Inc.
       All rights reserved.";
    list fib-ni-entry {
      key "instance-name";
      description
        "FIB Network Instances";
      uses fib-ios-xe-oper:fib-ni-entry;
    }
  }
}
