module Cisco-IOS-XE-rpc {
  namespace "http://cisco.com/ns/yang/Cisco-IOS-XE-rpc";
  prefix ios-xe-rpc;


  import ietf-inet-types {
    prefix inet;
  }

  organization "Cisco Systems";

  contact
    <mailto:cs-yang@cisco.com>;

  description
    "NED RPC YANG module for IOS
     Copyright (c) 2016 by Cisco Systems, Inc.
     All rights reserved.";

  // =========================================================================
  // REVISION
  // =========================================================================
  revision 2017-12-06 {
    description 
      "Add Viptela clear aaa local user lockout username <> command";
  }
  revision 2017-11-27 {
    description 
      "Add Viptela clear and release commands";
  }
  revision 2017-11-21 {
    description 
      "Clear flow commands";
  }
  revision 2017-11-14 {
    description
      "Add app-hosting and guestshell EXEC commands";
  }
  revision 2017-11-04 {
    description
      "Add reason to reload";
  }
  revision 2017-10-12 {
    description
      "Added more nodes to the license RPC";
  }
  revision 2017-10-10 {
    description
      "Add copy and delete EXEC commands";
  }
  revision 2017-09-21 {
    description
      "Add virtual-service EXEC commands";
  }
  revision 2017-08-28 {
    description
      "Added the force option to the reload RPC";
  }
  revision 2017-07-13 {
    description 
      "Added service sd-avc CLI";
  }
  revision 2017-02-07 {
    description
      "Initial revision";
  }

  grouping cisco-xe-rpc-output {
    description 
      "Used to return output from RPCs";
    leaf result {
      type string;
      description 
        "Output returned by the network element";
    }
  }

  rpc switch {
    input {
      leaf _switch-number {
        mandatory true;
        type uint8 {
          range "1..9";
         }
      }
      choice pri-renum-stack {
        mandatory true;
        case priority-case {
        leaf priority {
	  description 
	    "<1-15>  Switch Priority";
          type uint8 {
	    range "1..15";
          }
        }
	}
	case renumver-case {
        leaf renumber {
	  description 
	    "<1-9>  New number of the Switch";
          type uint8 {
	    range "1..9";
          }
        }
	}
	case stack-case {
	container statck {
          leaf port {
	    description 
	      "<1-2>  Stack port number to enable/disable";
            type uint8 {
	      range "1..2";
            }
          }
          }
        }
      }
    }
    output {
      uses cisco-xe-rpc-output; 
    }
  }
  rpc default {
    description 
      "Set a command to its defaults";
    input {
      choice default-choice {
        mandatory true;
        case interface-case {
          leaf interface {
            description 
	      "Select an interface to configure";
            type string {
              pattern "[A-Za-z]([\w/.-]+)";
            }

          }
        }
      }
    }
    output {
      uses cisco-xe-rpc-output; 
    }
  }
  rpc clear {
    description 
      "Clear";
    input {
      choice clear-choice {
        mandatory true;
        case interface-case {
          leaf interface {
            description 
	      "Select an interface to clear";
            type string {
              pattern "[A-Za-z]([\w/.-]+)";
            }
          }
        }
        case count-case {
          leaf count {
            description 
	      "Select an interface to clear";
            type string {
              pattern "[A-Za-z]([\w/.-]+)";
            }
          }
        }
        case flow-case {
          container flow {
            description "Flow monitor clear commands";
            choice flow-choice {
              case monitor-case {
                container monitor {
                  leaf name {
                    mandatory true;
                    type string;
                  }
                  choice monitor-option {
                    leaf force-export {
                      type empty;
                    }
                    leaf statistics {
                      type empty;
                    }
                    container cache {
                      leaf force-export {
                        type empty;
                      }
                    }
                  }
                }
              }
               case export-case {
                container exporter {
                  leaf name {
                    type string;
                  }
                  leaf statistics {
                    type empty;
                  }
                }
              }
            }
          } 
        }
        case ip-case {
	  container ip {
	    choice ip-protocol {
	      case dhcp-case {
	        container dhcp {
		  description
		    "Delete items from the DHCP database";
	          container binding {
		    description
		      "DHCP address bindings";
		    leaf vrf {
		      description 
		        "DHCP vrf bindings";
		      type string;
		    }
		    leaf _all {
		      description 
		        "Clear all automatic bindings";
                      mandatory true;
                      type string {
		        pattern "[*]";
		      }
		    }
	          }
	        }
              }
	      case ospf-case {
                container ospf {
		  leaf _id {
		    description
		      "Process ID number";
		    type uint16;
		  }
		  leaf process {
		    description
		      "Reset OSPF process";
		    type empty;
		  }
		}
	      }
	      case bgp-case {
	        container bgp {
		  description
		    "Clear BGP connections";
		  leaf _peer-address {
		    description
		      "BGP neighbor address to clear";
                    type union {
		      type inet:ipv4-address;
		      type inet:ipv6-address;
                    }
		  }
		  leaf vrf {
		    description
		      "Select a VPN Routing/Forwarding instance";
		    type string;
		  }
		}
	      }
            }
	  }
	}
	case arp-cache-case {
	  container arp-cache {
	    description 
	      "Clear the entire ARP cache";
	    presence true;
	    leaf vrf {
	      description 
	        "Clear entries for a VPN Routing/Forwarding instance";
	      type string;
            }
	    leaf interface {
	      description
	        "Clear the entire ARP cache on the interface";
              type string {
                pattern "[A-Za-z]([\w/.-]+)";
              }
	    }
	    leaf _ip {
	      description 
	        "IP address";
	      type inet:ipv4-address;
	    }
	  }
	}
	case aaa-case {
	  container aaa {
	    description
	      "Clear AAA values";
            container local {
	      description
	        "Clear AAA local method options";
              container user {
	        description
		  "Clear local AAA users";
                container lockout {
		  description
		    "Clear locked out local AAA users";
                  leaf username {
		    description
		      "Username of the locked-user";
                    type string;
                  }
                }
              }
            }
	  }
	}
      }
    }
    output {
      uses cisco-xe-rpc-output; 
    }
  }
  rpc release {
    description 
      "Release a resource";
    input {
      leaf dhcp {
        description
	  "Release a dhcp lease (an interface)";
        type string;
      }
    }
    output {
      uses cisco-xe-rpc-output;
    }
  }
  rpc reload {
    description 
      "Halt and perform a cold restart";
    input {
      leaf force {
        description "Force a restart even if there is unsaved config";
        type boolean;
      }
      leaf reason {
        description "Reload reason";
        type string;
      }
    }
    output {
      uses cisco-xe-rpc-output; 
    }
  }
rpc cellular {
    input {
      leaf _if-name {
          type string;
      }
      container lte {
        choice action {
          case tech  {
            container technology {
              choice action {
                case lte {
                   leaf lte {
                     type empty;
                   }
                }
                case auto {
                  leaf auto {
                    type empty;
                  }
                }
                case umts {
                  leaf umts {
                    type empty;
                  }
                }
              }
            }
          }
          case profile {
            container profile {
               choice prof {
                  case delete  {
                    description "Cellular Profile configuration";
                    container delete {
                      description "Delete a Profile";
                        leaf _profile-id {
                          description "Profile ID";
                          type uint8 {
                            range "1..16";
                          }
                        }
                    }
                  }
                  case create {
                    container create {
                      description "Create a Profile";
                      leaf _profile-id {
                        description "Profile ID";
                        type uint8 {
                          range "1..16";
                        }
                      }
                      leaf _prof_name {
                        description "Profile name";
                        type string;
                      }
                      choice auth {
                        case none {
                          leaf none {
                            type empty;
                          }
                        }
                        case chap {
                          leaf chap {
                            type empty;
                          }
                        }
                        case pap {
                          leaf pap {
                            type empty;
                          }
                        }
                        case pap_chap {
                          leaf pap_chap {
                            type empty;
                          }
                        }
                      }
                      leaf _user_name {
                        description "Username for authentication";
                        type string;
                      }
                      leaf _password {
                        description "Password for authentication";
                        type string;
                      }
                      choice pdn {
                        case ipv4 {
                          leaf ipv4 {
                            type empty;
                          }
                        }
                        case ipv6 {
                          leaf ipv6 {
                            type empty;
                          }
                        }
                        case ipv4v6 {
                          leaf ipv4v6 {
                            type empty;
                          }
                        }
                      }
                    }
                  }
                }
              }
            }
          }
        }
      }
    output {
      uses cisco-xe-rpc-output;
    }
  }
  rpc license {
    input {
      container smart {
        choice smart-choice {
	  mandatory true;
	  case register-case {
	    container register {
	      leaf idtoken {
	        mandatory true;
	        type string;
	      }
	      leaf force {
	        description "Forcefully register";
		type empty;
              }
	    }
	  }
	  case deregister-case {
	    leaf deregister {
	      type empty;
            }
	  }
	  case renew-case {
	    container renew {
	      choice renew-choice {
	        mandatory true;
	        leaf ID {
	          type empty;
                }
	        leaf auth {
	          type empty;
                }
              }
	    }
	  }
	}
      }
    }
    output {
      uses cisco-xe-rpc-output; 
    }
  }
  rpc service {
    description "SD-AVC service management";
    input {
      container sd-avc {
        choice sd-avc-choice {
          mandatory true;
          case activate-case {
            leaf activate {
              type empty;
            }
          }
          case configure-case {
            container configure {
              container gateway {
                leaf interface {
                  type string; 
                }
                leaf service-ip {
                  type inet:ipv4-address; 
                }
                leaf activate {
                  type empty;
                }
              }
            }
          }
          case connect-case {
            leaf connect {
              type empty;
            }
          }
          case help-case {
            leaf help {
              type empty;
            }
          }
          case deactivate-case {
            leaf deactivate {
              type empty;
            }
          }
          case install-case {
            container install {
              leaf package {
                type string;
              }
            }
          }
          case status-case {
            leaf status {
             type empty;
            }
          }
          case unconfigure-case {
            leaf unconfigure {
              type empty;
            }
          }
          case uninstall-case {
            leaf uninstall {
              type empty;
            }
          } 
          case upgrade-case {
            container upgrade {
              leaf package {
                type string;
              }
            }
          }
        }
      }
    }
    output {
      uses cisco-xe-rpc-output;
    }
  }
  rpc virtual-service {
    description
      "Virtual-service management";
    input {
      choice operation {
        mandatory true;
        container install {
          leaf name {
             type string;
           }
           leaf package {
             type string;
           }
           leaf media {
             type string;
           }
         }
         container uninstall {
          leaf name {
            type string;
          }
        }
        container upgrade {
          leaf name {
            type string;
          }
          leaf package {
            type string;
          }
        }
      }
    }
    output {
      uses cisco-xe-rpc-output;
    }
  }
  rpc copy {
    description
      "Copy from one file to another";
    input {
      leaf _source {
        mandatory true;
        type string {
          pattern "((((bootflash:)|(harddisk:)|(flash:)|(nvram:)|(ftp:)|(http:)|(https:)|(scp:)|(tftp:)).*)|((running-config)|(startup-config)))";
        }
      }
      leaf _destination {
        mandatory true;
        type string {
          pattern "((((bootflash:)|(harddisk:)|(flash:)|(nvram:)|(ftp:)|(http:)|(https:)|(scp:)|(tftp:)).*)|((running-config)|(startup-config)))";
        }
      }
    }
    output {
      uses cisco-xe-rpc-output;
    }
  }
  rpc delete {
    description
      "Delete a file";
    input {
      leaf _filename {
        mandatory true;
        type string {
          pattern "(((bootflash:)|(harddisk:)|(flash:)|(nvram:)).*)";
        }
      }
    }
    output {
      uses cisco-xe-rpc-output;
    }
  }
  rpc app-hosting {
    description
      "App-hosting management";
    input {
      choice lifecycle {
        mandatory true;
        container install {
          leaf appid {
            type string;
          }
          leaf package {
            type string;
          }
        }
        container uninstall {
          leaf appid {
            type string;
          }
        }
        container activate {
          leaf appid {
            type string;
          }
        }
        container deactivate {
          leaf appid {
            type string;
          }
        }
        container start {
          leaf appid {
            type string;
          }
        }
        container stop {
          leaf appid {
            type string;
          }
        }
      }
    }
    output {
      uses cisco-xe-rpc-output;
    }
  }
  rpc guestshell {
    description
      "guestshell managementshell";
    input {
      choice action {
        mandatory true;
        case destroy-case {
          leaf destroy {
            description "Destroy guestshell";
            type empty;
          }
        }
        case disable-case {
          leaf disable {
            description "Disable guestshell";
            type empty;
          }
        }
        case enable-case {
          leaf enable {
            description "Enable guestshell";
            type empty;
          }
        }
      }
    }
    output {
      uses cisco-xe-rpc-output;
    }
  }
}
