module Cisco-IOS-XE-mdt-common-defs {
  yang-version 1;
  namespace "http://cisco.com/ns/yang/Cisco-IOS-XE-mdt-common-defs";
  prefix mdt-common-defs;

  import ietf-inet-types {
    prefix inet;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of common YANG 
     definitions for streaming telemetry.
     Copyright (c) 2016-2017 by Cisco Systems, Inc.
     All rights reserved.";

  revision 2017-10-29 {
    description
      "TRANSFORM support for Native stream";
    reference "1.2.0";
  }
  revision 2017-07-01 {
    description
      "Add support for VRFs";
    reference "1.1.0";
  }
  revision 2017-03-02 {
    description
      "Initial revision";
    reference "1.0.0";
  }

  typedef mdt-sub-filter-type {
    type enumeration {
      enum "sub-filter-type-none" {
        value 0;
        description
          "Indicates that no filter has been specified.";
      }
      enum "sub-filter-type-xpath" {
        value 1;
        description
          "Xpath defining the data items of interest.
           A limited set of the Xpath 1.0 expressions is
           supported.";
      }
      enum "sub-filter-type-tdl-uri" {
        value 2;
        description
          "TDL-URI defining the data items of interest.";
      }
      enum "sub-filter-type-tdl-transform" {
        value 3;
        description
          "tdl-transform define transform scheme 
           to be subscribed.";
      }
    }
    description
      "Types of subscription filters.";
  }

  typedef mdt-sub-update-trigger {
    type enumeration {
      enum "sub-upd-trig-none" {
        value 0;
        description
          "Indicates trigger has not been specified.";
      }
      enum "sub-upd-trig-periodic" {
        value 1;
        description
          "Subscription is triggered on a periodic basis.";
      }
      enum "sub-upd-trig-on-change" {
        value 2;
        description
          "Subscription is triggered when a value changes.";
      }
    }
    description
      "Types of subscription update triggers.";
  }

  grouping mdt-subscription-base {
    description
      "Base subscription information. This is
       common to both operational and configuration
       table records.";
    leaf stream {
      type string;
      default "NETCONF";
      description
        "The name of the event stream being subscribed to.";
    }
    leaf encoding {
      type string;
      default "encode-xml";
      description
        "Update notification encoding";
    }
    leaf source-vrf {
      type string;
      description
        "Network instance name for the VRF.";
    }
    leaf source-address {
      type inet:ip-address;
      description
        "The source address for the notifications.";
    }
    choice update-trigger-choice {
      default "sub-upd-trig-none";
      description
        "Update trigger of the subscription.";
      case sub-upd-trig-none {
        description
          "Indicates trigger has not been specified.";
        leaf no-trigger {
          type uint32;
          default "0";
          description
            "Placeholder for unset value.";
        }
      }
      case sub-upd-trig-periodic {
        description
          "Subscription is triggered on a periodic basis.";
        leaf period {
          type uint32;
          units "centiseconds";
          mandatory true;
          description
            "Period of update notifications in 100ths
             of a second.";
        }
      }
      case sub-upd-trig-on-change {
        description
          "Subscription is triggered when a value changes.";
        leaf no-synch-on-start {
          type boolean;
          description
            "If true, there is no initial update notification
             with the current value of all the data.
             NOT CURRENTLY SUPPORTED. If specified, must
             be false.";
        }
      }
    }
    choice filter-type-choice {
      default "sub-filter-type-none";
      description
        "The type of filter chosen to select the events or the data
         for the update notification.";
      case sub-filter-type-none {
        description
          "Indicates that no filter has been specified.";
        leaf no-filter {
          type uint32;
          default "0";
          description
            "Placeholder for unset value.";
        }
      }
      case sub-filter-type-xpath {
        description
          "Xpath defining the data items of interest.
           A limited set of the Xpath 1.0 expressions is
           supported.";
        leaf xpath {
          type string;
          description
            "XPath expression describing the set of objects
             wanted as part of the subscription.";
        }
      }
      case sub-filter-type-tdl-uri {
        description
          "TDL-URI defining the data items of interest.";
        leaf tdl-uri {
          type string;
          description
            "TDL-URI expression describing the set of objects
             wanted as part of the subscription.";
        }
      }
      case sub-filter-type-tdl-transform {
        leaf transform-name {
          type string;
          description
            "Transform name is the reference to 
             tdl transform scheme.";
        }
      }
    }
  }

  grouping mdt-receiver-id {
    description
      "Receiver identifier.";
    leaf address {
      type inet:ip-address;
      mandatory true;
      description
        "IP address of the receiver.";
    }
    leaf port {
      type uint16;
      mandatory true;
      description
        "Network port of the receiver.";
    }
  }
}
