module Cisco-IOS-XE-nat {
  namespace "http://cisco.com/ns/yang/Cisco-IOS-XE-nat";
  prefix ios-nat;

  import ietf-inet-types {
    prefix inet;
  }


  import Cisco-IOS-XE-types {
    prefix ios-types;
  }

  import Cisco-IOS-XE-native {
    prefix ios;
  }

  import Cisco-IOS-XE-interface-common {
    prefix ios-ifc;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Network Address Translation (NAT) Yang model.
     Copyright (c) 2016-2017 by Cisco Systems, Inc.
     All rights reserved.";

  // =========================================================================
  // REVISION
  // =========================================================================
  revision 2017-11-27 {
     description
       "Added Change 25GE name";
  }

  revision 2017-11-14 {
    description 
      "Add 40 and 100GE support";
  }

  revision 2017-11-10 {
    description 
      "Add translation timeout support";
  }
  revision 2017-11-06 {
    description 
      "Add ip nat to interface BDI";
  }
  revision 2017-09-15 {
    description 
      "This revison has changes for new 2gig interface addition";
  }
  revision 2017-08-16 {
    description
      "This revision has changes for new 5gig and 25gig interfaces addition";
  }

  revision 2017-08-03 {
    description
      " Static NAT with VRF and route-map results in incorrect CLI order";
  }
  revision 2017-06-16 {
    description
      "Native Yang Support for NATv6";
  }
  revision 2017-03-14 {
    description
      "Add Container node Pool, Oer and Overload 
       under node Route-map.";
  }

  revision 2017-02-07 {
    description
      "Initial revision";
  }

  grouping config-interface-ip-nat-grouping {
    container nat {
      description
          "NAT interface commands";
      leaf allow-static-host {
        description
          "Allow static-ip clients";
        type empty;
      }
      leaf enable {
        description
          "Enable Address Translation (NVI)";
        type empty;
      }
      choice nat-choice {
        leaf inside {
          description
            "Inside interface for address translation";
          type empty;
        }
        leaf outside {
          description
            "Outside interface for address translation";
          type empty;
        }
      }
    }
  }
 
  grouping config-ip-nat-pool-interface-grouping {
    choice pool-or-interface {
    // ip nat inside source list * pool
    // ip nat inside source route-map * pool
        case pool-choice {
            leaf pool {
                description
                  "Name pool of global addresses";
                type string;
            }
            // [ redundancy <rg-id> ]
            leaf redundancy {
              description
                "NAT redundancy operation";
              type uint8 {
                range "1..2";
              }
            }
            // [ mapping-id <map-id> ]
            leaf mapping-id {
              description
                "Associate a mapping id to this mapping";
              type uint32 {
                range "1..2147483647";
              }
            }
        }
        // ip nat inside source list * interface
        case interface-choice {
            container interface {
              description
                "Specify interface for global address";
              uses ios-ifc:interface-grouping;
            }
        }
    }
    // [no-payload]
    leaf no-payload {
      description
        "No translation of embedded address/port in the payload";
      type empty;
    }
    // [reversible]
    leaf reversible {
      when "../../route-map";
      type empty;
    }
    // [ vrf name [match-in-vrf] ]
    leaf vrf {
      description
        "Specify vrf";
      type string;
    }
    leaf match-in-vrf {
      description
        "Match incoming vrf";
      when "../vrf";
      type empty;
    }
    // [overload]
    leaf overload {
      description
        "Overload an address translation";
      type empty;
    }
    // [oer]
    leaf oer {
      description
        "Use with vtemplate only. On new translation, if OER BR is UP,
         OER will select IP from outgoing Interface.
         All packets matching translation are forwarded over Interface
         for duration of translation.";
      type empty;
    }
  }
  
  grouping ip-nat-translation-port-number-grouping {
    container protocol {
      leaf port-numer {
        description
          "Port number";
        type uint16 {
          range "1..63535";
        }
      }
      leaf time-val {
        description
          "Timeout in seconds";
        type uint32 {
          range "0..536870";
        }
      }
      leaf never {
        description
          "Never timeout";
        type empty;
      }
    }
  }

  grouping ip-nat-translation-timeout-grouping {
    leaf time-val {
      description
        "Timeout in seconds";
      type uint32 {
        range "0..536870";
      }
    }
    leaf never {
      description
        "Never timeout";
      type empty;
    }
  }

  grouping config-ip-nat-grouping {
    container nat { //43751
      description
        "NAT configuration commands";
      // ip nat pool *
      list pool {
        description
          "Define pool of addresses";
        key "id";
        leaf id {
          type string;
        }
        leaf start-address {
          type inet:ipv4-address;
        }
        leaf end-address {
          when "../start-address" {
          }
          type inet:ipv4-address;
        }
        choice prefix-choice {
          leaf netmask {
            description
              "Specify the network mask";
            type inet:ipv4-address;
          }
          leaf prefix-length {
            description
              "Specify the prefix length";
            type uint8 {
              range "1..32";
            }
          }
        }
        leaf accounting {
          description
            "Specify the accounting";
          type string;
        }
        choice nat-choice {
          leaf arp-ping {
            description
              "WLAN ARP Ping";
            type empty;
          }
          leaf type {
            description
              "Specify the pool type";
            type enumeration {
              enum "match-host";
              enum "rotary";
            }
          }
          leaf add-route {
            description
              "Add special route to Virtual Interface";
            type empty;
          }
        }
      }
      // ip nat inside
      container inside {
        description
          "Inside address translation";
        // ip nat inside source
        container source {
          description
            "Source address translation";
          // ip nat inside source list *
          list list {
            description
              "Specify access list describing local addresses";
            key "id";
            leaf id {
              type union {
                type uint16 {
                  range "1..2699";
                }
                type string;
              }
            }
            uses config-ip-nat-pool-interface-grouping;             
            // [ portmap name ]
          }
          // ip nat inside source route-map *
          list route-map {
            description
              "Specify route-map";
            key "route-map-name";
            // [route-map-name]
            leaf route-map-name {
              description
                "Route-map name";
              type string;
            }
            container pool {
              description
                "Name pool of global addresses";
              leaf pool-name {
                description 
                  "Pool name for global addresses";
                type string;
              }
              // [ vrf name [match-in-vrf] ]
              leaf vrf {
                description
                  "Specify vrf";
                  type string;
                 }
              leaf match-in-vrf {
                description
                  "Match incoming vrf";
                type empty;
              }
            }
            container interface {
              description
                "Specify interface for global address";
              uses ios-ifc:interface-grouping;
            }
            container oer {
              description
                "Use with vtemplate only.  On new translation,
                 if OER BR is UP, OER will select IP from outgoing Interface.
                 All packets matching translation are forwarded over
                 Interface for duration of translation.";
              // [ overload ]
              leaf overload {
                description
                  "Overload an address translation";
                type empty;
              }
              // [ extended ]
              leaf extended {
                description
                  "Overload extended";
                type empty;
              }
            }
            container overload {
              description
                "Overload an address translation";
              // [ extended ]
              leaf extended {
                description
                  "Overload extended";
                type empty;
              }
              // [ oer ]
              leaf oer {
                description
                  "Use with vtemplate only.  On new translation,
                   if OER BR is UP, OER will select IP from outgoing
                   Interface.  All packets matching translation are
                   forwarded over Interface for duration of translation.";
                type empty;
              }
            }
            list vrf {
              description
                "Specify vrf";
              key "vrf-name";
              leaf vrf-name {
                description
                  "vrf name";
                type string;
              }
              container oer {
                description
                  "Use with vtemplate only.  On new translation,
                   if OER BR is UP, OER will select IP from outgoing
                   Interface.  All packets matching translation are
                   forwarded over Interface for duration of translation.";
                presence true;
                leaf overload {
                  description
                    "Overload an address translation";
                  type empty;
                }
              }
              container overload {
                description
                  "Overload an address translation";
                  presence true;
                  leaf oer {
                    description
                      "Use with vtemplate only.  On new translation,
                       if OER BR is UP, OER will select IP from outgoing
                       Interface.  All packets matching translation are
                       forwarded over Interface for duration of translation.";
                    type empty;
                  }
              }
            }
          } 
          // ip nat inside source static
          container static {
            description
              "Specify static local->global mapping";
            list nat-static-transport-list {
              key "local-ip global-ip";
              leaf local-ip {
                type inet:ipv4-address;
              }
              leaf global-ip {
                type inet:ipv4-address;
              }
              leaf proto {
                type enumeration {
                  enum "tcp";
                  enum "udp";
                }
              }
              leaf network {
                description
                  "Subnet translation";
                type empty;
              }
              leaf local-port {
                type uint16 {
                  range "1..65535";
                }
              }
              leaf mask {
                type union {
                  type string;
                  type inet:ipv4-address;
                }
              }
              leaf global-port {
                type uint16 {
                  range "1..65535";
                }
              }
              leaf vrf {
                description
                  "Specify vrf";
                type string;
              }
              leaf extendable {
                description
                  "Extend this translation when used";
                type empty;
              }
              leaf no-alias {
                description
                  "Do not create an alias for the global address";
                type empty;
              }
              leaf no-payload {
                description
                  "No translation of embedded address/port in the payload";
                type empty;
              }
              leaf route-map {
                description
                  "Specify route-map";
                type string;
              }
              leaf reversible {
                when "../route-map";
                type empty;
              }
              leaf redundancy {
                description
                  "NAT redundancy operation";
                type union {
                  type uint8;
                  type string;
                }
              }
              leaf mapping-id {
                description
                  "Associate a mapping id to this mapping";
                when "../redundancy";
                type uint32 {
                  range "1..2147483647";
                }
              }
              leaf match-in-vrf {
                description
                  "Match incoming vrf";
                when "../vrf";
                type empty;
              }
              leaf forced {
                description
                  "Delete this entry and its children, even if in use";
                type empty;
              }
              leaf overload {
                description
                  "Overload an address translation";
                type empty;
              }
            }
            list nat-static-transport-interface-list {
              key "proto local-ip local-port";
              leaf proto {
                type enumeration {
                  enum "tcp";
                  enum "udp";
                }
              }
              leaf local-ip {
                type inet:ipv4-address;
              }
              leaf local-port {
                type uint16 {
                  range "1..65535";
                }
              }
              container interface {
                description
                  "Specify interface for global address";
                uses ios-ifc:interface-grouping;
              }
              leaf global-port {
                type uint16 {
                  range "1..65535";
                }
              }
            }
          }
        }
        // ip nat inside destination
        container destination {
          description
            "Destination address translation";
          // ip nat inside destination list *
          list list {
            description
              "Specify access list describing global addresses";
            key "id";
            leaf id {
              type union {
                type uint16 {
                  range "1..2699";
                }
                type string;
              }
            }
            // ip nat inside destination list * pool *
            leaf pool {
              description
                "Name pool of local addresses";
              type string;
            }
            // [ redundancy redundancy-id ]
            leaf redundancy {
              description
                "NAT redundancy operation";
              type uint8 {
                range "1..2";
              }
            }
            leaf mapping-id {
              description
                "Associate a mapping id to this mapping";
              type uint32 {
                range "1..2147483647";
              }
            }
          }
        }
      }

      // ip nat outside
      container outside {
        description
          "Outside address translation";
        container source {
          description
            "Source address translation";
          // ip nat outside source static 
          container static {
            description 
              "Specify static global->local mapping";
            list nat-static-transport-list {
              key "global-ip local-ip";                                                       leaf global-ip {
                type inet:ipv4-address;
              }
              leaf local-ip {
                type inet:ipv4-address;
              } 
              leaf vrf {
                description
                  "Specify vrf";
                type string;
              }
              leaf extendable {
                description
                  "Extend this translation when used";
                type empty;
              }
              leaf no-payload {
                description
                  "No translation of embedded address/port in the payload";
                type empty;
              }
            }
          }
        }

        list list {
          description
            "Specify access list describing global addresses";
          key "id";
          leaf id {
            type union {
              type uint16 {
                range "1..2699";
              }
              type string;
            }
          }
          leaf pool {
            description
              "Name pool of local addresses";
            type string;
          }
          leaf mapping-id {
            description
              "Associate a mapping id to this mapping";
            type uint32 {
              range "1..2147483647";
            }
          }
          leaf vrf {
            description
              "Specify vrf";
            type string;
          }
          leaf add-route {
            description
              "Add a static route for outside local address";
            type empty;
          }
        }
        list route-map {
          description
            "Specify route-map";
          key "id";
          leaf id {
            type string;
          }
          leaf pool {
            description
              "Name pool of local addresses";
            type string;
          }
          leaf mapping-id {
            description
              "Associate a mapping id to this mapping";
            type uint32 {
              range "1..2147483647";
            }
          }
          leaf vrf {
            description
              "Specify vrf";
            type string;
          }
          leaf add-route {
            description
              "Add a static route for outside local address";
            type empty;
          }
        }
      }
      container translation {
        container dns-timeout {
          description
            "Specify timeout for NAT DNS flows";
          uses ip-nat-translation-timeout-grouping;
        }
        container finrst-timeout {
          description
            "Specify timeout for NAT TCP flows after a FIN or RST";
          uses ip-nat-translation-timeout-grouping;
        }
        container icmp-timeout {
          description
            "Specify timeout for NAT ICMP flows";
          uses ip-nat-translation-timeout-grouping;
        }
        container routemap-entry-timeout {
          description
            "Specify timeout for routemap created half entry";
          uses ip-nat-translation-timeout-grouping;
        }
        container syn-timeout {
          description
            "Specify timeout for NAT TCP flows after a SYN \
             and no further data";
          uses ip-nat-translation-timeout-grouping;
        }
        container tcp-timeout {
          description
            "Specify timeout for NAT TCP/UDP port specific flows";
          uses ip-nat-translation-timeout-grouping;
        }
        container timeout {
          description
            "Specify timeout for dynamic NAT translations";
          uses ip-nat-translation-timeout-grouping;
        }
        container udp-timeout {
          description
            "Specify timeout for NAT UDP flows";
          uses ip-nat-translation-timeout-grouping;
        }
        container port-timeout {
          description
            "Specify timeout for NAT TCP/UDP port specific flows";
          container tcp {
            description
              "TCP protocol";
            uses ip-nat-translation-port-number-grouping;
          }
          container udp {
            description
              "UDP protocol";
            uses ip-nat-translation-port-number-grouping;
          }
        }
      }
    }
  }


  grouping config-nat66-grouping {
    container nat66 {
      description
        "NAT66 configuration commands";
      container prefix {
        description
          "NAT66 prefix";
        list inside {
          description
            "inside prefix";

          key "inside-pfx";
          leaf inside-pfx {
            description
              "IPv6 prefix";
            type ios-types:ipv6-prefix;
          }

          leaf outside {
            description
              "outside prefix";
            type ios-types:ipv6-prefix;
          }
        }
      }
    }
  }

  grouping config-interface-nat66-grouping {
    leaf nat66 {
      description
        "NAT66 interface commands";
      type enumeration {
        enum "inside";
        enum "outside";
      }
    }
  }


  /////////////////////////////////////////////////////////
  // native / ip / nat
  /////////////////////////////////////////////////////////
  augment "/ios:native/ios:ip" {
    uses config-ip-nat-grouping;
  }


  /////////////////////////////////////////////////////////
  // native / interface * / ip
  /////////////////////////////////////////////////////////
  augment "/ios:native/ios:interface/ios:FastEthernet/ios:ip" {
    uses config-interface-ip-nat-grouping;
  }

  augment "/ios:native/ios:interface/ios:GigabitEthernet/ios:ip" {
    uses config-interface-ip-nat-grouping;
  }

  augment "/ios:native/ios:interface/ios:TenGigabitEthernet/ios:ip" {
    uses config-interface-ip-nat-grouping;
  }

  augment "/ios:native/ios:interface/ios:FiveGigabitEthernet/ios:ip" {
    uses config-interface-ip-nat-grouping;
  }

  augment "/ios:native/ios:interface/ios:TwentyFiveGigE/ios:ip" {
    uses config-interface-ip-nat-grouping;
  }

  augment "/ios:native/ios:interface/ios:TwoGigabitEthernet/ios:ip" {
    uses config-interface-ip-nat-grouping;
  }

  augment "/ios:native/ios:interface/ios:FortyGigabitEthernet/ios:ip" {
    uses config-interface-ip-nat-grouping;
  }

  augment "/ios:native/ios:interface/ios:HundredGigE/ios:ip" {
    uses config-interface-ip-nat-grouping;
  }

  augment "/ios:native/ios:interface/ios:Port-channel/ios:ip" {
    uses config-interface-ip-nat-grouping;
  }

  augment "/ios:native/ios:interface/ios:Loopback/ios:ip" {
    uses config-interface-ip-nat-grouping;
  }

  augment "/ios:native/ios:interface/ios:BDI/ios:ip" {
    uses config-interface-ip-nat-grouping;
  }

  /////////////////////////////////////////////////////////
  // native / nat66
  /////////////////////////////////////////////////////////
  augment "/ios:native" {
    uses config-nat66-grouping;
  }

  /////////////////////////////////////////////////////////
  // native / interface *
  /////////////////////////////////////////////////////////
  augment "/ios:native/ios:interface/ios:FastEthernet" {
    uses config-interface-nat66-grouping;
  }

  augment "/ios:native/ios:interface/ios:GigabitEthernet" {
    uses config-interface-nat66-grouping;
  }

  augment "/ios:native/ios:interface/ios:TenGigabitEthernet" {
    uses config-interface-nat66-grouping;
  }

  augment "/ios:native/ios:interface/ios:FiveGigabitEthernet" {
    uses config-interface-nat66-grouping;
  }

  augment "/ios:native/ios:interface/ios:TwentyFiveGigE" {
    uses config-interface-nat66-grouping;
  }

  augment "/ios:native/ios:interface/ios:TwoGigabitEthernet" {
    uses config-interface-nat66-grouping;
  }

  augment "/ios:native/ios:interface/ios:FortyGigabitEthernet" {
    uses config-interface-nat66-grouping;
  }

  augment "/ios:native/ios:interface/ios:HundredGigE" {
    uses config-interface-nat66-grouping;
  }

  augment "/ios:native/ios:interface/ios:Port-channel" {
    uses config-interface-nat66-grouping;
  }

  augment "/ios:native/ios:interface/ios:Loopback" {
    uses config-interface-nat66-grouping;
  }

  augment "/ios:native/ios:interface/ios:Tunnel" {
    uses config-interface-nat66-grouping;
  }
}
