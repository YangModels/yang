module cisco-xe-openconfig-spanning-tree-deviation {

  namespace "http://cisco.com/ns/yang/cisco-xe-openconfig-spanning-tree-deviation";

  prefix oc-stp-devs;
  
  import openconfig-spanning-tree { 
    prefix oc-stp; 
  }

  organization "Cisco Systems";

  description
     "Deviation YANG module for Openconfig-spanning-tree
      Copyright (c) 2017 by Cisco Systems, Inc.
      All rights reserved.";

  ////////////////////////////////////////////////////////////////////////////
  // REVISION
  ///////////////////////////////////////////////////////////////////////////
  revision 2017-08-21 {
     description "Fixed the range of mst instance";
  }

  revision 2017-08-13 {
     description "Fixed hold-count value range to match switch behavior";
  }

  revision 2017-07-10 {
     description "Initial revision";
  }

  //////////////////////////////////////////////////////////////////////////////
  // DEVIATION
  //////////////////////////////////////////////////////////////////////////////

  deviation "/oc-stp:stp/oc-stp:rstp" {
    deviate not-supported;
  }

  deviation "/oc-stp:stp/oc-stp:global/oc-stp:config" +
            "/oc-stp:bpduguard-timeout-recovery" {
    deviate not-supported;
  }

  deviation "/oc-stp:stp/oc-stp:global/oc-stp:state" +
            "/oc-stp:bpduguard-timeout-recovery" {
    deviate not-supported;
  }

  deviation "/oc-stp:stp/oc-stp:interfaces/oc-stp:interface" +
            "/oc-stp:config/oc-stp:edge-port" {
    deviate not-supported;
  }

  deviation "/oc-stp:stp/oc-stp:interfaces/oc-stp:interface" +
            "/oc-stp:state/oc-stp:edge-port" {
    deviate not-supported;
  }

  deviation "/oc-stp:stp/oc-stp:mstp/oc-stp:config" +
            "/oc-stp:hold-count" {
    deviate replace {
      type uint8 {
        range 1..20;
      }
    }
  }
 
  deviation "/oc-stp:stp/oc-stp:mstp/oc-stp:state" +
            "/oc-stp:hold-count" {
    deviate replace {
      type uint8 {
        range 1..20;
      }
    }
  }
 
  deviation "/oc-stp:stp/oc-stp:rapid-pvst/oc-stp:vlan" +
            "/oc-stp:config/oc-stp:hold-count" {
    deviate replace {
      type uint8 {
        range 1..20;
      }
    }
  }
 
  deviation "/oc-stp:stp/oc-stp:rapid-pvst/oc-stp:vlan" +
            "/oc-stp:state/oc-stp:hold-count" {
    deviate replace {
      type uint8 {
        range 1..20;
      }
    }
  }

  deviation "/oc-stp:stp/oc-stp:mstp/oc-stp:mst-instances" +
            "/oc-stp:mst-instance/oc-stp:config" +
            "/oc-stp:mst-id" {
    deviate replace {
      type uint16 {
        range 0..4094;
      }
    }
  }

  deviation "/oc-stp:stp/oc-stp:mstp/oc-stp:mst-instances" +
            "/oc-stp:mst-instance/oc-stp:state" +
            "/oc-stp:mst-id" {
    deviate replace {
      type uint16 {
        range 0..4094;
      }
    }
  }
}
