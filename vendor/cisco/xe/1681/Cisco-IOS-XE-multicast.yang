module Cisco-IOS-XE-multicast {
  namespace "http://cisco.com/ns/yang/Cisco-IOS-XE-multicast";
  prefix ios-mc;

  import ietf-inet-types {
    prefix inet;
  }

  import Cisco-IOS-XE-types {
    prefix ios-types;
  }


  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Multicast Yang model.
     Copyright (c) 2016-2017 by Cisco Systems, Inc.
     All rights reserved.";

  // =========================================================================
  // REVISION
  // =========================================================================
  revision 2017-11-27 {
     description
       "Added Change 25GE name";
  }

  revision 2017-11-14 {
    description
      "This revision has changes for new 100GE interface addition";
  }

  revision 2017-09-15 {
    description
      "This revision has changes for new 2gig interface addition";
  }
  revision 2017-08-28 {
    description
      "Extend modeling for multicast";
  }
  revision 2017-08-16 {
    description
      "This revision has changes for new 5gig and 25gig interfaces addition";
  }
  revision 2017-05-16 {
    description
      "Models under ip pim are missing for FortyGig interface";
  }
  revision 2017-04-24 {
    description
      "certain format of ip pim rpc is not able to push to the device";
  }
  revision 2017-02-07 {
    description
      "Initial revision";
  }

  grouping ip-multicast-multipath-group {
    container multipath {
      description
        "RPF across equal-cost paths";
      presence "true";
      leaf s-g-hash {
        description
          "Per-(source, group) load sharing algorithm selection";
        type enumeration {
          enum "basic";
          enum "next-hop-based";
        }
      }
    }
  }

  grouping config-ip-mcast-grouping {
    leaf route-limit {
      description "Maximum number of multicast routes";
      type uint32 {
        range "1..2147483647";
      }
    }
    uses ip-multicast-multipath-group;
    list vrf {
      description "Select VPN Routing/Forwarding instance";
      key "name";
      leaf name {
        description "VPN Routing/Forwarding instance name";
        type string;
      }
      uses ip-multicast-multipath-group;
      container route-limit {
          description "Maximum number of multicast routes";
          leaf no-routes {
              description "Number of routes";
              type uint32 {
                range "1..2147483647";
              }
           }
           leaf warning-threshold {
              description "Threshold at which to generate warning message";
              type uint32 {
                range "1..2147483647";
              }
           }
      }
      container rpf {
           description "RPF check configuration";
           container select {
               description "Select table for RPF check";
               list vrf {
                   description "Select VPN Routing/Forwarding instance";
                   key "name";
                   leaf name {
                      description "VPN Routing/Forwarding instance name";
                      type string;
                   }
                   list group-list {
                      description "Group access-list";
                      key "group-list-name";
                      leaf group-list-name {
                        type union {
                            type uint16 {
                                range "1..99";
                            }    
                            type string;
                        }
                      }
                   }    
               }
           }
      }
    }
  }

  // ipv6 multicast
  grouping config-ipv6-mcast-grouping {
        leaf vrf {
          description
            "Select VPN Routing/Forwarding instance";
          type string;
        }
        container rpf {
          description
            "Configure multicast RPF related commands";
          container backoff {
            description
              "Backoff delay after unicast routing change";
            leaf initial-delay {
              type uint16 {
                range "200..65535";
              }
            }
            leaf max-delay {
              type uint16 {
                range "200..65535";
              }
            }
          }
          leaf use-bgp {
            description
              "Use BGP routes for multicast RPF lookup";
            type empty;
          }
        }
  }

  grouping ip-pim-grouping {
    // ip pim accept-register
    container accept-register {
      description
        "Registers accept filter";
      leaf list {
        description
          "Access list";
        type ios-types:ext-acl-type;
      }
    }
    container autorp {
      description
        "Configure AutoRP global operations";
      presence "true";
      leaf listener {
        description
          "Allow AutoRP packets across sparse mode interface";
        type empty;
      }
    }
    leaf register-source {
      description
        "Source address for PIM Register";
      type string;
    }
    list rp-address {
      description
        "PIM RP-address (Rendezvous Point)";
      key address;
      leaf address {
        type inet:ipv4-address;
      }
      leaf access-list {
        type ios-types:std-acl-type;
      }
      leaf override {
        description
          "Overrides dynamically learnt RP mappings";
        type empty;
      }
    }
    //ip pim spt-threshold
    list spt-threshold {
      description
        "Source-tree switching threshold";
      key "how group-list";
      leaf how {
        type enumeration {
          enum 0;
          enum infinity;
        }
      }
      leaf group-list {
        description
          "Group address access-list";
        type ios-types:std-acl-type;
      }
    }
    container spt-threshold-container {
      container spt-threshold {
        description
          "Source-tree switching threshold";
        leaf how {
          type enumeration {
            enum 0;
            enum infinity;
          }
        }
      }
    }
    container send-rp-announce {
      description
        "Auto-RP send RP announcement";
      list interface_list {
        key "if-name";
        leaf if-name {
          type string;
        }
        container scope {
          description 
            "RP announcement scope";
          leaf pkt-ttl {
            description 
              "TTL of the RP announce packet";
            type uint8 {
              range "1..255";
            }
          }
          container group-list {
            description 
              "Group access-list";
            leaf acl-ref {
              description 
                "Access-list reference for multicast groups";
              type uint8 {
                range "1..99";
              }
            }
            leaf std-acl {
              description 
                "IP Named Standard Access list";
              type string;
            }
          }
        }
      }
      list Port-channel {
        description
          "Ethernet Channel of interfaces";
        key "name";
        leaf name {
          type uint32 {
            range "1..512";
          }
        }
        leaf scope {
          description
            "RP announcement scope";
          type uint8{
            range "1..255";
          }
        }
      }
    }

    container send-rp-discovery {
      description 
        "Auto-RP send RP discovery message (as RP-mapping agent)";
      leaf scope {
        description
          "Scope of the RP discovery packets: TTL";
        type uint8 {
          range "1..255";
        }
      }
    }

    // ip pim ssm
    container ssm {
      description
        "Configure Source Specific Multicast";
      leaf range {
        description
          "ACL for group range to be used for SSM";
        type union {
          type uint16 {
            range "1..99";
          }
          type string {
            pattern "[a-zA-Z].*";
          }
        }
      }
      leaf default {
        description
          "Use 232/8 group range for SSM";
        type empty;
      }
    }
  }


  grouping config-ip-pim-grouping {
    uses ip-pim-grouping;
    // ip pim vrf *
    list vrf {
      description
        "Select VPN Routing/Forwarding instance";
      key "id";
      leaf id {
        type string;
      }
      uses ip-pim-grouping;
    }
  }

  grouping ipv6-pim-grouping {
    container rp-address {
      description
        "Configure Sparse-Mode Rendezvous Point";
      leaf address {
        type union {
          type string;
          type inet:ipv6-address;
        }
      }
      leaf access-list {
        type union {
          type string;
        }
      }
      leaf bidir {
        description
          "Specify keyword bidir to configure a bidir RP";
        type empty;
      }
    }
  }

  grouping config-ipv6-pim-grouping {
    uses ipv6-pim-grouping;
    // ipv6 pim vrf *
    list vrf {
      description
        "Select VPN Routing/Forwarding instance";
      key "id";
      leaf id {
        type string;
      }
      uses ipv6-pim-grouping;
    }
  }

  grouping config-interface-ip-pim-grouping {
    container accept-register {
      leaf list {
        type string;
      }
    }

    // interface * / ip pim passive/dense-mode/sparse-mode/sparse-dense-mode
    leaf pim-mode {
      type enumeration{
        enum passive;
        enum dense-mode;
        enum sparse-mode;
        enum sparse-dense-mode;
      }
    }
    // interface * / ip pim nbma-mode
    leaf nbma-mode {
      description
        "Enable PIM nbma-mode operation";
      type empty;
    }
    // interface * / ip pim dr-priority
    leaf dr-priority {
      description
        "PIM router DR priority";
      type uint32;
    }
    // interface * / ip pim query-interval
    container query-interval {
      description
        "PIM router query interval";
      choice seconds-milliseconds {
        case seconds {
          leaf seconds-interval {
            type uint16 {
              range "1..18725";
            }
          }
        }
        case milliseconds {
          leaf milliseconds-interval {
            type uint16 {
              range "100..65535";
            }
          }
          leaf msec {
            description
              "Query interval in milliseconds";
            mandatory true;
            type empty;
          }
        }
      }
    }
    // interface * / ip pim spt-threshold
    leaf spt-threshold {
      type enumeration {
        enum "infinity";
      }
    }
  }

  grouping config-interface-ipv6-pim-grouping {
    choice ipv6-pim-choice {
      container no-pim {
        leaf pim {
          description
            "PIM interface commands";
          type boolean;
        }
      }
      // interface * / ipv6 pim
      container pim {
        description
          "PIM interface commands";
        leaf bfd {
          description
            "Configure BFD";
          type empty;
        }
        container bsr {
          description
            "Configure BSR";
          leaf border {
            description
              "Border of PIM BSR domain";
            type empty;
          }
        }
        leaf dr-priority {
          description
            "PIM Hello DR priority";
          type uint32;
        }
      }
    }
  }

  grouping config-mcr-conf-grouping {
    //unused /native/ip/mcr-conf
    container mcr-conf{ 
      leaf multicast-routing {
        description
          "Enable IP multicast forwarding";
        type empty;
      }
    }
  }

  grouping config-multicast-routing-grouping {
      container multicast-routing { 
        description
          "Enable IP multicast forwarding";
        presence "true";
        // ip multicast-routing vrf *
        list vrf {
          description
            "Select VPN Routing/Forwarding instance";
          key "name";
          leaf name {
            type string;
          }
          leaf distributed {
            description
              "Distributed multicast switching";
            type empty;
          }
        }
        // ip multicast-routing distributed
        leaf distributed {
          description
            "Distributed multicast switching";
          type empty;
        }
      }
  }

  grouping config-ipv6-multicast-routing-grouping {
      // ipv6 multicast-routing
      container multicast-routing { 
        description
          "Enable IPv6 multicast";
        presence "true";
        leaf vrf {
          description
            "Select VPN Routing/Forwarding instance";
          type string;
        }
      }
  }

  grouping ip-msdp-grouping {
    container peer {
      description
        "Configure an MSDP peer";
      leaf addr {
        type union {
          type string;
          type inet:ipv4-address;
        }
      }
      leaf connect-source {
        description
          "Configure source address used for MSDP connection";
        type string;
      }
      leaf remote-as {
        description
          "Configured AS number";
        type uint16;
      }
    }
    leaf cache-rejected-sa {
      description
        "Store rejected SAs from all peers";
      type uint32 {
        range "1..32766";
      }
    }
    leaf cache-sa-state {
      description
        "Configure this system to cache SA state";
      type empty;
    }
    container default-peer {
      description
        "Default MSDP peer to accept SA messages from";
      leaf name-addr {
        type union {
          type string;
          type inet:ipv4-address;
        }
      }
      leaf prefix-list {
        description
          "Prefix list";
        type string;
      }
    }
    container description {
      description
        "Peer specific description";
      leaf name-addr {
        type union {
          type string;
          type inet:ipv4-address;
        }
      }
      leaf description {
        type string;
      }
    }
    container filter-sa-request {
      description
        "Filter SA-Requests from peer";
      leaf name-addr {
        type union {
          type string;
          type inet:ipv4-address;
        }
      }
      leaf list {
        description
          "Access-list";
        type ios-types:std-acl-type;
      }
    }
    container keepalive {
      description
        "Configure keepalive parameters for a peer";
      leaf name-addr {
        type union {
          type string;
          type inet:ipv4-address;
        }
      }
      leaf keepalive {
        description
          "Send keepalive period in seconds";
        type uint8 {
          range "1..60";
        }
      }
      leaf max-wait {
        description
          "Maximum time in seconds to wait for a message";
        type uint8 {
          range "1..75";
        }
      }
    }
    container mesh-group {
      description
        "Configure an MSDP mesh-group";
      leaf name {
        type string;
      }
      leaf addr {
        type union {
          type string;
          type inet:ipv4-address;
        }
      }
    }
    leaf originator-id {
      description
        "Configure MSDP Originator ID";
      type string;
    }
    container password {
      description
        "Configure an MSDP password";
      container peer {
        description
          "MSDP peer on which the password is to be set";
        leaf addr {
          type union {
            type string;
            type inet:ipv4-address;
          }
        }
        leaf encryption {
          type uint8;
        }
        leaf password {
          type string;
        }
      }
    }
    container redistribute {
      description
        "Inject multicast route entries into MSDP";
      leaf list {
        description
          "Access-list";
        type ios-types:ext-acl-type;
      }
      leaf asn {
        description
          "AS access-list";
        type uint16;
      }
      leaf route-map {
        description
          "Route-map";
        type string;
      }
    }
    leaf rpf {
      description
        "MSDP rpf";
      type enumeration {
        enum "rfc3618";
      }
    }
    container sa-filter {
      description
        "Filter SA messages from peer";
      container in {
        description
          "Enable incoming SA filtering";
        leaf addr {
          type union {
            type string;
            type inet:ipv4-address;
          }
        }
        leaf list {
          description
            "Access list";
          type ios-types:ext-acl-type;
        }
        leaf route-map {
          description
            "Route map";
          type string;
        }
        leaf rp-list {
          description
            "Access-list for originating RP";
          type union {
            type uint16 {
              range "1..99";
            }
            type string;
          }
        }
        leaf rp-route-map {
          description
            "Route map for originating RP";
          type string;
        }
      }
      container out {
        description
          "Enable outgoing SA filtering";
        leaf addr {
          type union {
            type string;
            type inet:ipv4-address;
          }
        }
        leaf list {
          description
            "Access list";
          type ios-types:ext-acl-type;
        }
        leaf route-map {
          description
            "Route map";
          type string;
        }
        leaf rp-list {
          description
            "Access-list for originating RP";
          type union {
            type uint16 {
              range "1..99";
            }
            type string;
          }
        }
        leaf rp-route-map {
          description
            "Route map for originating RP";
          type string;
        }
      }
    }
    container sa-limit {
      description
        "Configure SA limit for a peer";
      leaf name-addr {
        type union {
          type string;
          type inet:ipv4-address;
        }
      }
      leaf limit {
        description
          "Limit of SAs";
        type uint32 {
          range "1..2147483646";
        }
      }
    }
    container shutdown {
      description
        "Administratively shutdown MSDP peer";
      leaf name-addr {
        type union {
          type string;
          type inet:ipv4-address;
        }
      }
    }
    leaf timer {
      description
        "MSDP timer";
      type uint8 {
        range "1..60";
      }
    }
    container ttl-threshold {
      description
        "Configure TTL Threshold for MSDP Peer";
      leaf name-addr {
        type union {
          type string;
          type inet:ipv4-address;
        }
      }
      leaf threshold {
        description
          "TTL Threshold Value";
        type uint8;
      }
    }
  }

  grouping config-ip-msdp-grouping {
      container msdp {
        description
          "MSDP global commands";
        uses ip-msdp-grouping;
        list vrf {
          description
            "Select VPN Routing/Forwarding instance";
          key "name";
          leaf name {
            type string;
          }
          uses ip-msdp-grouping;
        }
      }
  }

  grouping confif-ip-mroute-grouping {
      container mroute { 
        description
          "Configure static multicast routes";
        leaf source-address {
          type inet:ipv4-address;
        }
        leaf subnet-mask {
          type inet:ipv4-address;
        }
        leaf Tunnel {
          description
            "Tunnel interface";
          type int32 {
            range "0..2147483647";
          }
        }
      }
  }

  /////////////////////////////////////////////////////////
  // native / ip / multicast *
  /////////////////////////////////////////////////////////
  augment "/ios:native/ios:ip/ios:multicast" {
    uses config-ip-mcast-grouping;
  }

  /////////////////////////////////////////////////////////
  // native / ipv6 / multicast *
  /////////////////////////////////////////////////////////
  augment "/ios:native/ios:ipv6/ios:multicast" {
    uses config-ipv6-mcast-grouping;
  }

  /////////////////////////////////////////////////////////
  // native / ip / pim *
  /////////////////////////////////////////////////////////
  augment "/ios:native/ios:ip/ios:pim" {
    uses config-ip-pim-grouping;
  }

  /////////////////////////////////////////////////////////
  // native / ipv6 / pim *
  /////////////////////////////////////////////////////////
  augment "/ios:native/ios:ipv6/ios:pim" {
    uses config-ipv6-pim-grouping;
  }

  /////////////////////////////////////////////////////////
  // native / interface * / ip pim
  /////////////////////////////////////////////////////////
  augment "/ios:native/ios:interface/ios:FastEthernet/ios:ip/ios:pim" {
    uses config-interface-ip-pim-grouping;
  }

  augment "/ios:native/ios:interface/ios:GigabitEthernet/ios:ip/ios:pim" {
    uses config-interface-ip-pim-grouping;
  }

  augment "/ios:native/ios:interface/ios:TwoGigabitEthernet/ios:ip/ios:pim" {
    uses config-interface-ip-pim-grouping;
  }

  augment "/ios:native/ios:interface/ios:FiveGigabitEthernet/ios:ip/ios:pim" {
    uses config-interface-ip-pim-grouping;
  }

  augment "/ios:native/ios:interface/ios:TenGigabitEthernet/ios:ip/ios:pim" {
    uses config-interface-ip-pim-grouping;
  }

  augment "/ios:native/ios:interface/ios:TwentyFiveGigE/ios:ip/ios:pim" {
    uses config-interface-ip-pim-grouping;
  }

  augment "/ios:native/ios:interface/ios:FortyGigabitEthernet/ios:ip/ios:pim" {
    uses config-interface-ip-pim-grouping;
  }

  augment "/ios:native/ios:interface/ios:HundredGigE/ios:ip/ios:pim" {
    uses config-interface-ip-pim-grouping;
  }

  augment "/ios:native/ios:interface/ios:Port-channel/ios:ip/ios:pim" {
    uses config-interface-ip-pim-grouping;
  }

  augment "/ios:native/ios:interface/ios:Loopback/ios:ip/ios:pim" {
    uses config-interface-ip-pim-grouping;
  }

  augment "/ios:native/ios:interface/ios:Tunnel/ios:ip/ios:pim" {
    uses config-interface-ip-pim-grouping;
  }

  augment "/ios:native/ios:interface/ios:Vlan/ios:ip/ios:pim" {
    uses config-interface-ip-pim-grouping;
  }

  augment "/ios:native/ios:interface/ios:Port-channel-subinterface/ios:Port-channel/ios:ip/ios:pim" {
    uses config-interface-ip-pim-grouping;
  }

  /////////////////////////////////////////////////////////
  // native / interface * / ipv6 / pim
  /////////////////////////////////////////////////////////
  augment "/ios:native/ios:interface/ios:FastEthernet/ios:ipv6" {
    uses config-interface-ipv6-pim-grouping;
  }

  augment "/ios:native/ios:interface/ios:GigabitEthernet/ios:ipv6" {
    uses config-interface-ipv6-pim-grouping;
  }

  augment "/ios:native/ios:interface/ios:TwoGigabitEthernet/ios:ipv6" {
    uses config-interface-ipv6-pim-grouping;
  }

  augment "/ios:native/ios:interface/ios:FiveGigabitEthernet/ios:ipv6" {
    uses config-interface-ipv6-pim-grouping;
  }

  augment "/ios:native/ios:interface/ios:TenGigabitEthernet/ios:ipv6" {
    uses config-interface-ipv6-pim-grouping;
  }

  augment "/ios:native/ios:interface/ios:TwentyFiveGigE/ios:ipv6" {
    uses config-interface-ipv6-pim-grouping;
  }

  augment "/ios:native/ios:interface/ios:FortyGigabitEthernet/ios:ipv6" {
    uses config-interface-ipv6-pim-grouping;
  }

  augment "/ios:native/ios:interface/ios:HundredGigE/ios:ipv6" {
    uses config-interface-ipv6-pim-grouping;
  }

  augment "/ios:native/ios:interface/ios:Port-channel/ios:ipv6" {
   uses config-interface-ipv6-pim-grouping;
  }

  augment "/ios:native/ios:interface/ios:Loopback/ios:ipv6" {
    uses config-interface-ipv6-pim-grouping;
  }

  augment "/ios:native/ios:interface/ios:Tunnel/ios:ipv6" {
    uses config-interface-ipv6-pim-grouping;
  }

  augment "/ios:native/ios:interface/ios:Vlan/ios:ipv6" {
    uses config-interface-ipv6-pim-grouping;
  }

  /////////////////////////////////////////////////////////
  // native / ip / msdp
  /////////////////////////////////////////////////////////
  augment "/ios:native/ios:ip" {
    uses config-ip-msdp-grouping;
  }

  /////////////////////////////////////////////////////////
  // native / ip / multicast-routing
  /////////////////////////////////////////////////////////
  augment "/ios:native/ios:ip" {
    uses config-mcr-conf-grouping;
    uses config-multicast-routing-grouping;
  }

  /////////////////////////////////////////////////////////
  // native / ip / mroute
  /////////////////////////////////////////////////////////
  augment "/ios:native/ios:ip" {
    uses confif-ip-mroute-grouping;
  }

  /////////////////////////////////////////////////////////
  // native / ipv6 / multicast-routing
  /////////////////////////////////////////////////////////
  augment "/ios:native/ios:ipv6" {
    uses config-ipv6-multicast-routing-grouping;
  }
}
