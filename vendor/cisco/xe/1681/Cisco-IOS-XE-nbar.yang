module Cisco-IOS-XE-nbar {
  namespace "http://cisco.com/ns/yang/Cisco-IOS-XE-nbar";
  prefix ios-nbar;


  import Cisco-IOS-XE-native {
    prefix ios;
  }

  import ietf-inet-types {
        prefix inet;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Network-Based Application Recognition (NBAR) Yang model.
     Copyright (c) 2016-2017 by Cisco Systems, Inc.
     All rights reserved.";

  // =========================================================================
  // REVISION
  // =========================================================================
  revision 2017-11-27 {
     description
       "Added Change 25GE name";
  }

  revision 2017-11-14 {
    description
      "This revision has changes for new 40 and 100GE interface addition";
  }

  revision 2017-09-15 {
    description
      "This revision has changes for new 2gig interface addition";
  }
  revision 2017-08-16 {
    description
      "This revision has changes for new 5gig and 25gig interfaces addition";
  }

  revision 2017-07-31 {
    description
      "Added ip nbar classfication CLI's";
  }
  revision 2017-07-13 {
    description 
      "Support for dynamically updated protocol-pack, sd-avc, and missing CLI's";
  }
  revision 2017-02-07 {
    description
      "Initial revision";
  }

  grouping config-custom-grouping {
    container dscp {
      description "DSCP in IPv4 and IPv6 packets";
       leaf range {
         description "Differentiated services codepoint value";
         type uint8 {
           range "0..63";
         }
       }
       leaf af11 {
         description "Match packets with AF11 dscp (001010)";
         type empty;
       }
       leaf af12 {
         description "Match packets with AF12 dscp (001100)";
         type empty;
       }
       leaf af13 {
         description "Match packets with AF13 dscp (001110)";
         type empty;
       }
       leaf af21 {
         description "Match packets with AF21 dscp (010010)";
         type empty;
       }
       leaf af22 {
         description "Match packets with AF22 dscp (010100)";
         type empty;
       }
       leaf af23 {
         description "Match packets with AF23 dscp (010110)";
         type empty;
       }
       leaf af31 {
         description "Match packets with AF31 dscp (011010)";
         type empty;
       }
       leaf af32 {
         description "Match packets with AF32 dscp (011100)";
         type empty;
       }
       leaf af33 {
         description "Match packets with AF33 dscp (011110)";
         type empty;
       }
       leaf af41 {
         description "Match packets with AF41 dscp (100010)";
         type empty;
       }
       leaf af42 {
         description "Match packets with AF42 dscp (100100)";
         type empty;
       }
       leaf af43 {
         description "Match packets with AF43 dscp (100110)";
         type empty;
       }
       leaf cs1 {
         description "Match packets with CS1(precedence 1) dscp (001000)";
         type empty;
       }
       leaf cs2 {
         description "Match packets with CS2(precedence 2) dscp (010000)";
         type empty;
       }
       leaf cs3 {
         description "Match packets with CS3(precedence 3) dscp (011000)";
         type empty;
       }
       leaf cs4 {
         description "Match packets with CS4(precedence 4) dscp (100000)";
         type empty;
       }
       leaf cs5 {
         description "Match packets with CS5(precedence 5) dscp (101000)";
         type empty;
       }
       leaf cs6 {
         description "Match packets with CS6(precedence 6) dscp (110000)";
         type empty;
       }
       leaf cs7 {
         description "Match packets with CS7(precedence 7) dscp (111000)";
         type empty;
       }
       leaf default {
         description "Match packets with default dscp (000000)";
         type empty;
       }
       leaf ef {
         description "Match packets with EF dscp (101110)";
         type empty;
       }
    }
    container ip {
      description "ip address";
      list address {
        description "ip address list";
        key "address0";
        leaf address0 {
          description "List of up to 8 IPs separated by white-spaces"; 
          type inet:ipv4-address;
        }
        leaf address1 {
          description "List of up to 8 IPs separated by white-spaces";
          type inet:ipv4-address;
        }
        leaf address2 {
          description "List of up to 8 IPs separated by white-spaces";
          type inet:ipv4-address;
        }
        leaf address3 {
          description "List of up to 8 IPs separated by white-spaces";
          type inet:ipv4-address;
        }
        leaf address4 {
          description "List of up to 8 IPs separated by white-spaces";
          type inet:ipv4-address;
        }
        leaf address5 {
          description "List of up to 8 IPs separated by white-spaces";
          type inet:ipv4-address;
        }
        leaf address6 {
          description "List of up to 8 IPs separated by white-spaces";
          type inet:ipv4-address;
        }
        leaf address7 {
          description "List of up to 8 IPs separated by white-spaces";
          type inet:ipv4-address;
        }
      }
      container subnet {
        description "Subnet IP/mask length";
        leaf subnet {
          description "Subnet IP";
          type inet:ipv4-address;
        }
        leaf mask {
            type uint8 {
              range "0..32";
            }
        }
      }
    }
    container ipv6 {
      description "ipv6 address";
      list address {
        description "ipv6 address list";
        key "address0";
        leaf address0 {
          description "List of up to 8 IPs separated by white-spaces";
          type inet:ipv6-address;
        }
        leaf address1 {
          description "List of up to 8 IPs separated by white-spaces";
          type inet:ipv6-address;
        }
        leaf address2 {
          description "List of up to 8 IPs separated by white-spaces";
          type inet:ipv6-address;
        }
        leaf address3 {
          description "List of up to 8 IPs separated by white-spaces";
          type inet:ipv6-address;
        }
        leaf address4 {
          description "List of up to 8 IPs separated by white-spaces";
          type inet:ipv6-address;
        }
        leaf address5 {
          description "List of up to 8 IPs separated by white-spaces";
          type inet:ipv6-address;
        }
        leaf address6 {
          description "List of up to 8 IPs separated by white-spaces";
          type inet:ipv6-address;
        }
        leaf address7 {
          description "List of up to 8 IPs separated by white-spaces";
          type inet:ipv6-address;
        }
      }
      container subnet {
        description "Subnet IP/mask length";
          leaf subnet {
            description "Subnet IP";
            type inet:ipv6-address;
          }
          leaf mask {
            type uint8 {
              range "0..128";
            }
          } 
      } 
    }
    container direction {
      description "Flow direction";
      leaf any {
        description "Any Direction";
        type empty;
      }
      leaf destination {
        description "Destination Direction";
        type empty;
      }
      leaf source {
        description "Source Direction";
        type empty;
      }
    }
    container port {
      description "ports";
      list port-numbers {
        key "port-number0";
        leaf port-number0 {
          description "Up to 8 port numbers separated by white-spaces";
          type uint16 {
            range "1..65535";
          }
        }
        leaf port-number1 {
          description "Up to 8 port numbers separated by white-spaces";
          type uint16 {
            range "1..65535";
          }
        }
        leaf port-number2 {
          description "Up to 8 port numbers separated by white-spaces";
          type uint16 {
            range "1..65535";
          }           
        }
        leaf port-number3 {
          description "Up to 8 port numbers separated by white-spaces";
          type uint16 {
            range "1..65535";
          }           
        }
        leaf port-number4 {
          description "Up to 8 port numbers separated by white-spaces";
          type uint16 {
            range "1..65535";
          }           
        }
        leaf port-number5 {
          description "Up to 8 port numbers separated by white-spaces";
          type uint16 {
            range "1..65535";
          }           
        }
        leaf port-number6 {
          description "Up to 8 port numbers separated by white-spaces";
          type uint16 {
            range "1..65535";
          }           
        }
        leaf port-number7 {
          description "Up to 8 port numbers separated by white-spaces";
          type uint16 {
            range "1..65535";
          }
        } 
      } 
      container range {
        description "Range of maximum 1000 Ports. With IP option use maximum range of 8.";
          leaf start-range {
            description "Enter Start port number for Range";
            type uint16 {
              range "1..65535";
            }
          }
          leaf end-range {
            description "Enter Start port number for Range";
            type uint16 {
              range "1..65535";
            }
          }
      }
    }
  }
  grouping config-avc-grouping {
    container dns-as {
      description "DNS-AS based classification";
      container client {
        description "DNS-AS client based classification";
        leaf enable {
          description "enable DNS-AS client based classification";
          type empty;
        }
        container trusted-domains {
          description "Handle DNS-AS trusted domains";
          presence true;
            leaf domain {
              description "Add new trusted domain to DNS-AS";
              type string;
            }
          }
        }
    }
    container sd-service {
      description "SD-AVC service";
      presence true;
        leaf segment {
           description "Segment name identifying a group of devices sharing the same application services";
           type string;
        }
        container controller {
          description "Controller connectivity parameters";
          presence true;
            container address {
              description "Export destination configuration";
              list ipv4-or-hostname {
                key "ipv4-or-hostname";
                  leaf ipv4-or-hostname {
                    description "Primary controller's IPv4 address or hostname";
                    type inet:host;
                  }
                  leaf ipv4-or-hostname0 {
                    description "Secondary controller's IPv4 address or hostname";
                    type inet:host;
                  }
              }
           }
           container destination-ports {
             description "Ports used for communication with controller";
               leaf sensor-exporter {
                 description "UDP port used for sensor messages";
                 type uint16 {
                   range "1..65535";
                 }
               }
           }
           leaf dscp {
             description "DSCP marking";
             type uint8 {
               range "0..63";
             }
           }
           leaf vrf {
             description "VRF Label";
             type string;
           }
        }
     }
  }

  grouping ip-nbar-attribute-custom-grouping {
    list custom {
      description
        "Custom group to be created for this attribute";
      key "name";
      leaf name {
        description "Custom group value";
        type string;
      }
      leaf help {
        description "Help string";
        type string;
      }
    }
  }

  grouping config-interface-ip-nbar-grouping {
    container nbar {
      description
        "Network-Based Application Recognition";
      container protocol-discovery {
        description
          "Enable protocol discovery for both ipv4 and ipv6";
        presence "true";
        leaf ipv4-ipv6 {
          type enumeration {
            enum "ipv4";
            enum "ipv6";
          }
        }
      }
    }
  }

  grouping config-ip-nbar-grouping {
    container nbar {
      description
        "NBAR - Network Based Application Recognition";
      container attribute {
        description
          "Attribute for which custom group value can be created";
        container application-group {
          description
            "Application-group attribute";
          uses ip-nbar-attribute-custom-grouping;
        }
        container application-set {
         description "Application-set attribute"; 
         uses ip-nbar-attribute-custom-grouping;
        }
        container category {
          description
            "Category attribute";
          uses ip-nbar-attribute-custom-grouping;
        }
        container sub-category {
          description
            "Sub-category attribute";
          uses ip-nbar-attribute-custom-grouping;
        }
      }
      list attribute-map {
        description
          "Attribute Map";
        key "name";
        leaf name {
          type string;
        }
        container attribute {
          description
            "Attribute Name";
          leaf application-group {
            description
              "Application-group attribute";
            type string;
          }
          leaf application-set {
            description
              "Application-set attribute";
            type string;
          }
          leaf business-relevance {
            description
              "Application business-relevance";
            type string;
          }
          leaf category {
            description
              "Category attribute";
            type string;
          }
          leaf encrypted {
            description
              "Encrypted applications";
            type string;
          }
          leaf sub-category {
            description
              "Sub-category attribute";
            type string;
          }
          leaf traffic-class {
            description
              "SRND class";
            type string;
          }
          leaf tunnel {
            description
              "Tunnelled applications";
            type string;
          }
        }
      }
      list attribute-set {
        description
          "Set attribute Map";
        key "protocol-name";
        leaf protocol-name {
          description "Protocol Name";
          type string;
            //3com-amp3                      3Com AMP3
            //3com-tsmux                     3Com TSMUX
            //... ...
            //zserv                          Zebra server
            //zulily                         Zulily -
            //Online shopping aimed for Moms apparel and home decor items.
        }
        leaf profile-name {
          description "Attribute Profile Name";
          type string;
        }
      }
      container classification {
        description "NBAR Classification";
        container auto-learn {
          description "Statistics on unknown or generic traffic";
          presence true;
          leaf top-asymmetric-socket {
            description "Statistics on asymmetric socket";
            type empty;
          }
          container top-hosts {
            description "Statistics on generic traffic per host";
            presence true;
            leaf sample-rate {
              description "configure sampling rate";
              type uint16 {
                range "1..8192";
              }
            }
          }
          container top-ports {
            description "Statistics on unknown traffic per port";
            presence true;
            leaf sample-rate {
              description "configure sampling rate";
              type uint16 {
                range "1..8192";
              }
            }
          }
        }
        container dns {
          description "dns classification";
          leaf classify-by-domain {
            description "dns classification by domain";
            type empty;
          }
           container learning {
            description "dns learning";
            presence true;
            leaf guard {
              description "dns guard prevents learning from responses only";
              type empty;
            }
          }
        }
        container granularity {
          description "Force granularity mode";
          leaf coarse-grain {
            description "Force coarse-grain classification mode";
            type empty;
          }
          container fine-grain {
            description "Force fine-grain classification mode";
            presence true;
            container attribute {
              description "Force granularity for a single attribute";
              list application-group {
                description "Application-group attribute";
                key "name";
                leaf name {
                  type string;
                }
              }
              list application-set {
                description "Application-set attribute";
                key "name";
                leaf name {
                  type string;
                }
              }
              list business-relevance {
                description "Application business-relevance";
                key "name";
                leaf name {
                  type string;
                }
              }
              list category {
                description "Category attribute";
                key "name";
                leaf name {
                  type string;
                }
              }
              list encrypted {
                description "Encrypted applications";
                key "name";
                leaf name {
                  type string;
                }
              } 
              list sub-category {
                description "Sub-category attribute";
                key "name";
                leaf name {
                  type string;
                }
              } 
              list traffic-class {
                description "SRND class";
                key "name";
                leaf name {
                  type string;
                }
              } 
              list tunnel {
                description "Tunnelled applications";
                key "name";
                leaf name {
                  type string;
                }
              } 
            }
            container protocol {
              description "Force granularity for a single protocol";
              list protocols-list {
                key "name";
                leaf name {
                  type string;
                }
              }
            }
          }
         }
         container tunneled-traffic {
           description "Classify IPv6 Tunneled traffic";
           leaf capwap {
             description "Tunnel type CAPWAP";
             type empty;
           }
           leaf ipv6inip {
             description "Tunnel type IPv6 in IPv4";
             type empty;
           }
           leaf teredo {
             description "Tunnel type TEREDO";
             type empty;
           }
         }
      }
      list custom {
        description
          "Custom PDL (protocol description language) Module";
        key "name";
        leaf name {
          description "Name of the User defined Protocol";
          type string;
        }
        container composite {
          description "Custom protocols based on multiple underlying protocols";
          list  server-name {
            description "Match the server name based on various protocols";
            key "name";
            leaf name {
              description "Enter String Format - cannot exceed 30 characters";
              type string;
            }
            leaf id {
              description "Enter Selector ID";
              type uint16 {
                range "1..65535";
              }
            }
            leaf extends {
              description "Extend existing protocol";
              type string;
            }
          }
        }
        container dns {
          description "Custom protocols based on dns parameters";
          list domain-name {
            description "Domain name";
            key "name";
            leaf name {
              description "Enter String Format - cannot exceed 30 characters";
              type string;
            }
            leaf id {
              description "Selector ID";
              type uint16 {
                range 1..65535;
              }
            }
            leaf extends {
              description "Extend existing protocol";
              type string;
            }
          }
        }
        container http {
          description
            "Custom protocols based on http parameters";
          leaf cookie {
            description
              "HTTP Cookie";
            type string;
          }
          leaf host {
            description
              "Host name of Origin Server containing resource";
            type string;
          }
          leaf method {
            description
              "HTTP method";
            type string;
          }
          leaf referer {
            description
              "Address the resource request was obtained from";
            type string;
          }
          choice http-uv {
            case url-case {
              leaf url {
                description
                  "Uniform Resource Locator path";
                type string;
              }
            }
            case user-agent-case {
              leaf user-agent {
                description
                  "Software used by agent sending the request";
                type string;
              }
            }
            case version-case {
              leaf version {
                description
                  "HTTP version";
                type string;
              }
            }
            case via-case {
              leaf via {
                description
                  "HTTP via field";
                type string;
              }
            }
          }
          leaf id {
            description
              "Selector ID";
            type uint16 {
                range "1..65535";
              }
          }
        }
        container ssl {
          description "Custom protocols based on ssl parameters";
          list unique-name {
            description "SSL Server Name Indication (SNI) or Common Name (CN)";
            key "name";
            leaf name {
              description "Enter String Format - cannot exceed 30 characters";
              type string;
            }
            leaf id {
              description "Enter Selector ID";
              type uint16 {
                range "1..65535";
              }
            }
          }
        }
        container transport {
          description "Custom protocols based on the transport layer and below";
          container tcp {
            description "TCP transport";
            presence true;
            leaf id {
              description "Selector ID";
              type uint16 {
                range "1..65535";
              }
            }
            uses config-custom-grouping;
          }
          container udp {
            description "UDP transport";
            presence true;
            leaf id {
              description "Selector ID";
              type uint16 {
                range "1..65535";
              }
            }
            uses config-custom-grouping;
          }
          container udp-tcp {
            description "UDP or TCP transport";
            presence true;
            leaf id {
              description "Selector ID";
              type uint16 {
                range "1..65535";
              }
            }
            uses config-custom-grouping;
          }
        }
        container ip {
          description "Custom protocols based on the transport layer and below";
          container any {
            description "TCP transport";
            presence true;
            leaf id {
              description "Selector ID";
              type uint16 {
                range "1..65535";
              }
            }
            uses config-custom-grouping;
          }
        }
       }
       container protocol-pack {
         description "Protocol Pack";
         list filepath {
           key "filepath";
           leaf filepath {
             description "Path of protocol pack to load";
             type string;
           }
           leaf force {
             description "Force";
             type empty;
           }
         }
       }
       leaf http-services {
         description "Enable HTTP services";
         type empty;
       }
     }
   }


  /////////////////////////////////////////////////////////
  // native / ip / nbar
  /////////////////////////////////////////////////////////
  augment "/ios:native/ios:ip" {
    uses config-ip-nbar-grouping;
  }

  /////////////////////////////////////////////////////////
  // native / interface / ip
  /////////////////////////////////////////////////////////
  augment "/ios:native/ios:interface/ios:FastEthernet/ios:ip" {
    uses config-interface-ip-nbar-grouping;
  }

  augment "/ios:native/ios:interface/ios:GigabitEthernet/ios:ip" {
    uses config-interface-ip-nbar-grouping;
  }

  augment "/ios:native/ios:interface/ios:TenGigabitEthernet/ios:ip" {
    uses config-interface-ip-nbar-grouping;
  }

  augment "/ios:native/ios:interface/ios:FiveGigabitEthernet/ios:ip" {
    uses config-interface-ip-nbar-grouping;
  }

  augment "/ios:native/ios:interface/ios:TwentyFiveGigE/ios:ip" {
    uses config-interface-ip-nbar-grouping;
  }

  augment "/ios:native/ios:interface/ios:TwoGigabitEthernet/ios:ip" {
    uses config-interface-ip-nbar-grouping;
  }

  augment "/ios:native/ios:interface/ios:FortyGigabitEthernet/ios:ip" {
    uses config-interface-ip-nbar-grouping;
  }
  augment "/ios:native/ios:interface/ios:HundredGigE/ios:ip" {
    uses config-interface-ip-nbar-grouping;
  }

  augment "/ios:native/ios:interface/ios:Port-channel/ios:ip" {
    uses config-interface-ip-nbar-grouping;
  }

  augment "/ios:native/ios:interface/ios:Loopback/ios:ip" {
    uses config-interface-ip-nbar-grouping;
  }

  augment "/ios:native/ios:interface/ios:Tunnel/ios:ip" {
    uses config-interface-ip-nbar-grouping;
  }

  augment "/ios:native/ios:interface/ios:Vlan/ios:ip" {
    uses config-interface-ip-nbar-grouping;
  }

  /////////////////////////////////////////////////////////
  // native / avc
  /////////////////////////////////////////////////////////
  augment "/ios:native/ios:avc" {
    uses config-avc-grouping;
  }

}
