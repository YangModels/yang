module Cisco-IOS-XE-dhcp {
  namespace "http://cisco.com/ns/yang/Cisco-IOS-XE-dhcp";
  prefix ios-dhcp;

  import ietf-inet-types {
    prefix inet;
  }


  import Cisco-IOS-XE-native {
    prefix ios;
  }

  import Cisco-IOS-XE-types {
    prefix ios-types;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Dynamic Host Configuration Protocol (DHCP) Yang model.
     Copyright (c) 2016-2017 by Cisco Systems, Inc.
     All rights reserved.";

  // =========================================================================
  // REVISION
  // =========================================================================
  revision 2017-11-27 {
     description
       "Added Change 25GE name";
  }

  revision 2017-11-14 {
    description
      "Add 100GE interface";
  }

  revision 2017-11-06 {
    description
      "Remove choice for ip dhcp pool / client-identifier and hardware-address";
  }

  revision 2017-11-01 {
    description
      "Add ip dhcp pool / host, client-name, client-identifier, hardware-address";
  }

  revision 2017-10-18 {
    description
      "Add modeling to interface mode: ip dhcp client route distance/track";
  }

  revision 2017-09-14 {
    description 
      "This revison has changes for new 2gig interface addition";
  }
  revision 2017-08-16 {
    description
      "This revision has changes for new 5gig and 25gig interfaces addition";
  }

  revision 2017-04-28 {
    description
      "inet:ipv6-prefix changed to ios-types:ipv6-prefix";
  }
  revision 2017-03-02 {
    description
      "Re-arrange the order of vrf in ipv6 dhcp pool";
  }
  revision 2017-02-07 {
    description
      "Initial revision";
  }

  // interface * / ip dhcp
  grouping config-interface-ip-dhcp-grouping {
    container client {
      description
        "DHCP client configuration";
      leaf hostname {
        description
          "Specify hostname to use";
        type string;
      }
      container route {
        description
          "Options for routes installed by dhcp";
        leaf distance {
          description
            "set distance for dhcp static routes";
          type uint8 {
            range "1..254";
          }
        }
        leaf track {
          description
            "Track dhcp routes";
          type uint16 {
            range "1..1000";
          }
        }
      }
    }
    container relay {
      description
        "DHCP relay configuration parameters";
      container information {
        description
          "DHCP relay information option";
        container check-reply {
          description
            "Validate relay information in BOOTREPLY";
          presence "true";
          leaf none {
            description
              "Set to none";
            type empty;
          }
        }
        container option {
          description
            "DHCP relay information option";
          leaf subscriber-id {
            description
              "Subscriber identifier sub option";
            type string;
          }
        }
        container option-insert {
          description
            "Insert relay information in BOOTREQUEST";
          presence "true";
          leaf none {
            description
              "Set to none";
            type empty;
          }
        }
        leaf policy-action {
          description
            "Define reforwarding policy";
          type enumeration {
            enum "drop";
            enum "encapsulate";
            enum "keep";
            enum "replace";
          }
        }
        leaf trusted {
          description
            "Received DHCP packet may contain relay info option with zero giaddr";
          type empty;
        }
      }
      leaf source-interface {
        description
          "Set source interface for relayed messages";
        type string;
      }
    }
    container snooping {
      description
        "DHCP Snooping";
      container limit {
        description
          "DHCP Snooping limit";
        leaf rate {
          description
            "DHCP Snooping limit";
          type uint16 {
            range "1..2048";
          }
        }
      }
      leaf trust {
        description
          "DHCP Snooping trust config";
        type empty;
      }
      list vlan {
        description
          "DHCP Snooping vlan";
        key "id";
        leaf id {
          type uint16 {
            range "1..4094";
          }
        }
        container information {
          description
            "DHCP Snooping information";
          container option {
            description
              "DHCP Snooping information option";
            container format-type {
              description
                "Option 82 information format";
              container circuit-id {
                description
                  "Circuit id option 82 format";
                leaf string {
                  description
                    "User defined string for circuit id";
                  type string {
                    length "3..63";
                  }
                }
              }
            }
          }
        }
      }
    }
  }

  // interface * / ipv6 dhcp
  grouping config-interface-ipv6-dhcp-grouping {
    choice client-server-choice {
      container client {
        description "Act as an IPv6 DHCP client";
        container request {
          description "Request";
          leaf vendor {
            description "Request Vendor specific options";
            type empty;
          }
        }
      }
      list server {
        description
          "Act as an IPv6 DHCP server";
        key "word";
        leaf word {
          type string;
        }
        leaf preference {
          description
            "Preference";
          type uint8 {
            range "0..255";
          }
        }  
      }
    }
    container guard {
      description "Configure IPv6 DHCP guard on the interface";
      presence true;
      leaf attach-policy {
        description "Apply a policy for feature DHCP Guard";
        type string;
      }
    }
  }

  grouping ip-dhcp-grouping {
    // ip dhcp bootp
    container bootp {
      description "BOOTP specific configuration";
      leaf ignore {
        description "Configure this DHCP server to ignore to BOOTP requests.";
        type empty;
      }
    }
    list class {
      description
        "Configure DHCP classes";
      key "id";
      leaf id {
        type string;
      }
      // ip dhcp class * / relay
      container relay {
        description
          "Enter relay agent information option configuration submode";
        container agent {
          description
            "Enter relay agent information option configuration submode";
          leaf information {
            description
              "Enter relay agent information option configuration submode";
            type empty;
          }
        }
      }
      // ip dhcp class * / remark
      leaf remark {
        description
          "Specify a remark for this class";
        type string {
          length "1..240";
        }
      }
    }
    //  compatibility              Compatibility configuration
    //  conflict                   DHCP address conflict parameters
    //  database                   Configure DHCP database agents
    //  excluded-address        Prevent DHCP from assigning certain addresses
    //  limit                      Limit DHCP Lease
    //  limited-broadcast-address  Use all 1's broadcast address
    //  ping                       Specify ping parameters used by DHCP

    //ip dhcp conflict *
    container conflict {
      description
        "DHCP address conflict parameters";
      leaf logging {
        description
          "Record address conflicts in a log file";
        type boolean;
      }
      container resolution {
        description
          "DHCP address conflict resolution";
        presence "true";
        leaf interval {
          description
            "Time in Minutes";
          type uint32 {
            range "5..1440";
          }
        }
      }
    }
    //ip dhcp excluded-address
    list excluded-address {
      description
        "Prevent DHCP from assigning certain addresses";
      key "low-address";
      leaf low-address {
        type inet:ipv4-address;
      }
      leaf vrf {
        description
          "VRF name for excluded address range";
        type string;
      }
      leaf high-address {
        type inet:ipv4-address;
      }
    }
    // ip dhcp relay
    container relay {
      description
        "DHCP relay agent parameters";
      container information {
        description
          "Relay agent information option";
        leaf trust-all {
          description
            "Received DHCP packets may contain relay info option with zero giaddr";
          type empty;
        }
        container option {
          description
            "Insert relay information in BOOTREQUEST";
          leaf option-default {
            description "Default option, no vpn";
            type empty;
          }
          leaf vpn {
            description
              "Insert VPN sub-options and change the giaddr to the outgoing interface";
            type empty;
          }
        }
      }
    }
    // ip dhcp pool *
    list pool {
      description
        "Configure DHCP address pools";
      key "id";
      leaf id {
        type string;
      }
      //  accounting           Send Accounting Start/Stop messages
      //  bootfile             Boot file name
      //  netbios-name-server  NetBIOS (WINS) name servers
      //  netbios-node-type    NetBIOS node type
      //  next-server          Next server in boot process
      container option {                                      
        description "Raw DHCP options";                     
        list option-range {                                 
          key "option-range";                             
          leaf option-range {                             
            description "DHCP option code";             
            type uint8 {                                
              range "0..254";                         
            }                                           
          }                                               
          leaf ascii {                                    
            description "Data is an NVT ASCII string";  
            type string;                                
          }                                               
          container hex {                                 
            description "Data is a hexadecimal string"; 
            leaf hex-line {                             
              description 
                "Hexadecimal string, truncated to 180 hex characters entered";
              type string;                            
            }                                           
            leaf none {                                 
              description "No data";                  
              type empty;                             
            }
          }                                               
          leaf-list ip {                                  
            description "Data is one or more IP addresses";                                                                             
            type inet:host;                     
          }
        }
      }

      //  origin               Configure the origin of the pool
      //  relay                Function as a DHCP relay
      //  renew                Configure renewal policy
      //  server               Configure the server ID option value
      //  subnet               Subnet allocation commands
      //  update               Dynamic updates
      //  utilization          Configure various utilization parameters
      list class {
        description "Specify a DHCP class";
        key "name";
        leaf name {
          description "DHCP class name";
          type string;
        }
        container address {
          description "Specify an address range for this class";
          container range {
            leaf ipv4-start {
              description "Start IP address";
              type inet:ipv4-address;
            }

            leaf ipv4-end {
              description "End IP address";
              type inet:ipv4-address;
            }
          }
        }
      }
      leaf vrf {
        description "Associate this pool with a VRF";
        type string;
      }
      list lease {
        description
          "Address lease time";
        key "Days";
        leaf Days {
            type uint16 {
            range "0..365";
          }
        }
        leaf Hours {
          description
            "Hours";
          type uint8;
        }
        leaf Minutes {
          description
            "Minutes";
          type uint8;
        }
      }
      leaf-list default-router {
        description
          "Default routers";
        type union {
          type string;
          type inet:ipv4-address;
        }
      }
      leaf-list dns-server {
        description
          "DNS servers";
        type union {
          type string;
          type inet:ipv4-address;
        }
      }
      leaf domain-name {
        description
          "Domain name";
        type string;
      }
      container network {
        description
          "Network number and mask";
        leaf number {
          type inet:ipv4-address;
        }
        leaf mask {
          type union {
            type string;
            type inet:ipv4-address;
          }
        }
        leaf secondary {
          description
            "Configure as secondary subnet";
          type empty;
        }
      }
      container host {
        description
          "Client IP address and mask";
        leaf number {
          type inet:ipv4-address;
        }
        leaf mask {
          type inet:ipv4-address;
        }
      }
      choice hardware-addr-cient-id-choice {
        container hardware-address {
          description
            "Client hardware address";
          leaf hardware-address-val {
            description
              "Dotted-hexadecimal string (aabb.ccdd.eeff ...)";
            type ios-types:cisco-mac-address-type;
          }
        }
        leaf client-identifier {
          description
            "Client identifier, Dotted-hexadecimal string (aabb.ccdd.eeff ...)";
          type string;
        }
      }
      leaf client-name {
        description
          "Client name, Client name (domain should not be included)";
        type string;
      }
    }
    //  relay                      DHCP relay agent parameters
    //  route  Specify the type of routes for clients on unnumbered interfaces

    // ip dhcp smart-relay
    leaf smart-relay {
      description
        "Enable Smart Relay feature";
      type empty;
    }
    // ip dhcp snooping
    container snooping-conf {
      leaf snooping {
        description
          "DHCP Snooping";
        type empty;
      }
    }
    container snooping {
      description
        "DHCP Snooping";
      //  database     DHCP snooping database agent
      container database {
        description
          "DHCP snooping database agent";
        leaf url {
          type string;
        }
        leaf timeout {
          description
            "Configure abort timeout interval";
          type uint32 {
            range "0..86400";
          }
        }
        leaf write-delay {
          description
            "Configure delay timer for writes to URL";
          type uint32 {
            range "15..86400";
          }
        }
      }
      container information {
        description
          "DHCP Snooping information";
        leaf option-conf {
          type boolean;
        }
        container option {
          description
            "DHCP Snooping information option";
          presence "true";
          leaf allow-untrusted {
            description
              "DHCP Snooping information option allow-untrusted";
            type empty;
          }
          container format {
            description
              "Option 82 information format";
            container remote-id {
              description
                "Remote id option 82 format";
              choice remote-id-choice {
                leaf hostname {
                  description
                    "Use configured hostname for remote id";
                  type empty;
                }
                leaf string {
                  description
                    "User defined string for remote id";
                  type string;
                }
              }
            }
          }
        }
      }
      container track {
        description
          "DHCP snooping track";
        leaf host {
          description
            "DHCP snooping track host";
          type empty;
        }
      }
      container verify {
        description
          "DHCP snooping verify";
        leaf mac-address {
          description
            "DHCP snooping verify mac-address";
          type empty;
        }
        leaf no-relay-agent-address {
          description
            "DHCP snooping verify giaddr";
          type empty;
        }
      }
      leaf vlan {
        description
          "DHCP Snooping vlan";
        type string;
      }
    }
        //  use        Configure use of certain parameters during allocation
  }
  grouping ipv6-dhcp-grouping {
    container server {
      description "Configure IPv6 DHCP server";
      container vrf {
        description "Enable VRF Awareness on server";
        leaf enable {
          description "Enable Address/PD allocation based on VRF";
          type empty;
        }
      }
    }
    container guard {
      description "Configure IPv6 DHCP guard";
      list policy {
        description "Configure a policy for feature dhcp guard";
        key "dhcp-guard-policy-name" ;
        leaf dhcp-guard-policy-name{
          type string;
        }
        container device-role {
          description "Sets the role of the device attached to the port";
          leaf server {
            description "Attached device is a dhcp server";
            type empty;
          }
          leaf client {
            description "Attached device is a client (default)";
            type empty;
          }
        }
        container match {
          description "dhcp filtering";
          container server {
            description "permitted server source addresses";
            leaf access-list {
              description "specify access-list for match";
              type string;
            }
          }
        }		  
      }
    }
    list pool {
      description
        "Configure IPv6 DHCP pool";
      key "name";
      leaf name {
        description 
          "DHCP pool name";
        type string;
      }
      leaf vrf {
        description
          "VRF name";
        type string;
      }
      container address {
        description
          "IPv6 address allocation";
        list prefix {
          description
            "IPv6 address allocation prefix";
          key ipv6-address;
          leaf ipv6-address {
            type ios-types:ipv6-prefix;
          }
          container lifetime {
            description
              "Configure prefix lifetimes";
            leaf valid-lifetime {
              type union {
                type uint32 {
                  range "0 .. 4294967295";
                }
                type enumeration {
                  enum "infinite";
                }
              }
            }
            leaf preferred-lifetime {
              type union {
                type uint32 {
                  range "0 .. 4294967295";
                }
                type enumeration {
                  enum "infinite";
                }
              }
            }
          }
        }
      }
      leaf-list dns-server {
        description 
          "Server's name or IPv6 addres";
        type union {
          type string;
          type inet:ipv6-address;
        }
      }
      leaf domain-name {
        description 
          "Domain name to complete unqualified host names";
        type string;
      }
     
      list link-address {
        description "Link-address to match";
        key "address";
        leaf address {
          type ios-types:ipv6-prefix;
        }
      }
    }
  }

  /////////////////////////////////////////////////////////
  // native / ip / dhcp
  /////////////////////////////////////////////////////////
  augment "/ios:native/ios:ip/ios:dhcp" {
    uses ip-dhcp-grouping;
  }

  /////////////////////////////////////////////////////////
  // native / ipv6 / dhcp
  /////////////////////////////////////////////////////////
  augment "/ios:native/ios:ipv6/ios:dhcp" {
    uses ipv6-dhcp-grouping;
  }

  /////////////////////////////////////////////////////////
  // native / interface * / ip dhcp
  /////////////////////////////////////////////////////////
  augment "/ios:native/ios:interface/ios:FastEthernet/ios:ip/ios:dhcp" {
    uses config-interface-ip-dhcp-grouping;
  }

  augment "/ios:native/ios:interface/ios:GigabitEthernet/ios:ip/ios:dhcp" {
    uses config-interface-ip-dhcp-grouping;
  }

  augment "/ios:native/ios:interface/ios:TenGigabitEthernet/ios:ip/ios:dhcp" {
    uses config-interface-ip-dhcp-grouping;
  }

  augment "/ios:native/ios:interface/ios:FiveGigabitEthernet/ios:ip/ios:dhcp" {
    uses config-interface-ip-dhcp-grouping;
  }

  augment "/ios:native/ios:interface/ios:TwentyFiveGigE/ios:ip/ios:dhcp" {
    uses config-interface-ip-dhcp-grouping;
  }

  augment "/ios:native/ios:interface/ios:TwoGigabitEthernet/ios:ip/ios:dhcp" {
    uses config-interface-ip-dhcp-grouping;
  }

  augment "/ios:native/ios:interface/ios:FortyGigabitEthernet/ios:ip/ios:dhcp" {
    uses config-interface-ip-dhcp-grouping;
  }

  augment "/ios:native/ios:interface/ios:HundredGigE/ios:ip/ios:dhcp" {
    uses config-interface-ip-dhcp-grouping;
  }

  augment "/ios:native/ios:interface/ios:Port-channel/ios:ip/ios:dhcp" {
    uses config-interface-ip-dhcp-grouping;
  }

  augment "/ios:native/ios:interface/ios:Loopback/ios:ip/ios:dhcp" {
    uses config-interface-ip-dhcp-grouping;
  }

  augment "/ios:native/ios:interface/ios:Tunnel/ios:ip/ios:dhcp" {
    uses config-interface-ip-dhcp-grouping;
  }

  augment "/ios:native/ios:interface/ios:Vlan/ios:ip/ios:dhcp" {
    uses config-interface-ip-dhcp-grouping;
  }

  augment "/ios:native/ios:interface/ios:vasileft/ios:ip/ios:dhcp" {
    uses config-interface-ip-dhcp-grouping;
  }

  augment "/ios:native/ios:interface/ios:vasiright/ios:ip/ios:dhcp" {
    uses config-interface-ip-dhcp-grouping;
  }

  /////////////////////////////////////////////////////////
  // native / interface * / ipv6 / dhcp
  /////////////////////////////////////////////////////////
  augment "/ios:native/ios:interface/ios:FastEthernet/ios:ipv6/ios:dhcp" {
    uses config-interface-ipv6-dhcp-grouping;
  }

  augment "/ios:native/ios:interface/ios:GigabitEthernet/ios:ipv6/ios:dhcp" {
    uses config-interface-ipv6-dhcp-grouping;
  }

  augment "/ios:native/ios:interface/ios:TenGigabitEthernet/ios:ipv6/ios:dhcp" {
    uses config-interface-ipv6-dhcp-grouping;
  }

  augment "/ios:native/ios:interface/ios:FiveGigabitEthernet/ios:ipv6/ios:dhcp" {
    uses config-interface-ipv6-dhcp-grouping;
  }

  augment "/ios:native/ios:interface/ios:TwentyFiveGigE/ios:ipv6/ios:dhcp" {
    uses config-interface-ipv6-dhcp-grouping;
  }
  
  augment "/ios:native/ios:interface/ios:TwoGigabitEthernet/ios:ipv6/ios:dhcp" {
    uses config-interface-ipv6-dhcp-grouping;
  }

  augment "/ios:native/ios:interface/ios:FortyGigabitEthernet/ios:ipv6/ios:dhcp" {
    uses config-interface-ipv6-dhcp-grouping;
  }

  augment "/ios:native/ios:interface/ios:HundredGigE/ios:ipv6/ios:dhcp" {
    uses config-interface-ipv6-dhcp-grouping;
  }

  augment "/ios:native/ios:interface/ios:Port-channel/ios:ipv6/ios:dhcp" {
    uses config-interface-ipv6-dhcp-grouping;
  }

  augment "/ios:native/ios:interface/ios:Loopback/ios:ipv6/ios:dhcp" {
    uses config-interface-ipv6-dhcp-grouping;
  }

  augment "/ios:native/ios:interface/ios:Tunnel/ios:ipv6/ios:dhcp" {
    uses config-interface-ipv6-dhcp-grouping;
  }

  augment "/ios:native/ios:interface/ios:Vlan/ios:ipv6/ios:dhcp" {
    uses config-interface-ipv6-dhcp-grouping;
  }

  augment "/ios:native/ios:interface/ios:vasileft/ios:ipv6/ios:dhcp" {
    uses config-interface-ipv6-dhcp-grouping;
  }

  augment "/ios:native/ios:interface/ios:vasiright/ios:ipv6/ios:dhcp" {
    uses config-interface-ipv6-dhcp-grouping;
  }
}
