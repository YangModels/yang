module tailf-netconf-query {
  namespace "http://tail-f.com/ns/netconf/query";
  prefix tfncq;

  tailf:export netconf;

  import tailf-common {
    prefix tailf;
  }
  import tailf-common-query {
    prefix tfcq;
  }

  organization "Tail-f Systems";

  description
    "This module introduces four new rpc operations to run
     advanced search queries.

     The operation 'start-query' starts a query, with some search
     conditions and control parameters for how to return the results.
     This operation returns a query handle, to be used in subsequent
     operations.

     The operation 'fetch-query-result' is repeatedly to get result
     chunks from the query evaluation.

     The operation 'reset-query' can be used to restart the query.

     Finally 'stop-query' is used to clean up query resources on the
     server.";

  revision 2014-11-13 {
    description
      "Initial revision.";
  }

  rpc start-query {
    input {
      uses tfcq:start-query-parameters;
    }

    output {
      uses tfcq:query-handle;
    }
  }

  rpc fetch-query-result {
    input {
      uses tfcq:query-handle;
    }
    output {
      container query-result {
        uses tfcq:query-result;
      }
    }
  }

  rpc reset-query {
    input {
      uses tfcq:reset-query-parameters;
    }
  }

  rpc stop-query {
    input {
      uses tfcq:query-handle;
    }
  }

}
