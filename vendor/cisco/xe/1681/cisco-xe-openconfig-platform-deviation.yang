module cisco-xe-openconfig-platform-deviation {
  // namespace
  namespace "http://cisco.com/ns/yang/cisco-xe-openconfig-platform-deviation";

  prefix oc-platform-devs;

  import openconfig-platform {
    prefix oc-platform;
  }

  import cisco-xe-openconfig-platform-ext {
    prefix oc-platform-ext;
  }

  organization
    "Cisco Systems, Inc.";

  contact
    " Cisco Systems, Inc.
    Customer Service

    Postal: 170 W Tasman Drive
    San Jose, CA 95134

    Tel: +1 1800 553-NETS

    E-mail: cs-yang@cisco.com";

  description
    "This module defines deviation statements for openconfig-platform module.";

  // =========================================================================
  // REVISION
  // =========================================================================

  revision 2017-09-01 {
    description
      "Hided avg/min/max temperature because we do not support in NGWC";
  }

  revision 2017-03-21 {
    description
      "Initial Revision";

    reference
      "RFC 6020: YANG - A Data Modeling Language for the
       Network Configuration Protocol (NETCONF)";
  }

  // =========================================================================
  // DEVIATION
  // =========================================================================

  deviation "/oc-platform:components/oc-platform:component" +
            "/oc-platform:properties/oc-platform:property" +
            "/oc-platform:name" {
      deviate replace {
        type string;
      }
      description
        "platform is oper only in Cisco XE device.";
  }

  deviation "/oc-platform:components/oc-platform:component" +
            "/oc-platform:subcomponents/oc-platform:subcomponent" +
            "/oc-platform:name" {
      deviate replace {
        type string;
      }
      description
        "platform is oper only in Cisco XE device.";
  }

  deviation "/oc-platform:components/oc-platform:component" +
            "/oc-platform:subcomponents/oc-platform:subcomponent" +
            "/oc-platform:state/oc-platform:name" {
      deviate replace {
        type string;
      }
      description
        "platform is oper only in Cisco XE device.";
  }

  deviation "/oc-platform:components/oc-platform:component" +
            "/oc-platform:name" {
      deviate replace {
        type string;
      }
      description
        "platform is oper only in Cisco XE device.";
  }

  deviation "/oc-platform:components/oc-platform:component" +
            "/oc-platform:properties/oc-platform:property" +
            "/oc-platform:config" {
      deviate not-supported;
      description
        "platform is oper only in Cisco XE device.";
  }

  deviation "/oc-platform:components/oc-platform:component" +
            "/oc-platform:subcomponents/oc-platform:subcomponent" +
            "/oc-platform:config" {
      deviate not-supported;
      description
        "platform is oper only in Cisco XE device.";
  }

  deviation "/oc-platform:components/oc-platform:component" +
            "/oc-platform:config" {
      deviate not-supported;
      description
        "platform is oper only in Cisco XE device.";
  }

  deviation "/oc-platform:components/oc-platform:component" +
            "/oc-platform:name" {
      deviate replace {
        config false;
      }
      description
        "platform is oper only in Cisco XE device.";
  }

  deviation "/oc-platform:components/oc-platform:component" +
            "/oc-platform:properties/oc-platform:property" +
            "/oc-platform:name" {
      deviate replace {
        config false;
      }
      description
        "platform is oper only in Cisco XE device.";
  }

  deviation "/oc-platform:components/oc-platform:component" +
            "/oc-platform:subcomponents/oc-platform:subcomponent" +
            "/oc-platform:name" {
      deviate replace {
        config false;
      }
      description
        "platform is oper only in Cisco XE device.";
  }

  deviation "/oc-platform:components/oc-platform:component" +
            "/oc-platform:properties" {
      deviate replace {
        config false;
      }
      description
        "platform is oper only in Cisco XE device.";
  }

  deviation "/oc-platform:components/oc-platform:component" +
            "/oc-platform:properties/oc-platform:property" {
      deviate replace {
        config false;
      }
      description
        "platform is oper only in Cisco XE device.";
  }

  deviation "/oc-platform:components/oc-platform:component" +
            "/oc-platform:subcomponents" {
      deviate replace {
        config false;
      }
      description
        "platform is oper only in Cisco XE device.";
  }

  deviation "/oc-platform:components/oc-platform:component" +
            "/oc-platform:subcomponents/oc-platform:subcomponent" {
      deviate replace {
        config false;
      }
      description
        "platform is oper only in Cisco XE device.";
  }

  deviation "/oc-platform:components/oc-platform:component" +
            "/oc-platform:state/oc-platform:temperature/oc-platform:avg" {
      deviate not-supported;
  }

  deviation "/oc-platform:components/oc-platform:component" +
            "/oc-platform:state/oc-platform:temperature/oc-platform:min" {
      deviate not-supported;
  }

  deviation "/oc-platform:components/oc-platform:component" +
            "/oc-platform:state/oc-platform:temperature/oc-platform:max" {
      deviate not-supported;
  }
}
