module cisco-xe-openconfig-platform-ext {
    namespace "http://cisco.com/ns/yang/cisco-xe-openconfig-platform-ext";
    
    prefix oc-platform-ext;

    import openconfig-platform {
       prefix oc-platform;
    }

    import openconfig-platform-types {
       prefix oc-platform-types;
    }

    organization "Cisco Systems";

    description
       "Augmentation for oc-platform";

////////////////////////////////////////////////////////////////////////////
// REVISION
///////////////////////////////////////////////////////////////////////////

 revision 2017-05-11 {
   description "Initial Draft to add type CONTAINER";
 }

////////////////////////////////////////////////////////////////////////////
// IDENTITY
///////////////////////////////////////////////////////////////////////////

  identity CONTAINER {
    base oc-platform-types:OPENCONFIG_HARDWARE_COMPONENT;
    description
      "Cisco added type CONTAINER";
  }
}
