module Cisco-IOS-XE-mdt-oper {
  yang-version 1;
  namespace "http://cisco.com/ns/yang/Cisco-IOS-XE-mdt-oper";
  prefix mdt-oper;

  import Cisco-IOS-XE-mdt-common-defs {
    prefix mdt-common-defs;
  }
  import ietf-inet-types {
    prefix inet;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG 
     definitions for operational data of streaming telemetry.
     Copyright (c) 2016-2017 by Cisco Systems, Inc.
     All rights reserved.";

  revision 2017-09-20 {
    description
      "TLS support for Native stream";
    reference "2.1.0";
  }
  revision 2017-07-01 {
    description
      "Add support for VRFs";
    reference "2.0.0";
  }
  revision 2017-03-02 {
    description
      "Initial revision";
    reference "1.0.0";
  }

  typedef mdt-sub-type {
    type enumeration {
      enum "sub-type-dynamic" {
        value 1;
        description
          "Dynamic subscriptions
           -do not survive reboot
           -existence tied to connection they are created on
           -send updates only to peer that creates them";
      }
      enum "sub-type-static" {
        value 2;
        description
          "Static subscriptions
           -created, (modified), and deleted by management operations
           -survive reboot
           -receivers are configured ";
      }
    }
    description
      "Subscription types";
  }

  typedef mdt-sub-state {
    type enumeration {
      enum "sub-state-valid" {
        value 0;
        description
          "The subscription is valid and may be sending updates.";
      }
      enum "sub-state-suspended" {
        value 1;
        description
          "The subscription has been suspended and is not
           sending notifications even if there are updates.";
      }
      enum "sub-state-terminated" {
        value 2;
        description
          "The subscription is terminated. This state is valid
           only for static subscriptions.";
      }
      enum "sub-state-invalid" {
        value 3;
        description
          "The subscription is invalid. This state is valid
           only for static subscriptions.";
      }
    }
    description
      "Subscription states";
  }

  typedef mdt-receiver-state {
    type enumeration {
      enum "rcvr-state-invalid" {
        value 1;
        description
          "The receiver configuration is invalid and
           cannot be used.";
      }
      enum "rcvr-state-disconnected" {
        value 2;
        description
          "The receiver is disconnected and there is no
           attempt being made to connect to it.";
      }
      enum "rcvr-state-connecting" {
        value 3;
        description
          "An attempt is being made to connect to the receiver.";
      }
      enum "rcvr-state-connected" {
        value 4;
        description
          "The receiver is connected, and update notifications
           are being sent to the receiver when they occur";
      }
    }
    description
      "Receiver states.";
  }

  typedef mdt-con-state {
    type enumeration {
      enum "con-state-active" {
        value 0;
        description
          "The connection is active and usable.";
      }
      enum "con-state-connecting" {
        value 1;
        description
          "An attempt is being made to set the connection up.";
      }
      enum "con-state-pending" {
        value 2;
        description
          "The connection is down, but between connection
           attempts. It is in this state, for example, during
           the idle time between retries.";
      }
      enum "con-state-disconnecting" {
        value 3;
        description
          "The connection is the process of being disconnected.";
      }
    }
    description
      "Connection states.";
  }

  grouping mdt-stream {
    description
      "MDT stream table element.";
    leaf-list stream {
      type string;
      ordered-by user;
      description
        "Name of a supported stream.";
    }
  }

  grouping mdt-subscription-oper {
    description
      "Subscription operational data.";
    leaf subscription-id {
      type uint32;
      description
        "Unique subscription identifier.";
    }
    container base {
      description
        "Common subscription information.";
      uses mdt-common-defs:mdt-subscription-base;
    }
    leaf type {
      type mdt-oper:mdt-sub-type;
      description
        "Subscription type.";
    }
    leaf state {
      type mdt-oper:mdt-sub-state;
      description
        "Subscription state.";
    }
    leaf comments {
      type string;
      description
        "Comments related to subcription state.";
    }
    leaf updates-in {
      type uint64;
      description
        "Number of updates received from sensors as
         candidates for notifications.";
    }
    leaf updates-dampened {
      type uint64;
      description
        "Number of updates dropped due to dampening.";
    }
    leaf updates-dropped {
      type uint64;
      description
        "Number of updates dropped to other causes.";
    }
    list mdt-receivers {
      key "address port";
      description
        "List of MDT receivers.";
      uses mdt-oper:mdt-receiver-oper;
      uses mdt-common-defs:mdt-receiver-id;
    }
  }

  grouping mdt-receiver-oper {
    description
      "MDT receiver operational information.";
    leaf protocol {
      type string;
      description
        "Receiver transport protocol.";
    }
    leaf state {
      type mdt-oper:mdt-receiver-state;
      description
        "Receiver state.";
    }
    leaf comments {
      type string;
      description
        "Comments related to receiver state.";
    }
    leaf security-profile {
      type string;
      description
        "Receiver security profile.";
    }
  }

  grouping mdt-connection-id {
    description
      "Connection identifier";
    leaf address {
      type inet:ip-address;
      description
        "IP address";
    }
    leaf port {
      type uint16;
      description
        "Network port";
    }
    leaf source-vrf {
      type string;
      description
        "Network instance name for the VRF that the
         connection originates from.";
    }
    leaf source-address {
      type inet:ip-address;
      description
        "The source address used for the connection.";
    }
  }

  grouping mdt-connection-data {
    description
      "MDT connection data";
    leaf transport {
      type string;
      description
        "Transport protocol on this connection
         See transport-protocol from subscribed-notifications
         for possible values.";
    }
    leaf peer-id {
      type string;
      description
        "Identity of the peer at the other end of the connection.
         May be empty, depending on connection state.";
    }
    leaf state {
      type mdt-oper:mdt-con-state;
      description
        "Connection state";
    }
    list mdt-sub-con-stats {
      key "sub-id";
      description
        "List of subscription specific statistics for this
         connection.";
      uses mdt-oper:mdt-sub-con-stats;
    }
    leaf security-profile {
      type string;
      description
        "Security profile used with this connection.";
    }
  }

  grouping mdt-sub-con-stats {
    description
      "Per-subscription per-connection operational data.";
    leaf sub-id {
      type uint32;
      description
        "Subscription identifier.";
    }
    leaf updates-sent {
      type uint64;
      description
        "Number of update notifications sent to the receiver
         using this subscription";
    }
    leaf updates-dropped {
      type uint64;
      description
        "Number of dropped update notifications due to error or
         events not in other counters using this subscription.";
    }
  }

  container mdt-oper-data {
    config false;
    description
      "MDT operational data.";
    container mdt-streams {
      description
        "MDT streams table. The list of supported streams.";
      uses mdt-oper:mdt-stream;
    }
    list mdt-subscriptions {
      key "subscription-id";
      description
        "MDT subscription operational data.";
      uses mdt-oper:mdt-subscription-oper;
    }
    list mdt-connections {
      key "address port source-vrf source-address";
      description
        "MDT subscription connection operational data.";
      uses mdt-oper:mdt-connection-data;
      uses mdt-oper:mdt-connection-id;
    }
  }
}
