module Cisco-IOS-XE-eem {
  namespace "http://cisco.com/ns/yang/Cisco-IOS-XE-eem";
  prefix ios-eem;

  import ietf-inet-types {
    prefix inet;
  }


  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Embedded Event Manager (EEM) Yang model.
     Copyright (c) 2016-2017 by Cisco Systems, Inc.
     All rights reserved.";

  // =========================================================================
  // REVISION
  // =========================================================================
  revision 2017-11-20 {
    description
      "fix event oir event removal";
  }
 
  revision 2017-09-20 {
    description
      "Add some applet event support";
  }
 
  revision 2017-08-03 {
    description
      "Add event time full support";
  }

  revision 2017-04-13 {
    description
      "Add event track";
  }

  revision 2017-04-10 {
    description
      "Add cli command and exit for action";
  }

  revision 2017-02-07 {
    description
      "Initial revision";
  }

  typedef operator-type {
    type enumeration {
      enum "eq";
      enum "ge";
      enum "gt";
      enum "le";
      enum "lt";
      enum "ne";
    }
  }

  grouping eem-default-group {
    leaf default {
      description
        "Default action timer";
      type uint32;
    }
  }

  grouping eem-maxrun-group {
    leaf maxrun {
      description
        "Maximum runtime of applet";
      type uint32 {
        range "0..31536000";
      }
    }
  }

  grouping eem-maxrun-incomplete-group {
    leaf maxrun {
      description
        "Maximum runtime of applet";
      type uint32 {
        range "0..31536000";
      }
    }
  }

  grouping eem-ratelimit-group {
    leaf ratelimit {
      description
        "seconds[.milliseconds] value";
      type uint32 {
        range "0..31536000";
      }
    }
  }

  grouping eem-ratelimit-incomplete-group {
    leaf ratelimit {
      description
        "seconds[.milliseconds] value";
      type uint32 {
        range "0..31536000";
      }
    }
  }

  grouping eem-timer-cron-group {
    uses eem-maxrun-group;
    leaf name {
      description
        "Timer name string";
      type string;
    }
    uses eem-ratelimit-group;
    leaf cron-entry {
      description
        "Cron entry for cron timer";
      type string;
    }
  }

  grouping eem-timer-common-group {
    uses eem-maxrun-group;
    leaf name {
      description
        "Timer name string";
      type string;
    }
    uses eem-ratelimit-group;
    leaf time {
      description
        "Time period for watchdog / countdown / absolute timer";
      type uint32 {
        range "1..2085978494";
      }
    }
  }


  grouping config-eem-grouping {
    container manager {
      description
        "Event Manager configuration commands";
      // event manager environment *
      list environment {
        description
          "Set an Embedded Event Manager global environment variable";
        key "name";
        leaf name {
          type string;
        }
        leaf value {
          type string;
        }
      }
      // event manager directory
      container directory {
        description
          "Set Embedded Event Manager directory information";
        container user {
          description
            "Set Embedded Event Manager user directory information";
          leaf policy {
            description
              "Set Embedded Event Manager user policy directory";
            type string;
          }
        }
      }
      // event manager session
      container session {
        description
          "Set Embedded Event Manager session attributes";
        container cli {
           description
            "Set Embedded Event Manager session cli attributes";
           container username {
              description
                "Set username used in Embedded Event Manager cli sessions";
              list username_in_word {
                key "username_in_word";
                leaf username_in_word {
                  type string;
                }
                leaf privilege {
                  description
                    "Set user privilege level";
                  type uint8 {
                    range "0..15";
                  }
                }
              }
            }
         }
      }
      // event manager applet *
      list applet {
        description
          "Register an Event Manager applet";
        key "name";
        leaf name {
          type string;
        }
        leaf authorization {
          description
            "Specify an authorization type for the applet";
          type enumeration {
            enum "bypass";
          }
        }
        leaf class {
          description
            "Specify a class for the applet";
          type string {
            pattern "[A-Z]|default";
          }
        }
        leaf trap {
          description
            "Generate an SNMP trap when applet is triggered.";
          type empty;
        }
        container event {
          description
            "Add or modify event information";
          container timer {
            description
              "Timer event";
            container absolute  {
              description
                "Absolute timer event";
              uses eem-timer-common-group;
            }
            container countdown {
              description
                "Countdown timer event";
              uses eem-timer-common-group;
            }
            container cron {
              description
                "cron timer event";
              uses eem-timer-cron-group;
            }
            container watchdog {
              description
                "Watchdog timer event";
              uses eem-timer-common-group;
            }
          } 

          container snmp-notification {
            description
              "SNMP Notification Event";
            leaf oid {
              description
                "Object ID of data element";
              type string;
            }
            leaf oid-val {
              description
                "Comparison value";
              type string;
            }
            leaf op {
              description
                "Operator";
              type operator-type;
            }
            leaf src-ip-address {
              description
                "Source ip address";
              type union {
                type inet:ipv4-address;
                type inet:ipv6-address;
              }
            }
            leaf dest-ip-address {
              description
                "Destination ip address";
              type union {
                type inet:ipv4-address;
                type inet:ipv6-address;
              }
            }
          }
          container syslog {
            description
              "Syslog event";
            leaf pattern {
              description
                "Pattern match string for the entire message";
              type string;
            }
          }
          container track {
            description
              "Tracking object event";
            leaf track-object-number {
              description
                "Tracking object number";
              type uint16 {
                range "1..1000";
              }
            }
            leaf state {
              description
                "State of tracking object";
              type enumeration {
                enum "any";
                enum "down";
                enum "up";
              }
            }
          }
          container none {
            description
              "Manually run policy event";
            presence true;
            uses eem-default-group;
            uses eem-maxrun-group;
            uses eem-ratelimit-group;
            leaf sync {
              description
                "EEM policy execution sync or async";
              type enumeration {
                enum "yes";
                enum "no";
              }
            }
          }
          container resource {
            description 
              "Resource event";
            leaf policy {
              description
                "Resource policy name string";
              type string;
            } 
            uses eem-maxrun-incomplete-group;
            uses eem-ratelimit-incomplete-group;
          }
          container rpc {
            description
              "Remote Procedure Call event";
            presence true;
            uses eem-default-group;
            uses eem-maxrun-group;
            uses eem-ratelimit-group;
          }
          container config {
            description
              "Configuration policy event";
            presence true;
            uses eem-maxrun-group;
            uses eem-ratelimit-group;
          }
          container env {
            description
              "Environmental event";
            container severity {
              description
                "alarm severity";
              choice severty-level {
                container major {
                  description
                    "major environmental alarm";
                  presence true;
                  uses eem-maxrun-group;
                  uses eem-ratelimit-group;
                }
                container minor {
                  description
                    "minor environmental alarm";
                  presence true;
                  uses eem-maxrun-group;
                  uses eem-ratelimit-group;
                }
              }
            }
          }
          container oir {
            description
              "OIR event";
            presence true;
            leaf event {
              description
                "OIR event";
              type enumeration {
                enum "all";
                enum "insert";
                enum "removal";
              }
            }
            uses eem-maxrun-group;
          }
          container rf {
            description
              "event match string";
            leaf event {
              description
                "Event match string";
              type string;
            }
            uses eem-maxrun-group;
            uses eem-ratelimit-group;
          }
        }
        list action {
          description
            "Add or modify an action statement";
          ordered-by user;
          key "name";
          leaf name {
            type string;
          }
          container cli {
            description
              "Execute a CLI command";
            leaf command {
              description
                "CLI command";
              type string;
            }
          }
          container if {
            description
              "if conditional";
            leaf string-op-1 {
              type string;
            }
            leaf keyword {
              type operator-type;
            }
            leaf string-op-2 {
              type string;
            }
            leaf goto {
              description
                "goto label";
              type string;
            }
          }
          container info {
            description
              "Obtain system specific information";
            container type {
              description
                "Type of information to obtain";
              container snmp {
                description
                  "SNMP information";
                container var {
                  description
                    "Trap variable";
                  leaf variable-name {
                    type string;
                  }
                  leaf oid {
                    description
                      "SNMP object id";
                    type string;
                  }
                  leaf oid-type {
                    type enumeration {
                      enum "counter";
                      enum "gauge";
                      enum "int";
                      enum "ipv4";
                      enum "octet";
                      enum "string";
                      enum "uint";
                    }
                  }
                  leaf oid-type-value {
                    type string;
                  }
                }
                container trap {
                  description
                    "SNMP trap";
                  leaf enterprise-oid {
                    description
                      "Enterprise oid";
                    type string;
                  }
                  leaf generic-trapnum {
                    description
                      "Generic trap number";
                    type uint32;
                  }
                  leaf specific-trapnum {
                    description
                      "Specific trap number";
                    type uint32;
                  }
                  leaf trap-oid {
                    description
                      "Trap oid";
                    type string;
                  }
                  leaf trap-var {
                    description
                      "Trap variable";
                    type string;
                  }
                }
              }
            }
          }
          leaf end {
            description
              "end conditional block";
            type empty;
          }
          container regexp {
            description
              "regular expression match";
            leaf string-pattern {
              type string;
            }
            leaf string-input {
              type string;
            }
            leaf string-match {
              type string;
            }
            leaf string-submatch1 {
              type string;
            }
            leaf string-submatch2 {
              type string;
            }
            leaf string-submatch3 {
              type string;
            }
          }
          container snmp-trap {
            description
              "Send an SNMP trap";
            presence "true";
            leaf intdata1 {
              description
                "SNMP integer data1";
              type int32;
            }
            leaf intdata2 {
              description
                "SNMP integer data2";
              type int32;
            }
            leaf strdata {
              description
                "SNMP trap string";
              type string;
            }
          }
          container string {
            description
              "string commands";
            leaf trim {
              description
                "trim characters from both ends of string";
              type string;
            }
          }
          container syslog {
            description
              "Log a syslog message";
            leaf facility {
              description
                "Facility string";
              type string;
            }
            leaf msg {
              description
                "Syslog message";
              type string;
            }
            leaf priority {
              description
                "Priority of syslog message";
              type ios:logging-level-type;
            }
          }
          leaf exit {
            description
              "Exit from applet run";
            type empty;
          }
        }
        leaf description {
          description
            "Add or modify an applet description";
          type string;
        }
        // event manager applet * / trigger
        container trigger {
          description
            "Enter applet trigger configuration submode";
        }
      }
    }
  }

  /////////////////////////////////////////////////////////
  // native / event
  /////////////////////////////////////////////////////////
  augment "/ios:native/ios:event" {
    uses config-eem-grouping;
  }
}
