module Cisco-IOS-XE-features {
  namespace "http://cisco.com/ns/yang/Cisco-IOS-XE-features";
  prefix ios-features;

  organization
    "Cisco Systems, Inc.";

  contact
    "Cisco Systems, Inc.
     Customer Service

     Postal: 170 W Tasman Drive
     San Jose, CA 95134

     Tel: +1 1800 553-NETS

     E-mail: cs-yang@cisco.com";

  description
    "Cisco XE feature Definitions
     Copyright (c) 2016-2017 by Cisco Systems, Inc.
     All rights reserved.";

  // =========================================================================
  // REVISION
  // =========================================================================
  revision 2017-02-07 {
    description
      "Initial revision";
  }

  // =========================================================================
  // FEATURES
  // =========================================================================
  feature switching-platform { 
    description
      "switching platform specific features";
  }

  feature crypto { 
    description
      "crypto feature";
    //Cisco-IOS-XE-crypto (interface *)
  }

  feature device-tracking {
    description
      "device-tracking feature";
    //Cisco-IOS-XE-device-tracking 
  }

  feature dot1x {
    description
      "dot1x feature";
    //Cisco-IOS-XE-dot1x (interface *)
  }

  feature efp {
    description
      "Ethernet Flow Point (efp) feature";
    //Cisco-IOS-XE-l2vpn (interface *)
  }

  feature esmc {
    description
      "Ethernet Synchronization Messaging Channel (esmc) feature";
    //Cisco-IOS-XE-ethernet
  }

  feature eth-evc {
    description
      "Ethernet Virtual Circuit (EVC) feature";
    //Cisco-IOS-XE-ethernet
  }

  feature ezpm {
    description
      "Easy Performance Monitor feature";
    //Cisco-IOS-XE-ezpm (interface *)
  }

  feature l2 {
    description
      "Layer2 VPN feature";
    //Cisco-IOS-XE-l2vpn
  }

  feature l2vpn {
    description
      "Layer2 VPN feature";
    //Cisco-IOS-XE-l2vpn 
    //Cisco-IOS-XE-bgp 
  }

  feature macsec {
    description
      "macsec";
    //Cisco-IOS-XE-ethernet
  }

  feature mem-size {
    description
      "Memory size commands";
    //Cisco-IOS-XE-native
  }

  feature module {
    description
      "Device module feature";
    //Cisco-IOS-XE-switch 
  }

  feature multilink {
    description
      "PPP multilink global configuration";
    //Cisco-IOS-XE-ppp - multilink 
  }

  feature mls {
    description
      "Multilayer Switching feature";
    //Cisco-IOS-XE-mls 
  }

  feature parameter-map {
    description
      "Parameter Map feature";
    //Cisco-IOS-XE-policy
  }

  feature private-vlan {
    description
      "Private-vlan feature";
    //Cisco-IOS-XE-vlan 
  }

  feature punt-num {
    description
      "Police punt feature";
    //Cisco-IOS-XE-platform 
  }

  feature qos-qsm {
    description
      "QoS queue softmax multiplier";
    //Cisco-IOS-XE-qos  
  }

  feature setup {
    description
      "Express setup feature";
    //Cisco-IOS-XE-switch 
  }

  feature switch-virtual {
    description
      "Switch-virtual feature";
    //Cisco-IOS-XE-switch
  }

  feature table-map {
    description
      "table-map feature";
    //Cisco-IOS-XE-qos
  }

  feature tod-clock {
    description
      "Time of Day clock feature";
    //Cisco-IOS-XE-native
  }

  feature transceiver {
    description
      "Transceiver commands";
    //Cisco-IOS-XE-native
  }

  feature virtual-template {
    description
      "Virtual-template commands";
    //Cisco-IOS-XE-tunnel
  }

  feature vlan {
    description
      "Vlan feature";
    //Cisco-IOS-XE-native-vlan
  }
}
