module Cisco-IOS-XE-cellular {
  namespace "http://cisco.com/ns/yang/Cisco-IOS-XE-cellular";
  prefix ios-cell;

  import Cisco-IOS-XE-native {
    prefix ios;
  }


  import ietf-inet-types {
    prefix inet;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Cellular Interfaces.
     Copyright (c) 2016 by Cisco Systems, Inc.
     All rights reserved.";

  // =========================================================================
  // REVISION
  // =========================================================================
  revision 2017-12-20 {
    description
      "Add dialer and dialer-list";
  }
  revision 2017-12-13 {
    description
      "Add interface cellular / dialer-group and pulse-time";
  }
  revision 2017-02-07 {
    description
      "Initial revision";
  }

  grouping config-interface-cellular-grouping {
    //interface * / dialer
    container dialer {
      leaf in-band {
        type empty;
      }
      leaf idle-timeout {
        type uint32;
      }
      leaf string {
        type string;
      }
      leaf watch-group {
        type uint32;
      }
    }

    //interface * / dialer-group
    leaf dialer-group {
      description
        "Assign interface to dialer-list";
      type uint8 {
        range "1..128";
      }
    }

    //interface * / pulse-time
    leaf pulse-time {
      description
        "Assign interface to dialer-list";
      type uint8 {
        range "0..60";
      }
    }

    //interface * / async
    container async {
      leaf mode {
        type enumeration {
          enum "interactive";
        }
      }
    }
  }

  grouping config-dialer-grouping {
    container dialer {
      description
        "Dialer commands";
      list watch-list {
        description
          "Dialer watch list";
        key number;
        leaf number {
          type uint8 {
            range "1..255";
          }
        }
        list delay {
          description
            "Dialer watch delay";
          key interval;
          leaf interval {
            type enumeration {
              enum "connect";
              enum "disconnect";
              enum "route-check";
            }
          }
          leaf initial {
            description
              "Delay for initial check of watched route after boot";
            when "../interval = 'route-check'";
            type empty;
          }
          leaf delay-time {
            description
              "Delay time in seconds";
            type uint32 {
              range "1..2147483";
            }
          }
        }
        list ip {
          description
            "IP";
          key address;
          leaf address {
            description
              "IP address";
            type inet:ipv4-address;
          }
          leaf mask {
            description
              "IP subnet mask";
            type inet:ipv4-address;
          }
        }
      }
    }
  }

  grouping config-dialer-list-grouping {
    list dialer-list {
      description
        "Create a dialer list entry";
      key "group-number"; 
      leaf group-number {
        type uint8 {
          range "1..128";
        }
      }
      list protocol {
        key protocol-type;
        leaf protocol-type {
          type enumeration {
            enum "appletalk";
            enum "bridge";
            enum "clns";
            enum "clns_es";
            enum "clns_is";
            enum "decnet";
            enum "decnet_node";
            enum "decnet_router-L1";
            enum "decnet_router-L2";
            enum "ip";
            enum "ipv6";
            enum "ipx";
            enum "llc2";
            enum "netbios";
            enum "novell";
            enum "vines";
            enum "xns";
          }
        }
        leaf access {
          type enumeration {
            enum "deny";
            enum "list";
            enum "permit";
          }
        }
        leaf list-name {
          when "../access = 'list'";
          type string; 
        }
      }
    }
  }

  /////////////////////////////////////////////////////////
  // native / dialer
  /////////////////////////////////////////////////////////
  augment "/ios:native" {
     uses config-dialer-grouping;
  }

  /////////////////////////////////////////////////////////
  // native / dialer-list
  /////////////////////////////////////////////////////////
  augment "/ios:native" {
     uses config-dialer-list-grouping;
  }

  /////////////////////////////////////////////////////////
  // native / interface
  /////////////////////////////////////////////////////////
  augment "/ios:native/ios:interface/ios:Cellular" {
    uses config-interface-cellular-grouping;
  }
}
