module Cisco-IOS-XE-mdt-cfg {
  yang-version 1;
  namespace "http://cisco.com/ns/yang/Cisco-IOS-XE-mdt-cfg";
  prefix mdt-cfg;

  import Cisco-IOS-XE-mdt-common-defs {
    prefix mdt-common-defs;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG 
     definitions for configuration of streaming telemetry.
     Copyright (c) 2016-2017 by Cisco Systems, Inc.
     All rights reserved.";

  revision 2017-10-29 {
    description
      "Transform support for Native stream";
    reference "1.2.0";
  }
  revision 2017-09-20 {
    description
      "TLS support for Native stream";
    reference "1.1.0";
  }
  revision 2017-03-02 {
    description
      "Initial revision";
    reference "1.0.0";
  }

  typedef mdt-xfrm-attr-type {
    type enumeration {
      enum "mdt-xfrm-attr-none" {
        value 0;
        description
          "Indicates that no filter has been 
           specified.";
      }
      enum "mandatory" {
        value 1;
        description
          "Indicates that mandatory filter is set.";
      }
    }
    description
      "Types of subscription transform attribute type";
  }

  typedef mdt-xfrm-op-type {
    type enumeration {
      enum "sub-record" {
        value 0;
        description
          "Indicates that operation type is 
           sub-record";
      }
      enum "delta" {
        value 1;
        description
          "Indicates that operation type is delta";
      }
    }
    description
      "Types of subscription transform operations.";
  }

  typedef mdt-xfrm-logic-op {
    type enumeration {
      enum "mdt-xfrm-lop-none" {
        value 0;
        description
          "Indicates that no logical operation 
           is selected";
      }
      enum "and" {
        value 1;
        description
          "Indicates that logical operation 
           is 'and' ";
      }
      enum "or" {
        value 2;
        description
          "Indicates that logical operation is 'or' ";
      }
    }
    description
      "Types of subscription transform 
       logical operations.";
  }

  typedef mdt-xfrm-operator {
    type enumeration {
      enum "operator-none" {
        value 0;
        description
          "Default operator";
      }
      enum "eq" {
        value 1;
        description
          "Equal operator";
      }
      enum "ne" {
        value 2;
        description
          "Not equal operator";
      }
      enum "gt" {
        value 3;
        description
          "Greater than operator";
      }
      enum "ge" {
        value 4;
        description
          "Greater than or equal operator";
      }
      enum "lt" {
        value 5;
        description
          "Less than operator";
      }
      enum "le" {
        value 6;
        description
          "Less than or equal operator";
      }
    }
    description
      "Supported operator types";
  }

  grouping mdt-xfrm-op-event-type {
    description
      "Types of subscription 
       transform operation event type.";
    leaf onchange {
      type boolean;
      description
        "Indicates that onchange filter is set.";
    }
  }

  grouping mdt-xfrm-field-condition {
    description
      "Per field filter condition (e.g. f1 gt '5')";
    leaf operator {
      type mdt-cfg:mdt-xfrm-operator;
      description
        "Type of operator";
    }
    leaf value {
      type string;
      description
        "Field value to operate on";
    }
  }

  grouping mdt-xfrm-input-field {
    description
      "Configuration information for transform input uri table fields.";
    leaf field {
      type string;
      description
        "Transform input URI table field name";
    }
  }

  grouping mdt-xfrm-input {
    description
      "Configuration information for transform input.";
    leaf table-name {
      type string;
      description
        "Transform input URI table name";
    }
    leaf uri {
      type string;
      description
        "Transform input URI full-path";
    }
    list mdt-xfrm-input-field {
      key "field";
      description
        "Transform input URI table fields";
      uses mdt-cfg:mdt-xfrm-input-field;
    }
    leaf join-key {
      type string;
      description
        "Transform input table join-key";
    }
    leaf attr-type {
      type mdt-cfg:mdt-xfrm-attr-type;
      description
        "Transform input table attribute type 
         e.g. table is mandatory for join record";
    }
    leaf lop {
      type mdt-cfg:mdt-xfrm-logic-op;
      description
        "Logical operation with next
         input table event";
    }
  }

  grouping mdt-xfrm-op-filter {
    description
      "Configuration information for transform 
       operation filters.";
    leaf filter-id {
      type uint32;
      description
        "filters will be evaluated in sequence based 
         on filter_id";
    }
    leaf field {
      type string;
      description
        "Transform operation filter field name";
    }
    container op-event {
      description
        "Transform operation event flag (e.g. onchange)";
      uses mdt-cfg:mdt-xfrm-op-event-type;
    }
    leaf lop {
      type mdt-cfg:mdt-xfrm-logic-op;
      description
        "logical operation with condition";
    }
    container condition {
      description
        "Per field condition (e.g. f1 eq 'name')";
      uses mdt-cfg:mdt-xfrm-field-condition;
    }
    leaf next-lop {
      type mdt-cfg:mdt-xfrm-logic-op;
      description
        "logical operation with next filter condition";
    }
  }

  grouping mdt-xfrm-op-field {
    description
      "Configuration information for transform operations";
    leaf field-id {
      type uint32;
      description
        "Transform operation response field-id, part of response record.
         It is used to uniquely identify response record field";
    }
    leaf field {
      type string;
      description
        "Subscription transform field name on 
         which transform operation is performed";
    }
    leaf op-type {
      type mdt-cfg:mdt-xfrm-op-type;
      description
        "Subscription transform operation type";
    }
  }

  grouping mdt-xfrm-op {
    description
      "Configuration information for transform operation.";
    leaf id {
      type uint32;
      description
        "Unique transform operation id";
    }
    list mdt-xfrm-op-filters {
      key "filter-id";
      description
        "Transform operation filters. 
         These are evaluated before performing
         transform action (e.g. subrecord) 
         on the response record";
      uses mdt-cfg:mdt-xfrm-op-filter;
    }
    list mdt-xfrm-op-fields {
      key "field-id";
      description
        "Transform operation fields. 
         Default operation is subrecord.
         It is performed on each field";
      uses mdt-cfg:mdt-xfrm-op-field;
    }
  }

  grouping mdt-xfrm {
    description
      "Configuration information for 
       subscription transform.";
    leaf name {
      type string;
      description
        "Unique transform identifier.";
    }
    leaf fully-specify {
      type boolean;
      description
        "When fully-specify is set, 
         fully-specify field identifier is sent 
         in the response record along with field value";
    }
    list mdt-xfrm-input {
      key "table-name";
      description
        "Transform input information";
      uses mdt-cfg:mdt-xfrm-input;
    }
    list mdt-xfrm-op {
      key "id";
      description
        "Transform operations information";
      uses mdt-cfg:mdt-xfrm-op;
    }
  }

  grouping mdt-subscription-cnfg {
    description
      "Subscription configuration information.";
    leaf subscription-id {
      type uint32 {
        range "0 .. 2147483647";
      }
      description
        "Unique subscription identifier.";
    }
    container base {
      description
        "Common subscription information.";
      uses mdt-common-defs:mdt-subscription-base;
    }
    list mdt-receivers {
      key "address port";
      description
        "Configuration of receivers of configured 
         subscriptions.";
      uses mdt-cfg:mdt-receiver-cnfg;
      uses mdt-common-defs:mdt-receiver-id;
    }
  }

  grouping mdt-receiver-cnfg {
    description
      "Configuration information for subscription receiver.";
    leaf protocol {
      type string;
      default "netconf";
      description
        "Receiver transport protocol.";
    }
    leaf security-profile {
      type string;
      description
        "Receiver security profile.";
    }
  }

  container mdt-subscriptions {
    description
      "Subscription configuration";
    list mdt-subscription {
      key "subscription-id";
      description
        "List of subscriptions";
      uses mdt-cfg:mdt-subscription-cnfg;
    }
    list mdt-xfrm {
      key "name";
      description
        "List of subscription transforms";
      uses mdt-cfg:mdt-xfrm;
    }
  }
}
