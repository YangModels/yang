/*
 * Generated by confdc --mib2yang-std
 * Source: mgmt/dmi/model/mib/src/CISCO-POWER-ETHERNET-EXT-MIB.mib
 */
/*
 * This YANG module has been generated by smidump 0.5.0:
 *
 *      smidump -f yang CISCO-POWER-ETHERNET-EXT-MIB
 *
 * Do not edit. Edit the source file instead!
 */

module CISCO-POWER-ETHERNET-EXT-MIB {

  namespace "urn:ietf:params:xml:ns:yang:smiv2:CISCO-POWER-ETHERNET-EXT-MIB";
  prefix CISCO-POWER-ETHERNET-EXT-MIB;

  import CISCO-TC {
    prefix "cisco-tc";
  }

  import POWER-ETHERNET-MIB {
    prefix "power-ethernet";
  }

  import SNMP-FRAMEWORK-MIB {
    prefix "snmp-framework";
  }

  import ietf-yang-smiv2 {
    prefix "smiv2";
  }

  organization
   "Cisco Systems, Inc.";

  contact
   "Cisco Systems
    Customer Service
    
    Postal: 170 W Tasman Drive
    San Jose, CA 95134
    USA
    
    Tel: +1 800 553-NETS
    
    E-mail: cs-lan-switch-snmp@cisco.com";

  description
   "A MIB module for extending the POWER-ETHERNET-MIB
    (RFC3621) to add objects which provide additional
    management information about Power Sourcing Equipment
    (PSE) not available in POWER-ETHERNET-MIB.
    
    Glossary
    
    Power Sourcing Equipment (PSE)
        These are devices supplying electrical power to
        other equipment. They are, for example, inline power
        switches, inline power daughterboards and power patch
        panels.
    
    Powered Device (PD)
        These are devices receiving their electrical power
        supply from Power Sourcing Equipment. They are, for
        example, IP telephones and wireless access points
        or bridges.";

  revision 2009-12-11 {
    description
     "Added cpeExtPowerPriorityGroup, cpeExtPsePortLldpGroup
      and cpeExtPsePortCapabilitiesGroup.
      
      Added a new enumeration 'class4' in cpeExtPdStatsClass.
      
      Added TEXTUAL-CONVENTION CpeExtLldpPwrType,
      CpeExtLldpPwrSrc, and CpeExtPwrPriority.";
  }

  revision 2009-12-04 {
    description
     "Updated the DESCRIPTION of cpeExtPolicingNotif.";
  }

  revision 2007-04-12 {
    description
     "Added 'overdrawLog' value to cpeExtPsePortAdditionalStatus.
      Added cpeExtPortPolicingActionGroup, cpeExtPortPwrManAllocGroup
      cpeExtPolicingNotifEnableGroup, and cpeExtPolicingNotifGroup.";
  }

  revision 2007-02-02 {
    description
     "Added cpeExtPsePortEntPhyIndex,
      cpeExtPsePortPolicingCapable and 
      cpeExtPsePortPolicingEnable to cpeExtPsePortTable.
      Added cpeExtPdStatsTotalDevices and cpeExtPdStatsTable.
      Added enumerated value disable(5) to cpeExtPsePortEnable.";
  }

  revision 2005-06-10 {
    description
     "Added 'limit' to cpeExtPsePortEnable, 'overdraw' to
      cpeExtPsePortAdditionalStatus and the groups
      cpeExtPsePortPwrMonitorGroup and
      cpeExtMainPseGroup.";
  }

  revision 2004-04-12 {
    description
     "Initial version of this MIB module.";
  }

  typedef CpeExtLldpPwrType {
    type enumeration {
      enum "type1Pd" {
        value "1";
      }
      enum "type1Pse" {
        value "2";
      }
      enum "type2Pd" {
        value "3";
      }
      enum "type2Pse" {
        value "4";
      }
    }
    description
     "The requested Data Terminal Equipment (DTE) Power via
      Media Dependent Interface (MDI) type based on Data Link Layer
      (DLL) power classification.
      
      In Data Link Layer power classification, the PSE and PD perform 
      power negotiation using the Link Layer Discovery Protocol (LLDP)
      as soon as the data link is established. It has finer power
      resolution than the Physical Layer power classification and has
      the ability for the PSE and PD to participate in dynamic power
      allocation wherein allocated power to the PD may change one or
      more times during PD operation.
      
      'type1Pd'  - A PD that advertises a power draw less than or 
                   equal to 12.95 W (at the PD).
      'type1Pse' - A PSE that is designed to support a Type 1 PD.
      'type2Pd'  - A PD that advertises a power draw greater than
                   12.95 W (at the PD).
      'type2Pse  - A PSE that is designed to support either a Type 1
                   or a Type 2 PD.";
  }

  typedef CpeExtLldpPwrSrc {
    type enumeration {
      enum "pseAndLocal" {
        value "1";
      }
      enum "local" {
        value "2";
      }
      enum "pse" {
        value "3";
      }
      enum "backupSrc" {
        value "4";
      }
      enum "primarySrc" {
        value "5";
      }
      enum "unknown" {
        value "6";
      }
    }
    description
     "The power source of the PD or PSE port which implements the
      LLDP based Data Link Layer power classification.
      
      'pseAndLocal'   - A PD powered both locally and by a PSE.
      'local'         - A PD powered locally only.
      'pse'           - A PD powered by a PSE only.
      'backupSrc'     - A PSE powered by a backup power source.
      'primarySrc'    - A PSE powered by its primary power source.
      'unknown'       - A PD or PSE where the power source is
                        unknown.";
  }

  typedef CpeExtPwrPriority {
    type enumeration {
      enum "critical" {
        value "1";
      }
      enum "high" {
        value "2";
      }
      enum "low" {
        value "3";
      }
      enum "unknown" {
        value "4";
      }
    }
    description
     "The power priority for the PD on the PSE port which implements
      the LLDP based Data Link Layer power classification.
      
      'critical' - power priority is at critical level.
      'high'     - power priority is at high level.
      'low'      - power priority is at low level.
      'unknown'  - power priority level is unknown.";
  }


  container CISCO-POWER-ETHERNET-EXT-MIB {
    config false;

    container cpeExtMIBObjects {
      smiv2:oid "1.3.6.1.4.1.9.9.402.1";

      leaf cpeExtDefaultAllocation {
        type uint32;
        units "milliwatts";
        description
         "This object indicates the default inline power allocation per
          port. This is a global configuration parameter that applies
          to all inline power capable ports in the system.
          
          The system must consider this object as well as the per port
          configuration object, cpeExtPsePortPwrMax, when determining
          how much power to allocate to a port. The system will use the
          lower of the two numbers.";
        smiv2:max-access "read-write";
        smiv2:oid "1.3.6.1.4.1.9.9.402.1.1";
      }

      leaf cpeExtPolicingNotifEnable {
        type boolean;
        description
         "This object is used to enable/disable the
          the cpeExtPolicingNotif notification.";
        smiv2:max-access "read-write";
        smiv2:oid "1.3.6.1.4.1.9.9.402.1.5";
      }

      leaf cpeExtPowerPriorityEnable {
        type boolean;
        description
         "This object is the global control of the power priority
          feature on the device. 'true' indicates that the power priority
          feature is globally enabled. 'false' indicates that the power
          priority feature is globally disabled.";
        smiv2:max-access "read-write";
        smiv2:oid "1.3.6.1.4.1.9.9.402.1.6";
      }
    }

    container cpeExtPdStatistics {
      smiv2:oid "1.3.6.1.4.1.9.9.402.1.4";

      leaf cpeExtPdStatsTotalDevices {
        type uint32;
        description
         "This object indicates the total number of the
          powered devices with any power classifications
          in the system.
          
          Classification is a way to tag different terminals
          on the Power over LAN network according to their
          power consumption. Devices such as IP telephones,
          WLAN access points and others, will be classified
          according to their power requirements.";
        reference
         "IEEE Std 802.3af Section 30.9.1.1.6
          aPSEPowerClassification";
        smiv2:max-access "read-only";
        smiv2:oid "1.3.6.1.4.1.9.9.402.1.4.1";
      }
    }

    container cpeExtMainPseTable {
      description
       "This table contains the additional information for the
        main PSE group in pethMainPseTable.";
      reference
       "RFC3621, pethMainPseTable";
      smiv2:oid "1.3.6.1.4.1.9.9.402.1.3";

      list cpeExtMainPseEntry {
        key "pethMainPseGroupIndex";
        description
         "A cpeExtMainPseEntry contains information about
          a particular pethMainPseGroupIndex. An entry is
          created by the agent when a main PSE group is added
          to the pethMainPseTable. An entry is deleted by the
          agent when a main PSE group is removed from the
          pethMainPseTable.";
        reference
         "RFC3621, pethMainPseTable";
        smiv2:oid "1.3.6.1.4.1.9.9.402.1.3.1";

        leaf pethMainPseGroupIndex {
          type leafref {
            path "/power-ethernet:POWER-ETHERNET-MIB/power-ethernet:pethMainPseTable/power-ethernet:pethMainPseEntry/power-ethernet:pethMainPseGroupIndex";
          }
        }

        leaf cpeExtMainPseEntPhyIndex {
          type cisco-tc:EntPhysicalIndexOrZero;
          description
           "The entPhysicalIndex value that uniquely identifies the
            main PSE group. If the main PSE group does not have a
            corresponding physical entry in entPhysicalTable or if
            the entPhysicalTable is not supported by the management
            system, then this object has the value of zero.";
          reference
           "RFC 2737, entPhysicalIndex.";
          smiv2:max-access "read-only";
          smiv2:oid "1.3.6.1.4.1.9.9.402.1.3.1.1";
        }

        leaf cpeExtMainPseDescr {
          type snmp-framework:SnmpAdminString;
          description
           "A textual string containing information about the Power
            Source Equipment (PSE) group.";
          smiv2:max-access "read-only";
          smiv2:oid "1.3.6.1.4.1.9.9.402.1.3.1.2";
        }

        leaf cpeExtMainPsePwrMonitorCapable {
          type boolean;
          description
           "This object indicates if the given group is capable of
            monitoring the power consumption of the interfaces that
            belong to the group. The value 'true' means that the
            group is capable. The value 'false' means that the group
            in not capable.";
          smiv2:max-access "read-only";
          smiv2:oid "1.3.6.1.4.1.9.9.402.1.3.1.3";
        }

        leaf cpeExtMainPseUsedPower {
          type uint32;
          units "miliwatts";
          description
           "Used power expressed in miliwatts.";
          smiv2:max-access "read-only";
          smiv2:oid "1.3.6.1.4.1.9.9.402.1.3.1.4";
        }

        leaf cpeExtMainPseRemainingPower {
          type uint32;
          units "miliwatts";
          description
           "Remaining power expressed in miliwatts, this
            parameter is calculated as pethMainPsePower
            minus cpeExtMainPseUsedPower.";
          smiv2:max-access "read-only";
          smiv2:oid "1.3.6.1.4.1.9.9.402.1.3.1.5";
        }
      }
    }

    container cpeExtPdStatsTable {
      description
       "This table contains the statistics information
        of the powered devices fallen into different power
        classifications in the system.";
      reference
       "IEEE Std 802.3af Section 30.9.1.1.6
        aPSEPowerClassification";
      smiv2:oid "1.3.6.1.4.1.9.9.402.1.4.2";

      list cpeExtPdStatsEntry {
        key "cpeExtPdStatsClass";
        description
         "A cpeExtPdStatsEntry contains the statistics
          information about a particular power classification
          defined in cpeExtPdStatsIndex.";
        smiv2:oid "1.3.6.1.4.1.9.9.402.1.4.2.1";

        leaf cpeExtPdStatsClass {
          type enumeration {
            enum "cisco" {
              value "1";
            }
            enum "class0" {
              value "2";
            }
            enum "class1" {
              value "3";
            }
            enum "class2" {
              value "4";
            }
            enum "class3" {
              value "5";
            }
            enum "class4" {
              value "6";
            }
          }
          description
           "The power classification as the index for the
            statistics information for powered devices.
            
            A value of 'cisco' indicates that the powered
            devices are CISCO proprietary and their power 
            classification does not fall into any class
            in IEEE specifications.
            
            A value of 'class0' indicates that the power 
            classification of the powered devices falls into
            class 0 in IEEE specifications.
            
            A value of 'class1' indicates that the power
            classification of the powered devices falls into
            class 1 in IEEE specifications.
            
            A value of 'class2' indicates that the power
            classification of the powered devices falls into
            class 2 in IEEE specifications.
            
            A value of 'class3' indicates that the power
            classification of the powered devices falls into
            class 3 in IEEE specifications.
            
            A value of 'class4' indicates that the power
            classification of the powered devices falls into
            class 4 in IEEE specifications.";
          reference
           "IEEE Std 802.3af Section 30.9.1.1.6
            aPSEPowerClassification";
          smiv2:max-access "not-accessible";
          smiv2:oid "1.3.6.1.4.1.9.9.402.1.4.2.1.1";
        }

        leaf cpeExtPdStatsDeviceCount {
          type uint32;
          description
           "This object indicates the count of the powered
            devices whose power classification falls into 
            a specific value of cpeExtPdStatsIndex.";
          smiv2:max-access "read-only";
          smiv2:oid "1.3.6.1.4.1.9.9.402.1.4.2.1.2";
        }
      }
    }

    container cpeExtPsePortLldpTable {
      description
       "A table provides the Link Layer Discovery Protocol (LLDP)
        based Data Link Layer (DLL) power classification
        characteristics of PSE ports and PDs attached to them.";
      smiv2:oid "1.3.6.1.4.1.9.9.402.1.7";

      list cpeExtPsePortLldpEntry {
        key "pethPsePortGroupIndex pethPsePortIndex";
        description
         "A cpeExtPseDllPowerEntry entry contains the LLDP
          based DLL power classification characteristics for a particular
          PSE and the PD attached to it. 
          
          A PSE has its entry here when all of the following conditions
          are satisfied:
          - The LLDP power classification is globally enabled.
          - It has a PD attached.
          - LLDP is the operational power negotiation protocol between
            the PSE and the PD attached.";
        smiv2:oid "1.3.6.1.4.1.9.9.402.1.7.1";

        leaf pethPsePortGroupIndex {
          type leafref {
            path "/power-ethernet:POWER-ETHERNET-MIB/power-ethernet:pethPsePortTable/power-ethernet:pethPsePortEntry/power-ethernet:pethPsePortGroupIndex";
          }
        }

        leaf pethPsePortIndex {
          type leafref {
            path "/power-ethernet:POWER-ETHERNET-MIB/power-ethernet:pethPsePortTable/power-ethernet:pethPsePortEntry/power-ethernet:pethPsePortIndex";
          }
        }

        leaf cpeExtPsePortLldpPwrType {
          type CISCO-POWER-ETHERNET-EXT-MIB:CpeExtLldpPwrType;
          description
           "The DTE Power via MDI type of the local system (PSE).";
          smiv2:max-access "read-only";
          smiv2:oid "1.3.6.1.4.1.9.9.402.1.7.1.1";
        }

        leaf cpeExtPsePortLldpPdPwrType {
          type CISCO-POWER-ETHERNET-EXT-MIB:CpeExtLldpPwrType;
          description
           "The DTE Power via MDI type of the remote system (PD).";
          smiv2:max-access "read-only";
          smiv2:oid "1.3.6.1.4.1.9.9.402.1.7.1.2";
        }

        leaf cpeExtPsePortLldpPwrSrc {
          type CISCO-POWER-ETHERNET-EXT-MIB:CpeExtLldpPwrSrc;
          description
           "The power source of the local system (PSE).";
          smiv2:max-access "read-only";
          smiv2:oid "1.3.6.1.4.1.9.9.402.1.7.1.3";
        }

        leaf cpeExtPsePortLldpPdPwrSrc {
          type CISCO-POWER-ETHERNET-EXT-MIB:CpeExtLldpPwrSrc;
          description
           "The power source of the remote system (PD).";
          smiv2:max-access "read-only";
          smiv2:oid "1.3.6.1.4.1.9.9.402.1.7.1.4";
        }

        leaf cpeExtPsePortLldpPwrPriority {
          type CISCO-POWER-ETHERNET-EXT-MIB:CpeExtPwrPriority;
          description
           "The power priority of the local system (PSE).";
          smiv2:max-access "read-only";
          smiv2:oid "1.3.6.1.4.1.9.9.402.1.7.1.5";
        }

        leaf cpeExtPsePortLldpPdPwrPriority {
          type CISCO-POWER-ETHERNET-EXT-MIB:CpeExtPwrPriority;
          description
           "The power priority of the remote system (PD).";
          smiv2:max-access "read-only";
          smiv2:oid "1.3.6.1.4.1.9.9.402.1.7.1.6";
        }

        leaf cpeExtPsePortLldpPwrReq {
          type uint32;
          units "milliwatts";
          description
           "The requested PD power value that the local
            system (PSE) mirrors back to the remote system (PD).";
          smiv2:max-access "read-only";
          smiv2:oid "1.3.6.1.4.1.9.9.402.1.7.1.7";
        }

        leaf cpeExtPsePortLldpPdPwrReq {
          type uint32;
          units "milliwatts";
          description
           "The PD requested power value received from
            the remote system (PD).";
          smiv2:max-access "read-only";
          smiv2:oid "1.3.6.1.4.1.9.9.402.1.7.1.8";
        }

        leaf cpeExtPsePortLldpPwrAlloc {
          type uint32;
          units "milliwatts";
          description
           "The PSE allocated power value for the remote
            system (PD).";
          smiv2:max-access "read-only";
          smiv2:oid "1.3.6.1.4.1.9.9.402.1.7.1.9";
        }

        leaf cpeExtPsePortLldpPdPwrAlloc {
          type uint32;
          units "milliwatts";
          description
           "The PSE allocated power value received from the
            remote system (PD).";
          smiv2:max-access "read-only";
          smiv2:oid "1.3.6.1.4.1.9.9.402.1.7.1.10";
        }
      }
    }
  }

  smiv2:alias "cpeExtPsePortTable" {
    description
     "This table extends the POWER-ETHERNET-MIB pethPsePortTable
      for power Ethernet ports on a Powered Sourcing Equipment
      (PSE) device.";
    reference
     "RFC3621";
    smiv2:oid "1.3.6.1.4.1.9.9.402.1.2";
  }

  smiv2:alias "cpeExtPsePortEntry" {
    description
     "A cpeExtPsePortEntry extends a corresponding
      pethPsePortTable entry. This entry displays and
      controls more characteristics of a power Ethernet
      port on a PSE device.";
    smiv2:oid "1.3.6.1.4.1.9.9.402.1.2.1";
  }

  augment "/power-ethernet:POWER-ETHERNET-MIB/power-ethernet:pethPsePortTable/power-ethernet:pethPsePortEntry" {
    description
     "A cpeExtPsePortEntry extends a corresponding
      pethPsePortTable entry. This entry displays and
      controls more characteristics of a power Ethernet
      port on a PSE device.";
    smiv2:oid "1.3.6.1.4.1.9.9.402.1.2.1";

    leaf cpeExtPsePortEnable {
      type enumeration {
        enum "auto" {
          value "1";
        }
        enum "static" {
          value "2";
        }
        enum "limit" {
          value "3";
        }
        enum "disable" {
          value "4";
        }
      }
      description
       "This object is an extension of the pethPsePortAdminEnable
        object from RFC3621. It allows the user to be more specific
        when enabling the PSE functions. The states, 'auto', 'static'
        and 'limit' correspond to a value of 'true' for the
        pethPsePortAdminEnable object. The state 'disable' corresponds
        to a value of 'false' for the pethPsePortAdminEnable object.
        
        Setting this value to 'auto' enables Powered Device discovery
        on the interface and the amount of power allocated depends on
        the Powered Device discovered. If pethPsePortAdminEnable was
        'false' prior to this set operation, then it will become
        'true'.
        
        Setting this value to 'static' will also enable Powered
        Device discovery. However, this is different from 'auto'
        in that the amount of power is pre-allocated based on the
        configuration on the Power Sourcing Equipment. If
        pethPsePortAdminEnable was 'false' prior to this set
        operation, then it will become 'true'.
        
        Setting this value to 'limit' enables Powered Device
        discovery on the interface. The amount of power allocated
        depends on the Powered Device discovered and the value
        of cpeExtPsePortPwrMax. The lower value will be used.
        If pethPsePortAdminEnable was 'false' prior to this set
        operation, then it will become 'true'.
        
        Setting this value to 'disable' disables the PSE functions.
        The pethPsePortAdminEnable object will adopt the value of
        'false' if it was 'true' prior to this set operation. When
        setting the pethPsePortAdminEnable object to 'false' this
        object cpeExtPsePortEnable will adopt the value of 'disable'.
        
        If cpeExtPsePortPolicingCapable of the PSE port, or
        cpeExtMainPsePwrMonitorCapable of the PSE port's
        main group, has the value of 'false', this object
        can only be set to 'auto', 'static' or 'disable'.
        Otherwise, this object can be set to 'auto', 'static',
        'limit' or 'disable'.";
      smiv2:max-access "read-write";
      smiv2:oid "1.3.6.1.4.1.9.9.402.1.2.1.1";
    }

    leaf cpeExtPsePortDiscoverMode {
      type enumeration {
        enum "unknown" {
          value "1";
        }
        enum "off" {
          value "2";
        }
        enum "ieee" {
          value "3";
        }
        enum "cisco" {
          value "4";
        }
        enum "ieeeAndCisco" {
          value "5";
        }
      }
      description
       "This object indicates the discover mode used by the system to
        discover the PD.
        
        A value of 'unknown' indicates that the discover mode on the
        interface is unknown.
        
        A value of 'off' indicates that discovery is disabled on the
        interface.
        
        A value of 'ieee' indicates that the discover mode on the
        interface is IEEE based.
        
        A value of 'cisco' indicates that the discover mode on the
        interface is Cisco based.
        
        A value of 'ieeeAndCisco' indicates that the discover mode on
        the interface is both IEEE and Cisco based.";
      smiv2:max-access "read-only";
      smiv2:oid "1.3.6.1.4.1.9.9.402.1.2.1.2";
    }

    leaf cpeExtPsePortDeviceDetected {
      type boolean;
      description
       "This object indicates if a Powered Device (PD) has been
        detected on the interface.
        
        A value of 'true' indicates that a PD has been detected on
        the interface.
        
        A value of 'false' indicates that no PD has been detected on
        the interface.";
      smiv2:max-access "read-only";
      smiv2:oid "1.3.6.1.4.1.9.9.402.1.2.1.3";
    }

    leaf cpeExtPsePortIeeePd {
      type boolean;
      description
       "This object indicates whether the Powered Device attached
        to the interface is an IEEE compliant Powered Device or not.
        
        A value of 'true' indicates the attached Powered Device is
        an IEEE compliant Powered Device.
        
        A value of 'false' indicates the attached Powered Device
        is not an IEEE compliant Powered Device. This also means
        that the value of the corresponding object from the
        pethPsePortTable, pethPsePortPowerClassifications is
        irrelevant.";
      smiv2:max-access "read-only";
      smiv2:oid "1.3.6.1.4.1.9.9.402.1.2.1.4";
    }

    leaf cpeExtPsePortAdditionalStatus {
      type bits {
        bit deny {
          position "0";
        }
        bit overdraw {
          position "1";
        }
        bit overdrawLog {
          position "2";
        }
      }
      description
       "This object is an extension of the pethPsePortDetectionStatus
        object from RFC3621 and provides additional status
        information.
        
        deny: When set, the PD attached to the interface is being
              denied power due to insufficient power resources on
              the Power Sourcing Equipment.
        
        overdraw: When set, the PD attached to the interface is 
                  being denied power because the PD is trying 
                  to consume more power than it has been 
                  configured to consume.
        
        overdrawLog: When set, the PD attached to the interface 
                     is trying to consume more power than it has 
                     been configured to consume, but is not being 
                     denied power.";
      smiv2:max-access "read-only";
      smiv2:oid "1.3.6.1.4.1.9.9.402.1.2.1.5";
    }

    leaf cpeExtPsePortPwrMax {
      type uint32;
      units "milliwatts";
      description
       "This indicates the maximum amount of power that the PSE will
        make available to the PD connected to this interface.";
      smiv2:max-access "read-write";
      smiv2:oid "1.3.6.1.4.1.9.9.402.1.2.1.6";
    }

    leaf cpeExtPsePortPwrAllocated {
      type uint32;
      units "milliwatts";
      description
       "This object indicates the amount of power allocated from the
        PSE for the PD.";
      smiv2:max-access "read-only";
      smiv2:oid "1.3.6.1.4.1.9.9.402.1.2.1.7";
    }

    leaf cpeExtPsePortPwrAvailable {
      type uint32;
      units "milliwatts";
      description
       "This object indicates the amount of power available for
        the PD to use. This value may differ from the value
        cpeExtPsePortPwrAllocated due to the efficiency issues
        of delivering the power from the PSE to the PD.
        
        When sufficient power is available to power a PD, this
        value should be equal to the lower of the two objects,
        cpeExtDefaultAllocation and cpeExtPsePortPwrMax.";
      smiv2:max-access "read-only";
      smiv2:oid "1.3.6.1.4.1.9.9.402.1.2.1.8";
    }

    leaf cpeExtPsePortPwrConsumption {
      type uint32;
      units "milliwatts";
      description
       "This indicates the actual power consumption of the PD
        connected to this interface. It may not necessarily
        be equal to the value of cpeExtPsePortPwrAvailable.";
      smiv2:max-access "read-only";
      smiv2:oid "1.3.6.1.4.1.9.9.402.1.2.1.9";
    }

    leaf cpeExtPsePortMaxPwrDrawn {
      type uint32;
      units "milliwatts";
      description
       "This indicates the maximum amount of power drawn by the PD
        connected to this interface, since it was powered on.";
      smiv2:max-access "read-only";
      smiv2:oid "1.3.6.1.4.1.9.9.402.1.2.1.10";
    }

    leaf cpeExtPsePortEntPhyIndex {
      type cisco-tc:EntPhysicalIndexOrZero;
      description
       "The entPhysicalIndex value that uniquely identifies the
        PSE port. If the PSE port does not have a corresponding 
        physical entry in entPhysicalTable or if the 
        entPhysicalTable is not supported by the management
        system, this object has the value of zero.";
      reference
       "RFC 2737, entPhysicalIndex.";
      smiv2:max-access "read-only";
      smiv2:oid "1.3.6.1.4.1.9.9.402.1.2.1.11";
    }

    leaf cpeExtPsePortPolicingCapable {
      type boolean;
      description
       "This object indicates whether the PSE port hardware is
        capable of policing the port for proper power consumption 
        based on the allocated value.";
      smiv2:max-access "read-only";
      smiv2:oid "1.3.6.1.4.1.9.9.402.1.2.1.12";
    }

    leaf cpeExtPsePortPolicingEnable {
      type enumeration {
        enum "on" {
          value "1";
        }
        enum "off" {
          value "2";
        }
      }
      description
       "This object allows the user to turn on or turn off the
        power policing of the PSE port. If the instance value of 
        cpeExtPsePortPolicingCapable is 'TRUE', the user is allowed
        to set this object to 'on' or 'off'. Otherwise, this
        object is read-only and always has the value of 'off'.";
      smiv2:max-access "read-write";
      smiv2:oid "1.3.6.1.4.1.9.9.402.1.2.1.13";
    }

    leaf cpeExtPsePortPolicingAction {
      type enumeration {
        enum "deny" {
          value "1";
        }
        enum "logOnly" {
          value "2";
        }
      }
      description
       "This object specifies the power policing action that
        the device will take on this PSE port when the real-time 
        power consumption exceeds its max power allocation if 
        the value of cpeExtPsePortPolicingEnable is 'on'. 
             'deny'          - the device will deny the power to 
                               the PSE port 
             'logOnly'       - the device will not deny the power 
                               to the PSE port";
      smiv2:max-access "read-write";
      smiv2:oid "1.3.6.1.4.1.9.9.402.1.2.1.14";
    }

    leaf cpeExtPsePortPwrManAlloc {
      type uint32;
      units "milliwatts";
      description
       "This object specifies the manual power allocation that
        the PSE will allocate to the PD connected to this 
        interface regardless of the amount requested via CDP 
        or IEEE. 
        
        Setting this object value to zero disables the manual 
        power allocation. 
        
        Warning: Misconfiguring this manual power allocation may 
        cause damage to the system and void the warranty. Take 
        precautions not to oversubscribe the power supply.";
      smiv2:max-access "read-write";
      smiv2:oid "1.3.6.1.4.1.9.9.402.1.2.1.15";
    }

    leaf cpeExtPsePortCapabilities {
      type bits {
        bit policing {
          position "0";
        }
        bit poePlus {
          position "1";
        }
      }
      description
       "This object indicates the PSE functionality that
        this port supports.
        
        If the 'policing' BIT is set, then this PSE port is
        capable of policing the port for proper power consumption
        based on the allocated value.
        
        If the 'poePlus' BIT is set, then this PSE port supports
        PoE Plus functions.";
      smiv2:max-access "read-only";
      smiv2:oid "1.3.6.1.4.1.9.9.402.1.2.1.16";
    }
  }

  notification cpeExtPolicingNotif {
    description
     "This notification is generated when the 'overdraw' or
      'overdrawLog' bit in value of cpeExtPsePortAdditionalStatus
      is set or cleared.";
    smiv2:oid "1.3.6.1.4.1.9.9.402.0.1";

    container object-1 {

      leaf pethPsePortGroupIndex {
        type leafref {
          path "/power-ethernet:POWER-ETHERNET-MIB/power-ethernet:pethPsePortTable/power-ethernet:pethPsePortEntry/power-ethernet:pethPsePortGroupIndex";
        }
      }

      leaf pethPsePortIndex {
        type leafref {
          path "/power-ethernet:POWER-ETHERNET-MIB/power-ethernet:pethPsePortTable/power-ethernet:pethPsePortEntry/power-ethernet:pethPsePortIndex";
        }
      }

      leaf cpeExtPsePortPolicingAction {
        type leafref {
          path "/power-ethernet:POWER-ETHERNET-MIB/power-ethernet:pethPsePortTable/power-ethernet:pethPsePortEntry/CISCO-POWER-ETHERNET-EXT-MIB:cpeExtPsePortPolicingAction";
        }
      }
    }

    container object-2 {

      leaf pethPsePortGroupIndex {
        type leafref {
          path "/power-ethernet:POWER-ETHERNET-MIB/power-ethernet:pethPsePortTable/power-ethernet:pethPsePortEntry/power-ethernet:pethPsePortGroupIndex";
        }
      }

      leaf pethPsePortIndex {
        type leafref {
          path "/power-ethernet:POWER-ETHERNET-MIB/power-ethernet:pethPsePortTable/power-ethernet:pethPsePortEntry/power-ethernet:pethPsePortIndex";
        }
      }

      leaf cpeExtPsePortAdditionalStatus {
        type leafref {
          path "/power-ethernet:POWER-ETHERNET-MIB/power-ethernet:pethPsePortTable/power-ethernet:pethPsePortEntry/CISCO-POWER-ETHERNET-EXT-MIB:cpeExtPsePortAdditionalStatus";
        }
      }
    }

    container object-3 {

      leaf pethPsePortGroupIndex {
        type leafref {
          path "/power-ethernet:POWER-ETHERNET-MIB/power-ethernet:pethPsePortTable/power-ethernet:pethPsePortEntry/power-ethernet:pethPsePortGroupIndex";
        }
      }

      leaf pethPsePortIndex {
        type leafref {
          path "/power-ethernet:POWER-ETHERNET-MIB/power-ethernet:pethPsePortTable/power-ethernet:pethPsePortEntry/power-ethernet:pethPsePortIndex";
        }
      }

      leaf cpeExtPsePortPwrAllocated {
        type leafref {
          path "/power-ethernet:POWER-ETHERNET-MIB/power-ethernet:pethPsePortTable/power-ethernet:pethPsePortEntry/CISCO-POWER-ETHERNET-EXT-MIB:cpeExtPsePortPwrAllocated";
        }
      }
    }

    container object-4 {

      leaf pethPsePortGroupIndex {
        type leafref {
          path "/power-ethernet:POWER-ETHERNET-MIB/power-ethernet:pethPsePortTable/power-ethernet:pethPsePortEntry/power-ethernet:pethPsePortGroupIndex";
        }
      }

      leaf pethPsePortIndex {
        type leafref {
          path "/power-ethernet:POWER-ETHERNET-MIB/power-ethernet:pethPsePortTable/power-ethernet:pethPsePortEntry/power-ethernet:pethPsePortIndex";
        }
      }

      leaf cpeExtPsePortMaxPwrDrawn {
        type leafref {
          path "/power-ethernet:POWER-ETHERNET-MIB/power-ethernet:pethPsePortTable/power-ethernet:pethPsePortEntry/CISCO-POWER-ETHERNET-EXT-MIB:cpeExtPsePortMaxPwrDrawn";
        }
      }
    }
  }

  smiv2:alias "ciscoPowerEthernetExtMIB" {
    smiv2:oid "1.3.6.1.4.1.9.9.402";
  }

  smiv2:alias "cpeExtMIBNotifs" {
    smiv2:oid "1.3.6.1.4.1.9.9.402.0";
  }

  smiv2:alias "cpeExtMIBObjects" {
    smiv2:oid "1.3.6.1.4.1.9.9.402.1";
  }

  smiv2:alias "cpeExtPdStatistics" {
    smiv2:oid "1.3.6.1.4.1.9.9.402.1.4";
  }

  smiv2:alias "cpeExtMIBConformance" {
    smiv2:oid "1.3.6.1.4.1.9.9.402.2";
  }

  smiv2:alias "cpeExtMIBCompliances" {
    smiv2:oid "1.3.6.1.4.1.9.9.402.2.1";
  }

  smiv2:alias "cpeExtMIBGroups" {
    smiv2:oid "1.3.6.1.4.1.9.9.402.2.2";
  }

}
