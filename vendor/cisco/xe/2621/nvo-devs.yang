module nvo-devs {
  namespace "http://cisco.com/ns/nvo/devs";
  prefix nvo-devs;

  import nvo {
    prefix nvo;
  }

  organization
    "Cisco Systems, Inc.";
  contact
    " Cisco Systems, Inc.
     Customer Service

     Postal: 170 W Tasman Drive
     San Jose, CA 95134

     Tel: +1 1800 553-NETS

     E-mail: cs-yang@cisco.com";
  description
    "This module defines deviation statements for nvo (VxLAN) module.";

  revision 2015-09-11 {
    description
      "Initial Revision";
    reference
      "RFC 6020: YANG - A Data Modeling Language for the
       Network Configuration Protocol (NETCONF)";
  }

  deviation "/nvo:nvo-instances/nvo:nvo-instance/nvo:overlay-encapsulation" {
    deviate not-supported;
    description
      "Not supported in IOS-XE 3.17 release.";
  }

  deviation "/nvo:nvo-instances/nvo:nvo-instance/nvo:virtual-network"
          + "/nvo:replication-mode/nvo:static-peer-list" {
    deviate not-supported;
    description
      "Not supported in IOS-XE 3.17 release.";
  }

  deviation "/nvo:nvo-instances/nvo:nvo-instance/nvo:virtual-network"
          + "/nvo:replication-mode/nvo:bgp" {
    deviate not-supported;
    description
      "Not supported in IOS-XE 3.17 release.";
  }

  deviation "/nvo:nvo-instances/nvo:nvo-instance/nvo:virtual-network"
          + "/nvo:routing-instance" {
    deviate not-supported;
    description
      "Not supported in IOS-XE 3.17 release.";
  }

  deviation "/nvo:nvo-instances/nvo:nvo-instance/nvo:virtual-network"
          + "/nvo:end-host-discovery" {
    deviate not-supported;
    description
      "Not supported in IOS-XE 3.17 release.";
  }

  deviation "/nvo:nvo-instances/nvo:nvo-instance/nvo:virtual-network"
          + "/nvo:suppress-arp" {
    deviate not-supported;
    description
      "Not supported in IOS-XE 3.17 release.";
  }
}
