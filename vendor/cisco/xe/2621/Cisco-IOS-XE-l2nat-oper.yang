module Cisco-IOS-XE-l2nat-oper {
  yang-version 1.1;
  namespace "http://cisco.com/ns/yang/Cisco-IOS-XE-l2nat-oper";
  prefix l2nat-ios-xe-oper;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for L2NAT operational data.
     Copyright (c) 2023-2024 by Cisco Systems, Inc.
     All rights reserved.";

  revision 2026-08-01 {
    description
      "Updated descriptions of several model elements for improved clarity and accuracy.";
    reference
      "1.0.1";
    cisco-semver:module-version "1.0.1";
  }
  revision 2024-07-01 {
    description
      "Initial revision";
    reference
      "1.0.0";
    cisco-semver:module-version "1.0.0";
  }

  typedef l2nat-fixup-mode {
    type enumeration {
      enum l2nat-fixup-all {
        value 0;
        description
          "All traffic will be translated";
      }
      enum l2nat-fixup-arp {
        value 1;
        description
          "Only ARP traffic will be translated";
      }
      enum l2nat-fixup-icmp {
        value 2;
        description
          "Only ICMP traffic will be translated";
      }
    }
    description
      "Fixup mode in L2NAT instance";
  }

  typedef l2nat-permit-mode {
    type enumeration {
      enum l2nat-permit-no {
        value 0;
        description
          "No traffic will be permitted";
      }
      enum l2nat-permit-all {
        value 1;
        description
          "All untranslated traffic will be permitted on both direction.";
      }
      enum l2nat-permit-all-in {
        value 2;
        description
          "All untranslated traffic will be permitted only inside";
      }
      enum l2nat-permit-all-out {
        value 3;
        description
          "All untranslated traffic will be permitted only outside";
      }
      enum l2nat-permit-igmp {
        value 4;
        description
          "Only IGMP untranslated traffic will be permitted on both direction.";
      }
      enum l2nat-permit-igmp-in {
        value 5;
        description
          "Only IGMP untranslated traffic will be permitted only inside";
      }
      enum l2nat-permit-igmp-out {
        value 6;
        description
          "Only IGMP untranslated traffic will be permitted only outside";
      }
      enum l2nat-permit-mcast {
        value 7;
        description
          "Only multicast untranslated traffic will be permitted on both direction.";
      }
      enum l2nat-permit-mcast-in {
        value 8;
        description
          "Only multicast untranslated traffic will be permitted only inside";
      }
      enum l2nat-permit-mcast-out {
        value 9;
        description
          "Only multicast untranslated traffic will be permitted only outside";
      }
      enum l2nat-permit-unmatched {
        value 10;
        description
          "Only unmatched untranslated traffic will be permitted on both direction.";
      }
      enum l2nat-permit-unmatched-in {
        value 11;
        description
          "Only unmatched untranslated traffic will be permitted only inside";
      }
      enum l2nat-permit-unmatched-out {
        value 12;
        description
          "Only unmatched untranslated traffic will be permitted only outside";
      }
    }
    description
      "permit mode in L2NAT instance";
  }

  grouping l2nat-ins-hst-params {
    description
      "L2NAT instance ip address details for inside host";
    leaf orig-ip-addr {
      type inet:ip-address;
      description
        "Original IP address for inside host in a L2NAT instance";
    }
    leaf transl-ip-addr {
      type inet:ip-address;
      description
        "Translated IP address for inside host in a L2NAT instance";
    }
  }

  grouping l2nat-ins-rng-params {
    description
      "L2NAT instance ip address details for inside range";
    leaf orig-ip-addr {
      type inet:ip-address;
      description
        "Original IP address for inside range in a L2NAT instance";
    }
    leaf transl-ip-addr {
      type inet:ip-address;
      description
        "Translated IP address for inside range in a L2NAT instance";
    }
    leaf range {
      type uint16;
      description
        "Range for IP address for inside range in L2NAT instance";
    }
  }

  grouping l2nat-ins-nw-params {
    description
      "L2NAT instance ip address details for inside network";
    leaf orig-ip-addr {
      type inet:ip-address;
      description
        "Original IP address for inside network in a L2NAT instance";
    }
    leaf transl-ip-addr {
      type inet:ip-address;
      description
        "Translated IP address for inside network in a L2NAT instance";
    }
    leaf mask {
      type inet:ip-address;
      description
        "Subnet mask for the inside network in a L2NAT instance";
    }
  }

  grouping l2nat-outs-hst-params {
    description
      "L2NAT instance ip address details for outside host";
    leaf orig-ip-addr {
      type inet:ip-address;
      description
        "Original IP address for outside host in a L2NAT instance";
    }
    leaf transl-ip-addr {
      type inet:ip-address;
      description
        "Translated IP address for outside host in a L2NAT instance";
    }
  }

  grouping l2nat-outs-rng-params {
    description
      "L2NAT instance ip address details for outside range";
    leaf orig-ip-addr {
      type inet:ip-address;
      description
        "Original IP address for outside range in a L2NAT instance";
    }
    leaf transl-ip-addr {
      type inet:ip-address;
      description
        "Translated IP address for outside range in a L2NAT instance";
    }
    leaf range {
      type uint32;
      description
        "Range for IP address for outside range in L2NAT instance";
    }
  }

  grouping l2nat-outs-nw-params {
    description
      "L2NAT instance ip address details for outside network";
    leaf orig-ip-addr {
      type inet:ip-address;
      description
        "Original IP address for outside network in a L2NAT instance";
    }
    leaf transl-ip-addr {
      type inet:ip-address;
      description
        "Translated IP address for outside network in a L2NAT instance";
    }
    leaf mask {
      type inet:ip-address;
      description
        "Subnet mask for the outside network in a L2NAT instance";
    }
  }

  grouping l2nat-inst-info {
    description
      "Details of a L2NAT instance";
    leaf l2nat-inst-nm {
      type string;
      description
        "L2NAT instance identity";
    }
    leaf fixup {
      type l2nat-ios-xe-oper:l2nat-fixup-mode;
      description
        "Fixup mode of L2NAT";
    }
    leaf permit {
      type l2nat-ios-xe-oper:l2nat-permit-mode;
      description
        "Permitted Protocols for L2NAT";
    }
    container ins-hst-params {
      description
        "Contains configuration parameters for the inside host in a L2NAT instance, including original and translated IP addresses";
      uses l2nat-ios-xe-oper:l2nat-ins-hst-params;
    }
    container ins-rng-params {
      description
        "Contains configuration parameters for the inside range in a L2NAT instance, including original and translated IP addresses";
      uses l2nat-ios-xe-oper:l2nat-ins-rng-params;
    }
    container ins-nw-params {
      description
        "Contains configuration parameters for the inside network in a L2NAT instance, including original and translated IP addresses";
      uses l2nat-ios-xe-oper:l2nat-ins-nw-params;
    }
    container outs-hst-params {
      description
        "Contains configuration parameters for the outside host in a L2NAT instance, including original and translated IP addresses";
      uses l2nat-ios-xe-oper:l2nat-outs-hst-params;
    }
    container outs-rng-params {
      description
        "Contains configuration parameters for the outside range in a L2NAT instance, including original and translated IP addresses";
      uses l2nat-ios-xe-oper:l2nat-outs-rng-params;
    }
    container outs-nw-params {
      description
        "Contains configuration parameters for the outside network in a L2NAT instance, including original and translated IP addresses";
      uses l2nat-ios-xe-oper:l2nat-outs-nw-params;
    }
  }

  container l2nat-oper-data {
    config false;
    description
      "Container for operational data related to Layer 2 Network Address Translation (L2NAT) instances, including their configuration and status.";
    list l2nat-inst-info {
      key "l2nat-inst-nm";
      description
        "Details of L2NAT instance";
      uses l2nat-ios-xe-oper:l2nat-inst-info;
    }
  }
}
