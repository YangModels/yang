module Cisco-IOS-XE-wireless-dot11-cfg {
  yang-version 1.1;
  namespace "http://cisco.com/ns/yang/Cisco-IOS-XE-wireless-dot11-cfg";
  prefix wireless-dot11-cfg;

  import Cisco-IOS-XE-wireless-enum-types {
    prefix wireless-enum-types;
  }
  import Cisco-IOS-XE-wireless-types {
    prefix wireless-types;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Model for managing configurations related to various 802.11 protocols.
     Copyright (c) 2016-2020, 2022 by Cisco Systems, Inc.
     All rights reserved.";

  revision 2026-08-01 {
    description
      "- Updated descriptions for several model elements to clarify their meaning and purpose";
    reference
      "12.1.0";
    cisco-semver:module-version "12.1.0";
  }
  revision 2025-07-01 {
    description
      "- Added support for Tier E countries";
    reference
      "12.0.0";
    cisco-semver:module-version "12.0.0";
  }
  revision 2025-03-01 {
    description
      "- Added few must constraints to validate combination of 11n, 11ac, 11be and 11ax configurations while enabling or disabling
       - Added a validation to check if the sum of voice bandwidth and video bandwidth exceeds the limit of 85";
    reference
      "11.0.0";
    cisco-semver:module-version "11.0.0";
  }
  revision 2024-07-01 {
    description
      "- Obsolete channel switch configuration
       - Added 802.11be configuration";
    reference
      "10.3.0";
    cisco-semver:module-version "10.3.0";
  }
  revision 2023-11-01 {
    description
      "- removed the must constraint for event driven rrm on 6Ghz band";
    reference
      "10.2.0";
    cisco-semver:module-version "10.2.0";
  }
  revision 2023-03-01 {
    description
      "- Added support for additional country codes";
    reference
      "10.1.0";
    cisco-semver:module-version "10.1.0";
  }
  revision 2022-11-01 {
    description
      "- Added a constraint to prevent event driven rrm from being enabled on 6 GHz band
       - Added a deprecated status to AQ report enable as it is controlled by admin state
       - Added support for additional country codes
       - Update yang-version to 1.1";
    reference
      "10.0.0";
    cisco-semver:module-version "10.0.0";
  }
  revision 2022-07-01 {
    description
      "- Removed the support for country code j2 for Japan";
    reference
      "9.0.0";
    cisco-semver:module-version "9.0.0";
  }
  revision 2021-11-01 {
    description
      "- Modified the default value for Target Wake-up Time and Target Wake-up Time broadcast";
    reference
      "8.0.0";
    cisco-semver:module-version "8.0.0";
  }
  revision 2021-07-01 {
    description
      "- Added a constraint to prevent 802.11ax from being disabled on 6 GHz band";
    reference
      "7.0.0";
    cisco-semver:module-version "7.0.0";
  }
  revision 2020-11-01 {
    description
      "- Added configuration to enable/disable client load-based EDCA.";
    reference
      "6.3.0";
    cisco-semver:module-version "6.3.0";
  }
  revision 2020-07-01 {
    description
      "- Added RSSI threshold configuration for WiFi to Cellular steering.
       - Added Country code configuration.";
    reference
      "6.2.0";
    cisco-semver:module-version "6.2.0";
  }
  revision 2019-11-01 {
    description
      "- Added 802.11ax BSS color configuration
       - Added Target Wake-up Time support for 802.11ax.";
    reference
      "6.1.0";
    cisco-semver:module-version "6.1.0";
  }
  revision 2019-06-18 {
    description
      "- Enable 802.11ax feature by default.
       - Added semantic version.
       - Fixed must constraint for frame-burst leaf.
       - Removed  must constraint for frame-burst leaf.
       - Added when clause for frame-burst leaf.
       - Update the default values as per WLC configuration best practice";
    reference
      "6.0.0";
    cisco-semver:module-version "6.0.0";
  }
  revision 2019-02-21 {
    description
      "- Adding new enum type for dot11 band
       - Client Switch enable and mode Default and Type changed
       - Support for 802.11ax configuration
       - Support for dot11ax mcs index configuration
       - Removal of unused leaves
       - Cleaned up spelling errors in descriptions
       - Modified description of the leaves
       - Multicast related leaves name change
       - Modified description and names of the leaves
       - Adding new enum for 11ac MCS Data rate index
       - Changing type for leaf node smart-dfs
       - Updated name for QoS CAC voice leaf nodes
       - Updated frame-burst for 802.11n configuration";
    reference
      "5.0.0";
    cisco-semver:module-version "5.0.0";
  }
  revision 2018-06-13 {
    description
      "- Change TX MCS rate config for dot11ac
       - Remove SIP codec support
       - Add range constraints to integer.";
    reference
      "4.0.0";
    cisco-semver:module-version "4.0.0";
  }
  revision 2018-03-01 {
    description
      "Defaults changed";
    reference
      "3.0.0";
    cisco-semver:module-version "3.0.0";
  }
  revision 2018-01-24 {
    description
      "The first generally available version";
    reference
      "2.0.0";
    cisco-semver:module-version "2.0.0";
  }
  revision 2017-05-05 {
    description
      "Initial revision";
    reference
      "1.0.0";
    cisco-semver:module-version "1.0.0";
  }

  grouping dot11-cfg {
    description
      "802.11 default config";
    leaf fragmentation-threshold {
      type uint16 {
        range "256 .. 2346";
      }
      default "2346";
      description
        "Current maximum size, in octets, of the MPDU that may be delivered to the PHY.
         An MSDU shall be broken into fragments if its size exceeds the value of this attribute after adding MAC headers and trailers. An MSDU or MPDU shall be fragmented when the resulting frame has individual address in the Address1 field, and the length of the frame is larger than this threshold. The default value for this attribute shall be the lesser of 2346 or the aMPDUMaxLength of the attached PHY and shall never exceed the lesser of 2346 or the aMPDUMaxLength of the attached PHY. The value of this attribute shall never be less than 256.";
    }
    leaf default-tx-power-level {
      type uint16 {
        range "1 .. 5";
      }
      default "1";
      description
        "Specifies the default transmit power level currently used for data transmission. Some PHYs also use this value to determine receiver sensitivity requirements for Clear Channel Assessment (CCA).";
    }
  }

  grouping dot11-80211-capability-config {
    description
      "APF dot11 capability configuration";
    leaf apf-beacon-interval {
      type uint16 {
        range "20 .. 1000";
      }
      default "100";
      description
        "Number of time unit that a AP Radio shall use for scheduling Beacon transmissions. This value is transmitted in Beacon and Probe Response frames.";
    }
  }

  grouping dot11-ht-config {
    description
      "802.11n related configuration";
    leaf dot11n-enabled {
      type boolean;
      must "../../band = 'dot11-2-dot-4-ghz-band' or ../../band = 'dot11-6-ghz-band' or ../dot11n-enabled = 'true' or (../dot11n-enabled = 'false' and  ../../dot11ac-cfg/vht-enable = 'false' and ../../dot11ax-cfg/he-enable = 'false') or (../dot11n-enabled = 'false' and  ../../dot11ac-cfg/vht-enable = 'true' and ../../dot11ax-cfg/he-enable = 'false') or (../dot11n-enabled = 'false' and  ../../dot11ac-cfg/vht-enable = 'false' and ../../dot11ax-cfg/he-enable = 'true')" {
        error-message "802.11ac and 802.11ax must be disabled";
        error-app-tag "must-violation";
      }
      must "../../band = 'dot11-2-dot-4-ghz-band' or ../../band = 'dot11-6-ghz-band' or ../dot11n-enabled = 'true' or (../dot11n-enabled = 'false' and  ../../dot11ac-cfg/vht-enable = 'false') or (../dot11n-enabled = 'false' and  ../../dot11ax-cfg/he-enable = 'true')" {
        error-message "802.11ac must be disabled";
        error-app-tag "must-violation";
      }
      must "../../band = 'dot11-2-dot-4-ghz-band' or ../../band = 'dot11-6-ghz-band' or ../dot11n-enabled = 'true' or (../dot11n-enabled = 'false' and  ../../dot11ax-cfg/he-enable = 'false') or (../dot11n-enabled = 'false' and  ../../dot11ac-cfg/vht-enable = 'true')" {
        error-message "802.11ax must be disabled";
        error-app-tag "must-violation";
      }
      must "../../band = 'dot11-5-ghz-band' or ../../band = 'dot11-6-ghz-band' or (../../dot11ax-cfg/he-enable = 'false' and  ../dot11n-enabled = 'false') or (../../dot11ax-cfg/he-enable = 'true' and  ../dot11n-enabled = 'true') or (../../dot11ax-cfg/he-enable = 'false' and  ../dot11n-enabled = 'true')" {
        error-message "802.11ax must be disabled";
        error-app-tag "must-violation";
      }
      default "true";
      description
        "Enables the controller to manage 802.11n networks.
         True - 802.11n network is enabled.
         False - 802.11n network is disabled.";
    }
    leaf dot11n-rifs-tx-status {
      type boolean;
      default "true";
      description
        "Support for RIFS on this band.
         True - RIFS is enabled for this band.
         False - RIFS is disabled for this band.";
    }
    leaf dot11n-short-guard-enabled {
      type boolean;
      default "true";
      description
        "Support for 802.11n guard interval on this band.
         True - Guard interval is enabled for this band.
         False - Guard interval is disabled for this band.";
    }
  }

  grouping dot11-dot11ac-config {
    description
      "802.11ac feature related configuration";
    leaf vht-enable {
      type boolean;
      must "../../band = 'dot11-2-dot-4-ghz-band' or ../../band = 'dot11-6-ghz-band' or (../../dot11ax-cfg/he-enable = 'false' and  ../vht-enable = 'false') or (../vht-enable = 'true')" {
        error-message "802.11ax must be disabled";
        error-app-tag "must-violation";
      }
      must "../../band = 'dot11-2-dot-4-ghz-band' or ../../band = 'dot11-6-ghz-band' or (../../ht-cfg/dot11n-enabled = 'false' and  ../vht-enable = 'false') or (../../ht-cfg/dot11n-enabled = 'true')" {
        error-message "802.11n must be enabled";
        error-app-tag "must-violation";
      }
      default "true";
      description
        "Enables controller to manage 802.11ac networks.
         True - 802.11ac network is enabled.
         False - 802.11ac network is disabled.";
    }
  }

  grouping dot11-eht-config {
    description
      "802.11be related configuration";
    leaf eht-enable {
      type boolean;
      default "false";
      description
        "Enables the controller to manage 802.11be networks.
         True  - 802.11be network is enabled.
         False - 802.11be network is disabled.";
    }
  }

  grouping st-dot11-dot11ax-cfg-config {
    description
      "802.11ax protocol related configuration";
    leaf he-enable {
      type boolean;
      must "((../../band != 'dot11-6-ghz-band') or (../../dot11ax-cfg/he-enable = 'true'))" {
        error-message "802.11ax should not be disabled for 6 GHz band";
        error-app-tag "must-violation";
      }
      must "../../band = 'dot11-2-dot-4-ghz-band' or ../../band = 'dot11-6-ghz-band' or ../he-enable = 'false' or (../../ht-cfg/dot11n-enabled = 'true' and  ../../dot11ac-cfg/vht-enable = 'true' and ../he-enable = 'true') or (../../ht-cfg/dot11n-enabled = 'false' and  ../../dot11ac-cfg/vht-enable = 'true' and ../he-enable = 'true') or (../../ht-cfg/dot11n-enabled = 'true' and  ../../dot11ac-cfg/vht-enable = 'false' and ../he-enable = 'true')" {
        error-message "802.11n and 802.11ac must be enabled";
        error-app-tag "must-violation";
      }
      must "../../band = 'dot11-2-dot-4-ghz-band' or ../../band = 'dot11-6-ghz-band' or ../he-enable = 'false' or (../he-enable = 'true' and  ../../dot11ac-cfg/vht-enable = 'true') or (../he-enable = 'true' and  ../../ht-cfg/dot11n-enabled = 'false')" {
        error-message "802.11ac must be enabled";
        error-app-tag "must-violation";
      }
      must "../../band = 'dot11-2-dot-4-ghz-band' or ../../band = 'dot11-6-ghz-band' or ../he-enable  = 'false' or (../he-enable = 'true' and  ../../ht-cfg/dot11n-enabled = 'true') or (../he-enable = 'true' and  ../../dot11ac-cfg/vht-enable = 'false')" {
        error-message "802.11n must be enabled";
        error-app-tag "must-violation";
      }
      must "../../band = 'dot11-5-ghz-band' or ../../band = 'dot11-6-ghz-band' or (../he-enable = 'false' and  ../../ht-cfg/dot11n-enabled = 'false') or (../he-enable = 'true' and  ../../ht-cfg/dot11n-enabled = 'true') or (../he-enable = 'false' and  ../../ht-cfg/dot11n-enabled = 'true')" {
        error-message "802.11n must be enabled";
        error-app-tag "must-violation";
      }
      default "true";
      description
        "Configuration to enable 802.11ax support";
    }
    leaf he-dynamic-frag {
      type boolean;
      default "true";
      description
        "Configuration to enable 802.11ax Dynamic Fragmentation support";
    }
    leaf he-mbssid-cap {
      type boolean;
      default "true";
      description
        "Configuration to enable 802.11ax multiple bssid support";
    }
    leaf he-twt-enable {
      type boolean;
      default "false";
      description
        "Configures 802.11ax target wake-up time.
         True - Target Wake-up Time is enabled.
         False - Target Wake-up Time is disabled.";
    }
    leaf he-twt-broadcast-enable {
      type boolean;
      default "false";
      description
        "Configures 802.11ax target wake-up time broadcast.
         True - Target Wake-up Time broadcast is enabled.
         False - Target Wake-up Time broadcast is disabled.";
    }
    leaf he-bss-color {
      type boolean;
      default "false";
      description
        "Enables or disables 802.11ax BSS (Basic Service Set) color support, which allows differentiation between overlapping BSSs to improve spatial reuse and reduce co-channel interference.";
    }
  }

  grouping dot11h-config {
    description
      "802.11n feature related configuration";
    leaf channel-switch-enable {
      type boolean;
      default "true";
      status obsolete;
      description
        "Enables or disables channel switch. When disabling Channel Switch no need to pass mode and count";
    }
    leaf channel-switch-mode {
      type wireless-enum-types:enm-channel-switch-mode;
      default "chan-switch-mode-loud";
      description
        "Channel Switch Mode indicates any restriction on transmission until a channel switch.
         channel-switch-mode-loud - Does not impose any requirement on the receiving STA.
         channel-switch-mode-quiet - STA in a BSS to which the frame containing the element is addressed shall transmit no further frames with in the BSS until the scheduled channel switch.";
    }
    leaf power-constraint {
      type uint8 {
        range "0 .. 30";
      }
      default "0";
      description
        "Local maximum transmit power for a channel is defined as maximum transmit power level specified for the channel in the Country element minus the local power constraint specified for the channel in the Power Constraint element. The power constraint is coded as an unsigned integer in units of decibels. To disable power constraint set Power Constraint to 0.";
    }
    leaf smart-dfs {
      type boolean;
      default "true";
      description
        "Enables or disables Smart DFS (Dynamic Frequency Selection), which manages non-occupancy time for channels affected by radar interference. True enables Smart DFS; False disables it.";
    }
  }

  grouping dot11-80211-qos-pm-config {
    description
      "Radio policy related configuration";
    leaf qos-pm-name {
      type string;
      default "unknown";
      description
        "Specifies the name of the radio policy applied for 802.11 Quality of Service (QoS) and Power Management (PM) configuration.";
    }
    leaf def-11gn {
      type uint32 {
        range "15000 .. 200000000";
      }
      units "bps";
      default "200000000";
      description
        "Specifies the default policy rate, in bits per second, for 2.4 GHz 802.11n (11gn) radios. This value determines the baseline throughput or bandwidth allocation for the radio policy.";
    }
    leaf def-11an {
      type uint32 {
        range "15000 .. 400000000";
      }
      units "bps";
      default "400000000";
      description
        "Specifies the default policy rate, in bits per second, for 5 GHz 802.11n (11an) radios. This value determines the baseline throughput or bandwidth allocation for the radio policy.";
    }
    leaf def-11ac {
      type uint32 {
        range "15000 .. 1000000000";
      }
      units "bps";
      default "1000000000";
      description
        "Specifies the default policy rate, in bits per second, for 802.11ac radios. This value determines the baseline throughput or bandwidth allocation for the radio policy.";
    }
  }

  grouping st-80211be-mcs-key {
    description
      "802.11be MCS rates related configuration.";
    leaf spatial-stream {
      type uint8 {
        range "1 .. 4";
      }
      description
        "Spatial stream index for MCS data rate settings on the 802.11be radio.";
    }
    leaf index {
      type wireless-enum-types:dot11be-mcs-index;
      description
        "802.11be MCS rates. Key value is the spatial stream value.
         Possible values:
         dot11be-mcs-index-9  = MCS Data rate index 9 for 802.11be
         dot11be-mcs-index-11 = MCS Data rate index 11 for 802.11be
         dot11be-mcs-index-13 = MCS Data rate index 13 for 802.11be
         dot11be-mcs-index-14 = MCS Data rate index 14 for 802.11be
         dot11be-mcs-index-15 = MCS Data rate index 15 for 802.11be";
    }
  }

  grouping st-apf80211ax-mcs-key {
    description
      "802.11ax MCS rates related configuration.";
    leaf spatial-stream {
      type uint8 {
        range "1 .. 8";
      }
      description
        "Spatial stream index for MCS data rate settings on the 802.11ax band.";
    }
    leaf index {
      type wireless-enum-types:mcs-index;
      description
        "802.11ax MCS rates. Key value is the spatial stream value.
         Possible values:
         dot11ax-mcs-idx7  = MCS Data rate index 7 for dot11ax
         dot11ax-mcs-idx9  = MCS Data rate index 9 for dot11ax
         dot11ax-mcs-idx11 = MCS Data rate index 11 for dot11ax";
    }
  }

  grouping mcs-key-80211ac {
    description
      "802.11ac MCS rates related configuration.";
    leaf spatial-stream {
      type uint8 {
        range "1 .. 4";
      }
      description
        "Spatial stream number related to MCS data rate settings on the 802.11ac band.";
    }
    leaf index {
      type wireless-enum-types:dot11ac-mcs-rate-index;
      description
        "Specifies the Modulation and Coding Scheme (MCS) index for 802.11ac data rates. The index, combined with the spatial stream, identifies a specific MCS rate.";
    }
  }

  grouping st-80211be-mcs {
    description
      "802.11be MCS rate related configuration.";
    leaf be-mcs-tx-enable {
      type boolean;
      default "true";
      description
        "Enable configured MCS data rate.
         True - MCS data rate is enabled.
         False - MCS data rate is disabled.";
    }
  }

  grouping st-apf80211ax-mcs {
    description
      "802.11ax MCS rate related configuration.";
    leaf apf-80211ax-mcs-tx-enable {
      type boolean;
      default "true";
      description
        "80211ax MCS transit data rate.
         True - MCS data rate is enabled.
         False - MCS data rate is disabled.";
    }
  }

  grouping ac-mcs-80211 {
    description
      "MCS rates related configuration";
    leaf apf-80211ac-mcs-tx-enable {
      type boolean;
      default "true";
      description
        "802.11ac MCS data rate.
         True - MCS support is enabled.
         False - MCS support is disabled.";
    }
  }

  grouping ampdu-80211n {
    description
      "802.11n MSDU related configuration";
    leaf index {
      type uint8 {
        range "0 .. 7";
      }
      description
        "Unique index identifying an entry in the 802.11n A-MPDU configuration table.";
    }
    leaf apf-80211n-ampdu-tx-priority {
      type wireless-enum-types:apf-80211n-ampdu;
      default "apf-80211n-ampdu-invalid";
      description
        "802.11n-2.4 Ghz transmit A-MPDU.
         Possible values:
         apf-80211n-ampdu-disable - Transmit A-MPDU is disabled
         apf-80211n-ampdu-enable - Transmit A-MPDU is enabled
         apf-80211n-ampdu-invalid - Transmit A-MPDU is invalid";
    }
  }

  grouping ampdu-tx-scheduler {
    description
      "802.11n MSDU scheduler related configuration";
    leaf scheduler-enabled {
      type boolean;
      default "true";
      description
        "802.11n AMPDU scheduler is enabled.
         True -  Scheduler is enabled.
         False - Scheduler is disabled";
    }
    leaf rt-timeout {
      type uint32 {
        range "1 .. 1000";
      }
      default "10";
      description
        "A-MPDU transmit aggregation scheduler realtime traffic timeout in msec";
    }
    leaf frame-burst {
      when "(../../band = 'dot11-5-ghz-band')";
      type wireless-enum-types:frame-burst-mode;
      default "frame-burst-automatic";
      description
        "Optimal settings for bursting of 802.11n A-MPDUs.
         Possible values:
         frame-burst-automatic - Burst setting is automatic
         frame-burst-enabled - Burst setting is enabled
         frame-burst-disabled - Burst setting is disabled";
    }
  }

  grouping amsdu-11n {
    description
      "802.11n A-MSDU feature related configuration";
    leaf index {
      type uint8 {
        range "0 .. 7";
      }
      description
        "Spatial stream index. This is also the key to the A-mpdu configuration table";
    }
    leaf apf-80211n-amsdu-tx-priority {
      type wireless-enum-types:apf-80211n-amsdu;
      default "apf-80211n-amsdu-invalid";
      description
        "802.11n A-MSDU transmit priority
         Possible values:
         apf-80211n-amsdu-disable - Transmit priority is disabled
         apf-80211n-amsdu-enable - Transmit priority is enabled
         apf-80211n-amsdu-invalid - Transmit priority is invalid";
    }
  }

  grouping dot11 {
    description
      "802.11 related features";
    leaf band {
      type wireless-types:enm-ewlc-dot11-radio-band;
      description
        "Band to which the configuration belong to.
         dot11-2-dot-4ghz-band - Current operating band 2.4Ghz.
         dot11-5-ghz-band - Current operating band 5Ghz.";
    }
    leaf voice-adm-ctrl-support {
      type boolean;
      default "false";
      description
        "Admission control on voice access category.
         True - Voice traffic flowing through the 802.11a interfaces in the controller is enabled.
         False - Voice traffic flowing through the 802.11a interfaces in the controller is disabled.";
    }
    leaf video-adm-ctrl-support {
      type boolean;
      default "false";
      description
        "Admission control on video access category.
         True - Video traffic flowing through the 802.11a interfaces in the controller is enabled.
         False - Video traffic flowing through the 802.11a interfaces in the controller is disabled.";
    }
    leaf sip-cac-voice-sample-size {
      type uint8 {
        range "10 .. 80";
      }
      default "20";
      description
        "Voice sample size in milliseconds for SIP CAC configuration of the dot11 band for the APs associated with this controller.";
    }
    leaf sip-cac-config-bandwidth {
      type uint8 {
        range "8 .. 64";
      }
      default "64";
      description
        "Bandwidth in kbps for SIP CAC configuration of the dot11 band for the APs associated with this controller.";
    }
    leaf apf-network-state {
      type boolean;
      default "true";
      description
        "Indicates whether the 802.11 network is administratively enabled or disabled for this band. When set to true, the network is enabled; when set to false, the network is disabled.";
    }
    leaf apf-dot11g-supported {
      type boolean;
      default "true";
      description
        "802.11g protocol support also on the 802.11b network. Enabling 802.11g allows additional data rates: 6, 9, 12, 18, 24, 36, 48, 54 Mbps.";
    }
    leaf cac-voice-max-bandwidth {
      type uint8 {
        range "5 .. 85";
      }
      must '(../cac-voice-max-bandwidth + ../cac-video-max-bandwidth <= 85)' {
        error-message "Sum of voice bandwidth and video bandwidth exceeds limit";
        error-app-tag "must-violation";
      }
      default "75";
      description
        "Maximum bandwidth allocated to 802.11e clients.
         It is expressed as percentage of the total bandwidth of 802.11b network. The value of this attribute can vary from 0 to 100.";
    }
    leaf apf-dtpc {
      type boolean;
      default "true";
      description
        "Enables the DTPC support on all 802.11b/g radios.
         DTPC or Dynamic Transmit Power Control support means that the radio's transmit power will be advertised in the beacons and probe responses.";
    }
    leaf cac-video-max-bandwidth {
      type uint8 {
        range "5 .. 85";
      }
      default "5";
      description
        "Maximum bandwidth that can be allocated by controller for video traffic when admission control is enabled for 802.11a interfaces in the controller. When set to 0, all available bandwidth in 802.11a interfaces can be allocated to video traffic.";
    }
    leaf cac-voice-roam-bandwidth {
      type uint8 {
        range "0 .. 25";
      }
      default "6";
      description
        "Bandwidth relative to the maximum allocated bandwidth indicated by cac-voice-max-bandwidth, that can be allocated to roaming clients for voice traffic, when admission control is enabled for 802.11a interfaces in the controller.";
    }
    leaf cac-video-roam-bandwidth {
      type uint8 {
        range "0 .. 25";
      }
      default "0";
      description
        "Bandwidth relative to the maximum allocated bandwidth indicated by cac-video-max-bandwidth, that can be allocated to roaming clients for video traffic, when admission control is enabled for 802.11a interfaces in the controller.";
    }
    leaf tsm-enable {
      type boolean;
      default "false";
      description
        "802.11a traffic stream metrics support.
         True - Associated APs send the controller statistical data on traffic observed on their 802.11a interfaces in every 90 seconds.
         False - APs stop sending statistical data on the 802.11a interfaces to the controller.";
    }
    leaf exp-bandwidth-req-enable {
      type boolean;
      default "false";
      description
        "Expedited BW request support.
         True - APs advertise the expedited BW support in their beacons and association responses.
         False - APs do not advertise the expedited BW support in their beacons and association responses.";
    }
    leaf cac-voice-loadbased {
      type boolean;
      default "true";
      description
        "Enables or disables load-based Call Admission Control (CAC) for voice traffic. When enabled (true), the controller reserves and manages maximum and roaming bandwidth based on WLAN load. When disabled (false), the controller uses user-configured values for maximum (cac-voice-max-bandwidth) and roaming (cac-voice-roam-bandwidth) bandwidth. If ACM is disabled, admission control is not enforced, which may delay voice traffic depending on WLAN load.";
    }
    leaf cac-tspec-inactivity-timeout {
      type boolean;
      default "true";
      description
        "Enables or disables TSPEC inactivity timeout processing. When enabled, the controller will process inactivity timeouts for TSPEC streams, potentially releasing resources for inactive streams.";
    }
    leaf cac-stream-size {
      type uint32 {
        range "84000 .. 92100";
      }
      default "84000";
      description
        "Max data rate of the stream acceptable, between 84000 and 92100 range";
    }
    leaf cac-max-streams {
      type uint8 {
        range "1 .. 5";
      }
      default "2";
      description
        "Max number of streams per TSPEC";
    }
    leaf beamforming {
      type wireless-enum-types:nw-leg-beam-form;
      default "nw-leg-bf-disable";
      description
        "Status of legacy beam forming in this AP, applicable only for 11n supported APs.
         Possible values:
         nw-leg-bf-disable - Legacy beam forming is disabled for this AP
         nw-leg-bf-enable -  Legacy beam forming is enabled for this AP
         nw-leg-bf-na - Legacy beam forming is not applicable for this AP";
    }
    leaf world-mode-ie {
      type boolean;
      default "true";
      description
        "Indicates whether the World Mode Information Element (IE) should be included as part of the beacon frame.";
    }
    leaf cac-voice-sip {
      type boolean;
      default "false";
      description
        "Enables or disables Call Admission Control (CAC) for SIP-based voice traffic on this 802.11 band.";
    }
    leaf apf-dot11b-short-preamble {
      type boolean;
      default "true";
      description
        "Enables or disables the use of short preamble for 802.11b transmissions, which can improve throughput but may reduce compatibility with some legacy devices.";
    }
    leaf tx-power-control-threshold {
      type int8 {
        range "-80 .. -50";
      }
      default "-70";
      description
        "Global AP Transmit Power Threshold value. The permissible range is -80 dbm to -50 dbm";
    }
    leaf channel-aware-tpc {
      type boolean;
      default "false";
      description
        "Enables or disables channel-aware Transmit Power Control (TPC), allowing the TPC algorithm to adjust power levels based on channel conditions.";
    }
    container apf-dot11-default-cfg {
      description
        "Container for default configuration parameters for 802.11 operation on this band.";
      uses wireless-dot11-cfg:dot11-cfg;
    }
    container apf-dot11-capability {
      description
        "802.11 capabilities supported by the controller related configuration";
      uses wireless-dot11-cfg:dot11-80211-capability-config;
    }
    container ht-cfg {
      description
        "Container for configuration parameters related to the 802.11n (High Throughput) wireless protocol, including features and capabilities specific to 802.11n operation.";
      uses wireless-dot11-cfg:dot11-ht-config;
    }
    container dot11ac-cfg {
      description
        "Container for configuration parameters related to the 802.11ac (Very High Throughput) wireless protocol, including features and capabilities specific to 802.11ac operation.";
      uses wireless-dot11-cfg:dot11-dot11ac-config;
    }
    container dot11ax-cfg {
      description
        "Container for configuration parameters related to the 802.11ax (High Efficiency) wireless protocol, including features and capabilities specific to 802.11ax operation.";
      uses wireless-dot11-cfg:st-dot11-dot11ax-cfg-config;
    }
    container dot11h-cfg {
      description
        "Container for configuration parameters related to 802.11h, which provides spectrum and transmit power management features for wireless networks operating in the 5 GHz band.";
      uses wireless-dot11-cfg:dot11h-config;
    }
    container dot11-qos-pm {
      description
        "Container for configuration of radio policies related to 802.11 Quality of Service (QoS) and Power Management (PM) features.";
      uses wireless-dot11-cfg:dot11-80211-qos-pm-config;
    }
    leaf ate-oper-mode {
      type wireless-enum-types:apf-ate-mode;
      default "apf-atf-mode-disable";
      description
        "Sets the mode represented by radio type of ATF supported APs joined in the controller. Read operation may differ if config is overridden.
         Possible values:
         apf-atf-mode-disable - Oper mode is set to disabled
         apf-atf-mode-ssid - Oper mode is set to SSID
         apf-atf-mode-monitor - Oper mode is set to Monitor";
    }
    leaf ate-stealing {
      type wireless-enum-types:apf-ate-stealing-policy;
      default "apf-atf-stealing-policy-disable";
      description
        "Sets the mode represented by band of ATF supported APs joined in the controller. Read operation may differ if config is overridden.
         Possible values are:
         apf-atf-stealing-policy-disable - Stealing mode is set to disabled
         apf-atf-stealing-policy-enable - Stealing mode is set to enabled";
    }
    leaf g-edca {
      type wireless-enum-types:edca-profile;
      default "edca-wmm";
      description
        "EDCA profile to be used in EDCA Parameter set element.";
    }
    leaf medium-occupancy-limit {
      type uint32;
      default "100";
      description
        "Maximum amount of time, in TU, that a point coordinator may control the usage of the wireless medium without relinquishing control for long enough to allow at least one instance of DCF access to the medium. The default value of this attribute shall be 100, and the maximum value shall be 1000.";
    }
    leaf ed-threshold {
      type int32;
      default "-50";
      description
        "Current Energy Detect Threshold being used by the DSSS PHY";
    }
    leaf cfp-period {
      type uint32;
      default "4";
      description
        "Number of DTIM intervals between the start of CFPs. It is modified by MLME-START.request primitive.";
    }
    leaf cfp-max-duration {
      type uint32;
      default "60";
      description
        "Maximum duration of the CFP in TU that may be generated by the PCF. It is modified by MLME-START.request primitive.";
    }
    leaf rts-threshold {
      type uint32;
      default "2347";
      description
        "Number of octets in an MPDU, below which an RTS/CTS handshake shall not be performed.
         An RTS/CTS handshake shall be performed at the beginning of any frame exchange sequence where the MPDU is of type Data or Management, the MPDU has an individual address in the Address1 field, and the length of the MPDU is greater than this threshold. (For additional details, refer to Table 21 in 9.7.) Setting this attribute to be larger than the maximum MSDU size shall have the effect of turning off the RTS/CTS handshake for frames of Data or Management type transmitted by this STA. Setting this attribute to zero shall have the effect of turning on the RTS/CTS handshake for all frames of Data or Management type transmitted by this STA. The default value of this attribute shall be 2347.";
    }
    leaf cf-pollable {
      type boolean;
      default "false";
      description
        "Contention Free Poll with data frame.
         True - STA is able to respond to a CF-Poll with a data frame within a SIFS time.
         False - STA is not able to respond to a CF-Poll with a data frame within a SIFS time.";
    }
    leaf cf-poll-request {
      type boolean;
      default "false";
      description
        "Contention Free Poll request.
         True - CF-Poll is enabled.
         False - CF-Poll is disabled.";
    }
    leaf dtim-period {
      type uint32;
      default "1";
      description
        "Number of beacon intervals that shall elapse between transmission of Beacons frames containing a TIM element whose DTIM Count field is 0. This value is transmitted in the DTIM Period field of Beacon frames.";
    }
    leaf max-tx-power-level {
      type uint32;
      default "1";
      description
        "Maximum transmit power, in dBm, allowed in the subband for the associated domain country string. The default value of this attribute shall be zero.";
    }
    leaf short-retry-limit {
      type uint32;
      default "7";
      description
        "Maximum number of transmission attempts of a frame, the length of which is less than or equal to bsnGlobalDot11RTSThreshold, that shall be made before a failure condition is indicated. The default value of this attribute shall be 7.";
    }
    leaf long-retry-limit {
      type uint32;
      default "4";
      description
        "Maximum number of transmission attempts of a frame, the length of which is greater than bsnGlobalDot11RTSThreshold, that shall be made before a failure condition is indicated. The default value of this attribute shall be 4.";
    }
    leaf max-tx-msdu-lifetime {
      type uint32;
      default "512";
      description
        "MaxTransmitMSDULifetime shall be the elapsed time in TU, after the initial transmission of an MSDU, after which further attempts to transmit the MSDU shall be terminated. The default value of this attribute shall be 512.";
    }
    leaf max-rx-lifetime {
      type uint32;
      default "512";
      description
        "MaxReceiveLifetime shall be the elapsed time in TU, after the initial reception of a fragmented MMPDU or MSDU, after which further attempts to reassemble the MMPDU or MSDU shall be terminated. The default value shall be 512.";
    }
    leaf channel-agility {
      type boolean;
      default "false";
      description
        "PHY channel agility
         True - PHY channel agility is enabled.
         False - PHY channel agility is disabled.";
    }
    container ampdu-entries {
      description
        "Container for configuration settings related to 802.11n Aggregated MAC Protocol Data Unit (A-MPDU) features, such as enabling/disabling aggregation and tuning related parameters.";
      list ampdu-entry {
        key "index";
        description
          "List of configuration related to 802.11n A-MPDU";
        uses wireless-dot11-cfg:ampdu-80211n;
      }
    }
    container ampdu-tx-scheduler {
      presence "ampdu-tx-scheduler";
      description
        "List of configuration related to 802.11n A-MPDU transmit scheduler";
      uses wireless-dot11-cfg:ampdu-tx-scheduler;
    }
    container amsdu-entries {
      description
        "Container for configuration settings related to 802.11n Aggregated MAC Service Data Unit (A-MSDU) features, such as enabling/disabling aggregation and tuning related parameters.";
      list amsdu-entry {
        key "index";
        description
          "List of configuration related to 802.11n A-MSDU";
        uses wireless-dot11-cfg:amsdu-11n;
      }
    }
    container media-stream-band-info-cfg {
      presence "mediaStreamBandInfo";
      description
        "Configuration container for media stream parameters specific to a wireless band, including settings for multicast and video streams.";
      uses wireless-dot11-cfg:media-stream-band-info;
    }
    container spectrum-cfg {
      presence "spectrum-cfg";
      description
        "Configuration container for CleanAir features, which provide spectrum intelligence and interference mitigation for the specified 802.11 band.";
      uses wireless-dot11-cfg:spectrum-cfg;
    }
    container dot11ax-mcs-entries {
      description
        "Container for configuration settings related to 802.11ax Modulation and Coding Scheme (MCS) data rates for wireless networks.";
      list dot11ax-mcs-entry {
        key "spatial-stream index";
        description
          "Configuration for a specific 802.11ax Modulation and Coding Scheme (MCS) entry, identified by spatial stream and MCS index.";
        uses wireless-dot11-cfg:st-apf80211ax-mcs-key;
        uses wireless-dot11-cfg:st-apf80211ax-mcs;
      }
    }
    leaf cac-max-calls {
      type uint32;
      description
        "Specifies the maximum number of calls allowed by Call Admission Control (CAC) on this 802.11 band.";
    }
    leaf cell-handoff-rssi-thold {
      type int8;
      units "dBm";
      must '(../cell-handoff-rssi-thold <= -80 and ../cell-handoff-rssi-thold >= -90)' {
        error-message "Invalid input value";
        error-app-tag "must-violation";
      }
      default "-85";
      description
        "RSSI threshold value to trigger WiFi to Cellular steering";
    }
    leaf edca-client-load-based {
      type boolean;
      default "true";
      description
        "Client load-based EDCA on this band.
         True - Client load-based EDCA is enabled.
         False - Client load-based EDCA is disabled.";
    }
    container dot11be-cfg {
      description
        "Container for configuration settings related to the 802.11be (Wi-Fi 7) protocol on this band.";
      uses wireless-dot11-cfg:dot11-eht-config;
    }
    container dot11be-mcs-entries {
      description
        "Container for configuration settings related to Modulation and Coding Scheme (MCS) rates for 802.11be (Wi-Fi 7) radios.";
      list dot11be-mcs-entry {
        key "spatial-stream index";
        description
          "Configuration for a specific Modulation and Coding Scheme (MCS) entry for 802.11be, identified by spatial stream and MCS index.";
        uses wireless-dot11-cfg:st-80211be-mcs-key;
        uses wireless-dot11-cfg:st-80211be-mcs;
      }
    }
  }

  grouping spectrum-cfg {
    description
      "Clean Air related configuration. This node cannot be configured";
    leaf spectrum-admin-state-set {
      type boolean;
      default "true";
      description
        "Clean Air (CA) on this band.
         True - CA is enabled.
         False - CA is disabled.";
    }
    leaf si-admin-state-set {
      type boolean;
      default "false";
      description
        "Spectrum Intelligence (SI) on this band.
         True - SI is enabled.
         False - SI is disabled.";
    }
    leaf dev-report-state-set {
      type boolean;
      default "true";
      description
        "Device reporting state on this band.
         True - Device Reporting state is enabled.
         False - Device Reporting state is disabled.";
    }
    leaf aq-polling-period {
      type uint8;
      units "minutes";
      default "15";
      description
        "Specifies the polling interval, in minutes, for collecting Air Quality metrics on this 802.11 band.";
    }
    leaf id-report-enable {
      type boolean;
      default "false";
      description
        "IDR Reporting is on this band.
         True - IDR is enabled.
         False - IDR is disabled.";
    }
    leaf id-report-period {
      type uint8;
      default "90";
      description
        "Interferer reporting period, this is fixed at 90 seconds";
    }
    leaf aq-report-enable {
      type boolean;
      default "false";
      status deprecated;
      description
        "Air Quality Reporting on this band.
         True - Air Quality Reporting is enabled.
         False - Air Quality Reporting is disabled.";
    }
    leaf aq-alarm-mode {
      type boolean;
      default "false";
      description
        "Air Quality notification on this band.
         True - AQ notification is enabled.
         False - AQ notification is disabled.";
    }
    leaf aq-alarm-threshold {
      type uint8 {
        range "1 .. 100";
      }
      default "10";
      description
        "Specifies the air quality threshold value that, when exceeded, triggers an SNMP trap notification for spectrum events on this band.";
    }
    leaf dev-alarm-mode {
      type boolean;
      default "false";
      description
        "IDR notification on this band.
         True - IDR notification is enabled.
         False - IDR notification is disabled.";
    }
    leaf rrm-ed-enable {
      type boolean;
      default "false";
      description
        "Event driven RRM on this band.
         True - Event driven RRM is enabled.
         False - Event driven RRM is disabled.";
    }
    leaf rrm-ed-threshold-level {
      type wireless-enum-types:rrm-ed-threshold-level;
      default "rrm-cleanair-event-low";
      description
        "Event driven RRM threshold level.
         'low' - low level event driven RRM threshold value
         'medium' - medium level event driven RRM threshold value
         'high' - high level event driven RRM threshold value
         'custom' - user specified value of even driven RRM threshold";
    }
    leaf rrm-ed-custom-threshold-value {
      type uint32 {
        range "1 .. 99";
      }
      default "1";
      description
        "Event driven RRM Custom threshold value. This object only takes effect when the value of rrm-ed-threshold-level is 'custom'.";
    }
    leaf rrm-ed-rogue-enable {
      type boolean;
      default "false";
      description
        "Event driven RRM rogue contribution on this band.
         True - Rogue contribution is enabled.
         False - Rogue contribution is disabled.";
    }
    leaf rrm-ed-rogue {
      type uint8 {
        range "1 .. 99";
      }
      default "80";
      description
        "Specifies the duty cycle threshold value for rogue device contribution in event-driven Radio Resource Management (RRM) on this band.";
    }
    leaf idrv-period {
      type uint8;
      units "seconds";
      default "20";
      description
        "Specifies the reporting period, in seconds, for interferer device reports on this band.";
    }
    leaf aq-alarm2-control {
      type boolean;
      default "false";
      description
        "Enables or disables the air quality alarm when the severity for the unclassified interference category exceeds the configured threshold.";
    }
    leaf aq-alarm2-threshold {
      type uint8 {
        range "1 .. 100";
      }
      default "35";
      description
        "Config air quality alarm threshold for unclassified category severity, range 1(low) - 100(high)";
    }
    leaf cleanair-dev-all-mode {
      type boolean;
      default "true";
      description
        "Detection of all given interferer types on CleanAIR capable access points on this band.
         True - CleanAIR capable access points is enabled.
         False - CleanAIR capable access points is disabled.";
    }
    leaf rrm-pd-propagation {
      type boolean;
      default "false";
      description
        "Persistent Device Propagation to neighboring access points on this band.
         True - Persistent Device Propagation is enabled.
         False - Persistent Device Propagation is disabled.";
    }
    leaf cleanair-device-bt-link-mode {
      type boolean;
      default "true";
      description
        "Detection of bluetooth link device on CleanAIR capable access points on this band.
         True - CleanAIR capable access points is enabled.
         False - CleanAIR capable access points is disabled.";
    }
    leaf device-bt-link-mode {
      type boolean;
      default "false";
      description
        "Alarm for reporting bluetooth link on CleanAIR capable access points on this band.
         True - CleanAIR capable access points is enabled.
         False - CleanAIR capable access points is disabled.";
    }
    leaf cleanair-device-mw-oven-mode {
      type boolean;
      default "true";
      description
        "Detection of microwave oven interferer device types on CleanAIR capable access points on this band.
         True - CleanAIR capable access points is enabled.
         False - CleanAIR capable access points is disabled.";
    }
    leaf device-mw-oven-mode {
      type boolean;
      default "false";
      description
        "Alarm for reporting microwave oven on CleanAIR capable access points on this band.
         True - CleanAIR capable access points is enabled.
         False - CleanAIR capable access points is disabled.";
    }
    leaf cleanair-dev802fh-mode {
      type boolean;
      default "true";
      description
        "Enables or disables detection of frequency hopping 802.11-compliant devices on CleanAIR-capable access points for this band. When set to true, detection is enabled; when set to false, detection is disabled.";
    }
    leaf dev802fh-mode {
      type boolean;
      default "false";
      description
        "Enables or disables alarm reporting for frequency hopping 802.11-compliant device detection on CleanAIR-capable access points for this band. When set to true, the alarm is enabled; when set to false, the alarm is disabled.";
    }
    leaf cleanair-device-bt-discovery-mode {
      type boolean;
      default "true";
      description
        "Detection of bluetooth device on CleanAIR capable access points on this band.
         True - CleanAIR capable access points is enabled.
         False - CleanAIR capable access points is disabled.";
    }
    leaf device-bt-discovery-mode {
      type boolean;
      default "false";
      description
        "Alarm for reporting bluetooth on CleanAIR capable access points on this band.
         True - CleanAIR capable access points is enabled.
         False - CleanAIR capable access points is disabled.";
    }
    leaf cleanair-device-tddtx-mode {
      type boolean;
      default "true";
      description
        "Detection of time division duplex transmitter device on CleanAIR capable access points on this band.
         True - CleanAIR capable access points is enabled.
         False - CleanAIR capable access points is disabled.";
    }
    leaf device-tddtx-mode {
      type boolean;
      default "false";
      description
        "Alarm for reporting time division duplex transmitter on CleanAIR capable access points on this band.
         True - CleanAIR capable access points is enabled.
         False - CleanAIR capable access points is disabled.";
    }
    leaf cleanair-device-jammer-mode {
      type boolean;
      default "true";
      description
        "Detection of jammer device on CleanAIR capable access points on this band.
         True - CleanAIR capable access points is enabled.
         False - CleanAIR capable access points is disabled.";
    }
    leaf device-jammer-mode {
      type boolean;
      default "false";
      description
        "Alarm for reporting jammer on CleanAIR capable access points on this band.
         True - CleanAIR capable access points is enabled.
         False - CleanAIR capable access points is disabled.";
    }
    leaf cleanair-device-conttx-mode {
      type boolean;
      default "true";
      description
        "Detection of continuous transmitter device on CleanAIR capable access points on this band.
         True - CleanAIR capable access points is enabled.
         False - CleanAIR capable access points is disabled.";
    }
    leaf device-conttx-mode {
      type boolean;
      default "false";
      description
        "Alarm for reporting continuous transmitter on CleanAIR capable access points on this band.
         True - CleanAIR capable access points is enabled.
         False - CleanAIR capable access points is disabled.";
    }
    leaf cleanair-device-dect-like-mode {
      type boolean;
      default "true";
      description
        "Detection of DECT like device on CleanAIR capable access points on this band.
         True - CleanAIR capable access points is enabled.
         False - CleanAIR capable access points is disabled.";
    }
    leaf device-dect-like-mode {
      type boolean;
      default "false";
      description
        "Enables or disables alarm reporting for detected DECT-like devices on CleanAIR-capable access points for this band. When set to true, alarm reporting is enabled; when set to false, alarm reporting is disabled.";
    }
    leaf cleanair-device-video-mode {
      type boolean;
      default "true";
      description
        "Detection of video camera device on CleanAIR capable access points on this band.
         True - CleanAIR capable access points is enabled.
         False - CleanAIR capable access points is disabled.";
    }
    leaf device-video-mode {
      type boolean;
      default "false";
      description
        "Alarm for reporting video camera on CleanAIR capable access points on this band.
         True - CleanAIR capable access points is enabled.
         False - CleanAIR capable access points is disabled.";
    }
    leaf cleanair-device-zig-bee-mode {
      type boolean;
      default "true";
      description
        "Detection of zigbee device on CleanAIR capable access points on this band.
         True - CleanAIR capable access points is enabled.
         False - CleanAIR capable access points is disabled.";
    }
    leaf device-zig-bee-mode {
      type boolean;
      default "false";
      description
        "Alarm for reporting zigbee on CleanAIR capable access points on this band.
         True - CleanAIR capable access points is enabled.
         False - CleanAIR capable access points is disabled.";
    }
    leaf cleanair-device-inv-mode {
      type boolean;
      default "true";
      description
        "Detection of spectrally inverted wifi signal device on CleanAIR capable access points on this band.
         True - CleanAIR capable access points is enabled.
         False - CleanAIR capable access points is disabled.";
    }
    leaf device-inv-mode {
      type boolean;
      default "false";
      description
        "Alarm for reporting spectrally inverted wifi signal on CleanAIR capable access points on this band.
         True - CleanAIR capable access points is enabled.
         False - CleanAIR capable access points is disabled.";
    }
    leaf cleanair-device-nonstd-mode {
      type boolean;
      default "true";
      description
        "Detection of device using non standard wifi channels on CleanAIR capable access points on this band.
         True - CleanAIR capable access points is enabled.
         False - CleanAIR capable access points is disabled.";
    }
    leaf device-nonstd-mode {
      type boolean;
      default "false";
      description
        "Enables or disables the alarm for reporting detection of devices using non-standard Wi-Fi channels on CleanAIR-capable access points for this band. When set to true, the alarm is enabled; when set to false, the alarm is disabled.";
    }
    leaf cleanair-device-superag-mode {
      type boolean;
      default "true";
      description
        "Detection of superAG device on CleanAIR capable access points on this band.
         True - CleanAIR capable access points is enabled.
         False - CleanAIR capable access points is disabled.";
    }
    leaf device-superag-mode {
      type boolean;
      default "false";
      description
        "Alarm for reporting superAG on CleanAIR capable access points on this band.
         True - CleanAIR capable access points is enabled.
         False - CleanAIR capable access points is disabled.";
    }
    leaf cleanair-device-canopy-mode {
      type boolean;
      default "true";
      description
        "Detection of canopy device on CleanAIR capable access points on this band.
         True - CleanAIR capable access points is enabled.
         False - CleanAIR capable access points is disabled.";
    }
    leaf device-canopy-mode {
      type boolean;
      default "false";
      description
        "Alarm for reporting canopy on CleanAIR capable access points on this band.
         True - CleanAIR capable access points is enabled.
         False - CleanAIR capable access points is disabled.";
    }
    leaf cleanair-device-xbox-mode {
      type boolean;
      default "true";
      description
        "Enables or disables detection of Xbox devices on CleanAIR-capable access points for this band. When set to true, detection is enabled; when set to false, detection is disabled.";
    }
    leaf device-xbox-mode {
      type boolean;
      default "false";
      description
        "Enables or disables the alarm for reporting Xbox device detection on CleanAIR-capable access points for this band. When set to true, the alarm is enabled; when set to false, the alarm is disabled.";
    }
    leaf cleanair-device-wimax-mobile-mode {
      type boolean;
      default "true";
      description
        "Enables or disables detection of WiMAX mobile devices on CleanAIR-capable access points for this band. When set to true, detection is enabled; when set to false, detection is disabled.";
    }
    leaf device-wimax-mobile-mode {
      type boolean;
      default "false";
      description
        "Enables or disables the alarm for reporting WiMAX mobile device detection on CleanAIR-capable access points for this band. When set to true, the alarm is enabled; when set to false, the alarm is disabled.";
    }
    leaf cleanair-device-wimax-fixed-mode {
      type boolean;
      default "true";
      description
        "Enables or disables detection of WiMAX fixed devices on CleanAIR-capable access points for this band. When set to true, detection is enabled; when set to false, detection is disabled.";
    }
    leaf device-wimax-fixed-mode {
      type boolean;
      default "false";
      description
        "Enables or disables the alarm for reporting WiMAX fixed device detection on CleanAIR-capable access points for this band. When set to true, the alarm is enabled; when set to false, the alarm is disabled.";
    }
    leaf cleanair-device-ble-beacon-mode {
      type boolean;
      default "false";
      description
        "Enables or disables detection of BLE beacon devices on CleanAIR-capable access points for this band. When set to true, detection is enabled; when set to false, detection is disabled.";
    }
    leaf device-ble-beacon-mode {
      type boolean;
      default "false";
      description
        "Enables or disables the alarm for reporting BLE beacon device detection on CleanAIR-capable access points for this band. When set to true, the alarm is enabled; when set to false, the alarm is disabled.";
    }
    leaf si-device-fhss-mode {
      type boolean;
      default "true";
      description
        "Enables or disables detection of FHSS devices on SI-capable access points for this band. When set to true, detection is enabled; when set to false, detection is disabled.";
    }
    leaf device-fhss-mode {
      type boolean;
      default "false";
      description
        "Enables or disables the alarm for reporting FHSS device detection on SI-capable access points for this band. When set to true, the alarm is enabled; when set to false, the alarm is disabled.";
    }
  }

  grouping media-stream-band-info {
    description
      "Media stream band info related configuration.";
    leaf multicast-direct {
      type boolean;
      default "false";
      description
        "Decision flag to allow multicast direct stream on radio.";
    }
    leaf multicast-direct-adm-best-effort {
      type boolean;
      default "false";
      description
        "Admit a media stream in best effort queue.";
    }
    leaf video-redirect {
      type boolean;
      default "false";
      description
        "A unicast or multicast only video stream can be redirected to best effort.";
    }
    leaf cac-mmedia-max-bw {
      type uint32 {
        range "5 .. 85";
      }
      default "85";
      description
        "Maximum allowed bandwidth for media traffic.";
    }
    leaf cac-mstream-mdirect-min-client-rate {
      type wireless-enum-types:dot11-min-phy-rate;
      default "six";
      description
        "Minimum client rate for multicast direct streams.";
    }
    leaf cac-mstream-mdirect-max-retry-percent {
      type uint32 {
        range "0 .. 100";
      }
      default "80";
      description
        "Maximum retry percent for multicast direct streams.";
    }
    leaf mdirect-max-stream-per-radio {
      type uint32 {
        range "0 .. 20";
      }
      default "0";
      description
        "Maximum number of allowed streams per radio for a 802.11 band.";
    }
    leaf mdirect-max-stream-per-client {
      type uint32 {
        range "0 .. 15";
      }
      default "0";
      description
        "Maximum number of allowed streams per client for a 802.11 band.";
    }
  }

  grouping st-configured-country {
    description
      "country code configuration";
    leaf country-code {
      type wireless-enum-types:country-code;
      must "(../country-code = 'ad' or
             ../country-code = 'ae' or
             ../country-code = 'af' or
             ../country-code = 'ag' or
             ../country-code = 'ai' or
             ../country-code = 'al' or
             ../country-code = 'am' or
             ../country-code = 'an' or
             ../country-code = 'ao' or
             ../country-code = 'aq' or
             ../country-code = 'ar' or
             ../country-code = 'as' or
             ../country-code = 'at' or
             ../country-code = 'au' or
             ../country-code = 'aw' or
             ../country-code = 'ax' or
             ../country-code = 'az' or
             ../country-code = 'ba' or
             ../country-code = 'bb' or
             ../country-code = 'bd' or
             ../country-code = 'be' or
             ../country-code = 'bf' or
             ../country-code = 'bg' or
             ../country-code = 'bh' or
             ../country-code = 'bi' or
             ../country-code = 'bj' or
             ../country-code = 'bl' or
             ../country-code = 'bm' or
             ../country-code = 'bn' or
             ../country-code = 'bo' or
             ../country-code = 'bq' or
             ../country-code = 'br' or
             ../country-code = 'bt' or
             ../country-code = 'bu' or
             ../country-code = 'bv' or
             ../country-code = 'bw' or
             ../country-code = 'by' or
             ../country-code = 'bz' or
             ../country-code = 'ca' or
             ../country-code = 'cc' or
             ../country-code = 'cd' or
             ../country-code = 'cf' or
             ../country-code = 'cg' or
             ../country-code = 'ch' or
             ../country-code = 'ci' or
             ../country-code = 'ck' or
             ../country-code = 'cl' or
             ../country-code = 'cm' or
             ../country-code = 'cn' or
             ../country-code = 'co' or
             ../country-code = 'cr' or
             ../country-code = 'cu' or
             ../country-code = 'cv' or
             ../country-code = 'cw' or
             ../country-code = 'cx' or
             ../country-code = 'cy' or
             ../country-code = 'cz' or
             ../country-code = 'de' or
             ../country-code = 'dj' or
             ../country-code = 'dk' or
             ../country-code = 'dm' or
             ../country-code = 'do' or
             ../country-code = 'dz' or
             ../country-code = 'ec' or
             ../country-code = 'ee' or
             ../country-code = 'eg' or
             ../country-code = 'eh' or
             ../country-code = 'el' or
             ../country-code = 'er' or
             ../country-code = 'es' or
             ../country-code = 'et' or
             ../country-code = 'fi' or
             ../country-code = 'fj' or
             ../country-code = 'fk' or
             ../country-code = 'fm' or
             ../country-code = 'fo' or
             ../country-code = 'fr' or
             ../country-code = 'ga' or
             ../country-code = 'gb' or
             ../country-code = 'gd' or
             ../country-code = 'ge' or
             ../country-code = 'gf' or
             ../country-code = 'gg' or
             ../country-code = 'gh' or
             ../country-code = 'gi' or
             ../country-code = 'gl' or
             ../country-code = 'gm' or
             ../country-code = 'gn' or
             ../country-code = 'gp' or
             ../country-code = 'gq' or
             ../country-code = 'gr' or
             ../country-code = 'gs' or
             ../country-code = 'gt' or
             ../country-code = 'gu' or
             ../country-code = 'gw' or
             ../country-code = 'gy' or
             ../country-code = 'hk' or
             ../country-code = 'hm' or
             ../country-code = 'hn' or
             ../country-code = 'hr' or
             ../country-code = 'ht' or
             ../country-code = 'hu' or
             ../country-code = 'ib' or
             ../country-code = 'id' or
             ../country-code = 'ie' or
             ../country-code = 'il' or
             ../country-code = 'im' or
             ../country-code = 'in' or
             ../country-code = 'io' or
             ../country-code = 'iq' or
             ../country-code = 'ir' or
             ../country-code = 'is' or
             ../country-code = 'it' or
             ../country-code = 'je' or
             ../country-code = 'jm' or
             ../country-code = 'jo' or
             ../country-code = 'j2' or
             ../country-code = 'j4' or
             ../country-code = 'ke' or
             ../country-code = 'kg' or
             ../country-code = 'kh' or
             ../country-code = 'ki' or
             ../country-code = 'km' or
             ../country-code = 'kn' or
             ../country-code = 'kp' or
             ../country-code = 'kw' or
             ../country-code = 'ky' or
             ../country-code = 'kz' or
             ../country-code = 'la' or
             ../country-code = 'lb' or
             ../country-code = 'lc' or
             ../country-code = 'li' or
             ../country-code = 'lk' or
             ../country-code = 'lr' or
             ../country-code = 'ls' or
             ../country-code = 'lt' or
             ../country-code = 'lu' or
             ../country-code = 'lv' or
             ../country-code = 'ly' or
             ../country-code = 'ma' or
             ../country-code = 'mc' or
             ../country-code = 'md' or
             ../country-code = 'me' or
             ../country-code = 'mf' or
             ../country-code = 'mg' or
             ../country-code = 'mh' or
             ../country-code = 'mk' or
             ../country-code = 'ml' or
             ../country-code = 'mm' or
             ../country-code = 'mn' or
             ../country-code = 'mo' or
             ../country-code = 'mp' or
             ../country-code = 'mq' or
             ../country-code = 'mr' or
             ../country-code = 'ms' or
             ../country-code = 'mt' or
             ../country-code = 'mu' or
             ../country-code = 'mv' or
             ../country-code = 'mw' or
             ../country-code = 'mx' or
             ../country-code = 'my' or
             ../country-code = 'mz' or
             ../country-code = 'na' or
             ../country-code = 'nc' or
             ../country-code = 'ne' or
             ../country-code = 'nf' or
             ../country-code = 'ng' or
             ../country-code = 'ni' or
             ../country-code = 'nk' or
             ../country-code = 'nl' or
             ../country-code = 'no' or
             ../country-code = 'np' or
             ../country-code = 'nr' or
             ../country-code = 'nu' or
             ../country-code = 'nz' or
             ../country-code = 'om' or
             ../country-code = 'pa' or
             ../country-code = 'pe' or
             ../country-code = 'pf' or
             ../country-code = 'pg' or
             ../country-code = 'ph' or
             ../country-code = 'pk' or
             ../country-code = 'pl' or
             ../country-code = 'pm' or
             ../country-code = 'pn' or
             ../country-code = 'pr' or
             ../country-code = 'pt' or
             ../country-code = 'pw' or
             ../country-code = 'py' or
             ../country-code = 'qa' or
             ../country-code = 're' or
             ../country-code = 'ro' or
             ../country-code = 'rs' or
             ../country-code = 'ru' or
             ../country-code = 'rw' or
             ../country-code = 'sa' or
             ../country-code = 'sb' or
             ../country-code = 'sc' or
             ../country-code = 'sd' or
             ../country-code = 'se' or
             ../country-code = 'sg' or
             ../country-code = 'sh' or
             ../country-code = 'si' or
             ../country-code = 'sj' or
             ../country-code = 'sk' or
             ../country-code = 'sl' or
             ../country-code = 'sm' or
             ../country-code = 'sn' or
             ../country-code = 'so' or
             ../country-code = 'sr' or
             ../country-code = 'ss' or
             ../country-code = 'st' or
             ../country-code = 'sx' or
             ../country-code = 'sy' or
             ../country-code = 'sz' or
             ../country-code = 'tc' or
             ../country-code = 'td' or
             ../country-code = 'tf' or
             ../country-code = 'tg' or
             ../country-code = 'th' or
             ../country-code = 'ti' or
             ../country-code = 'tj' or
             ../country-code = 'tk' or
             ../country-code = 'tl' or
             ../country-code = 'tm' or
             ../country-code = 'tn' or
             ../country-code = 'to' or
             ../country-code = 'tr' or
             ../country-code = 'tv' or
             ../country-code = 'tw' or
             ../country-code = 'tz' or
             ../country-code = 'ua' or
             ../country-code = 'ug' or
             ../country-code = 'um' or
             ../country-code = 'us' or
             ../country-code = 'uy' or
             ../country-code = 'uz' or
             ../country-code = 'va' or
             ../country-code = 'vc' or
             ../country-code = 've' or
             ../country-code = 'vg' or
             ../country-code = 'vi' or
             ../country-code = 'vn' or
             ../country-code = 'vu' or
             ../country-code = 'wf' or
             ../country-code = 'ws' or
             ../country-code = 'xk' or
             ../country-code = 'xx' or
             ../country-code = 'ye' or
             ../country-code = 'yt' or
             ../country-code = 'za' or
             ../country-code = 'zm' or
             ../country-code = 'zw')" {
        error-message "Unsupported Country. Please configure supported country.";
        error-app-tag "must-violation";
      }
      description
        "Specifies the two-letter ISO country code used to define the regulatory domain for wireless operation.";
    }
  }

  container dot11-cfg-data {
    description
      "Root container for configuration settings related to 802.11 (Wi-Fi) features, including protocol, country codes, and MCS rates.";
    container configured-countries {
      description
        "Container for configuration of country codes used to define regulatory domains for wireless operation.";
      list configured-country {
        key "country-code";
        description
          "List of configured country codes";
        uses wireless-dot11-cfg:st-configured-country;
      }
    }
    container dot11ac-mcs-entries {
      description
        "802.11ac MCS rates related configuration.";
      list dot11ac-mcs-entry {
        key "spatial-stream index";
        description
          "802.11ac MCS rates related configuration";
        uses wireless-dot11-cfg:mcs-key-80211ac;
        uses wireless-dot11-cfg:ac-mcs-80211;
      }
    }
    container dot11-entries {
      description
        "Container for configuration settings related to 802.11 protocol parameters, such as operational modes and features.";
      list dot11-entry {
        key "band";
        description
          "List of 802.11 protocol configuration entries, each corresponding to a specific radio band (e.g., 2.4 GHz or 5 GHz), containing settings for wireless operation on that band.";
        uses wireless-dot11-cfg:dot11;
      }
    }
  }
}
