module Cisco-IOS-XE-rawsocket-oper {
  yang-version 1.1;
  namespace "http://cisco.com/ns/yang/Cisco-IOS-XE-rawsocket-oper";
  prefix raw-socket-ios-xe-oper;

  import Cisco-IOS-XE-common-types {
    prefix common-types-ios-xe;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Rawsocket operational data.
     Copyright (c) 2019, 2025-2026 by Cisco Systems, Inc.
     All rights reserved.";

  revision 2026-08-01 {
    description
      "Updated descriptions for several model elements to clarify their meaning and purpose";
    reference
      "1.3.0";
    cisco-semver:module-version "1.3.0";
  }
  revision 2026-02-01 {
    description
      "- The rs-udp-stats list is deprecated to prevent the reuse of
         shared statistics group between UDP and TCP protocols.
       - Introduced a new UDP protocol specific statistics list with
         VRF handling as per instance type oper model flow";
    reference
      "1.2.0";
    cisco-semver:module-version "1.2.0";
  }
  revision 2022-11-01 {
    description
      "Update yang-version to 1.1";
    reference
      "1.1.0";
    cisco-semver:module-version "1.1.0";
  }
  revision 2020-03-01 {
    description
      "Initial revision";
    reference
      "1.0.0";
    cisco-semver:module-version "1.0.0";
  }

  typedef rs-mode {
    type enumeration {
      enum rs-mode-server {
        value 0;
        description
          "Server mode";
      }
      enum rs-mode-client {
        value 1;
        description
          "Client mode";
      }
    }
    description
      "Mode of operation for the connection";
  }

  typedef rs-state {
    type enumeration {
      enum rs-state-down {
        value 0;
        description
          "State DOWN";
      }
      enum rs-state-up {
        value 1;
        description
          "State UP";
      }
    }
    description
      "State of the connection";
  }

  grouping connection-stats {
    description
      "Connection statistics for a line";
    leaf async-line {
      type string;
      description
        "Name of the async line";
    }
    leaf tty {
      type uint32;
      description
        "Identifier of the terminal (TTY) interface associated with the asynchronous serial line";
    }
    leaf vrf {
      type string;
      description
        "VRF name";
    }
    leaf num-sessions {
      type uint32;
      description
        "Number of active sessions";
    }
    leaf tcp-in-bytes {
      type uint64;
      units "bytes";
      description
        "Total number of bytes received over TCP for the associated asynchronous serial line";
    }
    leaf tcp-out-bytes {
      type uint64;
      units "bytes";
      description
        "Total number of bytes sent over TCP for the associated asynchronous serial line";
    }
    leaf tcp-to-tty-frames {
      type uint64;
      units "frames";
      description
        "Total number of TCP frames sent to the terminal (TTY) interface for the associated asynchronous serial line";
    }
    leaf tty-to-tcp-frames {
      type uint64;
      description
        "Total TCP frames received from TTY";
    }
  }

  grouping rs-session-info-key {
    description
      "Session information list key";
    leaf async-line {
      type string;
      description
        "Name of the async line";
    }
    leaf destination-ip {
      type inet:ip-address;
      description
        "Destination IP for the connection";
    }
    leaf destination-port {
      type uint16;
      description
        "Destination port for the connection";
    }
  }

  grouping rs-session-info-params {
    description
      "Session information parameters";
    leaf tty {
      type uint32;
      description
        "Identifier of the terminal (TTY) interface associated with the session";
    }
    leaf vrf {
      type string;
      description
        "VRF name";
    }
    leaf idle-timeout {
      type uint32;
      description
        "Idle timeout for the connection (in minutes)";
    }
    leaf mode {
      type raw-socket-ios-xe-oper:rs-mode;
      description
        "Mode of operation";
    }
    leaf local-ip {
      type inet:ip-address;
      description
        "Local IP for the connection";
    }
    leaf local-port {
      type uint16;
      description
        "Local port for the connection";
    }
    leaf socket {
      type uint32;
      description
        "Data socket associated with the connection";
    }
    leaf start-time {
      type yang:date-and-time;
      description
        "Timestamp indicating when the session was established";
    }
    leaf last-active-time {
      type yang:date-and-time;
      description
        "Timestamp of the last activity detected on the session";
    }
  }

  grouping rs-client-state-key {
    description
      "Client state key";
    leaf async-line {
      type string;
      description
        "Name of the async line";
    }
    leaf destination-ip {
      type inet:ip-address;
      description
        "Destination IP for the connection";
    }
    leaf destination-port {
      type uint16;
      description
        "Destination port for the connection";
    }
  }

  grouping rs-client-state-params {
    description
      "Client state parameters";
    leaf tty {
      type uint32;
      description
        "TTY ID";
    }
    leaf local-ip {
      type inet:ip-address;
      description
        "Local IP for the connection";
    }
    leaf local-port {
      type uint16;
      description
        "Local port for the connection";
    }
    leaf state {
      type raw-socket-ios-xe-oper:rs-state;
      description
        "Operational state of the Rawsocket client connection";
    }
  }

  grouping udp-con-stats {
    description
      "UDP Connection statistics for a line";
    leaf async-line {
      type string;
      description
        "Name of the async line";
    }
    leaf tty {
      type uint32;
      description
        "TTY identifier. Unique terminal interface
         associated with async serial line";
    }
    leaf ni-type {
      type common-types-ios-xe:net-inst-type;
      description
        "Network instance type. Differentiates between the
         default routing instance and VRFs";
    }
    leaf ni-name {
      type string;
      description
        "Network instance name. If the Network instance
         type is net-inst-default, then name is not meaningful";
    }
    leaf num-sessions {
      type uint32;
      description
        "Number of active sessions";
    }
    leaf udp-in-bytes {
      type uint64;
      description
        "Total input bytes";
    }
    leaf udp-out-bytes {
      type uint64;
      description
        "Total output bytes";
    }
    leaf udp-to-tty-frames {
      type uint64;
      description
        "Total UDP frames sent to TTY";
    }
    leaf tty-to-udp-frames {
      type uint64;
      description
        "Total UDP frames received from TTY";
    }
  }

  grouping tcp {
    description
      "Rawsocket TCP Operational Data";
    list rs-tcp-stats {
      key "async-line";
      description
        "Rawsocket TCP Statistics";
      uses raw-socket-ios-xe-oper:connection-stats;
    }
    list rs-tcp-sessions {
      key "async-line destination-ip destination-port";
      description
        "List of active Rawsocket TCP sessions, including async line, destination IP and port, and session parameters";
      uses raw-socket-ios-xe-oper:rs-session-info-key;
      uses raw-socket-ios-xe-oper:rs-session-info-params;
    }
    list rs-tcp-clients-state {
      key "async-line destination-ip destination-port";
      description
        "List of operational state entries for Rawsocket TCP client connections, where each entry represents the current state of one client connection";
      uses raw-socket-ios-xe-oper:rs-client-state-key;
      uses raw-socket-ios-xe-oper:rs-client-state-params;
    }
  }

  grouping udp {
    description
      "Rawsocket UDP Operational Data";
    list rs-udp-stats {
      key "async-line";
      status deprecated;
      description
        "Rawsocket UDP Statistics.
         This list is deprecated. Use rs-udp-con-stats instead";
      uses raw-socket-ios-xe-oper:connection-stats;
    }
    list rs-udp-sessions {
      key "async-line destination-ip destination-port";
      description
        "List of active Rawsocket UDP sessions, each representing a connection between an async line and a remote endpoint";
      uses raw-socket-ios-xe-oper:rs-session-info-key;
      uses raw-socket-ios-xe-oper:rs-session-info-params;
    }
    list rs-udp-clients-state {
      key "async-line destination-ip destination-port";
      description
        "Rawsocket UDP Clients State";
      uses raw-socket-ios-xe-oper:rs-client-state-key;
      uses raw-socket-ios-xe-oper:rs-client-state-params;
    }
    list rs-udp-con-stats {
      key "async-line";
      description
        "List of per-line UDP statistics for Rawsocket connections";
      uses raw-socket-ios-xe-oper:udp-con-stats;
    }
  }

  container rawsocket-oper-data {
    config false;
    description
      "Operational state of Rawsocket";
    container rs-udp {
      presence "rs-udp";
      description
        "Rawsocket UDP Operational Data";
      uses raw-socket-ios-xe-oper:udp;
    }
    container rs-tcp {
      presence "rs-tcp";
      description
        "Rawsocket TCP Operational Data";
      uses raw-socket-ios-xe-oper:tcp;
    }
  }
}
