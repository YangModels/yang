module Cisco-IOS-XE-wireless-urwb-oper {
  yang-version 1.1;
  namespace "http://cisco.com/ns/yang/Cisco-IOS-XE-wireless-urwb-oper";
  prefix wireless-urwb-oper;

  import Cisco-IOS-XE-wireless-enum-types {
    prefix wireless-enum-types;
  }
  import Cisco-IOS-XE-wireless-urwb-common-types {
    prefix wireless-urwb-common-types;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for URWB(Ultra Reliable Wireless Backhaul) operational data.
     Copyright (c) 2025-2026 by Cisco Systems, Inc.
     All rights reserved.";

  revision 2026-08-01 {
    description
      "- Added URWB Ethernet operational data leaves
       - Added configured URWB network name to operational data
       - Added learned URWB network name to operational data
       - Added URWB NAT operational data
       - Updated descriptions of urwb-oper-data list and urwb-support leaf for clarity, grammar, and consistency";
    reference
      "1.1.0";
    cisco-semver:module-version "1.1.0";
  }
  revision 2026-02-01 {
    description
      "Initial revision";
    reference
      "1.0.0";
    cisco-semver:module-version "1.0.0";
  }

  grouping st-urwb-radius-server {
    description
      "URWB RADIUS server configuration used for operational status reporting.";
    leaf ip-address {
      type inet:ip-address;
      description
        "IP address of the RADIUS server (IPv4 or IPv6).";
    }
    leaf auth-port {
      type uint16;
      description
        "Authentication port used by the RADIUS server.";
    }
  }

  grouping st-urwb-nat-rule-oper {
    description
      "URWB NAT rule operational entry.";
    leaf proto {
      type wireless-enum-types:urwb-nat-protocol;
      description
        "NAT protocol for the rule.";
    }
    leaf outside-port {
      type uint16;
      description
        "Outside port for the NAT rule.";
    }
    leaf inside-ip {
      type inet:ipv4-address;
      description
        "Inside IPv4 address for the NAT rule.";
    }
    leaf in-port {
      type uint16;
      description
        "Inside port for the NAT rule.";
    }
  }

  grouping st-urwb-oper-data {
    description
      "Operational data structure for each AP participating in URWB.
       Includes configuration, runtime state, error reporting, and radio details.";
    leaf wtp-mac {
      type yang:mac-address;
      description
        "Unique MAC address of the Wireless Termination Point (AP).
         Used as the key to identify each AP in the URWB network";
    }
    leaf urwb-prf-inuse {
      type string;
      description
        "Name of the URWB profile currently applied to the AP";
    }
    leaf enabled {
      type boolean;
      description
        "Boolean flag indicating whether URWB functionality is enabled
         on this AP";
    }
    leaf cfg-crd-mode {
      type wireless-enum-types:urwb-crd-mode;
      description
        "Coordinator mode as configured for the AP";
    }
    leaf crd-mode {
      type wireless-enum-types:urwb-crd-mode;
      description
        "Current operational coordinator mode of the AP.
         May differ from the configured mode due to runtime conditions";
    }
    leaf client-id {
      type string;
      description
        "Identifier for the client instance in the URWB network";
    }
    container mobility {
      description
        "Mobility configuration and runtime status for the AP";
      uses wireless-urwb-common-types:st-urwb-mob;
    }
    container mpls {
      description
        "MPLS (Multiprotocol Label Switching) configuration and status";
      uses wireless-urwb-common-types:st-urwb-mpls;
    }
    container mpo {
      description
        "MultiPath Operation (MPO) configuration and status.
         Details about multipath routing and redundancy for the AP";
      uses wireless-urwb-common-types:st-urwb-mpo;
    }
    leaf-list ethertypes {
      type uint16;
      max-elements 64;
      ordered-by user;
      description
        "List of EtherType values configured for the AP";
    }
    leaf urwb-support {
      type boolean;
      description
        "Indicates whether the access point supports URWB features and protocols.";
    }
    leaf mesh-id {
      type inet:ip-address;
      description
        "Identifier for the URWB mesh network to which the AP belongs";
    }
    leaf urwb-phr-hash {
      type string;
      description
        "Hash of the URWB passphrase sent to the AP";
    }
    leaf-list cfg-err-str {
      type string;
      max-elements 10;
      ordered-by user;
      description
        "List of configuration error strings encountered by the AP";
    }
    leaf mcast {
      type wireless-enum-types:urwb-mcast;
      description
        "Multicast mode configuration for the AP";
    }
    leaf-list urwb-cfg-err-type {
      type uint16;
      max-elements 10;
      ordered-by user;
      description
        "List of URWB configuration error types";
    }
    leaf ap-name {
      type string;
      description
        "Name of the Access Point";
    }
    leaf coord-name {
      type string;
      description
        "Name of the coordinator AP associated with this AP";
    }
    leaf urwb-cfg-status {
      type wireless-enum-types:urwb-cfg-status;
      description
        "Current configuration status of URWB on the AP.
         Indicates success, failure, or pending configuration apply";
    }
    leaf nw-tree-lvl {
      type uint16;
      description
        "Indicates the depth of AP in the coordinator's network hierarchy";
    }
    leaf rf-tag {
      type string;
      description
        "RF tag applied to the AP";
    }
    leaf coord-mac {
      type yang:mac-address;
      description
        "Base radio MAC address of the coordinator AP";
    }
    leaf-list rad-role {
      type wireless-urwb-common-types:eurr;
      max-elements 4;
      ordered-by user;
      description
        "List of radio roles assigned to the AP's radios";
    }
    leaf cfg-nw-name {
      type string;
      description
        "URWB network name that is configured on the coordinator mode AP";
    }
    leaf nw-name {
      type string;
      description
        "URWB network name that is currently active on the coordinator mode AP";
    }
    container eth {
      description
        "URWB ethernet operational data";
      uses wireless-urwb-common-types:st-urwb-eth;
    }
    list rad-srv {
      max-elements 2;
      description
        "List of URWB RADIUS servers configured on the AP; each entry represents a RADIUS server";
      uses wireless-urwb-oper:st-urwb-radius-server;
    }
    container nat {
      description
        "Contains the operational state of URWB NAT configuration for the AP, including the enabled status, inside IP address, and netmask.";
      uses wireless-urwb-common-types:st-urwb-nat;
    }
    list nat-rule-list {
      max-elements 100;
      description
        "List of URWB NAT rules configured on the AP; each entry contains
         protocol, outside port, inside IP, and inside port";
      uses wireless-urwb-oper:st-urwb-nat-rule-oper;
    }
  }

  container urwb-oper-data {
    config false;
    description
      "Top-level container for URWB operational data and configuration status
       across all access points in the network.";
    list urwb-oper-data {
      key "wtp-mac";
      description
        "Operational data and configuration status for each URWB access point.";
      uses wireless-urwb-oper:st-urwb-oper-data;
    }
  }
}
