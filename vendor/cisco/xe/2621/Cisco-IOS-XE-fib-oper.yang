module Cisco-IOS-XE-fib-oper {
  yang-version 1.1;
  namespace "http://cisco.com/ns/yang/Cisco-IOS-XE-fib-oper";
  prefix fib-ios-xe-oper;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for IOS-XE FIB/CEF operational data.
     Copyright (c) 2018-2022, 2026 by Cisco Systems, Inc.
     All rights reserved.";

  revision 2026-08-01 {
    description
      "Modified descriptions of several model elements to clarify their meaning and purpose";
    reference
      "1.8.0";
    cisco-semver:module-version "1.8.0";
  }
  revision 2022-11-01 {
    description
      "Update yang-version to 1.1";
    reference
      "1.7.0";
    cisco-semver:module-version "1.7.0";
  }
  revision 2022-03-01 {
    description
      "- Added CEF source only load balancing hashing algorithm type";
    reference
      "1.6.0";
    cisco-semver:module-version "1.6.0";
  }
  revision 2021-11-01 {
    description
      "- Added CEF switching statistics and switching statistics features
       - Added IPv6 state for interface state";
    reference
      "1.5.0";
    cisco-semver:module-version "1.5.0";
  }
  revision 2020-03-01 {
    description
      "- Added FIB adjacency and CEF state support
       - Rename IPv4 FIB state fields and add fib hash algorithm state
         for IPv4/IPv6 FIB state";
    reference
      "1.4.0";
    cisco-semver:module-version "1.4.0";
  }
  revision 2019-05-01 {
    description
      "Added semantic version";
    reference
      "1.3.0";
    cisco-semver:module-version "1.3.0";
  }
  revision 2018-10-29 {
    description
      "Cleaned up spelling errors in descriptions.";
    reference
      "1.2.0";
    cisco-semver:module-version "1.2.0";
  }
  revision 2018-03-07 {
    description
      "Adding support for resolved next hop field";
    reference
      "1.1.0";
    cisco-semver:module-version "1.1.0";
  }
  revision 2017-07-04 {
    description
      "Initial revision";
    reference
      "1.0.0";
    cisco-semver:module-version "1.0.0";
  }

  typedef fib-address-family {
    type enumeration {
      enum fib-addr-fam-unknown {
        value 0;
        description
          "Unknown Address Family";
      }
      enum fib-addr-fam-ipv4 {
        value 1;
        description
          "IPv4 Address Family";
      }
      enum fib-addr-fam-ipv6 {
        value 2;
        description
          "IPv6 Address Family";
      }
    }
    description
      "FIB Address Family Types";
  }

  typedef encapsulation-header-type {
    type enumeration {
      enum encap-hdr-type-unknown {
        value 0;
        description
          "Unknown encapsulation header type";
      }
      enum encap-hdr-type-gre {
        value 1;
        description
          "GRE encapsulation header type";
      }
      enum encap-hdr-type-ipv4 {
        value 2;
        description
          "IPv4 encapsulation header type";
      }
      enum encap-hdr-type-ipv6 {
        value 3;
        description
          "IPv6 encapsulation header type";
      }
      enum encap-hdr-type-mpls {
        value 4;
        description
          "MPLS encapsulation header type";
      }
    }
    description
      "Types of header for packet encapsulation";
  }

  typedef fib-path-type {
    type enumeration {
      enum fib-path-type-unknown {
        value 0;
        description
          "Unknown FIB path type";
      }
      enum fib-path-type-receive {
        value 1;
        description
          "Receive FIB path type";
      }
      enum fib-path-type-connected {
        value 2;
        description
          "Connected FIB path type";
      }
      enum fib-path-type-attached-prefix {
        value 3;
        description
          "Attached Prefix FIB path type";
      }
      enum fib-path-type-attached-host {
        value 4;
        description
          "Attached Host FIB path type";
      }
      enum fib-path-type-attached-nexthop {
        value 5;
        description
          "Attached next hop FIB path type";
      }
      enum fib-path-type-recursive {
        value 6;
        description
          "Recursive FIB path type";
      }
      enum fib-path-type-adjacency-prefix {
        value 7;
        description
          "Adjacency Prefix FIB path type";
      }
      enum fib-path-type-special-prefix {
        value 8;
        description
          "Special Prefix FIB path type";
      }
    }
    description
      "Type of FIB path used";
  }

  typedef adj-link-type {
    type enumeration {
      enum adj-link-ip {
        value 0;
        description
          "Link IP";
      }
      enum adj-link-ipv6 {
        value 1;
        description
          "Link IPv6";
      }
      enum adj-link-tag {
        value 2;
        description
          "Link TAG";
      }
      enum adj-link-raw {
        value 3;
        description
          "Link RAW";
      }
      enum adj-link-all {
        value 4;
        description
          "Link All";
      }
      enum adj-link-illegal {
        value 5;
        description
          "Link Illegal";
      }
    }
    description
      "Adjacency Link Types";
  }

  typedef fib-instance-type {
    type enumeration {
      enum fib-instance-type-unknown {
        value 0;
        description
          "FIB instance type unknown";
      }
      enum fib-instance-type-rp {
        value 1;
        description
          "FIB instance type RP";
      }
      enum fib-instance-type-lc {
        value 2;
        description
          "FIB Instance type LC";
      }
      enum fib-instance-type-rrp {
        value 3;
        description
          "FIB Instance type RRP";
      }
    }
    description
      "FIB Instance Types";
  }

  typedef fib-hash-algs-type {
    type enumeration {
      enum fib-hash-algorithms-type-invalid {
        value 0;
        description
          "FIB hash algorithms type invalid";
      }
      enum fib-hash-algorithms-type-original {
        value 1;
        description
          "FIB hash algorithms type original";
      }
      enum fib-hash-algorithms-type-tunnel {
        value 2;
        description
          "FIB hash algorithms type tunnel";
      }
      enum fib-hash-algorithms-type-universal {
        value 3;
        description
          "FIB hash algorithms type universal";
      }
      enum fib-hash-algorithms-type-include-ports-src {
        value 4;
        description
          "FIB hash algorithms type include ports source";
      }
      enum fib-hash-algorithms-type-include-ports-dst {
        value 5;
        description
          "FIB hash algorithms type include ports destination";
      }
      enum fib-hash-algorithms-type-include-ports-src-dst {
        value 6;
        description
          "FIB hash algorithms type include ports source destination";
      }
      enum fib-hash-algorithms-type-include-ports-src-dst-gtp {
        value 7;
        description
          "FIB hash algorithms type include ports source destination GTP";
      }
      enum fib-hash-algorithms-type-dpi {
        value 8;
        description
          "FIB hash algorithms type DPI";
      }
      enum fib-hash-algorithms-type-src-only {
        value 9;
        description
          "FIB hash algorithms type source only";
      }
    }
    description
      "FIB Hash Algorithms Type";
  }

  typedef ipv4-fib-not-cef-reason {
    type enumeration {
      enum v4fib-ncr-no-route {
        value 0;
        description
          "IPv4 FIB not CEF reason no route";
      }
      enum v4fib-ncr-receive {
        value 1;
        description
          "IPv4 FIB not CEF reason packet destined for-us";
      }
      enum v4fib-ncr-encap-failed {
        value 2;
        description
          "IPv4 FIB not CEF reason encapsulation failed";
      }
      enum v4fib-ncr-encap-resource {
        value 3;
        description
          "IPv4 FIB not CEF reason encapsulation resource";
      }
      enum v4fib-ncr-no-adjacency {
        value 4;
        description
          "IPv4 FIB not CEF reason no adjacency";
      }
      enum v4fib-ncr-incmp-adj {
        value 5;
        description
          "IPv4 FIB not CEF reason incomplete adjacency";
      }
      enum v4fib-ncr-loop-detected {
        value 6;
        description
          "IPv4 FIB not CEF reason output chain looped";
      }
      enum v4fib-ncr-inv-frag-return {
        value 7;
        description
          "IPv4 FIB not CEF reason failed fragmentation";
      }
      enum v4fib-ncr-unresolved {
        value 8;
        description
          "IPv4 FIB not CEF reason unresolved route";
      }
      enum v4fib-ncr-unsup {
        value 9;
        description
          "IPv4 FIB not CEF reason unsupported route";
      }
      enum v4fib-ncr-unsup-plat {
        value 10;
        description
          "IPv4 FIB not CEF reason unsupported platform";
      }
      enum v4fib-ncr-bad-checksum {
        value 11;
        description
          "IPv4 FIB not CEF reason bad checksum";
      }
      enum v4fib-ncr-ttl-expired {
        value 12;
        description
          "IPv4 FIB not CEF reason TTL expired";
      }
      enum v4fib-ncr-ip-options {
        value 13;
        description
          "IPv4 FIB not CEF reason IP options set";
      }
      enum v4fib-ncr-bad-pkt-len {
        value 14;
        description
          "IPv4 FIB not CEF reason bad IP packet length";
      }
      enum v4fib-ncr-frag-disabled {
        value 15;
        description
          "IPv4 FIB not CEF reason fragmentation disabled";
      }
      enum v4fib-ncr-frag-unsup {
        value 16;
        description
          "IPv4 FIB not CEF reason fragmentation unsupported";
      }
      enum v4fib-ncr-frag-fail-dfset {
        value 17;
        description
          "IPv4 FIB not CEF reason fragmentation failed, DF set";
      }
      enum v4fib-ncr-discard {
        value 18;
        description
          "IPv4 FIB not CEF reason discard";
      }
      enum v4fib-ncr-nu110 {
        value 19;
        description
          "IPv4 FIB not CEF reason routed to Null0";
      }
      enum v4fib-ncr-multicast {
        value 20;
        description
          "IPv4 FIB not CEF reason multicast";
      }
      enum v4fib-ncr-feat {
        value 21;
        description
          "IPv4 FIB not CEF reason features";
      }
      enum v4fib-ncr-ip-redrct {
        value 22;
        description
          "IPv4 FIB not CEF reason IP redirects";
      }
      enum v4fib-ncr-shaping {
        value 23;
        description
          "IPv4 FIB not CEF reason traffic shaping";
      }
      enum v4fib-ncr-unk-in-if {
        value 24;
        description
          "IPv4 FIB not CEF reason unknown input I/F";
      }
      enum v4fib-ncr-unk-dial-in-if {
        value 25;
        description
          "IPv4 FIB not CEF reason unknown dialer input I/F";
      }
      enum v4fib-ncr-enqueue-failed {
        value 26;
        description
          "IPv4 FIB not CEF reason enqueue failed";
      }
      enum v4fib-ncr-unclassified {
        value 27;
        description
          "IPv4 FIB not CEF reason unclassified reason";
      }
      enum v4fib-ncr-neighbor-res-req {
        value 28;
        description
          "IPv4 FIB not CEF reason neighbor resolution requested";
      }
      enum v4fib-ncr-bad-pkt-min-len {
        value 29;
        description
          "IPv4 FIB not CEF reason bad IP packet minimum length";
      }
      enum v4fib-ncr-no-adj-fltrd {
        value 30;
        description
          "IPv4 FIB not CEF reason no adjacency filtered";
      }
      enum v4fib-ncr-incmp-adj-fltrd {
        value 31;
        description
          "IPv4 FIB not CEF reason incomplete adjacency";
      }
      enum v4fib-ncr-decep-recursion-limit {
        value 32;
        description
          "IPv4 FIB not CEF reason decap recursion limit";
      }
      enum v4fib-ncr-td-frag-or-opt {
        value 33;
        description
          "IPv4 FIB not CEF reason tun decap, frag/options";
      }
      enum v4fib-ncr-td-src {
        value 34;
        description
          "IPv4 FIB not CEF reason tun decap, source";
      }
      enum v4fib-ncr-td-dst {
        value 35;
        description
          "IPv4 FIB not CEF reason tun decap, destination";
      }
      enum v4fib-ncr-td-transport-table {
        value 36;
        description
          "IPv4 FIB not CEF reason tun decap, transport table";
      }
      enum v4fib-ncr-td-protocol {
        value 37;
        description
          "IPv4 FIB not CEF reason tun decap, protocol";
      }
      enum v4fib-ncr-td-no-vector {
        value 38;
        description
          "IPv4 FIB not CEF reason tun decap, no vector";
      }
      enum v4fib-ncr-td-no-dispatcher {
        value 39;
        description
          "IPv4 FIB not CEF reason tun decap, no dispatcher";
      }
      enum v4fib-ncr-td-displatcher-drop {
        value 40;
        description
          "IPv4 FIB not CEF reason tun decap, dispatcher drop";
      }
      enum v4fib-ncr-td-no-protocol {
        value 41;
        description
          "IPv4 FIB not CEF reason tun decap, no protocol";
      }
      enum v4fib-ncr-td-gre-options {
        value 42;
        description
          "IPv4 FIB not CEF reason tun decap, GRE options";
      }
      enum v4fib-ncr-td-gre-key-mis {
        value 43;
        description
          "IPv4 FIB not CEF reason tun decap, GRE key mismatch";
      }
      enum v4fib-ncr-td-gre-unsup-pl {
        value 44;
        description
          "IPv4 FIB not CEF reason tun decap, GRE unsupported payload";
      }
      enum v4fib-ncr-no-adj-queue-res {
        value 45;
        description
          "IPv4 FIB not CEF reason no adjacency, queued resolution";
      }
      enum v4fib-ncr-incmp-adj-queued {
        value 46;
        description
          "IPv4 FIB not CEF reason incomplete adjacency, queued resolution";
      }
      enum v4fib-ncr-ssf-12-feat {
        value 47;
        description
          "IPv4 FIB not CEF reason i-edge L2 features";
      }
      enum v4fib-ncr-no-vc {
        value 48;
        description
          "IPv4 FIB not CEF reason no VC";
      }
      enum v4fib-ncr-bad-pkt-hdr-len {
        value 49;
        description
          "IPv4 FIB not CEF reason bad IP packet header length";
      }
      enum v4fib-ncr-frag-resource {
        value 50;
        description
          "IPv4 FIB not CEF reason fragmentation resource";
      }
      enum v4fib-ncr-ll-bcast {
        value 51;
        description
          "IPv4 FIB not CEF reason link-layer broadcast/multicast";
      }
      enum v4fib-ncr-frag-init {
        value 52;
        description
          "IPv4 FIB not CEF reason initializing fragment pak";
      }
      enum v4fib-ncr-get-frag {
        value 53;
        description
          "IPv4 FIB not CEF reason getting fragment pak";
      }
      enum v4fib-ncr-frag-ipinitbuf {
        value 54;
        description
          "IPv4 FIB not CEF reason IP initialize buffer not in use";
      }
      enum v4fib-ncr-frag-no-pak {
        value 55;
        description
          "IPv4 FIB not CEF reason fragmentation no pak";
      }
      enum v4fib-ncr-frag-tunnel {
        value 56;
        description
          "IPv4 FIB not CEF reason fragmentation tunnel";
      }
      enum v4fib-ncr-frag-mistral {
        value 57;
        description
          "IPv4 FIB not CEF reason fragmentation mistral";
      }
      enum v4fib-ncr-turbo-disabled {
        value 58;
        description
          "IPv4 FIB not CEF reason turbo disabled for adjacency";
      }
      enum v4fib-ncr-td-sec-chck-fail {
        value 59;
        description
          "IPv4 FIB not CEF reason tun decap, security check failed";
      }
      enum v4fib-ncr-un-to-coalesce {
        value 60;
        description
          "IPv4 FIB not CEF reason unable to coalesce";
      }
      enum v4fib-ncr-lisp-too-small {
        value 61;
        description
          "IPv4 FIB not CEF reason LISP too small";
      }
      enum v4fib-ncr-lisp-unkn-iid {
        value 62;
        description
          "IPv4 FIB not CEF reason LISP unknown instance id";
      }
      enum v4fib-ncr-frag-fail-mtu {
        value 63;
        description
          "IPv4 FIB not CEF reason fragmentation fail, MTU 0";
      }
      enum v4fib-ncr-rd-in-not-reached {
        value 64;
        description
          "IPv4 FIB not CEF reason input redirect not reached";
      }
      enum v4fib-ncr-rd-in-not-enctr {
        value 65;
        description
          "IPv4 FIB not CEF reason input redirect not reached";
      }
      enum v4fib-ncr-rd-for-us-not-enctr {
        value 66;
        description
          "IPv4 FIB not CEF reason for-us redirect not encountered";
      }
      enum v4fib-ncr-rd-out-not-enctr {
        value 67;
        description
          "IPv4 FIB not CEF reason output redirect not encountered";
      }
      enum v4fib-ncr-rd-out-wrong-idb {
        value 68;
        description
          "IPv4 FIB not CEF reason output redirect wrong IDB";
      }
      enum v4fib-ncr-tx-fs-unsup {
        value 69;
        description
          "IPv4 FIB not CEF reason TX fast switching unsupported";
      }
      enum v4fib-ncr-adj-fixup {
        value 70;
        description
          "IPv4 FIB not CEF reason adjacency fixup";
      }
      enum v4fib-ncr-td-gre-keepalive {
        value 71;
        description
          "IPv4 FIB not CEF reason Tun Decap, Gre Keepalive";
      }
    }
    description
      "Reason not IPV4 FIB/CEF switch statistics";
  }

  typedef ipv4-input-switching-feature {
    type enumeration {
      enum ipf-in-none {
        value 0;
        description
          "IPv4 input feature none";
      }
      enum ipf-in-debug-packet {
        value 1;
        description
          "IPv4 input feature debug packet";
      }
      enum ipf-in-pak-export {
        value 2;
        description
          "IPv4 input feature router IP traffic export";
      }
      enum ipf-in-packet-capture {
        value 3;
        description
          "IPv4 input feature CEF packet capture";
      }
      enum ipf-in-proc-packet-cap {
        value 4;
        description
          "IPv4 input feature process packet capture";
      }
      enum ipf-in-cft {
        value 5;
        description
          "IPv4 input feature common flow table";
      }
      enum ipf-in-cft-pre-waas {
        value 6;
        description
          "IPv4 input feature common flow table PRE WAAS";
      }
      enum ipf-in-msp {
        value 7;
        description
          "IPv4 input feature media services proxy";
      }
      enum ipf-in-stile {
        value 8;
        description
          "IPv4 input feature stateful inspection";
      }
      enum ipf-in-stile-cyph-txt {
        value 9;
        description
          "IPv4 input feature stateful inspection on cypher text";
      }
      enum ipf-in-onep-mpss-pkt {
        value 10;
        description
          "IPv4 input feature multiprotocol stateless switching IP header processing";
      }
      enum ipf-in-metadata {
        value 11;
        description
          "IPv4 input feature flow metadata";
      }
      enum ipf-in-cce-first-c {
        value 12;
        description
          "IPv4 input feature CCE input classification";
      }
      enum ipf-in-smef-c {
        value 13;
        description
          "IPv4 input feature service/metadata exchange input classification";
      }
      enum ipf-in-dpss-flow-acts {
        value 14;
        description
          "IPv4 input feature onep dpss flow actions";
      }
      enum ipf-in-onep-pol-acts {
        value 15;
        description
          "IPv4 input feature onep policy actions input";
      }
      enum ipf-in-ip-vrfauto {
        value 16;
        description
          "IPv4 input feature IP vrf auto classify";
      }
      enum ipf-in-perf-mon {
        value 17;
        description
          "IPv4 input feature input performance monitor";
      }
      enum ipf-in-perf-mon-ts {
        value 18;
        description
          "IPv4 input feature performance monitor get timestamp";
      }
      enum ipf-in-vqm {
        value 19;
        description
          "IPv4 input feature input video quality monitor";
      }
      enum ipf-in-fnf {
        value 20;
        description
          "IPv4 input feature input flexible netflow";
      }
      enum ipf-in-global-fnf {
        value 21;
        description
          "IPv4 input feature input global flexible netflow";
      }
      enum ipf-in-lisp-smr {
        value 22;
        description
          "IPv4 input feature LISP SMR";
      }
      enum ipf-in-srpm-pfp {
        value 23;
        description
          "IPv4 input feature source RPM performance routing";
      }
      enum ipf-in-qos-drop {
        value 24;
        description
          "IPv4 input feature QoS drop";
      }
      enum ipf-in-punt-unrec-feat {
        value 25;
        description
          "IPv4 input feature punt unrecognised feature";
      }
      enum ipf-in-dialer-in-if-or {
        value 26;
        description
          "IPv4 input feature dialer I/F override";
      }
      enum ipf-in-ip-not-en-dis {
        value 27;
        description
          "IPv4 input feature IP not enabled discard";
      }
      enum ipf-in-lisp-mobility {
        value 28;
        description
          "IPv4 input feature LISP mobility";
      }
      enum ipf-in-lisp-disable {
        value 29;
        description
          "IPv4 input feature LISP disable";
      }
      enum ipf-in-lisp {
        value 30;
        description
          "IPv4 input feature LISP ETR";
      }
      enum ipf-in-ppp-idle-to {
        value 31;
        description
          "IPv4 input feature PPP input idle timeout";
      }
      enum ipf-in-mip-fa-fwdto-mn {
        value 32;
        description
          "IPv4 input feature mip fa forward to mn";
      }
      enum ipf-in-iedge-ip-sc {
        value 33;
        description
          "IPv4 input feature i-Edge IP session input classifier";
      }
      enum ipf-in-sia-scl {
        value 34;
        description
          "IPv4 input feature service classifier";
      }
      enum ipf-in-sia-hdr {
        value 35;
        description
          "IPv4 input feature SIA header";
      }
      enum ipf-in-flow {
        value 36;
        description
          "IPv4 input feature ingress netflow";
      }
      enum ipf-in-bgp-pol-map {
        value 37;
        description
          "IPv4 input feature BGP policy map";
      }
      enum ipf-in-qos-c {
        value 38;
        description
          "IPv4 input feature QoS classification";
      }
      enum ipf-in-oer {
        value 39;
        description
          "IPv4 input feature optimized exit routing";
      }
      enum ipf-in-vfr {
        value 40;
        description
          "IPv4 input feature virtual fragment reassembly";
      }
      enum ipf-in-li {
        value 41;
        description
          "IPv4 input feature lawful intercept";
      }
      enum ipf-in-cce-sl-ips {
        value 42;
        description
          "IPv4 input feature stateless in IPS (atomic)";
      }
      enum ipf-in-fw {
        value 43;
        description
          "IPv4 input feature firewall (IDs and/or auth proxy)";
      }
      enum ipf-in-ip-learn {
        value 44;
        description
          "IPv4 input feature IP learn";
      }
      enum ipf-in-auth-proxy {
        value 45;
        description
          "IPv4 input feature auth proxy";
      }
      enum ipf-in-epm-http-redrct {
        value 46;
        description
          "IPv4 input feature EPM HTTP redirect";
      }
      enum ipf-in-cmnacl {
        value 47;
        description
          "IPv4 input feature common access list";
      }
      enum ipf-in-acl {
        value 48;
        description
          "IPv4 input feature access list";
      }
      enum ipf-in-per-src-acl {
        value 49;
        description
          "IPv4 input feature per source access list";
      }
      enum ipf-in-ip-multiplex {
        value 50;
        description
          "IPv4 input feature ipv4 multiplexing";
      }
      enum ipf-in-sbc {
        value 51;
        description
          "IPv4 input feature session border controller";
      }
      enum ipf-in-container {
        value 52;
        description
          "IPv4 input feature container input features";
      }
      enum ipf-in-fpm {
        value 53;
        description
          "IPv4 input feature flexible packet match";
      }
      enum ipf-in-ase {
        value 54;
        description
          "IPv4 input feature automatic signature extraction";
      }
      enum ipf-in-before-decrypt-n {
        value 55;
        description
          "IPv4 input feature IPSEC decrypt begins";
      }
      enum ipf-in-ipsec {
        value 56;
        description
          "IPv4 input feature IPSEC input classification";
      }
      enum ipf-in-after-decrypt-n {
        value 57;
        description
          "IPv4 input feature IPSEC decrypt ends";
      }
      enum ipf-in-ipsec-vfr {
        value 58;
        description
          "IPv4 input feature virtual fragment reassembly after IPSEC decryption";
      }
      enum ipf-in-ipsec-vrf {
        value 59;
        description
          "IPv4 input feature IPSEC input VRF switch";
      }
      enum ipf-in-ipsec-dacl {
        value 60;
        description
          "IPv4 input feature IPSEC post decrypt input ACL check";
      }
      enum ipf-in-rpf {
        value 61;
        description
          "IPv4 input feature unicast RPF";
      }
      enum ipf-in-rpf-vrfauto {
        value 62;
        description
          "IPv4 input feature unicast RPF (VRF auto)";
      }
      enum ipf-in-qos-marking {
        value 63;
        description
          "IPv4 input feature QoS marking";
      }
      enum ipf-in-ratelimit {
        value 64;
        description
          "IPv4 input feature input rate limit";
      }
      enum ipf-in-police {
        value 65;
        description
          "IPv4 input feature policing";
      }
      enum ipf-in-af-police {
        value 66;
        description
          "IPv4 input feature AF policing";
      }
      enum ipf-in-content-scan-pre-proxy {
        value 67;
        description
          "IPv4 input feature content scan PRE proxy";
      }
      enum ipf-in-content-scan {
        value 68;
        description
          "IPv4 input feature content scan proxy in";
      }
      enum ipf-in-cft-post-vpn {
        value 69;
        description
          "IPv4 input feature common flow table post VPN";
      }
      enum ipf-in-cce-post-crypto-c {
        value 70;
        description
          "IPv4 input feature CCE input post crypto classification";
      }
      enum ipf-in-perf-mon-async {
        value 71;
        description
          "IPv4 input feature in performance monitor async";
      }
      enum ipf-in-cent {
        value 72;
        description
          "IPv4 input feature input CENT smart probe";
      }
      enum ipf-in-pa-wccp-proxy {
        value 73;
        description
          "IPv4 input feature pa WCCP proxy";
      }
      enum ipf-in-pa {
        value 74;
        description
          "IPv4 input feature performance agent";
      }
      enum ipf-in-mace-pre-waas {
        value 75;
        description
          "IPv4 input feature measurement aggregation correlation engine input PRE WAAS";
      }
      enum ipf-in-waas {
        value 76;
        description
          "IPv4 input feature ios WAAS optimize";
      }
      enum ipf-in-cft-post-waas {
        value 77;
        description
          "IPv4 input feature common flow table post WAAS";
      }
      enum ipf-in-stile-clear-text {
        value 78;
        description
          "IPv4 input feature stateful inspection on clear text";
      }
      enum ipf-in-mace-post-waas {
        value 79;
        description
          "IPv4 input feature measurement aggregation correlation engine input post WAAS";
      }
      enum ipf-in-pa-post-waas {
        value 80;
        description
          "IPv4 input feature performance agent input post WAAS";
      }
      enum ipf-in-atomic-ips-p-crypto {
        value 81;
        description
          "IPv4 input feature post crypto IPS atomic";
      }
      enum ipf-in-ezvpn {
        value 82;
        description
          "IPv4 input feature ezvpn connect ACL";
      }
      enum ipf-in-crypto {
        value 83;
        description
          "IPv4 input feature crypto";
      }
      enum ipf-in-sia {
        value 84;
        description
          "IPv4 input feature SIA (platform independent interception point)";
      }
      enum ipf-in-cts-l3 {
        value 85;
        description
          "IPv4 input feature CTS l3 tunnel input classification";
      }
      enum ipf-in-cts-imt {
        value 86;
        description
          "IPv4 input feature CTS implicit tunnel input classification";
      }
      enum ipf-in-mppe-enc {
        value 87;
        description
          "IPv4 input feature input IDB microsoft point-to-point encryption";
      }
      enum ipf-in-mtr-c {
        value 88;
        description
          "IPv4 input feature multi topology routing classify";
      }
      enum ipf-in-mac-accounting {
        value 89;
        description
          "IPv4 input feature MAC accounting";
      }
      enum ipf-in-prec-accounting {
        value 90;
        description
          "IPv4 input feature precedence accounting";
      }
      enum ipf-in-portbundle {
        value 91;
        description
          "IPv4 input feature port bundle host key";
      }
      enum ipf-in-save-addr {
        value 92;
        description
          "IPv4 input feature pre-nat address capture";
      }
      enum ipf-in-n-out {
        value 93;
        description
          "IPv4 input feature NAT outside";
      }
      enum ipf-in-dnssnp {
        value 94;
        description
          "IPv4 input feature DNS snoop";
      }
      enum ipf-in-pre-sm-monitoring {
        value 95;
        description
          "IPv4 input feature before IDS monitoring";
      }
      enum ipf-in-sm-monitoring {
        value 96;
        description
          "IPv4 input feature IDS monitoring";
      }
      enum ipf-in-post-sm-monitoring {
        value 97;
        description
          "IPv4 input feature after WAAS monitoring";
      }
      enum ipf-in-nam-monitoring {
        value 98;
        description
          "IPv4 input feature NAM monitoring";
      }
      enum ipf-in-iedge {
        value 99;
        description
          "IPv4 input feature i-Edge";
      }
      enum ipf-in-iedge-ip-sess-feat {
        value 100;
        description
          "IPv4 input feature i-Edge IP session input features";
      }
      enum ipf-in-ssg {
        value 101;
        description
          "IPv4 input feature service selection gateway input feature";
      }
      enum ipf-in-cent-rc {
        value 102;
        description
          "IPv4 input feature input CENT route control";
      }
      enum ipf-in-cws {
        value 103;
        description
          "IPv4 input feature cloud web security in";
      }
      enum ipf-in-policy {
        value 104;
        description
          "IPv4 input feature policy routing";
      }
      enum ipf-in-mfib-nat {
        value 105;
        description
          "IPv4 input feature  multicast FIB NAT";
      }
      enum ipf-in-wccp {
        value 106;
        description
          "IPv4 input feature web cache communications protocol";
      }
      enum ipf-in-after-wccp {
        value 107;
        description
          "IPv4 input feature WCCP in after FW";
      }
      enum ipf-in-casa {
        value 108;
        description
          "IPv4 input feature CISCO appliance and services architecture";
      }
      enum ipf-in-urd {
        value 109;
        description
          "IPv4 input feature URD intercept";
      }
      enum ipf-in-mci-chk {
        value 110;
        description
          "IPv4 input feature MCI check";
      }
      enum ipf-in-vrfs {
        value 111;
        description
          "IPv4 input feature VRF select";
      }
      enum ipf-in-tweak-mss {
        value 112;
        description
          "IPv4 input feature TCP adjust MSS";
      }
      enum ipf-in-iedge-ip-sess-driv {
        value 113;
        description
          "IPv4 input feature i-Edge IP session RX driver";
      }
      enum ipf-in-gprs {
        value 114;
        description
          "IPv4 input feature GPRS uplink packet switch";
      }
      enum ipf-in-mip-revtunn {
        value 115;
        description
          "IPv4 input feature MIP reverse tunnel";
      }
      enum ipf-in-rb-proxy {
        value 116;
        description
          "IPv4 input feature role-based proxy";
      }
      enum ipf-in-bootp-reply {
        value 117;
        description
          "IPv4 input feature bootp reply";
      }
      enum ipf-in-dhcpc-reply {
        value 118;
        description
          "IPv4 input feature DHCP client reply";
      }
      enum ipf-in-agw {
        value 119;
        description
          "IPv4 input feature ASN GW uplink packet switch";
      }
      enum ipf-in-csg-app {
        value 120;
        description
          "IPv4 input feature CSG application";
      }
      enum ipf-in-bma-redrct {
        value 121;
        description
          "IPv4 input feature broadcast multi-access redirect";
      }
      enum ipf-in-lisp-alt-intercept {
        value 122;
        description
          "IPv4 input feature LISP ALT intercept";
      }
      enum ipf-in-tun-to-redrct {
        value 123;
        description
          "IPv4 input feature tunnel to traffic redirection";
      }
      enum ipf-in-hqf-queueing {
        value 124;
        description
          "IPv4 input feature ingress hierarchical queueing framework";
      }
      enum ipf-in-plat-sc {
        value 125;
        description
          "IPv4 input feature HW shortcut installation";
      }
      enum ipf-in-iedge-ip-sess-pre-n {
        value 126;
        description
          "IPv4 input feature i-Edge IP session input pre-NAT";
      }
      enum ipf-in-iedge-ip-sess-post-n {
        value 127;
        description
          "IPv4 input feature i-Edge IP session input post-NAT";
      }
      enum ipf-in-idletimer {
        value 128;
        description
          "IPv4 input feature dialer idle timer";
      }
      enum ipf-in-val {
        value 129;
        description
          "IPv4 input feature VAL input";
      }
    }
    description
      "IPv4 FIB/CEF input switch statistics feature";
  }

  typedef ipv4-output-switching-feature {
    type enumeration {
      enum ipf-o-none {
        value 0;
        description
          "IPv4 output feature none";
      }
      enum ipf-o-vfr-egress {
        value 1;
        description
          "IPv4 output feature virtual fragment reassembly on egress";
      }
      enum ipf-o-punt-unrecog-feat {
        value 2;
        description
          "IPv4 output feature punt unrecognised feature";
      }
      enum ipf-o-ppp-idle-timeout {
        value 3;
        description
          "IPv4 output feature PPP output idle timeout";
      }
      enum ipf-o-iedge-ip-sess-cls {
        value 4;
        description
          "IPv4 output feature i-Edge IP session output classifier";
      }
      enum ipf-o-gprs {
        value 5;
        description
          "IPv4 output feature gprs vpn";
      }
      enum ipf-o-cce-first-cls {
        value 6;
        description
          "IPv4 output feature CCE output classification";
      }
      enum ipf-o-reroute {
        value 7;
        description
          "IPv4 output feature IP reroute";
      }
      enum ipf-o-n-in {
        value 8;
        description
          "IPv4 output feature NAT inside";
      }
      enum ipf-o-cce-sl-ips {
        value 9;
        description
          "IPv4 output feature stateless out IPS (atomic)";
      }
      enum ipf-o-fw1 {
        value 10;
        description
          "IPv4 output feature firewall (IDS)";
      }
      enum ipf-o-rbscp {
        value 11;
        description
          "IPv4 output feature access-list based RBSCP";
      }
      enum ipf-o-nhrp-shortcut {
        value 12;
        description
          "IPv4 output feature NHRP shortcut switching";
      }
      enum ipf-o-nhrp-redrct {
        value 13;
        description
          "IPv4 output feature NHRP redirect";
      }
      enum ipf-o-wccp {
        value 14;
        description
          "IPv4 output feature web cache communications protocol";
      }
      enum ipf-o-after-wccp {
        value 15;
        description
          "IPv4 output feature WCCP out after FW";
      }
      enum ipf-o-iedge {
        value 16;
        description
          "IPv4 output feature i-Edge";
      }
      enum ipf-o-pre-sm-monitoring {
        value 17;
        description
          "IPv4 output feature before IDS monitoring";
      }
      enum ipf-o-sm-monitoring {
        value 18;
        description
          "IPv4 output feature IDS monitoring";
      }
      enum ipf-o-apa-monitoring {
        value 19;
        description
          "IPv4 output feature APA monitoring";
      }
      enum ipf-o-nam-monitoring {
        value 20;
        description
          "IPv4 output feature NAM monitoring";
      }
      enum ipf-o-post-sm-monitoring {
        value 21;
        description
          "IPv4 output feature after IDS monitoring";
      }
      enum ipf-o-sslvpn-check-bw {
        value 22;
        description
          "IPv4 output feature sslvpn bandwidth checking with evaluation license";
      }
      enum ipf-o-nat64 {
        value 23;
        description
          "IPv4 output feature post-routing NAT64 output";
      }
      enum ipf-o-n-nvi-output {
        value 24;
        description
          "IPv4 output feature post-routing NAT NVI output";
      }
      enum ipf-o-dnssnp {
        value 25;
        description
          "IPv4 output feature DNS snoop out";
      }
      enum ipf-o-n-out {
        value 26;
        description
          "IPv4 output feature post-routing NAT outside";
      }
      enum ipf-o-mfib-nat {
        value 27;
        description
          "IPv4 output feature multicast FIB NAT";
      }
      enum ipf-o-ip-multiplex {
        value 28;
        description
          "IPv4 output feature IP multiplexing";
      }
      enum ipf-o-cft {
        value 29;
        description
          "IPv4 output feature common flow table";
      }
      enum ipf-o-stile {
        value 30;
        description
          "IPv4 output feature stateful inspection";
      }
      enum ipf-o-metadata {
        value 31;
        description
          "IPv4 output feature flow metadata";
      }
      enum ipf-o-autoqos {
        value 32;
        description
          "IPv4 output feature autoqos dscp classification";
      }
      enum ipf-o-bgp-pol-map {
        value 33;
        description
          "IPv4 output feature BGP policy map";
      }
      enum ipf-o-li {
        value 34;
        description
          "IPv4 output feature lawful intercept";
      }
      enum ipf-o-post-route {
        value 35;
        description
          "IPv4 output feature IP post routing processing";
      }
      enum ipf-o-ipsec {
        value 36;
        description
          "IPv4 output feature IPSEC output classification";
      }
      enum ipf-o-cts-imt {
        value 37;
        description
          "IPv4 output feature CTS implicit tunnel output classification";
      }
      enum ipf-o-cts-l3 {
        value 38;
        description
          "IPv4 output feature CTS L3 tunnel output classification";
      }
      enum ipf-o-mppe-enc {
        value 39;
        description
          "IPv4 output feature output IDB microsoft point-to-point encryption";
      }
      enum ipf-o-qos-c {
        value 40;
        description
          "IPv4 output feature QoS classification";
      }
      enum ipf-o-before-cce-post-n-c {
        value 41;
        description
          "IPv4 output feature before CCE post NAT classification";
      }
      enum ipf-o-cce-post-n-c {
        value 42;
        description
          "IPv4 output feature CCE post NAT classification";
      }
      enum ipf-o-cce-stateful-ips {
        value 43;
        description
          "IPv4 output feature stateful IPS (cce)";
      }
      enum ipf-o-cce-firewall {
        value 44;
        description
          "IPv4 output feature firewall (cce)";
      }
      enum ipf-o-after-cce-post-n-c {
        value 45;
        description
          "IPv4 output feature after CCE post NAT classification";
      }
      enum ipf-o-onep-mpss-pkt {
        value 46;
        description
          "IPv4 output feature multiprotocol stateless switching IP header processing";
      }
      enum ipf-o-dpss-flow-acts {
        value 47;
        description
          "IPv4 output feature ONEP DPSS flow actions";
      }
      enum ipf-o-onep-pol-acts {
        value 48;
        description
          "IPv4 output feature ONEP policy actions output";
      }
      enum ipf-o-qos-drop {
        value 49;
        description
          "IPv4 output feature QoS drop";
      }
      enum ipf-o-fw2 {
        value 50;
        description
          "IPv4 output feature firewall (NAT)";
      }
      enum ipf-o-cmnacl {
        value 51;
        description
          "IPv4 output feature common access list";
      }
      enum ipf-o-acl {
        value 52;
        description
          "IPv4 output feature access list";
      }
      enum ipf-o-rb-rbacl {
        value 53;
        description
          "IPv4 output feature role-based access list";
      }
      enum ipf-o-container {
        value 54;
        description
          "IPv4 output feature container output features";
      }
      enum ipf-o-fpm {
        value 55;
        description
          "IPv4 output feature flexible packet match";
      }
      enum ipf-o-fw3 {
        value 56;
        description
          "IPv4 output feature firewall (inspect)";
      }
      enum ipf-o-auth-proxy {
        value 57;
        description
          "IPv4 output feature auth proxy (return traffic)";
      }
      enum ipf-o-tweak-mss {
        value 58;
        description
          "IPv4 output feature TCP adjust mss";
      }
      enum ipf-o-tcp-intercept {
        value 59;
        description
          "IPv4 output feature TCP intercept";
      }
      enum ipf-o-content-scan {
        value 60;
        description
          "IPv4 output feature content scan proxy out";
      }
      enum ipf-o-content-scan-post-proxy {
        value 61;
        description
          "IPv4 output feature content scan post proxy";
      }
      enum ipf-o-wan-optimization {
        value 62;
        description
          "IPv4 output feature WAN optimization";
      }
      enum ipf-o-n-alg {
        value 63;
        description
          "IPv4 output feature NAT alg proxy";
      }
      enum ipf-o-post-perf-mon-async {
        value 64;
        description
          "IPv4 output feature performance monitor async post";
      }
      enum ipf-o-perf-mon-async {
        value 65;
        description
          "IPv4 output feature out performance monitor async";
      }
      enum ipf-o-pa {
        value 66;
        description
          "IPv4 output feature performance agent";
      }
      enum ipf-o-mace-pre-waas {
        value 67;
        description
          "IPv4 output feature measurement aggregation correlation engine output pre waas";
      }
      enum ipf-o-waas {
        value 68;
        description
          "IPv4 output feature IOS WAAS optimize";
      }
      enum ipf-o-mace-post-waas {
        value 69;
        description
          "IPv4 output feature measurement aggregation correlation engine output post waas";
      }
      enum ipf-o-pa-post-waas {
        value 70;
        description
          "IPv4 output feature performance agent output post waas";
      }
      enum ipf-o-video-im {
        value 71;
        description
          "IPv4 output feature video intelligent marking";
      }
      enum ipf-o-qos-marking {
        value 72;
        description
          "IPv4 output feature QoS marking";
      }
      enum ipf-o-acctg {
        value 73;
        description
          "IPv4 output feature IP accounting";
      }
      enum ipf-o-rsvp {
        value 74;
        description
          "IPv4 output feature resource reservation protocol";
      }
      enum ipf-o-ratelimit {
        value 75;
        description
          "IPv4 output feature output rate limit";
      }
      enum ipf-o-qos-cac-fnf {
        value 76;
        description
          "IPv4 output feature output QoS cac netflow";
      }
      enum ipf-o-police {
        value 77;
        description
          "IPv4 output feature policing";
      }
      enum ipf-o-af-police {
        value 78;
        description
          "IPv4 output feature AF policing";
      }
      enum ipf-o-qos-preclass {
        value 79;
        description
          "IPv4 output feature QoS pre-classification";
      }
      enum ipf-o-mac-accounting {
        value 80;
        description
          "IPv4 output feature MAC accounting";
      }
      enum ipf-o-prec-accounting {
        value 81;
        description
          "IPv4 output feature precedence accounting";
      }
      enum ipf-o-flow {
        value 82;
        description
          "IPv4 output feature post ingress netflow";
      }
      enum ipf-o-ipsec-dacl {
        value 83;
        description
          "IPv4 output feature IPSEC pre encrypt output acl check";
      }
      enum ipf-o-in-fnf-pre-crypto {
        value 84;
        description
          "IPv4 output feature post input pre crypto flexible netflow";
      }
      enum ipf-o-ipsec-encrypt {
        value 85;
        description
          "IPv4 output feature IPSEC to crypto engine";
      }
      enum ipf-o-post-encrypt-feat {
        value 86;
        description
          "IPv4 output feature post encryption output features";
      }
      enum ipf-o-mip-coa-loop-drop {
        value 87;
        description
          "IPv4 output feature MIP COA loop drop";
      }
      enum ipf-o-egress-flow {
        value 88;
        description
          "IPv4 output feature egress netflow";
      }
      enum ipf-o-iedge-ip-sess-feat {
        value 89;
        description
          "IPv4 output feature i-Edge IP session output features";
      }
      enum ipf-o-input-interface-drop {
        value 90;
        description
          "IPv4 output feature input interface drop";
      }
      enum ipf-o-pak-export {
        value 91;
        description
          "IPv4 output feature router IP traffic export";
      }
      enum ipf-o-service-reflect {
        value 92;
        description
          "IPv4 output feature service reflect";
      }
      enum ipf-o-mfib-adj-fixup {
        value 93;
        description
          "IPv4 output feature multicast fib adjacency";
      }
      enum ipf-o-punt-unrec-pe-feat {
        value 94;
        description
          "IPv4 output feature punt unrecognised pe feature";
      }
      enum ipf-o-perf-mon {
        value 95;
        description
          "IPv4 output feature output performance monitor";
      }
      enum ipf-o-vqm {
        value 96;
        description
          "IPv4 output feature output video quality monitor";
      }
      enum ipf-o-cent {
        value 97;
        description
          "IPv4 output feature output cent smart probe";
      }
      enum ipf-o-input-fnf {
        value 98;
        description
          "IPv4 output feature post input flexible netflow";
      }
      enum ipf-o-fnf {
        value 99;
        description
          "IPv4 output feature output flexible netflow";
      }
      enum ipf-o-global-fnf {
        value 100;
        description
          "IPv4 output feature output global flexible netflow";
      }
      enum ipf-o-debug-packet {
        value 101;
        description
          "IPv4 output feature debug packet";
      }
      enum ipf-o-dialer-idle-reset {
        value 102;
        description
          "IPv4 output feature dialer idle reset";
      }
      enum ipf-o-dialer-pfle-idle-rst {
        value 103;
        description
          "IPv4 output feature dialer profile idle reset";
      }
      enum ipf-o-plat-sc {
        value 104;
        description
          "IPv4 output feature HW shortcut installation";
      }
      enum ipf-o-ipe-vlan {
        value 105;
        description
          "IPv4 output feature ipe vlan";
      }
      enum ipf-o-check-hwidb {
        value 106;
        description
          "IPv4 output feature check HW idb";
      }
      enum ipf-o-topo-acct {
        value 107;
        description
          "IPv4 output feature egress topology stats";
      }
      enum ipf-o-agw {
        value 108;
        description
          "IPv4 output feature asn gw downlink packet switch";
      }
      enum ipf-o-iedge-ip-session {
        value 109;
        description
          "IPv4 output feature i-Edge IP session output";
      }
      enum ipf-o-n-deprecated {
        value 110;
        description
          "IPv4 output feature network address translation";
      }
      enum ipf-o-crypto {
        value 111;
        description
          "IPv4 output feature crypto map";
      }
      enum ipf-o-iedge-n-out {
        value 112;
        description
          "IPv4 output feature i-Edge NAT out(inside->outside)";
      }
      enum ipf-o-pmip-gre {
        value 113;
        description
          "IPv4 output feature proxy mobile IP gre encap";
      }
      enum ipf-o-val {
        value 114;
        description
          "IPv4 output feature val output";
      }
    }
    description
      "IPv4 FIB/CEF output switch statistics feature";
  }

  typedef ipv4-post-encap-switching-feature {
    type enumeration {
      enum ipf-pe-none {
        value 0;
        description
          "IPv4 post encap feature none";
      }
      enum ipf-pe-can-not-reuse {
        value 1;
        description
          "IPv4 post encap feature can not reuse";
      }
      enum ipf-pe-tunnel-cmd-fixup {
        value 2;
        description
          "IPv4 post encap feature service/metadata exchange CMD fixup";
      }
      enum ipf-pe-nsh-fixup {
        value 3;
        description
          "IPv4 post encap feature service/metadata exchange NSH fixup";
      }
      enum ipf-pe-lisp-fixup {
        value 4;
        description
          "IPv4 post encap feature locator identifier separation protocol";
      }
      enum ipf-pe-fec {
        value 5;
        description
          "IPv4 post encap feature fast ethernet channel";
      }
      enum ipf-pe-ratelimit {
        value 6;
        description
          "IPv4 post encap feature post encap rate limit";
      }
      enum ipf-pe-mtu {
        value 7;
        description
          "IPv4 post encap feature MTU processing";
      }
      enum ipf-pe-outcounter {
        value 8;
        description
          "IPv4 post encap feature IP protocol output counter";
      }
      enum ipf-pe-out-acctg {
        value 9;
        description
          "IPv4 post encap feature IP accounting";
      }
      enum ipf-pe-mppe-enc {
        value 10;
        description
          "IPv4 post encap feature post-encap IDB microsoft point-to-point encryption";
      }
      enum ipf-pe-sendself {
        value 11;
        description
          "IPv4 post encap feature IP send self check";
      }
      enum ipf-pe-mac-accounting {
        value 12;
        description
          "IPv4 post encap feature MAC accounting";
      }
      enum ipf-pe-prec-accounting {
        value 13;
        description
          "IPv4 post encap feature precedence accounting";
      }
      enum ipf-pe-isl-mark {
        value 14;
        description
          "IPv4 post encap feature inter-switch link";
      }
      enum ipf-pe-dike {
        value 15;
        description
          "IPv4 post encap feature data over IKEV2 post encap output classification";
      }
      enum ipf-pe-ipsec {
        value 16;
        description
          "IPv4 post encap feature IPSEC post encap output classification";
      }
      enum ipf-pe-n-fixup {
        value 17;
        description
          "IPv4 post encap feature post encap NAT fixup";
      }
      enum ipf-pe-tunnel-n-fixup {
        value 18;
        description
          "IPv4 post encap feature tunnel fixup";
      }
      enum ipf-pe-sia {
        value 19;
        description
          "IPv4 post encap feature SIA post encap fixup";
      }
      enum ipf-pe-fm-ace {
        value 20;
        description
          "IPv4 post encap feature firmware access list";
      }
      enum ipf-pe-dhcps {
        value 21;
        description
          "IPv4 post encap feature DHCP snooping";
      }
      enum ipf-pe-plat-sc {
        value 22;
        description
          "IPv4 post encap feature HW shortcut installation";
      }
      enum ipf-pe-iphc {
        value 23;
        description
          "IPv4 post encap feature IPHC output classification";
      }
      enum ipf-pe-tunnel-traffic-shaping {
        value 24;
        description
          "IPv4 post encap feature tunnel traffic shaping";
      }
      enum ipf-pe-vmi {
        value 25;
        description
          "IPv4 post encap feature QoS on virtual multipoint interface";
      }
      enum ipf-pe-vmi-nbma-mcast {
        value 26;
        description
          "IPv4 post encap feature nbma multicast on virtual multipoint interface";
      }
      enum ipf-pe-tun-to {
        value 27;
        description
          "IPv4 post encap feature tunnel-to";
      }
      enum ipf-pe-pmip-gre-encap {
        value 28;
        description
          "IPv4 post encap feature proxy mobile IP gre encap";
      }
      enum ipf-pe-mip-mr-gre-encap {
        value 29;
        description
          "IPv4 post encap feature mip mr gre encap";
      }
      enum ipf-pe-qos-proc-marking {
        value 30;
        description
          "IPv4 post encap feature QoS marking";
      }
      enum ipf-pe-af-police {
        value 31;
        description
          "IPv4 post encap feature QoS policing";
      }
      enum ipf-pe-qos-marking {
        value 32;
        description
          "IPv4 post encap feature QoS marking";
      }
      enum ipf-pe-dpss-flow-acts {
        value 33;
        description
          "IPv4 post encap feature onep DPSS flow actions";
      }
      enum ipf-pe-onep-pol-acts {
        value 34;
        description
          "IPv4 post encap feature onep policy actions PE";
      }
      enum ipf-pe-ether-native-cmd {
        value 35;
        description
          "IPv4 post encap feature IPv4 ether native CMD fixup";
      }
      enum ipf-pe-ether-dot1q-cmd {
        value 36;
        description
          "IPv4 post encap feature IPv4 ether DOT1Q CMD fixup";
      }
      enum ipf-pe-ether-dot1q-in-1q-cmd {
        value 37;
        description
          "IPv4 post encap feature IPv4 ether DOT1Q in 1Q CMD fixup";
      }
      enum ipf-pe-cent {
        value 38;
        description
          "IPv4 post encap feature CENT auto tunnel";
      }
      enum ipf-pe-packet-capture {
        value 39;
        description
          "IPv4 post encap feature CEF packet capture";
      }
      enum ipf-pe-process-packet-capture {
        value 40;
        description
          "IPv4 post encap feature CEF process packet capture";
      }
      enum ipf-pe-out-li {
        value 41;
        description
          "IPv4 post encap feature post encap packet capture for lawful intercept";
      }
      enum ipf-pe-final-handoff-node {
        value 42;
        description
          "IPv4 post encap feature final output handoff node";
      }
      enum ipf-pe-trm-fixup {
        value 43;
        description
          "IPv4 post encap feature tenant routed multicast";
      }
    }
    description
      "IPv4 FIB/CEF post encap switch statistics feature";
  }

  typedef ipv4-for-us-switching-feature {
    type enumeration {
      enum ipf-for-us-none {
        value 0;
        description
          "IPv4 feature for us none";
      }
      enum ipf-for-us-rb-rbacl {
        value 1;
        description
          "IPv4 feature for us role-based access list";
      }
      enum ipf-for-us-nat {
        value 2;
        description
          "IPv4 feature for us network address translation";
      }
      enum ipf-for-us-cce-post-n-c {
        value 3;
        description
          "IPv4 feature for us CCE post NAT";
      }
      enum ipf-for-us-cce-firewall {
        value 4;
        description
          "IPv4 feature for us CCE firewall";
      }
      enum ipf-for-us-inspect {
        value 5;
        description
          "IPv4 feature for us inspect";
      }
      enum ipf-for-us-debug-packet {
        value 6;
        description
          "IPv4 feature for us debug packet";
      }
      enum ipf-for-us-rg-ar {
        value 7;
        description
          "IPv4 feature for us RG AR for us";
      }
      enum ipf-for-us-udp-fatpath {
        value 8;
        description
          "IPv4 feature for us UDP fast path";
      }
      enum ipf-for-us-copp {
        value 9;
        description
          "IPv4 feature for us control plane policing";
      }
    }
    description
      "IPV4 FIB/CEF for-us switch statistics feature";
  }

  typedef ipv4-punt-switching-feature {
    type enumeration {
      enum ipf-punt-none {
        value 0;
        description
          "IPv4 feature punt none";
      }
      enum ipf-punt-cppr {
        value 1;
        description
          "IPv4 feature punt control plane protection";
      }
      enum ipf-punt-sla {
        value 2;
        description
          "IPv4 feature punt service level agreement";
      }
      enum ipf-punt-netflow {
        value 3;
        description
          "IPv4 feature punt netflow";
      }
      enum ipf-punt-tcp-adjust-mss {
        value 4;
        description
          "IPv4 feature punt TCP adjust MSS";
      }
      enum ipf-punt-spd-c {
        value 5;
        description
          "IPv4 feature punt SPD classify";
      }
      enum ipf-punt-input-fnf {
        value 6;
        description
          "IPv4 feature punt input FNF";
      }
      enum ipf-punt-protbundle-in {
        value 7;
        description
          "IPv4 feature punt port bundle host key feature undo";
      }
      enum ipf-punt-packet-capture {
        value 8;
        description
          "IPv4 feature punt packet capture";
      }
      enum ipf-punt-wccp {
        value 9;
        description
          "IPv4 feature punt back out WCCp redirection";
      }
      enum ipf-punt-bma-redrct {
        value 10;
        description
          "IPv4 feature punt broadcast multi-access redirect";
      }
      enum ipf-punt-crypto-map-ipsec {
        value 11;
        description
          "IPv4 feature punt IPSec punt";
      }
      enum ipf-punt-cce-notify {
        value 12;
        description
          "IPv4 feature punt CCE DP turbo notify";
      }
      enum ipf-punt-perf-mon-async {
        value 13;
        description
          "IPv4 feature punt performance monitor async punt";
      }
      enum ipf-punt-ttl-check-multicast {
        value 14;
        description
          "IPv4 feature punt TTL check for multicast pkt";
      }
    }
    description
      "IPv4 FIB/CEF punt switch statistics feature";
  }

  typedef ipv4-local-switching-feature {
    type enumeration {
      enum ipf-local-none {
        value 0;
        description
          "IPv4 feature local none";
      }
      enum ipf-local-punt-unrec-feat {
        value 1;
        description
          "IPv4 feature local punt unrecognised feature";
      }
      enum ipf-local-nat {
        value 2;
        description
          "IPv4 feature local network address translation";
      }
      enum ipf-local-policy {
        value 3;
        description
          "IPv4 feature local policy routing";
      }
      enum ipf-local-casa {
        value 4;
        description
          "IPv4 feature local cisco appliance and services architecture";
      }
      enum ipf-local-packet-capture {
        value 5;
        description
          "IPv4 feature local packet capture";
      }
      enum ipf-local-udlr {
        value 6;
        description
          "IPv4 feature local uni-directional link routing";
      }
      enum ipf-local-rcli {
        value 7;
        description
          "IPv4 feature local remote CLI";
      }
      enum ipf-local-clustering {
        value 8;
        description
          "IPv4 feature local local clustering";
      }
      enum ipf-local-ezvpn {
        value 9;
        description
          "IPv4 feature local EzVPN local";
      }
      enum ipf-local-wlc {
        value 10;
        description
          "IPv4 feature local wireless controller";
      }
      enum ipf-local-sslvpn-bw-check {
        value 11;
        description
          "IPv4 feature local SSLVPN bandwidth check local";
      }
      enum ipf-local-csg-app {
        value 12;
        description
          "IPv4 feature local CSG application";
      }
      enum ipf-local-rb-proxy {
        value 13;
        description
          "IPv4 feature local role-based proxy";
      }
      enum ipf-local-pmip-mag-lmn {
        value 14;
        description
          "IPv4 feature local logical MN local";
      }
      enum ipf-local-ike-proxy {
        value 15;
        description
          "IPv4 feature local local-ike proxy";
      }
      enum ipf-local-auth-proxy {
        value 16;
        description
          "IPv4 feature local auth proxy";
      }
    }
    description
      "IPv4 FIB/CEF local switch statistics feature";
  }

  typedef ipv6-fib-not-cef-reason {
    type enumeration {
      enum v6fib-ncr-no-route {
        value 0;
        description
          "IPv6 FIB not CEF reason no route";
      }
      enum v6fib-ncr-receive {
        value 1;
        description
          "IPv6 FIB not CEF reason packet destined For-us";
      }
      enum v6fib-ncr-encap-failed {
        value 2;
        description
          "IPv6 FIB not CEF reason encapsulation failure";
      }
      enum v6fib-ncr-encap-resource {
        value 3;
        description
          "IPv6 FIB not CEF reason encapsulation resource";
      }
      enum v6fib-ncr-no-adjacency {
        value 4;
        description
          "IPv6 FIB not CEF reason no adjacency";
      }
      enum v6fib-ncr-incmp-adj {
        value 5;
        description
          "IPv6 FIB not CEF reason incomplete adjacency";
      }
      enum v6fib-ncr-loop-detected {
        value 6;
        description
          "IPv6 FIB not CEF reason output chain looped";
      }
      enum v6fib-ncr-unresolved {
        value 7;
        description
          "IPv6 FIB not CEF reason unresolved route";
      }
      enum v6fib-ncr-unsup {
        value 8;
        description
          "IPv6 FIB not CEF reason unsupported";
      }
      enum v6fib-ncr-illegal-len {
        value 9;
        description
          "IPv6 FIB not CEF reason illegal length";
      }
      enum v6fib-ncr-bad-hop {
        value 10;
        description
          "IPv6 FIB not CEF reason bad hop, TTL expired";
      }
      enum v6fib-ncr-hop-options {
        value 11;
        description
          "IPv6 FIB not CEF reason hop-by-hop header";
      }
      enum v6fib-ncr-frag-fail {
        value 12;
        description
          "IPv6 FIB not CEF reason fragmentation failed";
      }
      enum v6fib-ncr-discard {
        value 13;
        description
          "IPv6 FIB not CEF reason discard";
      }
      enum v6fib-ncr-nu110 {
        value 14;
        description
          "IPv6 FIB not CEF reason routed to Null0";
      }
      enum v6fib-ncr-multicast {
        value 15;
        description
          "IPv6 FIB not CEF reason multicast";
      }
      enum v6fib-ncr-feat {
        value 16;
        description
          "IPv6 FIB not CEF reason features";
      }
      enum v6fib-ncr-shaping {
        value 17;
        description
          "IPv6 FIB not CEF reason shaping";
      }
      enum v6fib-ncr-ip-redrct {
        value 18;
        description
          "IPv6 FIB not CEF reason IPv6 redirects";
      }
      enum v6fib-ncr-p2p-connected {
        value 19;
        description
          "IPv6 FIB not CEF reason routed to P2P prefix";
      }
      enum v6fib-ncr-mtu-exceeded {
        value 20;
        description
          "IPv6 FIB not CEF reason MTU exceeded";
      }
      enum v6fib-ncr-linklocal {
        value 21;
        description
          "IPv6 FIB not CEF reason link-local source address";
      }
      enum v6fib-ncr-unclassified {
        value 22;
        description
          "IPv6 FIB not CEF reason unclassified reason";
      }
      enum v6fib-ncr-access-fail {
        value 23;
        description
          "IPv6 FIB not CEF reason access-list deny";
      }
      enum v6fib-ncr-urpf-fail {
        value 24;
        description
          "IPv6 FIB not CEF reason unicast RPF fail";
      }
      enum v6fib-ncr-neighbor-res-req {
        value 25;
        description
          "IPv6 FIB not CEF reason neighbor resolution req";
      }
      enum v6fib-ncr-runt-packet {
        value 26;
        description
          "IPv6 FIB not CEF reason runt packet";
      }
      enum v6fib-ncr-bad-version {
        value 27;
        description
          "IPv6 FIB not CEF reason bad version";
      }
      enum v6fib-ncr-no-adj-fltrd {
        value 28;
        description
          "IPv6 FIB not CEF reason no adjacency (filtered)";
      }
      enum v6fib-ncr-incmp-adj-fltrd {
        value 29;
        description
          "IPv6 FIB not CEF reason incomplete adjacency (filtered)";
      }
      enum v6fib-ncr-decap-recursion-limit {
        value 30;
        description
          "IPv6 FIB not CEF reason decap recursion limit";
      }
      enum v6fib-ncr-td-pak-validation {
        value 31;
        description
          "IPv6 FIB not CEF reason tun decap, packet validation";
      }
      enum v6fib-ncr-td-src {
        value 32;
        description
          "IPv6 FIB not CEF reason tun decap, source";
      }
      enum v6fib-ncr-td-dst {
        value 33;
        description
          "IPv6 FIB not CEF reason tun decap, destination";
      }
      enum v6fib-ncr-td-transport-table {
        value 34;
        description
          "IPv6 FIB not CEF reason tun decap, transport table";
      }
      enum v6fib-ncr-td-protocol {
        value 35;
        description
          "IPv6 FIB not CEF reason tun decap, protocol";
      }
      enum v6fib-ncr-td-no-vector {
        value 36;
        description
          "IPv6 FIB not CEF reason tun decap, no vector";
      }
      enum v6fib-ncr-td-no-dispatcher {
        value 37;
        description
          "IPv6 FIB not CEF reason tun Decap, no dispatcher";
      }
      enum v6fib-ncr-td-dispatcher-drop {
        value 38;
        description
          "IPv6 FIB not CEF reason tun decap, dispatcher drop";
      }
      enum v6fib-ncr-td-no-protocol {
        value 39;
        description
          "IPv6 FIB not CEF reason tun decap, no protocol";
      }
      enum v6fib-ncr-td-gre-options {
        value 40;
        description
          "IPv6 FIB not CEF reason tun decap, GRE options";
      }
      enum v6fib-ncr-td-gre-key-mismatch {
        value 41;
        description
          "IPv6 FIB not CEF reason tun decap, GRE key";
      }
      enum v6fib-ncr-td-gre-unsup-payload {
        value 42;
        description
          "IPv6 FIB not CEF reason tun decap, GRE payload";
      }
      enum v6fib-ncr-no-adj-queued-resolution {
        value 43;
        description
          "IPv6 FIB not CEF reason no adjacency, queued resolution";
      }
      enum v6fib-ncr-incmp-adj-queued {
        value 44;
        description
          "IPv6 FIB not CEF reason incomplete adjacency, queued resolution";
      }
      enum v6fib-ncr-bad-checksum {
        value 45;
        description
          "IPv6 FIB not CEF reason bad checksum";
      }
      enum v6fib-ncr-unspec-src-addr {
        value 46;
        description
          "IPv6 FIB not CEF reason unspecified source address";
      }
      enum v6fib-ncr-bad-src-addr {
        value 47;
        description
          "IPv6 FIB not CEF reason bad source address";
      }
      enum v6fib-ncr-unable-to-coalesce {
        value 48;
        description
          "IPv6 FIB not CEF reason unable to coalesce";
      }
      enum v6fib-ncr-lisp-too-small {
        value 49;
        description
          "IPv6 FIB not CEF reason LISP too small";
      }
      enum v6fib-ncr-lisp-unkn-iid {
        value 50;
        description
          "IPv6 FIB not CEF reason LISP unknown instance ID";
      }
      enum v6fib-ncr-tx-fs-unsup {
        value 51;
        description
          "IPv6 FIB not CEF reason TX fast switching unsupported";
      }
      enum v6fib-ncr-adj-fixup {
        value 52;
        description
          "IPv6 FIB not CEF reason adjacency fixup";
      }
    }
    description
      "IPv6 FIB/CEF not CEF reason switch statistics";
  }

  typedef ipv6-input-switching-feature {
    type enumeration {
      enum ipv6f-in-none {
        value 0;
        description
          "IPv6 input feature none";
      }
      enum ipv6f-in-no-cef {
        value 1;
        description
          "IPv6 input feature no CEF switching";
      }
      enum ipv6f-in-debug-packet {
        value 2;
        description
          "IPv6 input feature debug packet";
      }
      enum ipv6f-in-cft {
        value 3;
        description
          "IPv6 input feature common flow table";
      }
      enum ipv6f-in-stile {
        value 4;
        description
          "IPv6 input feature stile classification";
      }
      enum ipv6f-in-stile-cypher-text {
        value 5;
        description
          "IPv6 input feature stile classification on cypher text";
      }
      enum ipv6f-in-metadata {
        value 6;
        description
          "IPv6 input feature flow metadata";
      }
      enum ipv6f-in-cce-c {
        value 7;
        description
          "IPv6 input feature CCE input classification";
      }
      enum ipv6f-in-perf-mon-c {
        value 8;
        description
          "IPv6 input feature input performance monitor classification";
      }
      enum ipv6f-in-smef-c {
        value 9;
        description
          "IPv6 input feature service/metadata exchange input classification";
      }
      enum ipv6f-in-onep-mpss-pkt {
        value 10;
        description
          "IPv6 input feature multiprotocol stateless switching IP header processing";
      }
      enum ipv6f-in-dpss-flow-acts {
        value 11;
        description
          "IPv6 input feature ONEP DPSS flow actions";
      }
      enum ipv6f-in-onep-pol-acts {
        value 12;
        description
          "IPv6 input feature input-onep-pol-acts";
      }
      enum ipv6f-in-perf-mon {
        value 13;
        description
          "IPv6 input feature input performance monitor";
      }
      enum ipv6f-in-perf-mon-ts {
        value 14;
        description
          "IPv6 input feature performance monitor get timestamp";
      }
      enum ipv6f-in-vqm {
        value 15;
        description
          "IPv6 input feature input video quality monitor";
      }
      enum ipv6f-in-fnf {
        value 16;
        description
          "IPv6 input feature input flexible netflow";
      }
      enum ipv6f-in-global-fnf {
        value 17;
        description
          "IPv6 input feature input global flexible netflow";
      }
      enum ipv6f-in-netflow-ingress {
        value 18;
        description
          "IPv6 input feature ingress netflow";
      }
      enum ipv6f-in-packet-capture {
        value 19;
        description
          "IPv6 input feature packet capture";
      }
      enum ipv6f-in-process-packet-capture {
        value 20;
        description
          "IPv6 input feature process packet capture";
      }
      enum ipv6f-in-lisp-smr {
        value 21;
        description
          "IPv6 input feature LISP-SMR";
      }
      enum ipv6f-in-punt-unrec-feat {
        value 22;
        description
          "IPv6 input feature punt unrecognised feature";
      }
      enum ipv6f-in-dialer-input-if-override {
        value 23;
        description
          "IPv6 input feature dialer I/F override";
      }
      enum ipv6f-in-lisp-mobility {
        value 24;
        description
          "IPv6 input feature LISP mobility";
      }
      enum ipv6f-in-lisp-disable {
        value 25;
        description
          "IPv6 input feature LISP disable";
      }
      enum ipv6f-in-lisp {
        value 26;
        description
          "IPv6 input feature LISP-ETR";
      }
      enum ipv6f-in-rtg-mode {
        value 27;
        description
          "IPv6 input feature host mode";
      }
      enum ipv6f-in-iedge-ip-sess-classifier {
        value 28;
        description
          "IPv6 input feature i-Edge IPv6 session input classifier";
      }
      enum ipv6f-in-nam-monitoring {
        value 29;
        description
          "IPv6 input feature NAM monitoring";
      }
      enum ipv6f-in-sm-monitoring {
        value 30;
        description
          "IPv6 input feature SM monitoring";
      }
      enum ipv6f-in-qos-c {
        value 31;
        description
          "IPv6 input feature QOS classify";
      }
      enum ipv6f-in-cpc {
        value 32;
        description
          "IPv6 input feature common pak sub-block";
      }
      enum ipv6f-in-vfr {
        value 33;
        description
          "IPv6 input feature virtual fragment reassembly";
      }
      enum ipv6f-in-auth-proxy {
        value 34;
        description
          "IPv6 input feature auth proxy";
      }
      enum ipv6f-in-epm-http-redrct {
        value 35;
        description
          "IPv6 input feature EPM HTTP redirect";
      }
      enum ipv6f-in-cmn-acl {
        value 36;
        description
          "IPv6 input feature common access list";
      }
      enum ipv6f-in-acl {
        value 37;
        description
          "IPv6 input feature access list";
      }
      enum ipv6f-in-qos-acts {
        value 38;
        description
          "IPv6 input feature QOS actions";
      }
      enum ipv6f-in-pbr {
        value 39;
        description
          "IPv6 input feature policy-based routing";
      }
      enum ipv6f-in-ipsec {
        value 40;
        description
          "IPv6 input feature IPSEC";
      }
      enum ipv6f-in-rpf {
        value 41;
        description
          "IPv6 input feature verify unicast reverse-path";
      }
      enum ipv6f-in-cft-post-vpn {
        value 42;
        description
          "IPv6 input feature common flow table post VPN";
      }
      enum ipv6f-in-cce-post-crypto-c {
        value 43;
        description
          "IPv6 input feature CCE input post crypto classification";
      }
      enum ipv6f-in-perf-mon-async {
        value 44;
        description
          "IPv6 input feature in performance monitor async";
      }
      enum ipv6f-in-pa {
        value 45;
        description
          "IPv6 input feature performance agent";
      }
      enum ipv6f-in-mace {
        value 46;
        description
          "IPv6 input feature measurement aggregation correlation engine input";
      }
      enum ipv6f-in-pa-post-waas {
        value 47;
        description
          "IPv6 input feature performance agent post WAAS";
      }
      enum ipv6f-in-stile-clear-text {
        value 48;
        description
          "IPv6 input feature stile classification on clear text";
      }
      enum ipv6f-in-ip-multiplex {
        value 49;
        description
          "IPv6 input feature IPv6 multiplexing";
      }
      enum ipv6f-in-mr {
        value 50;
        description
          "IPv6 input feature mobile router filters";
      }
      enum ipv6f-in-li {
        value 51;
        description
          "IPv6 input feature lawful intercept";
      }
      enum ipv6f-in-wccp {
        value 52;
        description
          "IPv6 input feature web cache communications protocol";
      }
      enum ipv6f-in-gtp {
        value 53;
        description
          "IPv6 input feature GPRS tunneling protocol";
      }
      enum ipv6f-in-sbc {
        value 54;
        description
          "IPv6 input feature session border controller";
      }
      enum ipv6f-in-casa {
        value 55;
        description
          "IPv6 input feature IPv6 CASA";
      }
      enum ipv6f-in-rb-proxy {
        value 56;
        description
          "IPv6 input feature role-based proxy";
      }
      enum ipv6f-in-pdsn {
        value 57;
        description
          "IPv6 input feature packet data serving node";
      }
      enum ipv6f-in-bma-redrct {
        value 58;
        description
          "IPv6 input feature broadcast multi access redirect";
      }
      enum ipv6f-in-csg2-app {
        value 59;
        description
          "IPv6 input feature CSG application";
      }
      enum ipv6f-in-lisp-alt-intercept {
        value 60;
        description
          "IPv6 input feature LISP ALT intercept";
      }
      enum ipv6f-in-rpl-fwd {
        value 61;
        description
          "IPv6 input feature routing policy language";
      }
      enum ipv6f-in-iedge {
        value 62;
        description
          "IPv6 input feature i-Edge IPv6 features input path";
      }
      enum ipv6f-in-iedge-ip-sess-feats {
        value 63;
        description
          "IPv6 input feature i-Edge IPv6 features input session";
      }
      enum ipv6f-in-iedge-ip-sess-driver {
        value 64;
        description
          "IPv6 input feature i-Edge IPv6 session RX driver";
      }
      enum ipv6f-in-pmip-revtunn {
        value 65;
        description
          "IPv6 input feature proxy mobile IPv6 reverse tunnel";
      }
      enum ipv6f-in-tun-to-redrct {
        value 66;
        description
          "IPv6 input feature tunnel to traffic redirection";
      }
      enum ipv6f-in-tweak-mss {
        value 67;
        description
          "IPv6 input feature IPv6 TCP adjust MSS";
      }
      enum ipv6f-in-vmi-switch-pak {
        value 68;
        description
          "IPv6 input feature virtual multipoint interface control plane packets switch";
      }
      enum ipv6f-in-plat-sc {
        value 69;
        description
          "IPv6 input feature HW shortcut installation";
      }
    }
    description
      "IPv6 FIB/CEF input switch statistics feature";
  }

  typedef ipv6-output-switching-feature {
    type enumeration {
      enum ipv6f-out-none {
        value 0;
        description
          "IPv6 output feature none";
      }
      enum ipv6f-out-punt-unrec-feat {
        value 1;
        description
          "IPv6 output feature punt unrecognised feature";
      }
      enum ipv6f-out-iedge-ip-sess-classifier {
        value 2;
        description
          "IPv6 output feature i-Edge IPv6 session output classifier";
      }
      enum ipv6f-out-ip-multiplex {
        value 3;
        description
          "IPv6 output feature IPv6 multiplexing";
      }
      enum ipv6f-out-cpc {
        value 4;
        description
          "IPv6 output feature common pak sub-block in egress";
      }
      enum ipv6f-out-vfr {
        value 5;
        description
          "IPv6 output feature virtual fragment reassembly in egress";
      }
      enum ipv6f-out-cft {
        value 6;
        description
          "IPv6 output feature common flow table";
      }
      enum ipv6f-out-stile {
        value 7;
        description
          "IPv6 output feature stile classification";
      }
      enum ipv6f-out-ioam6-pr6 {
        value 8;
        description
          "IPv6 output feature in-band oam IPv6 insertion";
      }
      enum ipv6f-out-metadata {
        value 9;
        description
          "IPv6 output feature flow metadata";
      }
      enum ipv6f-out-netflow-ingress {
        value 10;
        description
          "IPv6 output feature post ingress netflow";
      }
      enum ipv6f-out-rtg-mode {
        value 11;
        description
          "IPv6 output feature host mode";
      }
      enum ipv6f-out-wccp {
        value 12;
        description
          "IPv6 output feature web cache communications protocol";
      }
      enum ipv6f-out-cce-c {
        value 13;
        description
          "IPv6 output feature cce classification";
      }
      enum ipv6f-out-cce-firewall {
        value 14;
        description
          "IPv6 output feature zone based firewall";
      }
      enum ipv6f-out-qos-c {
        value 15;
        description
          "IPv6 output feature QoS classify";
      }
      enum ipv6f-out-rb-rbacl {
        value 16;
        description
          "IPv6 output feature role-based access list";
      }
      enum ipv6f-out-cmn-acl {
        value 17;
        description
          "IPv6 output feature common access list";
      }
      enum ipv6f-out-onep-mpss-pkt {
        value 18;
        description
          "IPv6 output feature multiprotocol stateless switching IP header processing";
      }
      enum ipv6f-out-dpss-flow-acts {
        value 19;
        description
          "IPv6 output feature onep DPSS flow actions";
      }
      enum ipv6f-out-onep-pol-acts {
        value 20;
        description
          "IPv6 output feature output onep policy actions";
      }
      enum ipv6f-out-video-im {
        value 21;
        description
          "IPv6 output feature video intelligent marking";
      }
      enum ipv6f-out-qos-acts {
        value 22;
        description
          "IPv6 output feature QoS actions";
      }
      enum ipv6f-out-mr {
        value 23;
        description
          "IPv6 output feature mobile router encapsulation";
      }
      enum ipv6f-out-inspect {
        value 24;
        description
          "IPv6 output feature firewall inspection";
      }
      enum ipv6f-out-post-perf-mon-async {
        value 25;
        description
          "IPv6 output feature performance monitor async post";
      }
      enum ipv6f-out-perf-mon-async {
        value 26;
        description
          "IPv6 output feature out performance monitor async";
      }
      enum ipv6f-out-pa {
        value 27;
        description
          "IPv6 output feature performance agent";
      }
      enum ipv6f-out-mace {
        value 28;
        description
          "IPv6 output feature measurement aggregation correlation engine output";
      }
      enum ipv6f-out-pa-post-waas {
        value 29;
        description
          "IPv6 output feature performance agent post waas";
      }
      enum ipv6f-out-nat64 {
        value 30;
        description
          "IPv6 output feature NAT64";
      }
      enum ipv6f-out-n-pt {
        value 31;
        description
          "IPv6 output feature NST PT";
      }
      enum ipv6f-out-li {
        value 32;
        description
          "IPv6 output feature lawful intercept";
      }
      enum ipv6f-out-iedge {
        value 33;
        description
          "IPv6 output feature i-Edge IPv6 features output path";
      }
      enum ipv6f-out-gtp {
        value 34;
        description
          "IPv6 output feature GPRS tunneling protocol";
      }
      enum ipv6f-out-mfib-adj-fixup {
        value 35;
        description
          "IPv6 output feature multicast FIB adjacency";
      }
      enum ipv6f-out-input-interface-drop {
        value 36;
        description
          "IPv6 output feature input interface drop";
      }
      enum ipv6f-out-nhrp-shortcut {
        value 37;
        description
          "IPv6 output feature NHRP shortcut switching";
      }
      enum ipv6f-out-nhrp-redrct {
        value 38;
        description
          "IPv6 output feature NHRP redirect";
      }
      enum ipv6f-out-input-fnf-pre-crypto {
        value 39;
        description
          "IPv6 output feature post input pre crypto flexible netflow";
      }
      enum ipv6f-out-ipsec {
        value 40;
        description
          "IPv6 output feature IPSEC";
      }
      enum ipv6f-out-check-hwidb {
        value 41;
        description
          "IPv6 output feature check HW IDB";
      }
      enum ipv6f-out-cts-l3 {
        value 42;
        description
          "IPv6 output feature CTS layer 3";
      }
      enum ipv6f-out-rpl-fwd {
        value 43;
        description
          "IPv6 output feature routing policy language";
      }
      enum ipv6f-out-iedge-ip-sess-feats {
        value 44;
        description
          "IPv6 output feature i-Edge IPv6 session output features";
      }
      enum ipv6f-out-pmip-gre {
        value 45;
        description
          "IPv6 output feature proxy mobile IPv6 GRE encap";
      }
      enum ipv6f-out-tweak-mss {
        value 46;
        description
          "IPv6 output feature IPv6 TCP adjust MSS";
      }
      enum ipv6f-out-nam-monitoring {
        value 47;
        description
          "IPv6 output feature NAM out packet monitoring";
      }
      enum ipv6f-out-sm-monitoring {
        value 48;
        description
          "IPv6 output feature SM out packet monitoring";
      }
      enum ipv6f-out-punt-unrec-pe-feat {
        value 49;
        description
          "IPv6 output feature punt unrecognised PE feature";
      }
      enum ipv6f-out-debug-packet {
        value 50;
        description
          "IPv6 output feature debug packet";
      }
      enum ipv6f-out-acl {
        value 51;
        description
          "IPv6 output feature access list";
      }
      enum ipv6f-out-plat-sc {
        value 52;
        description
          "IPv6 output feature hw shortcut installation";
      }
      enum ipv6f-out-dialer-idle-reset {
        value 53;
        description
          "IPv6 output feature dialer idle reset";
      }
      enum ipv6f-out-icmp-unreach {
        value 54;
        description
          "IPv6 output feature icmpv6 unreachables";
      }
      enum ipv6f-out-perf-mon {
        value 55;
        description
          "IPv6 output feature output performance monitor";
      }
      enum ipv6f-out-vqm {
        value 56;
        description
          "IPv6 output feature output video quality monitor";
      }
      enum ipv6f-out-input-fnf {
        value 57;
        description
          "IPv6 output feature post input flexible netflow";
      }
      enum ipv6f-out-fnf {
        value 58;
        description
          "IPv6 output feature output flexible netflow";
      }
      enum ipv6f-out-global-fnf {
        value 59;
        description
          "IPv6 output feature output global flexible netflow";
      }
    }
    description
      "IPv6 FIB/CEF output switch statistics feature";
  }

  typedef ipv6-post-encap-switching-feature {
    type enumeration {
      enum ipv6f-post-encap-none {
        value 0;
        description
          "IPv6 post encap feature none";
      }
      enum ipv6-feat-pe-tunnel-cmd-fixup {
        value 1;
        description
          "IPv6 post encap feature service/metadata exchange CMD fixup";
      }
      enum ipv6-feat-pe-nsh-fixup {
        value 2;
        description
          "IPv6 post encap feature service/metadata exchange NSH fixup";
      }
      enum ipv6-feat-pe-lisp-fixup {
        value 3;
        description
          "IPv6 post encap feature location identifier separation protocol";
      }
      enum ipv6-feat-pe-dike {
        value 4;
        description
          "IPv6 post encap feature data over IKEV2 post encap output classification";
      }
      enum ipv6f-post-encap-ipsec {
        value 5;
        description
          "IPv6 post encap feature IPSEC post encap output classification";
      }
      enum ipv6f-post-encap-hw-sc {
        value 6;
        description
          "IPv6 post encap feature HW shortcut";
      }
      enum ipv6f-post-encap-qos-acts {
        value 7;
        description
          "IPv6 post encap feature QoS actions";
      }
      enum ipv6f-post-encap-vmi {
        value 8;
        description
          "IPv6 post encap feature QoS on virtual multipoint interface";
      }
      enum ipv6-feat-pe-tun-to {
        value 9;
        description
          "IPv6 post encap feature tunnel-to";
      }
      enum ipv6-feat-pe-pmip-gre-encap {
        value 10;
        description
          "IPv6 post encap feature proxy mobile IP GRE encap";
      }
      enum ipv6-feat-pe-dpss-flow-acts {
        value 11;
        description
          "IPv6 post encap feature onep DPSS flow actions";
      }
      enum ipv6-feat-pe-onep-pol-acts {
        value 12;
        description
          "IPv6 post encap feature onep policy actions PE";
      }
      enum ipv6-feat-pe-ether-native-cmd {
        value 13;
        description
          "IPv6 post encap feature ipv6 ether native CMD fixup";
      }
      enum ipv6-feat-pe-ether-dot1q-cmd {
        value 14;
        description
          "IPv6 post encap feature ipv6 ether DOT1Q CMD fixup";
      }
      enum ipv6-feat-pe-ether-dot1q-in-1q-cmd {
        value 15;
        description
          "IPv6 post encap feature ipv6 ether DOT1Q in 1Q CMD fixup";
      }
      enum ipv6f-post-encap-packet-capture {
        value 16;
        description
          "IPv6 post encap feature packet capture";
      }
      enum ipv6-feat-pe-process-packet-capture {
        value 17;
        description
          "IPv6 post encap feature process packet capture";
      }
      enum ipv6-feat-pe-tun-6rd {
        value 18;
        description
          "IPv6 post encap feature tunnel 6RD";
      }
    }
    description
      "IPv6 fib/CEF post encap switch statistics feature";
  }

  typedef ipv6-for-us-switching-feature {
    type enumeration {
      enum ipv6f-for-us-none {
        value 0;
        description
          "IPv6 for-us feature none";
      }
      enum ipv6f-for-us-debud-packet {
        value 1;
        description
          "IPv6 for-us feature debug packet";
      }
      enum ipv6f-for-us-ipsec {
        value 2;
        description
          "IPv6 for-us feature ipsec protection for locally terminated IPv6 pak";
      }
      enum ipv6f-for-us-rb-rbacl {
        value 3;
        description
          "IPv6 for-us feature role-based access list";
      }
      enum ipv6f-for-us-cts-l3 {
        value 4;
        description
          "IPv6 for-us feature CTS layer 3";
      }
      enum ipv6f-for-us-cce-c {
        value 5;
        description
          "IPv6 for-us feature CCE classification";
      }
      enum ipv6f-for-us-cce-firewall {
        value 6;
        description
          "IPv6 for-us feature zone based firewall";
      }
      enum ipv6f-for-us-tcp-adjust-mss {
        value 7;
        description
          "IPv6 for-us feature IPv6 TCP adjust MSS";
      }
      enum ipv6f-for-us-wpan-mcast-fwd-agent {
        value 8;
        description
          "IPv6 for-us feature wireless personal area network IPv6 mesh multicast forward agent";
      }
      enum ipv6f-for-us-nat64-map {
        value 9;
        description
          "IPv6 for-us feature NAT64 map-e";
      }
      enum ipv6f-for-us-lfts-intercept {
        value 10;
        description
          "IPv6 for-us feature classic IOS LFTS intercept";
      }
    }
    description
      "IPv6 FIB/CEF for-us switch statistics feature";
  }

  typedef ipv6-punt-switching-feature {
    type enumeration {
      enum ipv6f-punt-none {
        value 0;
        description
          "IPv6 punt feature none";
      }
      enum ipv6f-punt-cppr {
        value 1;
        description
          "IPv6 punt feature control plane protection";
      }
      enum ipv6f-punt-fnf {
        value 2;
        description
          "IPv6 punt feature flexible netflow";
      }
      enum ipv6f-punt-wccp {
        value 3;
        description
          "IPv6 punt feature back out WCCP redirection";
      }
      enum ipv6f-punt-spd-c {
        value 4;
        description
          "IPv6 punt feature SPD classification";
      }
      enum ipv6f-punt-bma-redrct {
        value 5;
        description
          "IPv6 punt feature broadcast multi access redirect";
      }
      enum ipv6f-punt-packet-capture {
        value 6;
        description
          "IPv6 punt feature packet capture";
      }
      enum ipv6f-punt-tcp-adjust-mss {
        value 7;
        description
          "IPv6 punt feature IPv6 TCP adjust MSS";
      }
      enum ipv6f-punt-sla {
        value 8;
        description
          "IPv6 punt feature IPv6 SLA";
      }
      enum ipv6f-punt-perf-mon-async {
        value 9;
        description
          "IPv6 punt feature performance monitor async punt";
      }
      enum ipv6f-punt-ttl-check-multicast {
        value 10;
        description
          "IPv6 punt feature IPv6 TTL check for multicast";
      }
    }
    description
      "IPv6 FIB/CEF punt switch statistics feature";
  }

  grouping fib-nexthop-entry {
    description
      "FIB Next-hop Entry";
    leaf nh-addr {
      type inet:ip-prefix;
      description
        "Next hop IP Address";
    }
    leaf index {
      type uint32;
      description
        "Unique Next-hop Path Index";
    }
    leaf af {
      type fib-ios-xe-oper:fib-address-family;
      description
        "Specifies the address family (such as IPv4 or IPv6) for this next-hop entry.";
    }
    leaf ifname {
      type string;
      description
        "Output Interface Name";
    }
    leaf path-type {
      type fib-ios-xe-oper:fib-path-type;
      description
        "FIB path type";
    }
    leaf path-id {
      type uint32;
      description
        "Unique Next-hop Path Index";
    }
    leaf weight {
      type uint8;
      description
        "Relative weight assigned to this next-hop for load balancing purposes.";
    }
    leaf encap {
      type fib-ios-xe-oper:encapsulation-header-type;
      description
        "Type of encapsulation header applied to packets forwarded via this next-hop.";
    }
    leaf decap {
      type fib-ios-xe-oper:encapsulation-header-type;
      description
        "Type of header to be removed from packets received on this next-hop.";
    }
    leaf resolved-nh-addr {
      type inet:ip-prefix;
      description
        "Resolved Nexthop IP Address";
    }
  }

  grouping fib-entry {
    description
      "FIB Entry";
    leaf ip-addr {
      type inet:ip-prefix;
      description
        "IP prefix for this FIB entry.";
    }
    leaf instance-name {
      type string;
      description
        "Name of the FIB network instance (such as the VRF or default routing context) to which this entry belongs.";
    }
    leaf af {
      type fib-ios-xe-oper:fib-address-family;
      description
        "Specifies the address family (such as IPv4 or IPv6) associated with this FIB entry.";
    }
    leaf num-paths {
      type uint8;
      description
        "Number of Paths available";
    }
    leaf packets-forwarded {
      type uint64;
      description
        "Packets forwarded through this entry";
    }
    leaf octets-forwarded {
      type uint64;
      description
        "Octets forwarded through this entry";
    }
    list fib-nexthop-entries {
      key "nh-addr";
      description
        "List of FIB next-hop entries";
      uses fib-ios-xe-oper:fib-nexthop-entry;
    }
  }

  grouping fib-ni-entry {
    description
      "FIB Network Instance Entry";
    leaf instance-name {
      type string;
      description
        "Name of the FIB network instance (such as the VRF or default routing context) to which this FIB entry belongs.";
    }
    leaf af {
      type fib-ios-xe-oper:fib-address-family;
      description
        "Address family for the FIB network instance (for example, IPv4 or IPv6).";
    }
    leaf num-pfx {
      type uint32;
      description
        "Number of prefixes";
    }
    leaf num-pfx-fwd {
      type uint32;
      description
        "Number of forwarding prefixes";
    }
    leaf num-pfx-non-fwd {
      type uint32;
      description
        "Number of non-forwarding prefixes";
    }
    list fib-entries {
      key "ip-addr";
      description
        "List of FIB entries";
      uses fib-ios-xe-oper:fib-entry;
    }
  }

  grouping adjacency-entry {
    description
      "FIB adjacency";
    leaf refcount {
      type uint32;
      description
        "Specifies the reference count for the adjacency entry, indicating how many routes or entities are currently using this adjacency in the FIB.";
    }
    leaf incomplete {
      type boolean;
      description
        "Indicates whether the adjacency entry is incomplete, typically meaning that the next-hop information is unresolved or missing.";
    }
  }

  grouping adjacency-entry-key {
    description
      "FIB adjacency key";
    leaf connection-id {
      type uint64;
      description
        "Unique identifier for the adjacency connection, used to distinguish between different adjacency entries in the FIB.";
    }
    leaf address {
      type inet:ip-address;
      description
        "IP address associated with the adjacency entry, representing the next-hop address for forwarding.";
    }
    leaf linktype {
      type fib-ios-xe-oper:adj-link-type;
      description
        "Type of link for the adjacency entry, such as point-to-point, broadcast, or other link layer types.";
    }
    leaf if-name {
      type string;
      description
        "Name of the outgoing interface associated with the adjacency entry.";
    }
  }

  grouping adjacency-table {
    description
      "Adjacency information";
    leaf num-adjacencies {
      type uint32;
      description
        "Number of adjacencies";
    }
    leaf num-complete-adjacencies {
      type uint32;
      description
        "Number of complete adjacencies";
    }
    leaf num-incomplete-adjacencies {
      type uint32;
      description
        "Number of incomplete adjacencies";
    }
    list adjacency-entry {
      key "connection-id address linktype if-name";
      description
        "Adjacency node information";
      uses fib-ios-xe-oper:adjacency-entry;
      uses fib-ios-xe-oper:adjacency-entry-key;
    }
  }

  grouping ipv4-fib-state {
    description
      "Operational state information for IPv4 FIB/CEF on the device.";
    leaf fib-enabled {
      type empty;
      description
        "Indicates whether FIB/CEF is enabled for IPv4 on the device.";
    }
    leaf fib-running {
      type empty;
      description
        "Indicates whether FIB/CEF processes are currently running for IPv4.";
    }
    leaf fib-reenable {
      type empty;
      description
        "Indicates whether FIB/CEF for IPv4 have been re-enabled after being disabled.";
    }
    leaf fib-dist-enabled {
      type empty;
      description
        "Indicates whether distributed FIB/CEF are enabled for IPv4, allowing forwarding decisions to be made on line cards or distributed processing units.";
    }
    leaf fib-dist-running {
      type empty;
      description
        "Indicates whether distributed FIB/CEF processes are currently running for IPv4.";
    }
    leaf fib-dist-reenable {
      type empty;
      description
        "Indicates whether distributed FIB/CEF for IPv4 have been re-enabled after being disabled.";
    }
    leaf fib-shutting-down {
      type empty;
      description
        "Indicates whether FIB/CEF for IPv4 are in the process of shutting down.";
    }
    leaf fib-switching-enabled {
      type empty;
      description
        "Indicates whether packet switching using FIB/CEF is enabled for IPv4.";
    }
    leaf fib-switching-running {
      type empty;
      description
        "Indicates whether packet switching using FIB/CEF is currently active for IPv4.";
    }
    leaf alg-type {
      type fib-ios-xe-oper:fib-hash-algs-type;
      description
        "Specifies the type of hash algorithm used by the FIB for IPv4 route lookups.";
    }
  }

  grouping ipv6-fib-state {
    description
      "Operational state information for IPv6 FIB/CEF on the device.";
    leaf fib-enabled {
      type empty;
      description
        "Indicates whether FIB/CEF is enabled for IPv6.";
    }
    leaf fib-running {
      type empty;
      description
        "Indicates whether FIB/CEF processes are currently running for IPv6.";
    }
    leaf fib-dist-enabled {
      type empty;
      description
        "Indicates whether distributed FIB/CEF are enabled for IPv6.";
    }
    leaf fib-dist-running {
      type empty;
      description
        "Indicates whether distributed FIB/CEF processes are currently running for IPv6.";
    }
    leaf alg-type {
      type fib-ios-xe-oper:fib-hash-algs-type;
      description
        "Specifies the type of hash algorithm used by the FIB for IPv6 route lookups.";
    }
  }

  grouping fib-rrp-state {
    description
      "FIB/CEF redundant route processor (RRP) state";
    leaf i-am-standby {
      type empty;
      description
        "Indicates whether this device is operating as the standby RRP.";
    }
    leaf peer-presence {
      type empty;
      description
        "Indicates whether a Redundancy Facility (RF) peer is present for the RRP.";
    }
    leaf peer-comm-reached {
      type empty;
      description
        "Indicates that communication with the Redundancy Framework (RF) peer has been successfully established.";
    }
    leaf rf-has-done-standby-config {
      type empty;
      description
        "Indicates that the Redundancy Framework (RF) peer has completed standby configuration.";
    }
    leaf rf-prog-blocked {
      type empty;
      description
        "RF progression blocked";
    }
    leaf nsf-sync-enabled {
      type empty;
      description
        "NSF sync enabled";
    }
    leaf lc-nsf-sync-running {
      type empty;
      description
        "LC NSF sync running";
    }
  }

  grouping fib-issu-state {
    description
      "FIB/CEF in-service software upgrade (ISSU) state";
    leaf xdrc-fibhwidb-broker {
      type empty;
      description
        "External Data Representation client FIB Hardware IDB broker";
    }
    leaf xdrc-fibidb-broker {
      type empty;
      description
        "External Data Representation client FIB IDB broker";
    }
    leaf xdrc-fibhwsb-broker {
      type empty;
      description
        "External Data Representation client FIB Hardware Sub-block broker";
    }
    leaf xdrc-fibswsb-broker {
      type empty;
      description
        "External Data Representation client FIB Software Sub-block broker";
    }
    leaf xdrc-adj-broker {
      type empty;
      description
        "Indicates the presence of the External Data Representation client responsible for managing adjacency information during ISSU operations in the FIB/CEF subsystem.";
    }
    leaf xdrc-ipv4-broker {
      type empty;
      description
        "Indicates the presence of the External Data Representation client responsible for managing IPv4 forwarding information during ISSU operations in the FIB/CEF subsystem.";
    }
    leaf xdrc-ipv6-broker {
      type empty;
      description
        "Indicates the presence of the External Data Representation client responsible for managing IPv6 forwarding information during ISSU operations in the FIB/CEF subsystem.";
    }
    leaf xdrc-cef {
      type empty;
      description
        "Indicates the presence of the External Data Representation client responsible for managing CEF state during ISSU operations.";
    }
  }

  grouping fib-state {
    description
      "State information for the FIB/CEF instance.";
    leaf instance-type {
      type fib-ios-xe-oper:fib-instance-type;
      description
        "Specifies the type of FIB/CEF instance, such as IPv4, IPv6, or MPLS.";
    }
    leaf fib-common-enabled {
      type boolean;
      description
        "Indicates whether the common FIB/CEF functionality is enabled for this instance.";
    }
    container ipv4 {
      description
        "Operational state information for IPv4 FIB/CEF on the device.";
      uses fib-ios-xe-oper:ipv4-fib-state;
    }
    container ipv6 {
      description
        "Operational state information for IPv6 FIB/CEF on the device.";
      uses fib-ios-xe-oper:ipv6-fib-state;
    }
    container rrp {
      description
        "Operational state information for the RRP in FIB/CEF.";
      uses fib-ios-xe-oper:fib-rrp-state;
    }
    container issu {
      description
        "In-service software upgrade (ISSU) FIB/CEF state";
      uses fib-ios-xe-oper:fib-issu-state;
    }
  }

  grouping ipv4-fib-capability-state {
    description
      "FIB/CEF IPv4 capability state";
    leaf default-fib-switching {
      type empty;
      description
        "Indicates whether default FIB/CEF switching is enabled for IPv4 traffic.";
    }
    leaf always-fib-switching {
      type empty;
      description
        "Indicates whether FIB/CEF switching is always enabled for IPv4 traffic, regardless of other conditions.";
    }
    leaf default-dfib-switching {
      type empty;
      description
        "Indicates whether default distributed FIB/CEF switching is enabled for IPv4 traffic.";
    }
    leaf always-dfib-switching {
      type empty;
      description
        "Indicates whether distributed FIB/CEF switching is always enabled for IPv4 traffic, regardless of other conditions.";
    }
    leaf multicast-pkt-drop {
      type empty;
      description
        "Drop multicast packets";
    }
    leaf punt-ok {
      type empty;
      description
        "Indicates whether it is acceptable for the FIB/CEF process to punt IPv4 packets to the next processing layer.";
    }
    leaf do-not-nvgen-fib-state {
      type empty;
      description
        "Indicates whether the FIB/CEF state for IPv4 is excluded from the saved configuration (not subject to NVGEN).";
    }
    leaf fastsend-used {
      type empty;
      description
        "Indicates whether the fast send function is enabled for IPv4 CEF, allowing for optimized packet forwarding.";
    }
    leaf no-per-packet-load {
      type empty;
      description
        "Indicates whether per-packet load sharing is not supported for IPv4 CEF; when present, traffic is not distributed across multiple paths on a per-packet basis.";
    }
    leaf mcast-groups-in-table {
      type empty;
      description
        "Multicast (*,G) groups in CEF";
    }
    leaf rib-installs-locals {
      type empty;
      description
        "Install local entries from RIB";
    }
  }

  grouping ipv6-fib-capability-state {
    description
      "IPv6 FIB/CEF capability state";
    leaf default-fib-switching {
      type empty;
      description
        "Indicates whether default FIB/CEF switching is enabled for IPv6 traffic.";
    }
    leaf always-fib-switching {
      type empty;
      description
        "Indicates whether FIB/CEF switching is always enabled for IPv6 traffic, regardless of other conditions.";
    }
    leaf default-dfib-switching {
      type empty;
      description
        "Indicates whether default distributed FIB/CEF switching is enabled for IPv6 traffic.";
    }
    leaf always-dfib-switching {
      type empty;
      description
        "Indicates whether distributed FIB/CEF switching is always enabled for IPv6 traffic, regardless of other conditions.";
    }
    leaf multicast-pkt-drop {
      type empty;
      description
        "Drop multicast packets";
    }
    leaf punt-ok {
      type empty;
      description
        "Indicates that it is permissible to punt IPv6 packets to the next processing layer when they cannot be handled by CEF.";
    }
    leaf do-not-nvgen-fib-state {
      type empty;
      description
        "Indicates whether the FIB/CEF state for IPv6 is excluded from the saved configuration (not subject to NVGEN).";
    }
    leaf fastsend-used {
      type empty;
      description
        "Indicates that the fast send function is being used for IPv6 packet forwarding in CEF.";
    }
  }

  grouping fib-capability-state {
    description
      "FIB/CEF capability state";
    leaf distributed-platform {
      type empty;
      description
        "Indicates whether the FIB/CEF subsystem is operating in a distributed platform environment, where forwarding is handled by multiple hardware components.";
    }
    leaf warm-or-hot-standby-supported {
      type empty;
      description
        "Warm or Hot Standby supported";
    }
    leaf non-stop-forwarding {
      type empty;
      description
        "CEF NSF capable";
    }
    leaf hw-fwd-in-use {
      type empty;
      description
        "Indicates whether hardware-based packet forwarding is currently in use by the FIB/CEF subsystem.";
    }
    leaf fib-chck-auto-repair {
      type empty;
      description
        "Checker auto-repair supported";
    }
    leaf crashdump-when-no-mem {
      type empty;
      description
        "Crash dump on memory failure";
    }
    leaf block-sso-until-rrp-synced {
      type empty;
      description
        "Indicates whether stateful switchover (SSO) is blocked on the standby hot processor until RRP state is fully synchronized.";
    }
    container ipv4 {
      description
        "IPv4 CEF capability state";
      uses fib-ios-xe-oper:ipv4-fib-capability-state;
    }
    container ipv6 {
      description
        "IPv6 CEF capability state";
      uses fib-ios-xe-oper:ipv6-fib-capability-state;
    }
  }

  grouping cef-state {
    description
      "CEF state";
    container fib {
      description
        "FIB/CEF state";
      uses fib-ios-xe-oper:fib-state;
    }
    container capability {
      description
        "FIB/CEF capability state";
      uses fib-ios-xe-oper:fib-capability-state;
    }
  }

  grouping ip-cef-lisp-statistics {
    description
      "FIB/CEF LISP statistics";
    leaf map-requests {
      type uint64;
      description
        "Number of map requests sent or received by the FIB/CEF LISP forwarding module.";
    }
    leaf unexpected-map-requests {
      type uint64;
      description
        "Number of unexpected map requests received by the FIB/CEF LISP forwarding module.";
    }
    leaf map-cache-deletes {
      type uint64;
      description
        "Number of map cache entries deleted by the FIB/CEF LISP forwarding module.";
    }
    leaf map-requests-resolve-dgt {
      type uint64;
      description
        "Number of LISP map requests that required resolution via the default gateway table (DGT).";
    }
  }

  grouping ipv4-switching-in-feat {
    description
      "IPv4 FIB/CEF input switching statistics feature";
    leaf input-features {
      type fib-ios-xe-oper:ipv4-input-switching-feature;
      description
        "Name of the input feature for which IPv4 FIB/CEF switching statistics are collected.";
    }
    leaf total-drop {
      type uint64;
      description
        "Total number of IPv4 packets dropped for this input feature during FIB/CEF switching.";
    }
    leaf total-consume {
      type uint64;
      description
        "Total number of IPv4 packets consumed and counted for this input feature during FIB/CEF switching.";
    }
    leaf total-punt {
      type uint64;
      description
        "Total punt to next switching layer action";
    }
    leaf total-punt2host {
      type uint64;
      description
        "Total number of IPv4 packets punted to the host CPU for processing for this input feature during FIB/CEF switching.";
    }
    leaf total-gave-route {
      type uint64;
      description
        "Total number of packets for which the route was provided by the input feature during IPv4 CEF switching.";
    }
  }

  grouping ipv4-swi-output-feat {
    description
      "IPv4 FIB/CEF output switching statistics feature";
    leaf output-features {
      type fib-ios-xe-oper:ipv4-output-switching-feature;
      description
        "Name of the output feature for which IPv4 CEF switching statistics are collected.";
    }
    leaf total-drop {
      type uint64;
      description
        "Total number of packets dropped by the output feature during IPv4 CEF switching.";
    }
    leaf total-consume {
      type uint64;
      description
        "Total number of packets consumed (processed locally) and counted by the output feature during IPv4 CEF switching.";
    }
    leaf total-punt {
      type uint64;
      description
        "Total punt to next switching layer action";
    }
    leaf total-punt2host {
      type uint64;
      description
        "Total punt to process action";
    }
    leaf total-new-if {
      type uint64;
      description
        "Total resume switching on different interface (new I/F) action";
    }
  }

  grouping ipv4-swi-post-encap-feat {
    description
      "IPv4 FIB/CEF post-encap switching statistics feature";
    leaf post-encap-features {
      type fib-ios-xe-oper:ipv4-post-encap-switching-feature;
      description
        "Name of the post-encapsulation feature for which IPv4 CEF switching statistics are collected.";
    }
    leaf total-drop {
      type uint64;
      description
        "Total number of packets dropped after IPv4 post-encapsulation feature processing in CEF switching.";
    }
    leaf total-consume {
      type uint64;
      description
        "Total number of packets consumed and counted by the IPv4 post-encapsulation feature in CEF switching.";
    }
    leaf total-punt {
      type uint64;
      description
        "Total punt to next switching layer action";
    }
    leaf total-punt2host {
      type uint64;
      description
        "Total number of packets punted to the host processor for further processing after IPv4 post-encapsulation feature in CEF.";
    }
    leaf total-new-if {
      type uint64;
      description
        "Total resume switching on different interface (new I/F) action";
    }
  }

  grouping ipv4-swi-for-us-feat {
    description
      "IPv4 FIB/CEF for-us switching statistics feature";
    leaf for-us-features {
      type fib-ios-xe-oper:ipv4-for-us-switching-feature;
      description
        "Type of IPv4 CEF switching feature for packets destined for the local device ('for-us').";
    }
    leaf total-drop {
      type uint64;
      description
        "Total number of packets dropped by the IPv4 'for-us' feature in CEF switching.";
    }
    leaf total-consume {
      type uint64;
      description
        "Total number of packets consumed and counted by the IPv4 'for-us' feature in CEF switching.";
    }
    leaf total-punt {
      type uint64;
      description
        "Total punt to next switching layer action";
    }
    leaf total-punt2host {
      type uint64;
      description
        "Total number of IPv4 packets punted from hardware forwarding to the host CPU for further processing.";
    }
    leaf total-new-if {
      type uint64;
      description
        "Total number of times IPv4 packet forwarding was resumed on a different (new) interface.";
    }
  }

  grouping ipv4-swi-punt-feat {
    description
      "IPv4 FIB/CEF punt switching statistics feature";
    leaf punt-features {
      type fib-ios-xe-oper:ipv4-punt-switching-feature;
      description
        "Name of the IPv4 punt switching feature for which statistics are collected.";
    }
    leaf total-drop {
      type uint64;
      description
        "Total number of IPv4 packets dropped during punt switching.";
    }
    leaf total-consume {
      type uint64;
      description
        "Total number of IPv4 packets consumed (processed locally) and counted during punt switching.";
    }
    leaf total-punt {
      type uint64;
      description
        "Total punt to next switching layer action";
    }
    leaf total-punt2host {
      type uint64;
      description
        "Total number of IPv4 packets punted from hardware forwarding to the host CPU for further processing.";
    }
    leaf total-new-if {
      type uint64;
      description
        "Total number of times IPv4 packet forwarding was resumed on a different (new) interface.";
    }
  }

  grouping ipv4-swi-local-feat {
    description
      "IPv4 FIB/CEF local switching statistics feature";
    leaf local-features {
      type fib-ios-xe-oper:ipv4-local-switching-feature;
      description
        "Specifies the local switching feature for which IPv4 FIB/CEF switching statistics are collected.";
    }
    leaf total-drop {
      type uint64;
      description
        "Total number of packets dropped by the local switching feature.";
    }
    leaf total-consume {
      type uint64;
      description
        "Total number of packets consumed and counted by the local switching feature.";
    }
    leaf total-punt {
      type uint64;
      description
        "Total punt to next switching layer action";
    }
    leaf total-punt2host {
      type uint64;
      description
        "Total punt to process action";
    }
    leaf total-gave-route {
      type uint64;
      description
        "Total number of times a local IPv4 switching feature supplied an alternate route/adjacency, bypassing the normal FIB lookup.";
    }
  }

  grouping ipv6-switching-in-feat {
    description
      "IPv6 FIB/CEF input switching statistics feature";
    leaf input-features {
      type fib-ios-xe-oper:ipv6-input-switching-feature;
      description
        "Specifies the input switching feature for which IPv6 FIB/CEF switching statistics are collected.";
    }
    leaf total-drop {
      type uint64;
      description
        "Total number of packets dropped by the input switching feature.";
    }
    leaf total-consume {
      type uint64;
      description
        "Total number of packets consumed and counted by the input switching feature.";
    }
    leaf total-punt {
      type uint64;
      description
        "Total punt to next switching layer action";
    }
    leaf total-punt2host {
      type uint64;
      description
        "Total number of IPv6 packets punted to the host CPU for processing.";
    }
    leaf total-gave-route {
      type uint64;
      description
        "Total number of times a local IPv6 switching feature supplied an alternate route/adjacency, bypassing the normal FIB lookup.";
    }
  }

  grouping ipv6-switching-out-feat {
    description
      "IPv6 FIB/CEF output switching statistics feature";
    leaf output-features {
      type fib-ios-xe-oper:ipv6-output-switching-feature;
      description
        "Specifies the output switching feature for which IPv6 FIB/CEF statistics are collected.";
    }
    leaf total-drop {
      type uint64;
      description
        "Total number of IPv6 packets dropped during output switching.";
    }
    leaf total-consume {
      type uint64;
      description
        "Total number of IPv6 packets consumed (processed locally) and counted during output switching.";
    }
    leaf total-punt {
      type uint64;
      description
        "Total punt to next switching layer action";
    }
    leaf total-punt2host {
      type uint64;
      description
        "Total number of IPv6 packets punted to the host CPU for processing during output switching.";
    }
    leaf total-new-if {
      type uint64;
      description
        "Total resume switching on different interface (new I/F) action";
    }
  }

  grouping ipv6-switching-pe-feat {
    description
      "IPv6 FIB/CEF post-encap switching statistics feature";
    leaf post-encap-features {
      type fib-ios-xe-oper:ipv6-post-encap-switching-feature;
      description
        "Specifies the IPv6 FIB/CEF switching feature for which post-encapsulation statistics are collected.";
    }
    leaf total-drop {
      type uint64;
      description
        "Total number of IPv6 packets dropped after post-encapsulation processing.";
    }
    leaf total-consume {
      type uint64;
      description
        "Total number of IPv6 packets consumed (processed locally) and counted after post-encapsulation.";
    }
    leaf total-punt {
      type uint64;
      description
        "Total punt to next switching layer action";
    }
    leaf total-punt2host {
      type uint64;
      description
        "Total punt to process action";
    }
    leaf total-new-if {
      type uint64;
      description
        "Total resume switching on different interface (new I/F) action";
    }
  }

  grouping ipv6-switching-for-us-feat {
    description
      "IPv6 FIB/CEF for-us switching statistics feature";
    leaf for-us-features {
      type fib-ios-xe-oper:ipv6-for-us-switching-feature;
      description
        "Specifies the IPv6 FIB/CEF switching feature for which statistics are collected for packets destined to the local device.";
    }
    leaf total-drop {
      type uint64;
      description
        "Total number of IPv6 packets destined for the local device that were dropped.";
    }
    leaf total-consume {
      type uint64;
      description
        "Total number of IPv6 packets consumed and counted by the 'for-us' feature during CEF switching.";
    }
    leaf total-punt {
      type uint64;
      description
        "Total punt to next switching layer action";
    }
    leaf total-punt2host {
      type uint64;
      description
        "Total number of IPv6 packets punted to the host processor for further processing by the 'for-us' feature during CEF switching.";
    }
    leaf total-new-if {
      type uint64;
      description
        "Total resume switching on different interface (new I/F) action";
    }
  }

  grouping ipv6-switching-punt-feat {
    description
      "IPv6 FIB/CEF punt switching statistics feature";
    leaf punt-features {
      type fib-ios-xe-oper:ipv6-punt-switching-feature;
      description
        "Name of the punt switching feature for which IPv6 FIB/CEF statistics are collected.";
    }
    leaf total-drop {
      type uint64;
      description
        "Total number of IPv6 packets dropped by the punt feature during CEF switching.";
    }
    leaf total-consume {
      type uint64;
      description
        "Total number of IPv6 packets consumed and counted by the punt feature during CEF switching.";
    }
    leaf total-punt {
      type uint64;
      description
        "Total punt to next switching layer action";
    }
    leaf total-punt2host {
      type uint64;
      description
        "Total number of IPv6 packets punted to the host processor for further processing by the punt feature during CEF switching.";
    }
    leaf total-new-if {
      type uint64;
      description
        "Total number of times IPv6 packets were punted and resumed switching on a different (new) interface.";
    }
  }

  grouping ipv4-switching {
    description
      "IPV4 FIB/CEF switching statistics";
    leaf reason {
      type fib-ios-xe-oper:ipv4-fib-not-cef-reason;
      description
        "Reason no FIB/CEF switch statistics";
    }
    leaf total-drop {
      type uint64;
      description
        "Total drop action";
    }
    leaf total-punt {
      type uint64;
      description
        "Total punt action";
    }
    leaf total-punt2host {
      type uint64;
      description
        "Total punt to process action";
    }
  }

  grouping ipv6-switching {
    description
      "IPV6 FIB/CEF switching statistics";
    leaf reason {
      type fib-ios-xe-oper:ipv6-fib-not-cef-reason;
      description
        "Indicates the reason why FIB/CEF switching statistics are not available for this IPv6 entry.";
    }
    leaf total-drop {
      type uint64;
      description
        "Total number of IPv6 packets dropped during FIB/CEF switching for this reason.";
    }
    leaf total-punt {
      type uint64;
      description
        "Total number of IPv6 packets punted to the next processing layer during FIB/CEF switching for this reason.";
    }
    leaf total-punt2host {
      type uint64;
      description
        "Total number of IPv6 packets punted to the host CPU for processing during FIB/CEF switching for this reason.";
    }
  }

  grouping cef-statistics {
    description
      "CEF statistics";
    container ipv4-lisp {
      description
        "IPV4 FIB/CEF LISP forwarding module statistics";
      uses fib-ios-xe-oper:ip-cef-lisp-statistics;
    }
    container ipv6-lisp {
      description
        "IPV6 FIB/CEF LISP forwarding module statistics";
      uses fib-ios-xe-oper:ip-cef-lisp-statistics;
    }
    list ipv4-switching {
      key "reason";
      description
        "List of IPV4 FIB/CEF switching statistics";
      uses fib-ios-xe-oper:ipv4-switching;
    }
    list ipv6-switching {
      key "reason";
      description
        "List of IPV6 FIB/CEF switching statistics";
      uses fib-ios-xe-oper:ipv6-switching;
    }
    list ipv4-swi-input-feat {
      key "input-features";
      description
        "List of IPv4 FIB/CEF switching statistics input feature";
      uses fib-ios-xe-oper:ipv4-switching-in-feat;
    }
    list ipv4-swi-output-feat {
      key "output-features";
      description
        "List of IPv4 FIB/CEF switching statistics output feature";
      uses fib-ios-xe-oper:ipv4-swi-output-feat;
    }
    list ipv4-swi-post-encap-feat {
      key "post-encap-features";
      description
        "List of IPv4 FIB/CEF switching statistics post-encap feature";
      uses fib-ios-xe-oper:ipv4-swi-post-encap-feat;
    }
    list ipv4-swi-for-us-feat {
      key "for-us-features";
      description
        "List of IPv4 FIB/CEF switching statistics for-us feature";
      uses fib-ios-xe-oper:ipv4-swi-for-us-feat;
    }
    list ipv4-swi-punt-feat {
      key "punt-features";
      description
        "List of IPv4 FIB/CEF switching statistics punt feature";
      uses fib-ios-xe-oper:ipv4-swi-punt-feat;
    }
    list ipv4-swi-local-feat {
      key "local-features";
      description
        "List of IPv4 FIB/CEF switching statistics local feature";
      uses fib-ios-xe-oper:ipv4-swi-local-feat;
    }
    list ipv6-swi-input-feat {
      key "input-features";
      description
        "List of IPv6 FIB/CEF switching statistics input feature";
      uses fib-ios-xe-oper:ipv6-switching-in-feat;
    }
    list ipv6-swi-output-feat {
      key "output-features";
      description
        "List of IPv6 FIB/CEF switching statistics output feature";
      uses fib-ios-xe-oper:ipv6-switching-out-feat;
    }
    list ipv6-swi-post-encap-feat {
      key "post-encap-features";
      description
        "List of IPv6 FIB/CEF switching statistics post-encap feature";
      uses fib-ios-xe-oper:ipv6-switching-pe-feat;
    }
    list ipv6-swi-for-us-feat {
      key "for-us-features";
      description
        "List of IPv6 FIB/CEF switching statistics for-us feature";
      uses fib-ios-xe-oper:ipv6-switching-for-us-feat;
    }
    list ipv6-swi-punt-feat {
      key "punt-features";
      description
        "List of IPv6 FIB/CEF switching statistics punt feature";
      uses fib-ios-xe-oper:ipv6-switching-punt-feat;
    }
  }

  grouping ip-input-features {
    description
      "List of interface IPv4 enabled input features";
    leaf-list feature {
      type fib-ios-xe-oper:ipv4-input-switching-feature;
      max-elements 131;
      ordered-by user;
      description
        "Specifies the IPv4 input features that are enabled on this interface for CEF processing.";
    }
  }

  grouping ip-output-features {
    description
      "List of interface IPv4 enabled output features";
    leaf-list feature {
      type fib-ios-xe-oper:ipv4-output-switching-feature;
      max-elements 115;
      ordered-by user;
      description
        "Specifies the IPv4 output features that are enabled on this interface for CEF processing.";
    }
  }

  grouping ip-post-encap-features {
    description
      "List of interface IPv4 enabled post encap features";
    leaf-list feature {
      type fib-ios-xe-oper:ipv4-post-encap-switching-feature;
      max-elements 44;
      ordered-by user;
      description
        "Specifies the IPv4 post-encapsulation features that are enabled on this interface for CEF processing.";
    }
  }

  grouping ip-states {
    description
      "Interface IP states";
    leaf ip-ucast-rpf-chk-en {
      type boolean;
      description
        "IP unicast RPF check";
    }
    leaf ip-pol-routing-en {
      type boolean;
      description
        "IP policy routing";
    }
    leaf ip-cef-swi-en {
      type boolean;
      description
        "IP CEF switching";
    }
  }

  grouping bgp-states {
    description
      "BGP based policy states";
    leaf bgp-pol-acc-in-en {
      type boolean;
      description
        "Indicates whether BGP input policy accounting is enabled on this interface.";
    }
    leaf bgp-pol-acc-out-en {
      type boolean;
      description
        "Indicates whether BGP output policy accounting is enabled on this interface.";
    }
  }

  grouping if-unnumbered-info {
    description
      "Unnumbered interface name and IP address";
    leaf unnum-if-name {
      type string;
      description
        "Unnumbered interface name";
    }
    leaf unnum-addr {
      type inet:ip-address;
      description
        "Unnumbered interface IP address";
    }
  }

  grouping if-secondary-addresses {
    description
      "List of interface secondary IP addresses";
    leaf ip-addr {
      type inet:ip-address;
      description
        "Interface secondary IP address";
    }
  }

  grouping ipv6-states {
    description
      "Interface IPv6 states";
    leaf ipv6-en {
      type boolean;
      description
        "Indicates whether IPv6 is enabled on this interface.";
    }
    leaf cef-swi-en {
      type boolean;
      description
        "Indicates whether CEF switching for IPv6 is enabled on this interface.";
    }
    leaf dcef-swi-en {
      type boolean;
      description
        "Indicates whether distributed CEF switching is enabled on this interface.";
    }
    leaf intf-punt-pak {
      type boolean;
      description
        "Packets to this interface are punted";
    }
    leaf intf-lc-punt-pak {
      type boolean;
      description
        "Packets to this interface are punted on the linecard";
    }
    leaf intf-drop-pak {
      type boolean;
      description
        "Packets to this interface are dropped";
    }
  }

  grouping cef-interface {
    description
      "FIB/CEF interface";
    leaf if-name {
      type string;
      description
        "Name of the interface as used in the system.";
    }
    leaf if-number {
      type uint32;
      description
        "System-assigned numeric identifier for the interface.";
    }
    leaf if-up {
      type boolean;
      description
        "Either interface is up or down";
    }
    leaf addr {
      type inet:ip-prefix;
      description
        "IP address for this interface";
    }
    leaf if-unnum-config {
      type empty;
      description
        "When configured, unnumbered interface info is present";
    }
    container if-unnum {
      when 'boolean(../if-unnum-config)';
      description
        "Unnumbered interface name and IP address";
      uses fib-ios-xe-oper:if-unnumbered-info;
    }
    list if-sec-addr {
      description
        "List of interface secondary IP addresses";
      uses fib-ios-xe-oper:if-secondary-addresses;
    }
    leaf hwidb-fast-if-num {
      type uint32;
      description
        "The fast interface number as represented in the hardware interface database (hwidb) for this interface.";
    }
    leaf hwidb-firstsw-if-num {
      type uint32;
      description
        "The first software interface number as recorded in the hardware interface database (hwidb) for this interface.";
    }
    container ip-states {
      description
        "Interface IP states";
      uses fib-ios-xe-oper:ip-states;
    }
    leaf ipv6-sub-block {
      type empty;
      description
        "IPv6 Sub-block on interface";
    }
    container ipv6-states {
      when 'boolean(../ipv6-sub-block)';
      description
        "Interface IPv6 states";
      uses fib-ios-xe-oper:ipv6-states;
    }
    container bgp-states {
      description
        "Interface BGP based policy accounting states";
      uses fib-ios-xe-oper:bgp-states;
    }
    container ip-input-features {
      description
        "List of IPv4 enabled input features";
      uses fib-ios-xe-oper:ip-input-features;
    }
    container ip-output-features {
      description
        "List of IPv4 enabled output features";
      uses fib-ios-xe-oper:ip-output-features;
    }
    container ip-post-encap-features {
      description
        "List of IPv4 enabled post encap features";
      uses fib-ios-xe-oper:ip-post-encap-features;
    }
    leaf if-index {
      type uint32;
      description
        "Specifies the interface index for this CEF interface.";
    }
    leaf ip-mtu {
      type uint32;
      units "bytes";
      description
        "Specifies the maximum transmission unit (MTU) in bytes for IPv4 packets on this interface.";
    }
    leaf slot-unit {
      type uint32;
      description
        "Slot unit number";
    }
    leaf slot-vc {
      type int32;
      description
        "Specifies the Virtual Circuit (VC) number associated with this interface.";
    }
  }

  container fib-oper-data {
    config false;
    description
      "Top-level container for Cisco Express Forwarding (CEF) and FIB operational data, including forwarding entries, adjacencies, interface states, and switching statistics.";
    list fib-ni-entry {
      key "instance-name";
      description
        "List of FIB network instances, each representing a separate routing or forwarding context (such as a VRF).";
      uses fib-ios-xe-oper:fib-ni-entry;
    }
    container adjacency-table {
      presence "adjacency-table";
      description
        "FIB adjacency information";
      uses fib-ios-xe-oper:adjacency-table;
    }
    container cef-state {
      presence "cef-state";
      description
        "CEF state information";
      uses fib-ios-xe-oper:cef-state;
    }
    container cef-statistics {
      presence "cef-statistics";
      description
        "CEF statistics information";
      uses fib-ios-xe-oper:cef-statistics;
    }
    list cef-interface {
      key "if-name";
      description
        "CEF interface information";
      uses fib-ios-xe-oper:cef-interface;
    }
  }
}
