module Cisco-IOS-XE-sse-events {
  yang-version 1.1;
  namespace "http://cisco.com/ns/yang/Cisco-IOS-XE-sse-events";
  prefix sse-ios-xe-events;

  import Cisco-IOS-XE-ios-common-oper {
    prefix ios-common-ios-xe-oper;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for SSE Events data.
     Copyright (c) 2023 by Cisco Systems, Inc.
     All rights reserved.";

  revision 2023-11-01 {
    description
      "Initial revision";
    reference
      "1.0.0";
    cisco-semver:module-version "1.0.0";
  }

  typedef sse-ipsec-tunnel-fail-reasons {
    type enumeration {
      enum sse-ipsec-tunnel-fail-other {
        value 0;
        description
          "IPSEC tunnel setup failed";
      }
      enum sse-ipsec-tunnel-peer-del-request {
        value 1;
        description
          "Tunnel failed because of peer delete request";
      }
      enum sse-ipsec-tunnel-peer-lost {
        value 2;
        description
          "Tunnel failed because contact was lost with peer";
      }
      enum sse-ipsec-tunnel-local-failure {
        value 3;
        description
          "Tunnel had a local failure on the device";
      }
      enum sse-ipsec-tunnel-auth-failure {
        value 4;
        description
          "Tunnel has an authorization failure";
      }
      enum sse-ipsec-tunnel-hash-failure {
        value 5;
        description
          "Hash validation failed for the tunnel ";
      }
      enum sse-ipsec-tunnel-encrypt-failure {
        value 6;
        description
          "Encryption failure for the tunnel";
      }
      enum sse-ipsec-tunnel-internal-error {
        value 7;
        description
          "Internal error for the tunnel";
      }
      enum sse-ipsec-tunnel-sys-cap-exceeded {
        value 8;
        description
          "Number of ipsec tunnel exceeded system capability";
      }
      enum sse-ipsec-tunnel-proposal-failure {
        value 9;
        description
          "IPSEC tunnel proposal failed";
      }
      enum sse-ipsec-tunnel-peer-cert-unavail {
        value 10;
        description
          "Peer certificate was unavailable";
      }
      enum sse-ipsec-tunnel-cert-not-valid {
        value 11;
        description
          "Certificate not valid for the tunnel";
      }
      enum sse-ipsec-tunnel-local-cert-expired {
        value 12;
        description
          "Local certificate expired";
      }
      enum sse-ipsec-tunnel-crl-failure {
        value 13;
        description
          "Certificate remove list failure";
      }
      enum sse-ipsec-tunnel-peer-encoding-error {
        value 14;
        description
          "Peer encoding error";
      }
      enum sse-ipsec-tunnel-non-existent-sa {
        value 15;
        description
          "Non existent security association";
      }
      enum sse-ipsec-tunnel-xauth-failure {
        value 16;
        description
          "Extended authentication failed";
      }
      enum sse-ipsec-tunnel-oper-request {
        value 17;
        description
          "Operator requested failure";
      }
      enum sse-ipsec-tunnel-redirected {
        value 18;
        description
          "Redirected to another gateway";
      }
    }
    description
      "Ipsec tunnel fail reasons";
  }

  grouping sse-tunnel-params-absent {
    description
      "SSE tunnel parameters are absent";
    leaf severity {
      type ios-common-ios-xe-oper:notification-severity;
      description
        "Event severity";
    }
    leaf host-name {
      type string;
      description
        "Host name of the device";
    }
    leaf system-ip {
      type inet:ip-address;
      description
        "System IP of the device";
    }
    leaf if-name {
      type string;
      description
        "WAN interface name";
    }
    leaf wan-if-ip {
      type inet:ip-address;
      description
        "Public IP of the WAN interface";
    }
  }

  grouping sse-ipsec-tunnel-failure {
    description
      "IPSEC tunnel failure on the device";
    leaf severity {
      type ios-common-ios-xe-oper:notification-severity;
      description
        "Notification severity";
    }
    leaf host-name {
      type string {
        length "1..255";
      }
      description
        "Host name on the device";
    }
    leaf tunnel-name {
      type string;
      description
        "Tunnel name on the device";
    }
    leaf fail-reason {
      type sse-ios-xe-events:sse-ipsec-tunnel-fail-reasons;
      description
        "Fail reason for the ipsec tunnel";
    }
  }

  notification sse-tunnel-params-absent {
    description
      "SSE WAN interface update notification";
    uses sse-ios-xe-events:sse-tunnel-params-absent;
  }

  notification sse-ipsec-tunnel-failure {
    description
      "IPSEC tunnel failure on the device";
    uses sse-ios-xe-events:sse-ipsec-tunnel-failure;
  }
}
