module Cisco-IOS-XE-stack-member-oper {
  yang-version 1.1;
  namespace "http://cisco.com/ns/yang/Cisco-IOS-XE-stack-member-oper";
  prefix stack-member-ios-xe-oper;

  import Cisco-IOS-XE-common-types {
    prefix common-types-ios-xe;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for operational data of all Stack members.
     Copyright (c) 2019-2020, 2022-2023, 2026 by Cisco Systems, Inc.
     All rights reserved.";

  revision 2026-08-01 {
    description
      "Updated descriptions of several model elements to clarify their meaning and purpose";
    reference
      "1.5.1";
    cisco-semver:module-version "1.5.1";
  }
  revision 2025-07-01 {
    description
      "- Added stackwise-virtual DAD PAgP trust mode flag,
       - Added stackwise-virtual bandwidth information";
    reference
      "1.5.0";
    cisco-semver:module-version "1.5.0";
  }
  revision 2025-03-01 {
    description
      "Added support for displaying stack member port info,
       including link ok, link active, sync ok and loop back";
    reference
      "1.4.0";
    cisco-semver:module-version "1.4.0";
  }
  revision 2023-11-01 {
    description
      "Added stack node latency";
    reference
      "1.3.0";
    cisco-semver:module-version "1.3.0";
  }
  revision 2022-11-01 {
    description
      "Update yang-version to 1.1";
    reference
      "1.2.0";
    cisco-semver:module-version "1.2.0";
  }
  revision 2021-03-01 {
    description
      "Added Stackwise-Virtual oper data";
    reference
      "1.1.0";
    cisco-semver:module-version "1.1.0";
  }
  revision 2020-11-01 {
    description
      "Initial revision";
    reference
      "1.0.0";
    cisco-semver:module-version "1.0.0";
  }

  typedef svl-protocol-status {
    type enumeration {
      enum svl-conn-disconnected {
        value 0;
        description
          "Stackwise-Virtual connection disconnected";
      }
      enum svl-conn-pending {
        value 1;
        description
          "Stackwise-Virtual connection pending";
      }
      enum svl-conn-ready {
        value 2;
        description
          "Stackwise-Virtual connection ready";
      }
      enum svl-conn-error {
        value 3;
        description
          "Stackwise-Virtual connection error";
      }
      enum svl-conn-timeout {
        value 4;
        description
          "Stackwise-Virtual connection timeout";
      }
    }
    description
      "Stackwise-Virtual port status";
  }

  typedef svl-port-status {
    type enumeration {
      enum svl-port-down {
        value 0;
        description
          "Stackwise-Virtual port down";
      }
      enum svl-port-up {
        value 1;
        description
          "Stackwise-Virtual port up";
      }
    }
    description
      "Stackwise-Virtual port status";
  }

  typedef stacking-mode {
    type enumeration {
      enum mode-stackwise-rear {
        value 0;
        description
          "Mode Stackwise Rear";
      }
      enum mode-active-standby {
        value 1;
        description
          "Mode Active Standby";
      }
      enum mode-stackwise-geo {
        value 2;
        description
          "Mode Stackwise Geo";
      }
      enum mode-stackwise-virtual {
        value 3;
        description
          "Mode Stackwise Virtual";
      }
      enum mode-unknown {
        value 4;
        description
          "Mode Unknown";
      }
    }
    description
      "Stack Mode";
  }

  grouping svl-keepalive-stats {
    description
      "Stackwise-virtual keepalive statistics";
    leaf lmp-tx {
      type uint64;
      description
        "Link-Management-Protocol TX counter";
    }
    leaf lmp-rx {
      type uint64;
      description
        "Link-Management-Protocol RX counter";
    }
    leaf lmp-tx-seq-no {
      type uint64;
      description
        "Last Link-Management-Protocol TX seq num";
    }
    leaf lmp-rx-seq-no {
      type uint64;
      description
        "Last Link-Management-Protocol RX seq num";
    }
    leaf lmp-rx-last-good-count {
      type uint64;
      description
        "Link-Management-Protocol RX last good count";
    }
    leaf latency-rx-err-count {
      type uint64;
      description
        "Number of latency-related errors detected on received packets for this port.";
    }
    leaf seq-err-rx-count {
      type uint64;
      description
        "Number of sequence errors detected in received packets on this port.";
    }
    leaf link-timeout-flap-count {
      type uint64;
      description
        "Link-Management-Protocol link timeout flap counts";
    }
  }

  grouping svl-slot-port {
    description
      "Stackwise-virtual port identification";
    leaf chassis {
      type uint32;
      description
        "Switch number";
    }
    leaf slot {
      type uint32;
      description
        "Switch Slot";
    }
    leaf port {
      type uint32;
      description
        "Port number of the remote switch in the Stackwise-Virtual link.";
    }
  }

  grouping svl-port-info {
    description
      "Stackwise-virtual port information";
    container local-port {
      description
        "Identification information for the local Stackwise-Virtual port.";
      uses stack-member-ios-xe-oper:svl-slot-port;
    }
    container remote-port {
      description
        "Identification information for the remote Stackwise-Virtual port.";
      uses stack-member-ios-xe-oper:svl-slot-port;
    }
    leaf port-status {
      type stack-member-ios-xe-oper:svl-port-status;
      description
        "Operational status of the Stackwise-Virtual port (up or down).";
    }
    leaf link-status-change-time {
      type yang:date-and-time;
      description
        "Link status change timestamp";
    }
    leaf link-protocol-status {
      type stack-member-ios-xe-oper:svl-protocol-status;
      description
        "Link protocol status";
    }
    leaf conn-status-change-time {
      type yang:date-and-time;
      description
        "Connection status change timestamp";
    }
    container port-stats {
      description
        "Local Port statistics";
      uses stack-member-ios-xe-oper:svl-keepalive-stats;
    }
  }

  grouping dad-port-info {
    description
      "Dual-Active-Detection port information";
    container dad-port {
      description
        "Information identifying the Dual-Active Detection (DAD) port, including chassis, slot, and port numbers.";
      uses stack-member-ios-xe-oper:svl-slot-port;
    }
    leaf port-status {
      type stack-member-ios-xe-oper:svl-port-status;
      description
        "DAD Port status info";
    }
    leaf tx-seq-no {
      type uint32;
      description
        "DAD Port next TX seq num";
    }
  }

  grouping stack-node-keepalive {
    description
      "SDP keepalive counters";
    leaf sent {
      type uint64;
      description
        "Keepalives sent";
    }
    leaf received {
      type uint64;
      description
        "Keepalives received";
    }
    leaf sent-failure {
      type uint64;
      description
        "Keepalives failed to be sent";
    }
    leaf receive-failure {
      type uint64;
      description
        "Keepalives failed to be received";
    }
    leaf consecutive-losses {
      type uint64;
      description
        "Consecutive keepalives lost";
    }
  }

  grouping stack-ports-stats {
    description
      "Stack port stats";
    leaf rac-inserted {
      type uint64;
      units "bytes";
      description
        "Outgoing byte count on stack port";
    }
    leaf rac-copied {
      type uint64;
      units "bytes";
      description
        "Incoming byte count on stack port";
    }
    leaf rac-data-crc-err {
      type uint64;
      description
        "Stack interface data CRC error";
    }
    leaf rac-invalid-ringword-err {
      type uint64;
      description
        "Stack interface invalid ring word error";
    }
    leaf rac-pcs-codeword-err {
      type uint64;
      description
        "Stack interface PCS error";
    }
    leaf rac-rwcrc-err {
      type uint64;
      description
        "Stack interface ring word CRC error";
    }
  }

  grouping stack-member-peer-timeout-info {
    description
      "Peer timeout Info";
    leaf peer-timeout-cfg {
      type uint64;
      units "milliseconds";
      description
        "Peer timeout in milliseconds";
    }
    leaf watermark-50-cnt {
      type uint64;
      description
        "Number of times keepalives missed for 50% of timeout value";
    }
    leaf watermark-75-cnt {
      type uint64;
      description
        "Number of times keepalives missed for 75% of timeout value";
    }
    leaf last-watermark-50time {
      when '(../watermark-50-cnt > 0)';
      type yang:date-and-time;
      description
        "Last time 50% watermark was exceeded";
    }
    leaf last-watermark-75time {
      when '(../watermark-75-cnt > 0)';
      type yang:date-and-time;
      description
        "Last time 75% watermark was exceeded";
    }
  }

  grouping stack-member-port-info {
    description
      "Stack member port data";
    leaf port-num {
      type uint8;
      description
        "Port number of the stack member's stack port.";
    }
    leaf cable-length-cm {
      type uint16;
      units "centimeters";
      description
        "Stack cable length in centimetres";
    }
    leaf nbr-port-num {
      type uint8;
      description
        "Port number of the neighboring stack member connected to this stack port.";
    }
    leaf link-flaps {
      type uint16;
      description
        "Number of link flaps";
    }
    container stats {
      description
        "Statistical information and counters for the stack member's stack port.";
      uses stack-member-ios-xe-oper:stack-ports-stats;
    }
    leaf stats-time {
      type yang:date-and-time;
      description
        "Last time stats were collected";
    }
    list svl-port {
      when "(../../stack-mode='mode-stackwise-virtual')";
      description
        "Stackwise-virtual ports statistics";
      uses stack-member-ios-xe-oper:svl-port-info;
    }
    leaf link-ok {
      type boolean;
      description
        "Functional stack cable connected to stack port";
    }
    leaf link-actv {
      type boolean;
      description
        "Functional neighbor connected at the other end of the stack cable, making the link active";
    }
    leaf sync-ok {
      type boolean;
      description
        "The link partner sends valid protocol messages to the stack port";
    }
    leaf in-loop-bk {
      type boolean;
      description
        "No stack cables attached on the member ports";
    }
  }

  grouping stack-member-info {
    description
      "Stack member data";
    leaf chassis-num {
      type uint8;
      description
        "Switch number";
    }
    list mbr-port {
      description
        "Stack member port data";
      uses stack-member-ios-xe-oper:stack-member-port-info;
    }
    container mbr-keepalive {
      description
        "Stack member keepalive data";
      uses stack-member-ios-xe-oper:stack-node-keepalive;
    }
    container mbr-peer-timeout {
      description
        "Stack member peer timeout data";
      uses stack-member-ios-xe-oper:stack-member-peer-timeout-info;
    }
    leaf stack-mode {
      type stack-member-ios-xe-oper:stacking-mode;
      description
        "Indicates the current stacking mode of the switch";
    }
    list dad-port {
      when "(../stack-mode='mode-stackwise-virtual')";
      description
        "Stackwise-virtual DAD ports statistics";
      uses stack-member-ios-xe-oper:dad-port-info;
    }
    leaf mbr-boottime {
      type yang:date-and-time;
      description
        "Stack member boot time";
    }
    leaf latency {
      type uint32;
      units "nanoseconds";
      description
        "Round trip delay to reach peer stack node";
    }
    leaf pagp-dad-enbl {
      when "(../stack-mode='mode-stackwise-virtual')";
      type boolean;
      description
        "Dual-active detection using Port Aggregation Protocol(PAgP)";
    }
    leaf svl-bw {
      when "(../stack-mode='mode-stackwise-virtual')";
      type uint32;
      units "Gbps";
      description
        "Total bandwidth of the available stackwise virtual links in a stackwise virtual system";
    }
  }

  container stack-member-oper-data {
    config false;
    description
      "Stack member operational data";
    list location {
      key "fru slot bay chassis node";
      description
        "A list of data provider locations";
      uses common-types-ios-xe:extended-location;
      list stack-member-info {
        key "chassis-num";
        description
          "Stack member data";
        uses stack-member-ios-xe-oper:stack-member-info;
      }
    }
  }
}
