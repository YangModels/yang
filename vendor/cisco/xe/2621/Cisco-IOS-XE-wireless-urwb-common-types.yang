module Cisco-IOS-XE-wireless-urwb-common-types {
  yang-version 1.1;
  namespace "http://cisco.com/ns/yang/Cisco-IOS-XE-wireless-urwb-common-types";
  prefix wireless-urwb-common-types;

  import Cisco-IOS-XE-wireless-enum-types {
    prefix wireless-enum-types;
  }
  import Cisco-IOS-XE-wireless-types {
    prefix wireless-types;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Ultra Reliable Wireless Backhaul (URWB) configuration data.
     Copyright (c) 2025-2026 by Cisco Systems, Inc.
     All rights reserved.";

  revision 2026-08-01 {
    description
      "- Added URWB LAN ID Ethernet configuration leaf
       - Added URWB LAN PoE Ethernet configuration leaf
       - Added URWB traffic egress point leaf
       - Moved URWB NAT configuration grouping from cfg module to common types
       - Added URWB NAT rule key grouping
       - Updated descriptions for URWB mobility and MPLS leaves
       - Updated descriptions for chan and c-width leaves in st-urwb-chan-list-entry grouping
       - Updated descriptions of several model elements for clarity, grammar, and consistency";
    reference
      "2.1.0";
    cisco-semver:module-version "2.1.0";
  }
  revision 2026-02-01 {
    description
      "Add new URWB parameters for mobility and reliability
       Added new URWB radio parameters for mobility, reliability and radio role enumeration";
    reference
      "2.0.0";
    cisco-semver:module-version "2.0.0";
  }
  revision 2025-07-01 {
    description
      "Initial revision";
    reference
      "1.0.0";
    cisco-semver:module-version "1.0.0";
  }

  typedef eurr {
    type enumeration {
      enum eurr-fixed-base {
        value 0;
        description
          "AP radio role fixed base";
      }
      enum eurr-ptmp-prim {
        value 1;
        description
          "AP radio role PTMP base";
      }
      enum eurr-ptmp-sec {
        value 2;
        description
          "AP radio role PTMP secondary";
      }
      enum eurr-fl-base {
        value 3;
        description
          "AP radio role mobility base";
      }
      enum eurr-fl-client {
        value 4;
        description
          "AP radio role mobility client";
      }
    }
    description
      "Enumeration for URWB radio role";
  }

  grouping st-urwb-mob {
    description
      "Attributes of URWB mobility config";
    leaf role {
      type wireless-enum-types:urwb-mob-mode;
      default "urwb-mob-base";
      description
        "This value indicates role of backhaul device";
    }
    leaf scan-idle {
      type uint32 {
        range "0 .. 65535";
      }
      units "seconds";
      default "0";
      description
        "Specifies the interval, in seconds, for periodic background channel scanning by the URWB device.";
    }
    leaf scan-after {
      type uint32 {
        range "0 .. 65535";
      }
      units "milliseconds";
      default "0";
      description
        "This value indicates the timeout for running an active scanning when the device is isolated from the infrastructure";
    }
    leaf scan-rssi-th {
      type uint32 {
        range "0 .. 96";
      }
      units "dBm";
      default "0";
      description
        "This value depicts RSSI threshold for active scanning";
    }
    leaf warmup {
      type uint32 {
        range "0 .. 300000";
      }
      units "milliseconds";
      default "30000";
      description
        "This value depicts warm up time before accepting/initiating handoff";
    }
    leaf timeout {
      type uint16;
      units "milliseconds";
      default "800";
      description
        "Specifies the timeout, in milliseconds, for candidate infrastructure units.";
    }
    leaf rssi-dhi {
      type uint16 {
        range "0 .. 96";
      }
      units "dBm";
      default "6";
      description
        "This value indicates mobility handoff hysteresis high threshold value";
    }
    leaf rssi-dlo {
      type uint16 {
        range "0 .. 96";
      }
      default "3";
      description
        "This value indicates mobility handoff hysteresis low threshold value";
    }
    leaf rssi-dth {
      type uint16 {
        range "0 .. 96";
      }
      units "dBm";
      default "35";
      description
        "Specifies the RSSI threshold value, in dBm, used for determining low or high signal conditions during mobility operations.";
    }
    leaf ra-red {
      type uint8 {
        range "1 .. 5";
      }
      default "1";
      description
        "This value indicates level of redundancy for route advertisement signalling";
    }
    leaf bc-eth {
      type wireless-enum-types:urwb-mob-bce;
      default "urwb-mbce-dis";
      description
        "Specifies the handoff behavior when all Ethernet ports are disconnected.";
    }
    leaf bc-crd {
      type wireless-enum-types:urwb-mob-bcc;
      default "urwb-mbcc-dis";
      description
        "Specifies the handoff behavior when the coordinator is unreachable.";
    }
    leaf fast-drop {
      type uint16 {
        range "0 .. 65535";
      }
      default "0";
      description
        "Specifies maximum number of consecutive lost packets before triggering fast drop event";
    }
    leaf egress-point {
      type wireless-enum-types:urwb-egress-point;
      default "egress-point-coord";
      description
        "Specifies where URWB traffic exits from the network, either at the coordinator or at the controller";
    }
  }

  grouping st-urwb-mpls {
    description
      "Attributes of URWB MPLS config";
    leaf ha-en {
      type boolean;
      default "false";
      description
        "This value indicates whether high availability is enabled on the backhaul radio";
    }
    leaf ha-timeout {
      type uint16;
      units "milliseconds";
      default "100";
      description
        "Specifies the MPLS high-availability timeout, in milliseconds.";
    }
    leaf uni-fl {
      type boolean;
      default "false";
      description
        "This value indicates MPLS unicast flood is enabled";
    }
    leaf uni-fl-l {
      type boolean;
      default "false";
      description
        "Specifies whether limits are applied to MPLS unicast flooding on the backhaul radio.";
    }
    leaf eth-1 {
      type boolean;
      default "false";
      description
        "Indicates whether Ethernet I-frame forwarding is enabled on the backhaul radio.";
    }
    leaf eth-fm {
      type wireless-enum-types:urwb-efm;
      default "urwb-efm-none";
      description
        "This value indicates the method of configuration for the ethernet filter";
    }
  }

  grouping st-urwb-mpo {
    description
      "Attributes of URWB mobility config";
    leaf status {
      type wireless-enum-types:urwb-mpo-st;
      default "urwb-mpo-dis";
      description
        "Specifies the MPO operating status on the backhaul radio.";
    }
    leaf max-links {
      type uint8 {
        range "1 .. 4";
      }
      default "2";
      description
        "Specifies the maximum number of MPO links on the backhaul radio.";
    }
    leaf min-rssi {
      type int8 {
        range "0 .. 96";
      }
      units "dBm";
      default "20";
      description
        "Specifies the minimum RSSI, in dBm, required to establish MPO redundant links.";
    }
    leaf class-cs {
      type uint8 {
        range "0 .. 7";
      }
      default "6";
      description
        "Specifies the class of service of traffic to protect with MPO redundancy.";
    }
    leaf tlmtry {
      type boolean;
      default "false";
      description
        "Indicates whether MPO telemetry is enabled.";
    }
  }

  grouping st-urwb-eth {
    description
      "Attributes of URWB ethernet config";
    leaf lan-id {
      type uint8 {
        range "0 .. 4";
      }
      default "0";
      description
        "This value indicates the LAN interface identifier for URWB ethernet configuration";
    }
    leaf lan-poe {
      type boolean;
      default "false";
      description
        "This value indicates whether Power over Ethernet (PoE) is enabled on LAN interface";
    }
  }

  grouping st-urwb-radio {
    description
      "Attributes of URWB radio";
    leaf role {
      type wireless-enum-types:enm-radio-urwb-role;
      default "urwb-rad-role-none";
      description
        "This value indicates URWB radio role";
    }
    leaf band {
      type wireless-types:enm-ewlc-dot11-radio-band;
      default "dot11-invalid-band";
      description
        "This value indicates URWB radio band";
    }
    leaf chan {
      type uint16 {
        range "1 .. 233";
      }
      default "1";
      description
        "This value indicates URWB channel";
    }
    leaf c-width {
      type wireless-enum-types:rrm-chan-width;
      units "MHz";
      default "rrm-channel-width-20-mhz";
      description
        "This value indicates URWB channel width";
    }
    leaf crypto {
      type wireless-enum-types:enm-radio-urwb-crypto;
      default "urwb-rad-crypt-fxkey";
      description
        "This value indicates AES key type";
    }
    leaf kc-rt {
      type uint16;
      units "seconds";
      default "15";
      description
        "This value indicates key control rotation timeout";
    }
    leaf rssi-th {
      type uint8 {
        range "0..96";
      }
      units "dBm";
      default "0";
      description
        "This value indicates RSSI threshold  for PTMP scanning";
    }
    leaf autoscan {
      type boolean;
      default "false";
      description
        "This value indicates whether autoscan is enabled for PTMP";
    }
    leaf cl-id {
      type string;
      default "CiscoURWB";
      description
        "This value indicates cluster id for PTMP";
    }
    leaf tw-id {
      type string;
      default "";
      description
        "This value indicates tower id for PTMP";
    }
    leaf pkt-retries {
      type uint8 {
        range "0 .. 32";
      }
      default "32";
      description
        "Specifies the maximum number of packet retries allowed on the URWB radio";
    }
    leaf max-link-dist {
      type uint8 {
        range "0 .. 99";
      }
      units "km";
      default "3";
      description
        "Specifies the maximum allowed link distance for the URWB radio";
    }
    leaf mcs-dot11-type {
      type wireless-enum-types:urwb-dot11-proto;
      default "urwb-80211-none";
      description
        "Specifies the 802.11 protocol type used for Modulation and Coding Scheme(MCS) index";
    }
    leaf dot11n-max-mcs {
      type uint8 {
        range "0 .. 7";
      }
      default "7";
      description
        "Specifies the maximum MCS index supported for 802.11n on the URWB radio";
    }
    leaf dot11ac-max-mcs {
      type uint8 {
        range "0 .. 9";
      }
      default "9";
      description
        "Specifies the maximum MCS index supported for 802.11ac on the URWB radio";
    }
    leaf dot11ax-max-mcs {
      type uint8 {
        range "0 .. 11";
      }
      default "9";
      description
        "Specifies the maximum MCS index supported for 802.11ax on the URWB radio";
    }
  }

  grouping st-urwb-radio-exec {
    description
      "URWB radio execution configuration and status";
    leaf cfg-ptmp-primary-enable {
      type boolean;
      description
        "Configured point-to-multipoint primary enable status";
    }
    leaf ptmp-primary-enable {
      type boolean;
      description
        "Actual point-to-multipoint primary enable status";
    }
    leaf cfg-dfs-role {
      type wireless-enum-types:urwb-rad-dfs;
      description
        "Configured DFS role for URWB radio";
    }
    leaf dfs-role {
      type wireless-enum-types:urwb-rad-dfs;
      description
        "Actual DFS role for URWB radio";
    }
  }

  grouping st-urwb-chan-list-entry {
    description
      "Attributes of URWB channel list";
    leaf chan {
      type uint16 {
        range "1 .. 233";
      }
      description
        "Indicates URWB channel number";
    }
    leaf c-width {
      type uint16;
      units "MHz";
      description
        "Indicates URWB channel width in MHz";
    }
  }

  grouping st-urwb-nat-rule-key {
    description
      "URWB NAT rule key definition";
    leaf outside-port {
      type uint16 {
        range "1 .. 65535";
      }
      must '. != 651 and . != 5246 and . != 5247 and . != 6600 and . != 6610' {
        error-message "The specified outside port is reserved and unavailable for NAT - reserved ports: 651, 5246, 5247, 6600, 6610";
        error-app-tag "must-violation";
      }
      description
        "Outside port number for NAT rule";
    }
    leaf proto {
      type wireless-enum-types:urwb-nat-protocol;
      description
        "Protocol type (TCP or UDP) for NAT rule";
    }
  }

  grouping st-urwb-nat {
    description
      "URWB NAT configuration";
    leaf enable {
      type boolean;
      default "false";
      description
        "Indicates whether URWB NAT functionality is enabled; true enables NAT, false disables it.";
    }
    leaf nat-addr {
      type inet:ip-address;
      must "not(starts-with(., '0.')) and not(starts-with(., '127.')) and not(starts-with(., '224.')) and not(starts-with(., '225.')) and not(starts-with(., '226.')) and not(starts-with(., '227.')) and not(starts-with(., '228.')) and not(starts-with(., '229.')) and not(starts-with(., '230.')) and not(starts-with(., '231.')) and not(starts-with(., '232.')) and not(starts-with(., '233.')) and not(starts-with(., '234.')) and not(starts-with(., '235.')) and not(starts-with(., '236.')) and not(starts-with(., '237.')) and not(starts-with(., '238.')) and not(starts-with(., '239.')) and not(starts-with(., '240.')) and not(starts-with(., '241.')) and not(starts-with(., '242.')) and not(starts-with(., '243.')) and not(starts-with(., '244.')) and not(starts-with(., '245.')) and not(starts-with(., '246.')) and not(starts-with(., '247.')) and not(starts-with(., '248.')) and not(starts-with(., '249.')) and not(starts-with(., '250.')) and not(starts-with(., '251.')) and not(starts-with(., '252.')) and not(starts-with(., '253.')) and not(starts-with(., '254.')) and not(starts-with(., '255.')) and not(. = '128.0.0.0') and not(. = '192.0.0.0')" {
        error-message "Invalid NAT IP Address - cannot be 0.x.x.x, loopback, multicast (224.0.0.0-239.255.255.255), Class E (240.0.0.0-255.255.255.255), or reserved subnet-mask edge values (128.0.0.0, 192.0.0.0)";
        error-app-tag "must-violation";
      }
      description
        "Inside IP address for NAT translation";
    }
    leaf net-mask {
      type inet:ip-address;
      must "not(starts-with(., '0.')) and (starts-with(., '255.') or starts-with(., '254.') or starts-with(., '252.') or starts-with(., '248.') or starts-with(., '240.') or starts-with(., '224.') or starts-with(., '192.') or starts-with(., '128.'))" {
        error-message "Invalid NAT netmask - must be a valid contiguous subnet mask";
        error-app-tag "must-violation";
      }
      description
        "Netmask for the NAT inside IP address";
    }
    leaf out-port-min {
      type uint16 {
        range "1 .. 65535";
      }
      must '. <= ../out-port-max' {
        error-message "NAT outside port minimum must be less than or equal to maximum";
        error-app-tag "must-violation";
      }
      must 'not((. <= 651 and ../out-port-max >= 651) or (. <= 5247 and ../out-port-max >= 5246) or (. <= 6610 and ../out-port-max >= 6600))' {
        error-message "NAT outside port range cannot include reserved ports: 651, 5246, 5247, 6600, 6610";
        error-app-tag "must-violation";
      }
      description
        "Minimum port number for NAT outside port range";
    }
    leaf out-port-max {
      type uint16 {
        range "1 .. 65535";
      }
      description
        "Maximum port number for NAT outside port range";
    }
  }
}
