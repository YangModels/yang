module Cisco-IOS-XE-dhcp {
  yang-version 1.1;
  namespace "http://cisco.com/ns/yang/Cisco-IOS-XE-dhcp";
  prefix ios-dhcp;

  import cisco-semver {
    prefix cisco-semver;
  }
  import ietf-inet-types {
    prefix inet;
  }
  import Cisco-IOS-XE-native {
    prefix ios;
  }
  import Cisco-IOS-XE-types {
    prefix ios-types;
  }
  import Cisco-IOS-XE-features {
    prefix ios-features;
  }
  import Cisco-IOS-XE-interface-common {
    prefix ios-ifc;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Dynamic Host Configuration Protocol (DHCP) Yang model.
     Copyright (c) 2016-2022 by Cisco Systems, Inc.
     All rights reserved.";

  revision 2026-08-01 {
    description
      "- Added snooping leaf under dhcp-snoop-conf container to solve the xpath issue
       - Added support for Address and VRF option after dhcp-server
       - Added support for match server mac access-list
       - Added TwoHundredGigE and FourHundredGigE interface support
       - Added warnings to url leaf for insecure protocols FTP, HTTP, TFTP, RCP";
    cisco-semver:module-version "15.1.0";
  }
  revision 2026-02-01 {
    description
      "- Added yang support for ip dhcp-relay source-interface
       - Moved deprecated nodes between 17.12 to 17.14 to obsolete
       - Moved string node under circuit-id container to obsolete
       - Moved interface node under ipv6 dhcp relay destination to obsolete
       - Moved nodes client, server, monitor under device-role to obsolete
       - Moved nodes mac-address, no-relay-agent-address to obsolete
       - Added yang model support for redundancy CLI under ip dhcp pool
       - Added yang support for ip dhcp client lease for interfaces
       - Added tailf:cli-diff-delete-before to process none before vlan-name, add, all
       - Deprecated the leaf ignore under bootp and updated the new leaf ignore-bootp
       - Added yang support for dhcp pool authorization shared password
       - Added Type6 encryption support for ipv6 dhcp framed password
       - Added DHCP CLI support for Port-channel subinterface
       - Added default valid preferred lifetime for IPv6 DHCP pool address prefix cli
       - Added FourHundredGigE interface support";
    cisco-semver:module-version "15.0.0";
  }
  revision 2025-07-01 {
    description
      "- Added support for dhcp-server-tracking
       - Added FiftyGigabitEthernet interface support
       - Re-ordered the network container before address list in dhcp pool and there is no change in model";
    cisco-semver:module-version "14.1.0";
  }
  revision 2025-03-01 {
    description
      "- Updated vendor-specific suboption's leaf list address to leaf-list to hold multiple addresses
       - Added support for new DHCP options";
    cisco-semver:module-version "14.0.0";
  }
  revision 2024-11-01 {
    description
      "- Adding a yang module for Netbios-name-server under Pool
       - Updating a module to accept valid password types
       - Updating dependency constraint for address client-id with network config
       - Modified the range for dhcp client route track";
    cisco-semver:module-version "13.0.0";
  }
  revision 2024-07-01 {
    description
      "- Updated IP address list in DHCP pool raw options CLI to store user-specified order
       - Default value update for link-selection compatibility suboption under IP DHCP in the data model
       - Default value update for server-override compatibility suboption under IP DHCP in the data model
       - OBSOLETE the model which was deprecated before 17.6 release
       - Updated new-class container for DHCP class management in the data model
       - Add support for DHCPv4 lease-query compatibility, reforwarding policy
       - Add support for DHCPv4 server and client parameters
       - Add support for DHCPv6 IA NA, IA PD Route Addition and DHCPv6 client link address flag
       - Default value update for lease under IP DHCP POOL in the data model
       - Update must constraint for ipv6 dhcp guard
       - Fixing ipv6 dhcp guard device-role annotations
       - Added a when statement for AAA leaf under use class module";
    cisco-semver:module-version "12.0.0";
  }
  revision 2024-03-01 {
    description
      "- Updated default value for ping timeout
       - Added support for ip dhcp auto-broadcast and relay information check Cli's
       - Add information option allow-untrusted under ip dhcp snooping
       - Added vlan-v2 and obsolete vlan and vlan-list
       - Added default value for timeout and write-delay leafs
       - Deprecated empty type leafs under verify container and implemented the type of leafs as boolean
       - Obsolete guard attach-policy";
    cisco-semver:module-version "11.0.0";
  }
  revision 2023-11-01 {
    description
      "- Updated hex string pattern for DHCP option 124
       - Add maximum length constraint to ip/dhcp/pool/id node";
    cisco-semver:module-version "10.1.0";
  }
  revision 2023-07-01 {
    description
      "- Add ip dhcp restrict-next-hop CLI under interface mode
       - Updated must conditions in ipv6 dhcp pool for better performance
       - Extended DHCPv6 support for Dialer interface
       - Added support for DHCP snooping track server
       - Added support for snooping";
    cisco-semver:module-version "10.0.0";
  }
  revision 2023-03-01 {
    description
      "- Adding ipv6 dhcp support for interface Cellular and Ethernet
       - Deprecated interface leaf under ipv6 dhcp relay destination to leaf-list
       - Update vrf-name leaf under ipv6 dhcp relay destination to allow defined VRFs only
       - Updated relay-interface under ipv6 dhcp relay destination to allow only interface strings
       - Enforced hexadecimal string format on pool/option/hex node";
    cisco-semver:module-version "9.0.0";
  }
  revision 2022-11-01 {
    description
      "- Update yang-version to 1.1
       - Adding DHCPv4 and DHCPv6 CLI to configure vendor-identifying Vendor class data
       - Added support for override string
       - Deprecated leaf string under circuit-id container
       - Added if-feature statement to disable IPv6 DHCP Guard commands on platforms where this feature is not supported";
    cisco-semver:module-version "8.0.0";
  }
  revision 2022-07-01 {
    description
      "- Adding DHCPv4 short-lease leaf for interface and global level";
    cisco-semver:module-version "7.1.0";
  }
  revision 2022-03-01 {
    description
      "- Obsolete interface container under import container
       - Added support for ip dhcp event-notification interval
       - Add vpn-id and server-id-override options to ip dhcp relay information option";
    cisco-semver:module-version "7.0.0";
  }
  revision 2021-11-01 {
    description
      "- Added length constraint to DHCP pool name
       - Added support for prefix-delegation dhcpv6 pool
       - Added support for prefix-delegation dhcpv6 client
       - Added support for dhcpv6 bulk-lease commands
       - Added vendor-specific and sub options
       - Added rapid-commit and allow-hint under ipv6 dhcp server <pool name>
       - Added ipv6 dhcp ping packets, ipv6 dhcp database <agent> and options
       - Added ipv6 dhcp framed password and ipv6 dhcp client information refresh minimum
       - Hardened vrf <vrf name> for ipv6 dhcp pool <pool name>";
    cisco-semver:module-version "6.0.0";
  }
  revision 2021-07-01 {
    description
      "- Updated when statement under match container for dhcp guard
       - Adding short-lease leaf for interface and global level
       - Adding the support for class-id and client-id containers";
    cisco-semver:module-version "5.0.0";
  }
  revision 2021-03-01 {
    description
      "- Fixed the issue with device-role for dhcp guard
       - Adding the support for max and min leaf under pre container in dhcp guard
       - Adding the support for attaching policy under vlan for dhcp guard
       - Added default in host
       - Added acl leaf in snooping-conf
       - Added vlan-list in snooping conf to take vlan range and deprecated vlan";
    cisco-semver:module-version "4.0.0";
  }
  revision 2020-07-01 {
    description
      "- Added ordered-by user under leaf-list dns-server-list
       - Added constraints and yang code to support for Stateless dhcpv6 ";
    cisco-semver:module-version "3.0.0";
  }
  revision 2020-03-01 {
    description
      "- Added constraints and defaults";
    cisco-semver:module-version "2.1.0";
  }
  revision 2019-11-01 {
    description
      "- Added new subnet config";
    cisco-semver:module-version "2.0.0";
  }
  revision 2019-07-01 {
    description
      "- Establish semantic version baseline
       - Added dhcp relay options
       - Added <ipv6 dhcp binding> and <ipv6 dhcp ppp> options
       - dhcp pool utilization mark support";
    cisco-semver:module-version "1.0.0";
  }
  revision 2019-01-25 {
    description
      "Added leaf for App-hosting Gigabit Ethernet interface";
  }
  revision 2018-11-29 {
    description
      "make dhcp snooping changes updated in the netconf datastore";
  }
  revision 2018-11-16 {
    description
      "Cleanup spelling errors in description statements";
  }
  revision 2018-11-05 {
    description
      "Delete intf 'ipv6 dhcp relay destination vrf' before 'vrf forwaring'";
  }
  revision 2018-07-26 {
    description
      "Added some support for interface ipv6 dhcp relay";
  }
  revision 2018-07-25 {
    description
      "Add ip dhcp route";
  }
  revision 2018-07-24 {
    description
      "Fix ip dhcp secondary address and inline lease";
  }
  revision 2018-06-16 {
    description
      "Fix ip dhcp database";
  }
  revision 2018-06-13 {
    description
      "Add more ip dhcp support";
  }
  revision 2018-05-30 {
    description
      "Add ipv6 dhcp relay commands and remove unsupported guard command";
  }
  revision 2018-05-19 {
    description
      "Add dhcp models under ATM interface and sub interface";
  }
  revision 2018-05-17 {
    description
      "Added default-router container support with augmenting the Dialer interface";
  }
  revision 2018-05-11 {
    description
      "allow ip dhcp pool option to remove one ip in rpc";
  }
  revision 2018-05-07 {
    description
      "Add ip dhcp to interface Ethernet";
  }
  revision 2018-03-22 {
    description
      "Fix ip dhcp use vrf connected default behavior";
  }
  revision 2018-03-12 {
    description
      "Add vrf and high-address to the key for ip dhcp excluded-address";
  }
  revision 2018-02-26 {
    description
      "add ip dhcp use support";
  }
  revision 2018-01-16 {
    description
      "Make it take multiple vlans: ip dhcp snooping vlan <num>";
  }
  revision 2018-01-10 {
    description
      "Changed ip dhcp pool / dns-server to cli-flat-list-syntax";
  }
  revision 2017-11-27 {
    description
      "Added Change 25GE name";
  }
  revision 2017-11-14 {
    description
      "Add 100GE interface";
  }
  revision 2017-11-06 {
    description
      "Remove choice for ip dhcp pool / client-identifier and hardware-address";
  }
  revision 2017-11-01 {
    description
      "Add ip dhcp pool / host, client-name, client-identifier, hardware-address";
  }
  revision 2017-10-18 {
    description
      "Add modeling to interface mode: ip dhcp client route distance/track";
  }
  revision 2017-09-14 {
    description
      "This revison has changes for new 2gig interface addition";
  }
  revision 2017-08-16 {
    description
      "This revision has changes for new 5gig and 25gig interfaces addition";
  }
  revision 2017-04-28 {
    description
      "inet:ipv6-prefix changed to ios-types:ipv6-prefix";
  }
  revision 2017-03-02 {
    description
      "Re-arrange the order of vrf in ipv6 dhcp pool";
  }
  revision 2017-02-07 {
    description
      "Initial revision";
  }

  grouping config-interface-ipv6-dhcp-guard-vlan-grouping {
    container vlan {
      description
        "Configure the vlan list for which this policy applies (default: all)";
      leaf vlan-name {
        description
          "VLAN IDs of the VLANs for which this policy applies";
        type string;
      }
      leaf add {
        description
          "add VLANs to the current list";
        type string;
      }
      leaf all {
        description
          "all VLANs";
        type empty;
      }
      leaf except {
        description
          "VLAN IDs of disallowed VLANS for this policy on this port";
        type string;
      }
      leaf none {
        description
          "no VLANs";
        type empty;
      }
      leaf remove {
        description
          "Remove VLANs from the current list";
        type string;
      }
    }
  }

  grouping config-interface-ip-dhcp-grouping {
    container client {
      description
        "DHCP client configuration";
      container lease {
        description
          "Address lease time";
        leaf days {
          description
            "Days";
          type uint16 {
            range "0..365";
          }
        }
        leaf hours {
          description
            "Hours";
          when '../days';
          type uint8 {
            range "0..23";
          }
        }
        leaf minutes {
          description
            "Minutes";
          when '../hours';
          type uint8 {
            range "0..59";
          }
        }
      }
      leaf hostname {
        description
          "Specify hostname to use";
        type string;
      }
      container option {
        description
          "DHCP Client options";
        list option-range {
          key "option-range";
          leaf option-range {
            description
              "DHCP option code (1-254)";
            type uint8 {
              range "1..254";
            }
          }
          container option_path {
            leaf hex {
              description
                "Input hex string";
              type string;
            }
            leaf ascii {
              description
                "Input ascii string";
              type string;
            }
            leaf-list ip {
              description
                "Input IP Address";
              type inet:host;
            }
          }
          container option125_path {
            leaf enterprise_id {
              type uint32;
            }
            leaf suboption {
              type uint8 {
                range "1..3";
              }
            }
            leaf ascii {
              description
                "Input ascii string";
              type string;
            }
            leaf hex {
              description
                "Input hex string";
              type string;
            }
          }
        }
      }
      container request {
        description
          "Specify options (not) to request";
        leaf option {
          description
            "DHCP options";
          type uint8 {
            range "1..254";
          }
        }
      }
      container route {
        description
          "Options for routes installed by dhcp";
        leaf distance {
          description
            "set distance for dhcp static routes";
          type uint8 {
            range "1..254";
          }
          default "254";
        }
        leaf track {
          description
            "Track dhcp routes";
          type uint16 {
            range "1..32767";
          }
        }
      }
      container default-router {
        description
          "Set DHCP default router related information";
        leaf distance {
          description
            "Set the DHCP derived default route metric";
          type uint8 {
            range "1..255";
          }
        }
      }
      container class-id {
        description
          "Specify Class-ID to use";
        choice class-id-type {
          leaf LINE {
            description
              "Class-ID string, truncated to 200 characters";
            type string {
              length "1..200";
            }
          }
          leaf hex {
            description
              "Specify hexadecimal class-ID";
            type string {
              pattern '[0-9a-fA-F]*' {
                error-message "Incorrect format";
              }
            }
          }
        }
      }
      container client-id {
        description
          "Specify Client-ID to use";
        choice client-id-type {
          container int-config {
            description
              "Specify interface to use";
            uses ios-ifc:interface-grouping;
          }
          leaf hex {
            description
              "Client-ID in hex";
            type string {
              pattern '[0-9a-fA-F]*' {
                error-message "Incorrect format";
              }
            }
          }
          leaf ascii {
            description
              "Client-ID as ascii string";
            type string {
              length "1..200";
            }
          }
        }
      }
      uses vendor-class-grouping;
    }
    container server {
      description
        "Configure DHCP server behavior";
      container use {
        description
          "Configure use of options";
        choice client-type {
          container subscriber-id {
            description
              "Configure use of subscriber-id suboption";
            leaf client-id {
              description
                "Use subscriber-id suboption as client-id";
              type empty;
            }
          }
          container hardware-address {
            description
              "Configure use of hardware address";
            leaf client-id {
              description
                "Use hardware address as client-id";
              type empty;
            }
          }
        }
      }
    }
    container relay {
      description
        "DHCP relay configuration parameters";
      container information {
        description
          "DHCP relay information option";
        container check-reply {
          description
            "Validate relay information in BOOTREPLY";
          presence "true";
          leaf none {
            description
              "Set to none";
            type empty;
          }
        }
        container option {
          description
            "DHCP relay information option";
          leaf subscriber-id {
            description
              "Subscriber identifier sub option";
            type string;
          }
          leaf vpn-id {
            description
              "Enable vpn-id support on this interface";
            type empty;
          }
          leaf server-id-override {
            description
              "Insert server-id-override and link-selection suboption";
            type empty;
          }
        }
        container option-insert {
          description
            "Insert relay information in BOOTREQUEST";
          presence "true";
          leaf none {
            description
              "Set to none";
            type empty;
          }
        }
        leaf policy-action {
          description
            "Define reforwarding policy";
          type enumeration {
            enum drop;
            enum encapsulate;
            enum keep;
            enum replace;
          }
        }
        leaf trusted {
          description
            "Received DHCP packet may contain relay info option with zero giaddr";
          type empty;
        }
      }
      leaf source-interface {
        description
          "Set source interface for relayed messages";
        type string;
      }
      leaf short-lease {
        description
          "Short lease value in seconds";
        type uint16 {
          range "60..3600";
        }
      }
    }
    container snooping {
      description
        "DHCP Snooping";
      container information {
        description
          "DHCP Snooping information";
        container option {
          description
            "DHCP Snooping information option";
          leaf allow-untrusted {
            description
              "DHCP Snooping information option allow-untrusted";
            type empty;
          }
        }
      }
      container limit {
        description
          "DHCP Snooping limit";
        leaf rate {
          description
            "DHCP Snooping limit";
          type uint16 {
            range "1..2048";
          }
        }
      }
      leaf trust {
        description
          "DHCP Snooping trust config";
        type empty;
      }
      list vlan {
        description
          "DHCP Snooping vlan";
        key "id";
        leaf id {
          type uint16 {
            range "1..4094";
          }
        }
        container information {
          description
            "DHCP Snooping information";
          container option {
            description
              "DHCP Snooping information option";
            container format-type {
              description
                "Option 82 information format";
              container circuit-id {
                description
                  "Circuit id option 82 format";
                choice string-choice {
                  container override {
                    description
                      "Override all contents of circuit-id";
                    leaf string {
                      description
                        "User defined string for circuit id";
                      type string {
                        length "3..63";
                      }
                    }
                  }
                  leaf str {
                    description
                      "User defined string for circuit id";
                    type string {
                      length "3..63";
                    }
                  }
                }
                leaf string {
                  description
                    "(OBSOLETE) User defined string for circuit id";
                  status obsolete;
                  type string {
                    length "3..63";
                  }
                }
              }
            }
          }
        }
      }
    }
    leaf restrict-next-hop {
      description
        "Limit DHCP lease to immediate neighbors";
      type enumeration {
        enum cdp {
          description
            "restrict dhcp lease to cdp neighbors";
        }
        enum lldp {
          description
            "restrict dhcp lease to lldp neighbors";
        }
        enum both {
          description
            "restrict dhcp lease to both lldp and cdp neighbors";
        }
      }
    }
  }

  grouping config-interface-dhcp-server-tracking-grouping {
    container dhcp-server-tracking {
      if-feature "ios-features:dhcp-server-tracking";
      description
        "Configure DHCP Server Tracking policy on the interface";
      presence "true";
    }
  }

  grouping config-interface-ipv6-dhcp-grouping {
    choice client-server-relay-choice {
      container client {
        description
          "Act as an IPv6 DHCP client";
        container request {
          description
            "Request";
          leaf vendor {
            description
              "Request Vendor specific options";
            type empty;
          }
        }
        uses vendor-class-grouping;
        container pd {
          description
            "Prefix-Delegation";
          container pd-prefix {
            leaf prefix-name {
              description
                "Prefix name, truncated to 200 characters";
              type string {
                length "1..200";
              }
            }
            leaf rapid-commit {
              description
                "Enable Rapid-Commit";
              type empty;
            }
          }
          leaf-list hint {
            description
              "IPv6 x:x::y/<z>";
            ordered-by user;
            type ios-types:ipv6-prefix;
          }
        }
        container information {
          description
            "Configure information refresh option";
          container refresh {
            description
              "Configure information refresh parameters";
            leaf minimum {
              description
                "Minimum information refresh time";
              type uint16 {
                range "60..3600";
              }
            }
          }
        }
      }
      list server {
        max-elements 1;
        description
          "Act as an IPv6 DHCP server";
        key "word";
        leaf word {
          type string;
        }
        leaf allow-hint {
          description
            "Allow hint from client";
          type empty;
        }
        leaf rapid-commit {
          description
            "Enable Rapid-Commit";
          type empty;
        }
        leaf preference {
          description
            "Preference";
          when "not(contains(../word,'automatic'))";
          type uint8 {
            range "0..255";
          }
        }
      }
      container relay {
        description
          "Act as an IPv6 DHCP relay agent";
        container destination {
          description
            "Configure relay destination";
          list address {
            key "ipv6-address";
            leaf ipv6-address {
              description
                "IPv6 Address";
              type inet:ipv6-address;
            }
            uses interface-leaf-list-grouping;
            leaf interface {
              description
                "(OBSOLETE) Interface for IPv6 relay address";
              status obsolete;
              type string;
            }
          }
          list vrf {
            key "vrf-name relay-address";
            leaf vrf-name {
              must '/ios:native/ios:vrf/ios:definition[ios:name=current()]/ios:address-family/ios:ipv6' {
                error-message "% Specified IPv6 VRF must be created first, deleted last";
              }
              type string;
            }
            leaf relay-address {
              description
                "Relay Agent IPv6 Address";
              type inet:ipv6-address;
            }
            leaf-list relay-interface {
              must '/ios:native/ios:interface/*[concat(local-name(.), ios:name) = current()]' {
                error-message "Unsupported NED interface type";
              }
              type string;
            }
          }
          list global {
            key "relay-address";
            leaf relay-address {
              description
                "Relay Agent IPv6 Address";
              type inet:ipv6-address;
            }
            leaf-list relay-interface {
              must '/ios:native/ios:interface/*[concat(local-name(.), ios:name) = current()]' {
                error-message "Unsupported NED interface type";
              }
              type string;
            }
          }
        }
        leaf trust {
          description
            "Interface is trusted to process relay-replies";
          type empty;
        }
        container option {
          description
            "Insert options in Relay-forward messages";
          leaf vpn {
            description
              "Insert VSS option in Relay-Forward Messages";
            type empty;
          }
        }
        container source-interface {
          description
            "Insert VSS option in Relay-Forward Messages";
          uses ios-ifc:interface-grouping;
        }
        leaf short-lease {
          description
            "Short lease value in seconds";
          type uint16 {
            range "60..3600";
          }
        }
      }
    }
    container framed {
      description
        "Framed-IPv6-Prefix allocation";
      container password {
        description
          "Set password for Prefix allocation";
        leaf encryption {
          description
            "Encryption type (0=none, 6=type 6, 7=type 7)";
          type uint8 {
            range "0|6|7";
          }
          default "0";
        }
        leaf word {
          description
            "Password for Framed-IPv6-Prefix allocation";
          type string;
        }
      }
    }
    container guard {
      if-feature "ios-features:dhcp-guard";
      description
        "Configure IPv6 DHCP guard on the interface";
      presence "true";
      list attached-policies {
        key "attach-policy";
        leaf attach-policy {
          description
            "Apply a policy for feature DHCP guard";
          type string;
          must "(/ios:native/ios:ipv6/ios:dhcp/ios-dhcp:guard/ios-dhcp:policy[ios-dhcp:dhcp-guard-policy-name=current()]) or .='default'" {
            error-message "Create dhcp guard policy first, then attach policy; Detach policy from interface before removing the policy";
          }
        }
        uses config-interface-ipv6-dhcp-guard-vlan-grouping;
      }
      container default-policy {
        uses config-interface-ipv6-dhcp-guard-vlan-grouping;
      }
      leaf attach-policy {
        status obsolete;
        description
          "Apply a policy for feature DHCP Guard";
        type string;
      }
    }
  }

  grouping ip-dhcp-grouping {
    container aaa {
      description
        "Configure aaa attributes";
      container default {
        description
          "Specify default values for aaa attributes";
        leaf username {
          description
            "Default username for non-VRF pool subnet request or release";
          type string;
        }
      }
    }
    container bootp {
      description
        "BOOTP specific configuration";
      leaf ignore {
        status deprecated;
        description
          "Configure this DHCP server to ignore to BOOTP requests.";
        type empty;
      }
      leaf ignore-bootp {
        description
          "Configure this DHCP server to ignore to BOOTP requests.";
        type boolean;
        default "true";
      }
    }
    list class {
      description
        "Configure DHCP classes";
      key "id";
      leaf id {
        type string;
      }
      container option {
        description
          "Raw DHCP options";
        list option-list {
          key "option-range";
          leaf option-range {
            description
              "DHCP option code (1-254)";
            type uint8 {
              range "1..254";
            }
          }
          leaf LINE {
            description
              "Specify a regular expression string";
            type string;
          }
          list hex-list {
            key "hex-string";
            leaf hex-string {
              type string;
            }
            leaf mask {
              description
                "Specify a bit mask for the pattern";
              type inet:ipv4-address;
            }
          }
        }
      }
      container relay {
        description
          "Enter relay agent information option configuration submode";
        container agent {
          description
            "Enter relay agent information option configuration submode";
          leaf information {
            description
              "Enter relay agent information option configuration submode";
            type empty;
          }
        }
      }
      leaf remark {
        description
          "Specify a remark for this class";
        type string {
          length "1..240";
        }
      }
    }
    container compatibility {
      container suboption {
        leaf link-selection {
          type enumeration {
            enum cisco;
            enum standard;
          }
          default "cisco";
        }
        leaf server-override {
          type enumeration {
            enum cisco;
            enum standard;
          }
          default "cisco";
        }
      }
      container lease-query {
        description
          "Compatibility for lease-query message type";
        leaf client {
          description
            "Client side support (default: cisco)";
          type enumeration {
            enum cisco;
            enum standard;
          }
          default "cisco";
        }
      }
    }
    container ping {
      description
        "Specify ping parameters used by DHCP";
      container packets {
        description
          "Specify number of ping packets";
        presence "true";
        leaf number-packets {
          description
            "Number of ping packets (0 disables ping)";
          type uint8 {
            range "0..10";
          }
          default "2";
        }
      }
      leaf timeout {
        description
          "Specify ping timeout";
        type uint16 {
          range "100..10000";
        }
        default "500";
      }
    }
    container conflict {
      description
        "DHCP address conflict parameters";
      leaf logging {
        description
          "Record address conflicts in a log file";
        type boolean;
        default "true";
      }
      container resolution {
        description
          "DHCP address conflict resolution";
        presence "true";
        leaf interval {
          description
            "Time in Minutes";
          type uint32 {
            range "5..1440";
          }
        }
      }
    }
    container excluded-address {
      description
        "Prevent DHCP from assigning certain addresses";
      list low-address-list {
        key "low-address";
        leaf low-address {
          type inet:ipv4-address;
        }
      }
      list low-high-address-list {
        key "low-address high-address";
        leaf low-address {
          type inet:ipv4-address;
        }
        leaf high-address {
          type inet:ipv4-address;
        }
      }
      list vrf-low-address-list {
        key "vrf low-address";
        leaf vrf {
          description
            "VRF name for excluded address range";
          type string;
        }
        leaf low-address {
          type inet:ipv4-address;
        }
      }
      list vrf-low-high-address-list {
        key "vrf low-address high-address";
        leaf vrf {
          description
            "VRF name for excluded address range";
          type string;
        }
        leaf low-address {
          type inet:ipv4-address;
        }
        leaf high-address {
          type inet:ipv4-address;
        }
      }
    }
    container binding {
      description
        "DHCP address bindings";
      container cleanup {
        description
          "Remove expired bindings";
        leaf interval {
          description
            "Time in seconds";
          type uint16 {
            range "10..600";
          }
        }
      }
    }
    container database {
      description
        "Configure DHCP database agents";
      list resource {
        description
          "Uniform Resource Locator (URL)";
        key "resource-locator";
        leaf resource-locator {
          description
            "Uniform Resource Locator (URL)";
          type string;
        }
        leaf write-delay {
          description
            "Set the database write delay";
          type uint32 {
            range "60..4294967295";
          }
        }
        leaf timeout {
          description
            "Set the database transfer timeout";
          type uint16 {
            range "0..3600";
          }
        }
      }
    }
    container limit {
      description
        "Limit DHCP Lease";
      container lease {
        description
          "DHCP lease";
        leaf log {
          description
            "Limit DHCP Lease";
          type empty;
        }
        container per {
          description
            "per";
          leaf interface {
            description
              "interface";
            type uint16 {
              range "1..65535";
            }
          }
        }
      }
    }
    container subscriber-id {
      description
        "Global subscriber-id configuration";
      leaf interface-name {
        description
          "Use interface short-name";
        type empty;
      }
    }
    container route {
      description
        "Specify the type of routes for clients on unnumbered interfaces";
      leaf route {
        type enumeration {
          enum connected;
          enum static;
        }
        default "static";
      }
    }
    container relay {
      description
        "DHCP relay agent parameters";
      container information {
        description
          "Relay agent information option";
        leaf policy {
          description
            "Reforwarding policy definition";
          type enumeration {
            enum drop;
            enum encapsulate;
            enum keep;
            enum replace;
          }
          default "replace";
        }
        leaf trust-all {
          description
            "Received DHCP packets may contain relay info option with zero giaddr";
          type empty;
        }
        container option {
          description
            "Insert relay information in BOOTREQUEST";
          leaf option-default {
            description
              "Default option, no vpn";
            type empty;
          }
          leaf vpn {
            description
              "Insert VPN sub-options and change the giaddr to the outgoing interface";
            type empty;
          }
        }
        leaf check {
          description
            "Validate relay information in BOOTREPLY";
          type boolean;
          default "true";
        }
      }
      container bootp {
        description
          "BOOTP specific configuration";
        leaf ignore {
          description
            "Configure this DHCP relay to ignore to BOOTP requests.";
          type empty;
        }
      }
    }
    list pool {
      description
        "Configure DHCP address pools";
      key "id";
      leaf id {
        type string {
          length "1..236";
        }
      }
      leaf-list netbios-name-server {
        description
          "NetBIOS (WINS) name servers";
        ordered-by user;
        type inet:ipv4-address;
      }
      container subnet {
        description
          "Subnet";
        leaf prefix-length {
          description
            "prefix length of subnet";
          type uint8 {
            range "1..32";
          }
        }
      }
      container network {
        description
          "Network number and mask";
        container primary-network {
          description
            "Network number and mask";
          leaf number {
            description
              "Network number";
            type inet:ipv4-address;
          }
          leaf mask {
            description
              "Network mask";
            type union {
              type string;
              type inet:ipv4-address;
            }
          }
        }
        list secondary-network {
          description
            "Secondary number and mask";
          key "number";
          leaf number {
            description
              "Network number";
            type inet:ipv4-address;
          }
          leaf mask {
            description
              "Secondary mask";
            type union {
              type string;
              type inet:ipv4-address;
            }
          }
          leaf secondary {
            description
              "Configure as secondary subnet";
            type empty;
          }
        }
      }
      list address {
        description
          "ip address";
        when '../network/primary-network/number';
        key "ip";
        leaf ip {
          description
            "IP address";
          type inet:ipv4-address;
        }
        leaf client-id {
          description
            "Client ID for which address has to be assigned";
          type string;
        }
        leaf ascii {
          description
            "If the value given is ascii";
          type empty;
        }
      }
      container option {
        description
          "Raw DHCP options";
        list option-range {
          key "option-range";
          leaf option-range {
            description
              "DHCP option code";
            type uint8 {
              range "0..254";
            }
          }
          choice option-range-choice {
            case ascii-case {
              leaf ascii-new {
                description
                  "Data is an NVT ASCII string";
                type string {
                  length "1..225";
                }
              }
            }
            case hex-case {
              container hex-new {
                description
                  "Data is a hexadecimal string";
                leaf hex-line {
                  description
                    "Hexadecimal string, truncated to 180 hex characters entered";
                  type string {
                    pattern '(([0-9a-fA-F]{4}\.*)*(([0-9a-fA-F]{2})|([0-9a-fA-F]{4})))' {
                      error-message "Incorrect format: input must be an even length dotted-hexadecimal string (e.g. aabb.ccdd.eeff ...)";
                    }
                    length "1..180";
                  }
                }
                leaf none-new {
                  description
                    "No data";
                  type empty;
                }
              }
            }
            case ip-case {
              leaf-list ip-ordered {
                description
                  "Data is one or more IP addresses";
                ordered-by user;
                type inet:host;
              }
              leaf-list ip-new {
                status deprecated;
                description
                  "Data is one or more IP addresses";
                type inet:host;
              }
            }
          }
          leaf ascii {
            description
              "(OBSOLETE) Data is an NVT ASCII string";
            status obsolete;
            type string {
              length "1..225";
            }
          }
          container hex {
            description
              "(OBSOLETE) Data is a hexadecimal string";
            status obsolete;
            leaf hex-line {
              description
                "(OBSOLETE) Hexadecimal string, truncated to 180 hex characters entered";
              status obsolete;
              type string {
                length "1..180";
              }
            }
            leaf none {
              description
                "(OBSOLETE) No data";
              status obsolete;
              type empty;
            }
          }
          leaf-list ip {
            description
              "(OBSOLETE) Data is one or more IP addresses";
            status obsolete;
            type inet:host;
          }
        }
      }
      container authorization {
        description
          "Obtain address allocation information from AAA";
        container shared-password {
          description
            "Specify password used for authorization attempts";
          leaf encryption {
            description
              "Encryption type (0=none, 6=type 6)";
            type uint8 {
              range "0|6";
            }
            default "0";
          }
          leaf word {
            description
              "Password for authorization attempts";
            type string;
          }
        }
      }
      list class {
        description
          "Specify a DHCP class";
        key "name";
        leaf name {
          description
            "DHCP class name";
          type string;
        }
        container import {
          description
            "Programmatically importing DHCP option parameters";
          container interface {
            description
              "Specify interface to import options from";
            uses ios-ifc:interface-grouping;
          }
        }
        container option {
          description
            "DHCP option";
          leaf option {
            description
              "Options";
            type uint8 {
              range "1..254";
            }
          }
          leaf ascii {
            description
              "Data is an NVT ASCII string";
            type string;
          }
          leaf hex {
            description
              "Input hex string";
            type string;
          }
          leaf-list ip {
            description
              "Input IP Address";
            type inet:host;
          }
          container ext {
            leaf option {
              description
                "Options";
              type uint8 {
                range "1..254";
              }
            }
            leaf ascii {
              description
                "Data is an NVT ASCII string";
              type string;
            }
            leaf hex {
              description
                "Input hex string";
              type string;
            }
          }
        }
        container address {
          description
            "Specify an address range for this class";
          container range {
            leaf ipv4-start {
              description
                "Start IP address";
              type inet:ipv4-address;
            }
            leaf ipv4-end {
              description
                "End IP address";
              type inet:ipv4-address;
            }
          }
        }
      }
      leaf vrf {
        description
          "Associate this pool with a VRF";
        type string;
      }
      container lease {
        description
          "Address lease time";
        choice lease {
          container lease-value {
            description
              "lease in numbers";
            leaf days {
              description
                "Days";
              type uint16 {
                range "0..365";
              }
              default "1";
            }
            leaf hours {
              description
                "Hours";
              when '../days';
              type uint8 {
                range "0..23";
              }
              default "0";
            }
            leaf minutes {
              description
                "Minutes";
              when '../hours';
              type uint8 {
                range "0..59";
              }
              default "0";
            }
          }
          leaf infinite {
            description
              "Infinite lease";
            type empty;
          }
        }
      }
      container default-router {
        leaf-list default-router-list {
          description
            "Default routers";
          type union {
            type inet:ipv4-address;
            type string;
          }
        }
      }
      container utilization {
        description
          "Configure various utilization commands";
        container mark {
          description
            "Configure thresholds for subnet release or request";
          container high {
            description
              "Specify high utilization mark of the pool";
            leaf high-value {
              description
                "Specify high utilization mark of the pool";
              type uint8 {
                range "1..100";
              }
              must '(not (../../low/low-value)) or (current() > ../../low/low-value)' {
                error-message "High utilization must be greater than low utilization percentage.";
              }
            }
            leaf log {
              description
                "Log a system message when high/low state is detected";
              type empty;
            }
          }
          container low {
            description
              "Specify low utilization mark of the pool";
            leaf low-value {
              description
                "Specify low utilization mark of the pool";
              type uint8 {
                range "1..100";
              }
              must '(not (../../high/high-value)) or(current() < ../../high/high-value)' {
                error-message "Low utilization must be less than high utilization percentage.";
              }
            }
            leaf log {
              description
                "Log a system message when high/low state is detected";
              type empty;
            }
          }
        }
      }
      container dns-server {
        leaf-list dns-server-list {
          ordered-by user;
          description
            "DNS servers";
          type union {
            type inet:ipv4-address;
            type string;
          }
        }
      }
      leaf domain-name {
        description
          "Domain name";
        type string;
      }
      container host {
        description
          "Client IP address and mask";
        leaf number {
          description
            "IP address in dotted-decimal notation";
          must 'not (../../network/primary-network/number)' {
            error-message "The host command may not be used with network, origin, vrf or relay pools and vice versa";
          }
          type inet:ipv4-address;
        }
        leaf mask {
          description
            "Network mask";
          when '../number';
          type inet:ipv4-address;
          default "255.0.0.0";
        }
      }
      choice hardware-addr-cient-id-choice {
        container hardware-address {
          description
            "Client hardware address";
          must 'not (../network/primary-network/number)' {
            error-message "hardware-address command may not be used with origin, network or vrf pools and vice versa";
          }
          leaf hardware-address-val {
            description
              "Dotted-hexadecimal string (aabb.ccdd.eeff ...)";
            type ios-types:cisco-mac-address-type;
          }
        }
        leaf client-identifier {
          description
            "Client identifier, Dotted-hexadecimal string (aabb.ccdd.eeff ...)";
          must 'not (../network/primary-network/number)' {
            error-message "client-identifier command may not be used with origin, network or vrf pools and vice versa";
          }
          type string {
            pattern '([0-9a-fA-F]{4}(.[0-9a-fA-F]{4})*((.[0-9a-fA-F]{2})|(.[0-9a-fA-F]{4})))?' {
              error-message "Incorrect format for client-identifier Number: regular expression must be of the form ([0-9a-fA-F]{4}(.[0-9a-fA-F]{4})*((.[0-9a-fA-F]{2})|(.[0-9a-fA-F]{4})))?";
            }
          }
        }
      }
      leaf client-name {
        description
          "Client name, Client name (domain should not be included)";
        type string;
      }
      leaf bootfile {
        description
          "Boot file name";
        type string {
          length "1..127" {
            error-message "String length must be less than or equal to 127 characters.";
          }
        }
      }
      leaf redundancy {
        description
          "Redundancy group ID";
        type uint8 {
          range "1..2";
        }
      }
      leaf-list next-server {
        description
          "IPv4 address in dotted-decimal notation";
        ordered-by user;
        max-elements 8;
        type inet:ipv4-address;
      }
    }
    leaf smart-relay {
      description
        "Enable Smart Relay feature";
      type empty;
    }
    container dhcp-snoop-conf {
      leaf snooping {
        description
          "DHCP Snooping";
        type empty;
      }
    }
    leaf snooping {
      status deprecated;
      description
        "DHCP Snooping deprecated";
      type empty;
    }
    container snooping-conf {
      container snooping {
        description
          "DHCP Snooping";
        container database {
          description
            "DHCP snooping database agent";
          leaf url {
            description
              "DHCP snooping database url. WARNING: ftp|http|tftp|rcp options are deprecated
               and will be removed in future due to security concerns";
            type string;
          }
          leaf timeout {
            description
              "Configure abort timeout interval";
            type uint32 {
              range "0..86400";
            }
            default "300";
          }
          leaf write-delay {
            description
              "Configure delay timer for writes to URL";
            type uint32 {
              range "15..86400";
            }
            default "300";
          }
        }
        leaf glean {
          description
            "DHCP read only snooping";
          type empty;
        }
        leaf acl {
          description
            "MAC Access-list name";
          type string;
        }
        container information {
          description
            "DHCP Snooping information";
          leaf option {
            type boolean;
            default "true";
          }
          container options {
            container option {
              description
                "DHCP Snooping information option";
              leaf allow-untrusted {
                description
                  "DHCP Snooping information option allow-untrusted";
                type empty;
              }
              container format {
                description
                  "Option 82 information format";
                container remote-id {
                  description
                    "Remote id option 82 format";
                  choice remote-id-choice {
                    leaf hostname {
                      description
                        "Use configured hostname for remote id";
                      type empty;
                    }
                    leaf string {
                      description
                        "User defined string for remote id";
                      type string;
                    }
                  }
                }
              }
            }
          }
        }
        container track {
          description
            "DHCP snooping track";
          leaf host {
            description
              "DHCP snooping track host";
            type empty;
          }
          container server {
            description
              "DHCP snooping track server";
            presence "true";
            choice server-option {
              case all-dhcp-acks-option {
                leaf all-dhcp-acks {
                  description
                    "Track all DHCP ACKs";
                  type empty;
                }
              }
              case limit-option {
                leaf limit {
                  description
                    "Maximum size of the server tracking table";
                  type uint16 {
                    range "1..512";
                  }
                }
              }
            }
          }
        }
        container verify {
          description
            "DHCP snooping verify";
          leaf mac-address-v2 {
            description
              "DHCP snooping verify mac-address";
            type boolean;
            default "true";
          }
          leaf no-relay-agent-address-v2 {
            description
              "DHCP snooping verify giaddr";
            type boolean;
            default "true";
          }
          leaf mac-address {
            status obsolete;
            description
              " (OBSOLETE) DHCP snooping verify mac-address";
            type empty;
          }
          leaf no-relay-agent-address {
            status obsolete;
            description
              " (OBSOLETE) DHCP snooping verify giaddr";
            type empty;
          }
        }
        list vlan-v2 {
          description
            "DHCP Snooping vlan";
          key "id";
          leaf id {
            type uint16 {
              range "1..4094";
            }
          }
        }
        list vlan-list {
          status obsolete;
          description
            "DHCP Snooping vlan (OBSOLETE)";
          key "id";
          leaf id {
            status obsolete;
            description
              "DHCP Snooping vlan first number or vlan range,example: 1,3-5,7,9-11";
            type string {
              pattern '(((409[0-4]|40[0-8][0-9]|[1-3][0-9]{3}|[1-9][0-9]{1,2}|[1-9])(\-(409[0-4]|40[0-8][0-9]|[1-3][0-9]{3}|[1-9][0-9]{1,2}|[1-9]))?)(,((409[0-4]|40[0-8][0-9]|[1-3][0-9]{3}|[1-9][0-9]{1,2}|[1-9])(\-(409[0-4]|40[0-8][0-9]|[1-3][0-9]{3}|[1-9][0-9]{1,2}|[1-9]))?))*)';
            }
          }
        }
        list vlan {
          status obsolete;
          description
            "DHCP Snooping vlan (OBSOLETE)";
          key "id";
          leaf id {
            status obsolete;
            type uint16 {
              range "1..4094";
            }
          }
        }
        container wireless {
          description
            "DHCP snooping wireless";
          container bootp-broadcast {
            description
              "DHCP snooping wireless bootp-broadcast";
            leaf enable {
              description
                "DHCP snooping wireless bootp-broadcast enable";
              type empty;
            }
          }
        }
      }
    }
    container use {
      description
        "Configure use of certain parameters during allocation";
      choice client-type {
        container subscriber-id {
          leaf client-id {
            description
              "Use subscriber-id suboption as client-id";
            type empty;
          }
        }
        container hardware-address {
          description
            "Configure use of hardware address (i.e., MAC)";
          leaf client-id {
            description
              "Use hardware address as client-id";
            type empty;
          }
        }
      }
      container new-class {
        description
          "Class configuration.";
        leaf class {
          description
            "Allow use of DHCP classes";
          type boolean;
          default "true";
        }
        leaf aaa {
          description
            "Allow use of AAA to get class";
          when "../class = 'true'";
          type empty;
        }
      }
      container class {
        presence "true";
        status deprecated;
        leaf aaa {
          description
            "Configure use of aaa to get class";
          status deprecated;
          type empty;
        }
      }
      container vrf {
        description
          "Ignore or use receiving interface VRF";
        leaf connected {
          description
            "Use input interface VRF when servicing connected clients";
          type boolean;
          default "true";
        }
        leaf remote {
          description
            "Use input interface VRF when servicing remote clients";
          type empty;
        }
      }
    }
    container event-notification {
      description
        "DHCP event notifications";
      leaf interval {
        description
          "Time in seconds";
        type uint16 {
          range "1..300";
        }
      }
    }
    leaf auto-broadcast {
      description
        "Configure auto broadcast feature";
      type boolean;
      default "true";
    }
  }

  grouping ip-dhcp-relay-grouping {
    leaf short-lease {
      description
        "Short lease value in seconds";
      type uint16 {
        range "60..3600";
      }
    }
    container source-interface {
      description
        "Set source interface for relayed messages";
      uses ios-ifc:interface-grouping;
    }
  }

  grouping ip-dhcp-server-grouping {
    description
      "Specifies target DHCP server parameters";
    list address {
      description
        "Configure target DHCP server";
      ordered-by user;
      key "address";
      leaf address {
        description
          "IP address of DHCP server";
        type inet:ipv4-address;
      }
    }
    container vrf {
      description
        "Configure target DHCP server per VRF";
      list server {
        description
          "Configure target DHCP server in a VRF";
        ordered-by user;
        key "vrf-name address";
        leaf vrf-name {
          description
            "VRF name";
          must '/ios:native/ios:vrf/ios:definition[ios:name=current()] or /ios:native/ios:ip/ios:vrf[ios:name=current()]' {
            error-message "VRF must be created first, deleted last";
          }
          type string;
        }
        leaf address {
          description
            "IP address of DHCP server";
          type inet:ipv4-address;
        }
      }
    }
    container query {
      description
        "Configure query parameters";
      container lease {
        description
          "Global lease query parameters";
        leaf retries {
          description
            "Maximum number of retransmissions";
          type uint8 {
            range "0..5";
          }
          default "2";
        }
        leaf timeout {
          description
            "Timeout between retry (in seconds)";
          type uint8 {
            range "1..60";
          }
          default "10";
        }
      }
    }
  }

  grouping ip-dhcp-client-grouping {
    description
      "Parameters for DHCP client operation";
    leaf broadcast-flag {
      description
        "The broadcast flag";
      type boolean;
      default "true";
    }
    container default-router {
      description
        "DHCP default router related information";
      leaf distance {
        description
          "The DHCP derived default route metric";
        type uint8 {
          range "1..255";
        }
        default "254";
      }
    }
  }

  grouping ipv6-dhcp-grouping {
    container server {
      description
        "Configure IPv6 DHCP server";
      container vrf {
        description
          "Enable VRF Awareness on server";
        leaf enable {
          description
            "Enable Address/PD allocation based on VRF";
          type empty;
        }
      }
    }
    container guard {
      if-feature "ios-features:dhcp-guard";
      description
        "Configure IPv6 DHCP guard";
      list policy {
        description
          "Configure a policy for feature dhcp guard";
        key "dhcp-guard-policy-name";
        leaf dhcp-guard-policy-name {
          type string;
        }
        container device-role {
          description
            "Sets the role of the device attached to the port";
          container device-role-choice {
            leaf role-choice {
              default "client";
              type enumeration {
                enum server;
                enum monitor;
                enum client;
              }
            }
          }
          leaf server {
            status obsolete;
            description
              "(OBSOLETE), use other leaf role-choice. Attached device is a dhcp server";
            type empty;
          }
          leaf monitor {
            status obsolete;
            description
              "(OBSOLETE), use other leaf role-choice. Attached device is a monitor/sniffer";
            type empty;
          }
          leaf client {
            status obsolete;
            description
              "(OBSOLETE), use other leaf role-choice. Attached device is a client (default)";
            type empty;
          }
        }
        container match {
          description
            "dhcp filtering";
          when "../device-role/device-role-choice/role-choice = 'server'";
          container server {
            description
              "permitted server source addresses";
            container mac {
              description
                "Match based on server MAC address using access control lists";
              leaf access-list {
                description
                  "specify MAC access-list for match";
                type string;
              }
            }
            leaf access-list {
              description
                "specify access-list for match";
              type string;
            }
          }
          container reply {
            description
              "permitted server source addresses";
            leaf prefix-list {
              description
                "specify prefix-list for match";
              type string;
            }
          }
        }
        container preference {
          description
            "Preference to be used";
          when "../device-role/device-role-choice/role-choice = 'server'";
          leaf max {
            description
              "maximum allowed advertised server preference";
            must '(not (../min)) or (current() >= ../min)' {
              error-message "max must be greater than or equal to min";
            }
            type uint32 {
              range "0 .. 255";
            }
          }
          leaf min {
            description
              "minimum allowed advertised server preference";
            must '(not (../max)) or (current() <= ../max)' {
              error-message "max must be greater than or equal to min";
            }
            type uint32 {
              range "0 .. 255";
            }
          }
        }
        leaf trusted-port {
          description
            "This is a trusted port (no policing)";
          type empty;
        }
      }
    }
    list pool {
      description
        "Configure IPv6 DHCP pool";
      key "name";
      leaf name {
        description
          "DHCP pool name";
        type string {
          length "1..232";
        }
      }
      leaf vrf {
        description
          "VRF name";
        type string;
      }
      container address {
        description
          "IPv6 address allocation";
        list prefix {
          description
            "IPv6 address allocation prefix";
          key "ipv6-address";
          leaf ipv6-address {
            type ios-types:ipv6-prefix;
          }
          container lifetime {
            description
              "Configure prefix lifetimes";
            leaf valid-lifetime {
              type union {
                type uint32 {
                  range "5 .. 4294967295";
                }
                type enumeration {
                  enum infinite;
                }
              }
              default "172800";
            }
            leaf preferred-lifetime {
              must "((../valid-lifetime = 'infinite') or ((not (current() = 'infinite')) and (current() <= ../valid-lifetime)))";
              type union {
                type uint32 {
                  range "5 .. 4294967295";
                }
                type enumeration {
                  enum infinite;
                }
              }
              default "86400";
            }
          }
        }
      }
      container prefix-delegation {
        description
          "IPv6 prefix delegation";
        list pd-prefix {
          key "ipv6-prefix";
          leaf ipv6-prefix {
            description
              "IPv6 x:x::y/<z>";
            type ios-types:ipv6-prefix;
          }
          leaf Hex-string {
            description
              "DHCPv6 unique identifier";
            type string {
              pattern '[0-9a-fA-F]*' {
                error-message "Incorrect format";
              }
            }
          }
          leaf iaid {
            description
              "DHCPv6 unique identifier";
            type string {
              pattern '[0-9a-fA-F]*' {
                error-message "Incorrect format";
              }
            }
          }
          container lifetime {
            description
              "Configure prefix lifetimes";
            leaf valid-lifetime {
              type union {
                type uint32 {
                  range "0 .. 4294967295";
                }
                type enumeration {
                  enum infinite;
                }
              }
            }
            leaf preferred-lifetime {
              must '. <= ../valid-lifetime' {
                error-message "Preferred lifetime must not exceed valid lifetime";
              }
              type union {
                type uint32 {
                  range "0 .. 4294967295";
                }
                type enumeration {
                  enum infinite;
                }
              }
            }
          }
        }
        container pool {
          description
            "IPv6 prefix pool";
          leaf pool-name {
            description
              "IPv6 prefix pool";
            type string {
              length "1..512";
            }
          }
          container lifetime {
            description
              "Configure prefix lifetimes";
            leaf valid-lifetime {
              type union {
                type uint32 {
                  range "0 .. 4294967295";
                }
                type enumeration {
                  enum infinite;
                }
              }
            }
            leaf preferred-lifetime {
              must '. <= ../valid-lifetime' {
                error-message "Preferred lifetime must not exceed valid lifetime";
              }
              type union {
                type uint32 {
                  range "0 .. 4294967295";
                }
                type enumeration {
                  enum infinite;
                }
              }
            }
          }
        }
      }
      leaf-list dns-server {
        description
          "Server's name or IPv6 address";
        ordered-by user;
        must 'not(../import/dns-server)' {
          error-message "Both Static and Import DNS-Server cannot be configured at the same time.";
        }
        type union {
          type inet:ipv6-address;
          type string;
        }
      }
      leaf-list domain-names {
        ordered-by user;
        must 'not(../import/domain-name)' {
          error-message "Both Static and Import Domain-name cannot be configured at the same time.";
        }
        description
          "Domain name to complete unqualified host names";
        type string;
      }
      leaf domain-name {
        status obsolete;
        description
          "Domain name (OBSOLETE) to complete unqualified host names";
        type string;
      }
      container sntp {
        description
          "SNTP server options";
        leaf-list address {
          description
            "SNTP server address";
          ordered-by user;
          type inet:ipv6-address;
          must 'not(../../import/sntp/address)' {
            error-message "Both Static and Import SNTP-Address cannot be configured at the same time.";
          }
        }
      }
      container nis {
        description
          "NIS server options";
        leaf-list address {
          description
            "NIS server address";
          type inet:ipv6-address;
          ordered-by user;
          must 'not(../../import/nis/address)' {
            error-message "Both Static and Import NIS-Address cannot be configured at the same time.";
          }
        }
        leaf-list domain-name {
          description
            "NIS server domain name";
          ordered-by user;
          type string;
          must 'not(../../import/nis/domain-name)' {
            error-message "Both Static and Import NIS-Domain-name cannot be configured at the same time.";
          }
        }
      }
      container nisp {
        description
          "NISP server options";
        leaf-list address {
          description
            "NISP server address";
          ordered-by user;
          type inet:ipv6-address;
          must 'not(../../import/nisp/address)' {
            error-message "Both Static and Import NISP-Address cannot be configured at the same time.";
          }
        }
        leaf-list domain-name {
          description
            "NISP server domain name";
          ordered-by user;
          type string;
          must 'not(../../import/nisp/domain-name)' {
            error-message "Both Static and Import NISP-Domain-name cannot be configured at the same time.";
          }
        }
      }
      container sip {
        description
          "SIP server options";
        leaf-list address {
          description
            "SIP server address";
          ordered-by user;
          type inet:ipv6-address;
          must 'not(../../import/sip/address)' {
            error-message "Both Static and Import SIP-Address cannot be configured at the same time.";
          }
        }
        leaf-list domain-name {
          description
            "SIP server domain-name";
          ordered-by user;
          type string;
          must 'not(../../import/sip/domain-name)' {
            error-message "Both Static and Import SIP-Domain-name cannot be configured at the same time.";
          }
        }
      }
      container information {
        description
          "Information refresh option";
        container refresh {
          description
            "Information refresh option";
          choice refresh {
            container refresh-value {
              description
                "Information refresh numbers";
              leaf days {
                must 'not(../../../../import/information/refresh)' {
                  error-message "Both Static and Import INFO-Refresh cannot be configured at the same time.";
                }
                description
                  "Days";
                type uint16 {
                  range "0..365";
                }
              }
              leaf hours {
                description
                  "Hours";
                when '../days';
                type uint8 {
                  range "0..23";
                }
              }
              leaf minutes {
                description
                  "Minutes";
                when '../hours';
                type uint8 {
                  range "0..59";
                }
              }
            }
            leaf infinite {
              must 'not(../../../import/information/refresh)' {
                error-message "Both Static and Import INFO-Refresh cannot be configured at the same time.";
              }
              description
                "Infinite lease";
              type empty;
            }
          }
        }
      }
      container import {
        description
          "Programmatically importing DHCP option parameters";
        container information {
          description
            "Import information refresh option";
          leaf refresh {
            description
              "Import information refresh option";
            type empty;
          }
        }
        leaf bootfile-url {
          description
            "Bootfile Uniform Resource Locator(URL)";
          must 'not(../../bootfile-url) or not (current())' {
            error-message "Both Static and Import Bootfile-URL cannot be configured at the same time.";
          }
          type empty;
        }
        leaf dns-server {
          description
            "Import DNS address";
          type empty;
        }
        leaf domain-name {
          description
            "Import Domain name option";
          type empty;
        }
        container nis {
          description
            "Import NIS options";
          leaf address {
            description
              "Import NIS address option";
            type empty;
          }
          leaf domain-name {
            description
              "Import NIS domain option";
            type empty;
          }
        }
        container nisp {
          description
            "Import NISP options";
          leaf address {
            description
              "Import NISP address option";
            type empty;
          }
          leaf domain-name {
            description
              "Import NISP domain option";
            type empty;
          }
        }
        container sip {
          description
            "Import SIP options";
          leaf address {
            description
              "Import SIP address option";
            type empty;
          }
          leaf domain-name {
            description
              "Import SIP domain option";
            type empty;
          }
        }
        container sntp {
          description
            "Import SNTP option";
          leaf address {
            description
              "Import SNTP address option";
            type empty;
          }
        }
        leaf all {
          status obsolete;
          description
            "all DHCP options";
          type empty;
        }
        container interface {
          status obsolete;
          description
            "Specify interface to import options from";
          uses ios-ifc:interface-obsolete-grouping;
        }
      }
      list link-address {
        description
          "Link-address to match";
        key "address";
        leaf address {
          type ios-types:ipv6-prefix;
        }
      }
      leaf bootfile-url {
        description
          "Boot file url";
        type string;
      }
      container option {
        description
          "DHCPv6 Options configuration";
        leaf include-all {
          description
            "Include all DHCPv6 configured options in REPLY";
          type empty;
        }
      }
      list vendor-specific {
        description
          "Configure Vendor-specific option";
        key "value";
        leaf value {
          description
            "Enterprise ID";
          type uint32 {
            range "1..4294967295";
          }
        }
        list suboption {
          description
            "Vendor-specific suboption";
          key "number";
          leaf number {
            description
              "Suboption number";
            type uint16 {
              range "1..65535";
            }
          }
          container addresses {
            leaf-list address {
              description
                "List of IPv6 addresses";
              ordered-by user;
              type inet:ipv6-address;
            }
          }
          leaf address {
            status deprecated;
            description
              "IPv6 address - Deprecated";
            type inet:ipv6-address;
          }
          leaf ascii {
            description
              "ASCII string";
            type string;
          }
          leaf hex {
            description
              "Hex string";
            type string {
              pattern '[0-9a-fA-F]*' {
                error-message "Incorrect format";
              }
            }
          }
        }
      }
    }
    container binding {
      description
        "Configure IPv6 DHCP binding parameters";
      container track {
        description
          "Track bindings associated with a virtual interface";
        leaf ppp {
          description
            "Clear bindings when PPP session goes down";
          type empty;
        }
      }
    }
    container ppp {
      description
        "PPP specific commands";
      container framed-prefix {
        description
          "Framed ipv6 prefix specific commands";
        leaf cache {
          description
            "Cache the Framed-IPv6 address for PPP sessions";
          type boolean;
          default "true";
        }
      }
      leaf terminate {
        description
          "Terminate a PPP session when prefix is not available";
        type boolean;
        default "true";
      }
    }
    container ping {
      description
        "Configure IPv6 DHCP pinging";
      container packets {
        description
          "Ping packets to send";
        leaf number-packets {
          description
            "Number (0 disables ping)";
          type uint8 {
            range "0..10";
          }
          default "0";
        }
      }
    }
    list database {
      description
        "Configure IPv6 DHCP database agents";
      key "name";
      leaf name {
        description
          "Database agent name";
        type string {
          length "1..230";
        }
      }
      leaf write-delay {
        description
          "Set the database write delay";
        type uint32 {
          range "60..4294967295";
        }
      }
      leaf timeout {
        description
          "Set the database transfer timeout";
        type uint32 {
          range "120..4294967295";
        }
      }
    }
    leaf iapd-route-add {
      description
        "Adds route for IA PD";
      type boolean;
      default "true";
    }
    leaf iana-route-add {
      description
        "Adds route for IA NA";
      type empty;
    }
  }

  grouping ipv6-dhcp-relay-grouping {
    container bulk-lease {
      description
        "Configure IPv6 DHCP Bulk Lease Query";
      container data-timeout-retry {
        leaf data-timeout {
          description
            "Set the bulk lease query data timeout";
          type uint16 {
            range "60..600";
          }
          default "300";
        }
        leaf retry {
          description
            "Set the bulk lease query and connection retries";
          type uint8 {
            range "0..15";
          }
          default "5";
        }
      }
      leaf disable {
        description
          "Disable bulk lease query";
        type empty;
      }
      leaf timeout {
        description
          "Minutes - DHCPV6 Bulk Lease Query waits for Configured Source Interface";
        type uint8 {
          range "1..40";
        }
        default "30";
      }
    }
    container option {
      description
        "Insert option in Relay-Forward messages";
      leaf vpn {
        description
          "Insert VSS option in Relay-Forward messages";
        type empty;
      }
      leaf client-link-addr {
        description
          "Insert client link-layer address in Relay-Forward messages";
        type boolean;
        default "true";
      }
    }
    leaf source-interface {
      description
        "Set source interface for relayed messages";
      type string;
    }
    leaf trust-all {
      description
        "All interfaces are trusted to process relay-replies";
      type boolean;
      default "true";
    }
    leaf short-lease {
      description
        "Short lease value in seconds";
      type uint16 {
        range "60..3600";
      }
    }
  }

  grouping vendor-class-grouping {
    container vendor-class {
      description
        "Configure vendor class data";
      choice vendor-class-option {
        leaf ascii {
          description
            "Vendor class data as string";
          type string {
            length "1..200";
          }
        }
        leaf disable {
          description
            "Disable sending vendor-class data";
          type empty;
        }
        leaf hex {
          description
            "Vendor class data as hex";
          type string {
            pattern '[0-9a-fA-F]*' {
              error-message "Incorrect format";
            }
          }
        }
        leaf mac-address {
          description
            "Mac address as vendor class data";
          type empty;
        }
      }
    }
  }

  grouping interface-leaf-list-grouping {
    leaf-list interface-list {
      must '/ios:native/ios:interface/*[concat(local-name(.), ios:name) = current()]' {
        error-message "Unsupported NED interface type";
      }
      type string;
    }
  }

  augment "/ios:native/ios:ip/ios:dhcp" {
    uses ip-dhcp-grouping;
  }

  augment "/ios:native/ios:ip/ios:dhcp-relay" {
    uses ip-dhcp-relay-grouping;
  }

  augment "/ios:native/ios:ip/ios:dhcp-server" {
    uses ip-dhcp-server-grouping;
  }

  augment "/ios:native/ios:ip/ios:dhcp-client" {
    uses ip-dhcp-client-grouping;
  }

  augment "/ios:native/ios:ipv6/ios:dhcp" {
    uses ipv6-dhcp-grouping;
  }

  augment "/ios:native/ios:ipv6/ios:dhcp-relay" {
    uses ipv6-dhcp-relay-grouping;
  }

  augment "/ios:native/ios:interface/ios:Ethernet/ios:ip/ios:dhcp" {
    uses config-interface-ip-dhcp-grouping;
  }

  augment "/ios:native/ios:interface/ios:FastEthernet/ios:ip/ios:dhcp" {
    uses config-interface-ip-dhcp-grouping;
  }

  augment "/ios:native/ios:interface/ios:GigabitEthernet/ios:ip/ios:dhcp" {
    uses config-interface-ip-dhcp-grouping;
  }

  augment "/ios:native/ios:interface/ios:TenGigabitEthernet/ios:ip/ios:dhcp" {
    uses config-interface-ip-dhcp-grouping;
  }

  augment "/ios:native/ios:interface/ios:FiveGigabitEthernet/ios:ip/ios:dhcp" {
    uses config-interface-ip-dhcp-grouping;
  }

  augment "/ios:native/ios:interface/ios:AppGigabitEthernet/ios:ip/ios:dhcp" {
    uses config-interface-ip-dhcp-grouping;
  }

  augment "/ios:native/ios:interface/ios:TwentyFiveGigE/ios:ip/ios:dhcp" {
    uses config-interface-ip-dhcp-grouping;
  }

  augment "/ios:native/ios:interface/ios:TwoGigabitEthernet/ios:ip/ios:dhcp" {
    uses config-interface-ip-dhcp-grouping;
  }

  augment "/ios:native/ios:interface/ios:FortyGigabitEthernet/ios:ip/ios:dhcp" {
    uses config-interface-ip-dhcp-grouping;
  }

  augment "/ios:native/ios:interface/ios:FiftyGigabitEthernet/ios:ip/ios:dhcp" {
    uses config-interface-ip-dhcp-grouping;
  }

  augment "/ios:native/ios:interface/ios:HundredGigE/ios:ip/ios:dhcp" {
    uses config-interface-ip-dhcp-grouping;
  }

  augment "/ios:native/ios:interface/ios:TwoHundredGigE/ios:ip/ios:dhcp" {
    uses config-interface-ip-dhcp-grouping;
  }

  augment "/ios:native/ios:interface/ios:FourHundredGigE/ios:ip/ios:dhcp" {
    uses config-interface-ip-dhcp-grouping;
  }

  augment "/ios:native/ios:interface/ios:Port-channel/ios:ip/ios:dhcp" {
    uses config-interface-ip-dhcp-grouping;
  }

  augment "/ios:native/ios:interface/ios:Port-channel-subinterface/ios:Port-channel/ios:ip/ios:dhcp" {
    uses config-interface-ip-dhcp-grouping;
  }

  augment "/ios:native/ios:interface/ios:Loopback/ios:ip/ios:dhcp" {
    uses config-interface-ip-dhcp-grouping;
  }

  augment "/ios:native/ios:interface/ios:Tunnel/ios:ip/ios:dhcp" {
    uses config-interface-ip-dhcp-grouping;
  }

  augment "/ios:native/ios:interface/ios:Vlan/ios:ip/ios:dhcp" {
    uses config-interface-ip-dhcp-grouping;
  }

  augment "/ios:native/ios:interface/ios:Dialer/ios:ip/ios:dhcp" {
    uses config-interface-ip-dhcp-grouping;
  }

  augment "/ios:native/ios:interface/ios:vasileft/ios:ip/ios:dhcp" {
    uses config-interface-ip-dhcp-grouping;
  }

  augment "/ios:native/ios:interface/ios:vasiright/ios:ip/ios:dhcp" {
    uses config-interface-ip-dhcp-grouping;
  }

  augment "/ios:native/ios:interface/ios:ATM/ios:ip/ios:dhcp" {
    uses config-interface-ip-dhcp-grouping;
  }

  augment "/ios:native/ios:interface/ios:ATM-subinterface/ios:ATM/ios:ip/ios:dhcp" {
    uses config-interface-ip-dhcp-grouping;
  }

  augment "/ios:native/ios:interface/ios:FastEthernet/ios:ipv6/ios:dhcp" {
    uses config-interface-ipv6-dhcp-grouping;
  }

  augment "/ios:native/ios:interface/ios:GigabitEthernet/ios:ipv6/ios:dhcp" {
    uses config-interface-ipv6-dhcp-grouping;
  }

  augment "/ios:native/ios:interface/ios:TenGigabitEthernet/ios:ipv6/ios:dhcp" {
    uses config-interface-ipv6-dhcp-grouping;
  }

  augment "/ios:native/ios:interface/ios:FiveGigabitEthernet/ios:ipv6/ios:dhcp" {
    uses config-interface-ipv6-dhcp-grouping;
  }

  augment "/ios:native/ios:interface/ios:AppGigabitEthernet/ios:ipv6/ios:dhcp" {
    uses config-interface-ipv6-dhcp-grouping;
  }

  augment "/ios:native/ios:interface/ios:TwentyFiveGigE/ios:ipv6/ios:dhcp" {
    uses config-interface-ipv6-dhcp-grouping;
  }

  augment "/ios:native/ios:interface/ios:TwoGigabitEthernet/ios:ipv6/ios:dhcp" {
    uses config-interface-ipv6-dhcp-grouping;
  }

  augment "/ios:native/ios:interface/ios:FortyGigabitEthernet/ios:ipv6/ios:dhcp" {
    uses config-interface-ipv6-dhcp-grouping;
  }

  augment "/ios:native/ios:interface/ios:FiftyGigabitEthernet/ios:ipv6/ios:dhcp" {
    uses config-interface-ipv6-dhcp-grouping;
  }

  augment "/ios:native/ios:interface/ios:HundredGigE/ios:ipv6/ios:dhcp" {
    uses config-interface-ipv6-dhcp-grouping;
  }

  augment "/ios:native/ios:interface/ios:TwoHundredGigE/ios:ipv6/ios:dhcp" {
    uses config-interface-ipv6-dhcp-grouping;
  }

  augment "/ios:native/ios:interface/ios:FourHundredGigE/ios:ipv6/ios:dhcp" {
    uses config-interface-ipv6-dhcp-grouping;
  }

  augment "/ios:native/ios:interface/ios:Port-channel/ios:ipv6/ios:dhcp" {
    uses config-interface-ipv6-dhcp-grouping;
  }

  augment "/ios:native/ios:interface/ios:Port-channel-subinterface/ios:Port-channel/ios:ipv6/ios:dhcp" {
    uses config-interface-ipv6-dhcp-grouping;
  }

  augment "/ios:native/ios:interface/ios:Loopback/ios:ipv6/ios:dhcp" {
    uses config-interface-ipv6-dhcp-grouping;
  }

  augment "/ios:native/ios:interface/ios:Tunnel/ios:ipv6/ios:dhcp" {
    uses config-interface-ipv6-dhcp-grouping;
  }

  augment "/ios:native/ios:interface/ios:Vlan/ios:ipv6/ios:dhcp" {
    uses config-interface-ipv6-dhcp-grouping;
  }

  augment "/ios:native/ios:interface/ios:vasileft/ios:ipv6/ios:dhcp" {
    uses config-interface-ipv6-dhcp-grouping;
  }

  augment "/ios:native/ios:interface/ios:vasiright/ios:ipv6/ios:dhcp" {
    uses config-interface-ipv6-dhcp-grouping;
  }

  augment "/ios:native/ios:interface/ios:ATM/ios:ipv6/ios:dhcp" {
    uses config-interface-ipv6-dhcp-grouping;
  }

  augment "/ios:native/ios:interface/ios:ATM-subinterface/ios:ATM/ios:ipv6/ios:dhcp" {
    uses config-interface-ipv6-dhcp-grouping;
  }

  augment "/ios:native/ios:interface/ios:Cellular/ios:ipv6/ios:dhcp" {
    uses config-interface-ipv6-dhcp-grouping;
  }

  augment "/ios:native/ios:interface/ios:Ethernet/ios:ipv6/ios:dhcp" {
    uses config-interface-ipv6-dhcp-grouping;
  }

  augment "/ios:native/ios:interface/ios:Dialer/ios:ipv6/ios:dhcp" {
    uses config-interface-ipv6-dhcp-grouping;
  }

  augment "/ios:native/ios:interface/ios:FastEthernet" {
    uses config-interface-dhcp-server-tracking-grouping;
  }

  augment "/ios:native/ios:interface/ios:GigabitEthernet" {
    uses config-interface-dhcp-server-tracking-grouping;
  }

  augment "/ios:native/ios:interface/ios:TenGigabitEthernet" {
    uses config-interface-dhcp-server-tracking-grouping;
  }

  augment "/ios:native/ios:interface/ios:FiveGigabitEthernet" {
    uses config-interface-dhcp-server-tracking-grouping;
  }

  augment "/ios:native/ios:interface/ios:AppGigabitEthernet" {
    uses config-interface-dhcp-server-tracking-grouping;
  }

  augment "/ios:native/ios:interface/ios:TwentyFiveGigE" {
    uses config-interface-dhcp-server-tracking-grouping;
  }

  augment "/ios:native/ios:interface/ios:TwoGigabitEthernet" {
    uses config-interface-dhcp-server-tracking-grouping;
  }

  augment "/ios:native/ios:interface/ios:FortyGigabitEthernet" {
    uses config-interface-dhcp-server-tracking-grouping;
  }

  augment "/ios:native/ios:interface/ios:FiftyGigabitEthernet" {
    uses config-interface-dhcp-server-tracking-grouping;
  }

  augment "/ios:native/ios:interface/ios:HundredGigE" {
    uses config-interface-dhcp-server-tracking-grouping;
  }

  augment "/ios:native/ios:interface/ios:TwoHundredGigE" {
    uses config-interface-dhcp-server-tracking-grouping;
  }

  augment "/ios:native/ios:interface/ios:FourHundredGigE" {
    uses config-interface-dhcp-server-tracking-grouping;
  }

  augment "/ios:native/ios:interface/ios:Port-channel" {
    uses config-interface-dhcp-server-tracking-grouping;
  }

  augment "/ios:native/ios:interface/ios:Loopback" {
    uses config-interface-dhcp-server-tracking-grouping;
  }

  augment "/ios:native/ios:interface/ios:Tunnel" {
    uses config-interface-dhcp-server-tracking-grouping;
  }

  augment "/ios:native/ios:interface/ios:Vlan" {
    uses config-interface-dhcp-server-tracking-grouping;
  }

  augment "/ios:native/ios:interface/ios:vasileft" {
    uses config-interface-dhcp-server-tracking-grouping;
  }

  augment "/ios:native/ios:interface/ios:vasiright" {
    uses config-interface-dhcp-server-tracking-grouping;
  }

  augment "/ios:native/ios:interface/ios:ATM" {
    uses config-interface-dhcp-server-tracking-grouping;
  }

  augment "/ios:native/ios:interface/ios:ATM-subinterface/ios:ATM" {
    uses config-interface-dhcp-server-tracking-grouping;
  }

  augment "/ios:native/ios:interface/ios:Cellular" {
    uses config-interface-dhcp-server-tracking-grouping;
  }

  augment "/ios:native/ios:interface/ios:Ethernet" {
    uses config-interface-dhcp-server-tracking-grouping;
  }

  augment "/ios:native/ios:interface/ios:Dialer" {
    uses config-interface-dhcp-server-tracking-grouping;
  }
}
