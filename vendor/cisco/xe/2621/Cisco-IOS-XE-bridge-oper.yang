module Cisco-IOS-XE-bridge-oper {
  yang-version 1.1;
  namespace "http://cisco.com/ns/yang/Cisco-IOS-XE-bridge-oper";
  prefix bridge-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for bridge data.
     Copyright (c) 2018-2019, 2022-2026 by Cisco Systems, Inc.
     All rights reserved.";

  revision 2026-08-01 {
    description
      "Updated descriptions of several model elements to clarify their meaning and purpose";
    reference
      "1.4.0";
    cisco-semver:module-version "1.4.0";
  }
  revision 2022-11-01 {
    description
      "Update yang-version to 1.1";
    reference
      "1.3.0";
    cisco-semver:module-version "1.3.0";
  }
  revision 2019-05-01 {
    description
      "Added semantic version";
    reference
      "1.2.0";
    cisco-semver:module-version "1.2.0";
  }
  revision 2018-10-29 {
    description
      "Cleaned up spelling errors in descriptions.";
    reference
      "1.1.0";
    cisco-semver:module-version "1.1.0";
  }
  revision 2018-03-10 {
    description
      "Initial revision";
    reference
      "1.0.0";
    cisco-semver:module-version "1.0.0";
  }

  typedef intf-status-type {
    type enumeration {
      enum up {
        value 0;
      }
      enum down {
        value 1;
      }
    }
    description
      "Interface status type";
  }

  typedef bridge-mac-type {
    type enumeration {
      enum bridge-mac-type-static {
        value 0;
      }
      enum bridge-mac-type-dynamic {
        value 1;
      }
    }
    description
      "MAC address type";
  }

  grouping bridge-intf-entry {
    description
      "Bridge interface operational data";
    leaf if-name {
      type string;
      description
        "Name of the switch port that belongs to the bridge.";
    }
    leaf vlan {
      type uint32;
      description
        "VLAN identifier associated with the bridge interface.";
    }
    leaf native-vlan {
      type boolean;
      description
        "Indicates whether this VLAN is the native VLAN for the bridge interface.";
    }
    leaf admin-status {
      type bridge-ios-xe-oper:intf-status-type;
      description
        "Bridge interface administration status";
    }
    leaf oper-status {
      type bridge-ios-xe-oper:intf-status-type;
      description
        "Bridge interface operational status";
    }
    leaf encap-type {
      type string;
      description
        "Bridge interface encapsulation type";
    }
    leaf ifindex {
      type uint32;
      description
        "Bridge interface index";
    }
    leaf mtu {
      type uint32;
      units "bytes";
      description
        "Maximum Transmission Unit (in bytes) for the bridge interface.";
    }
  }

  grouping bridge-matm-entry {
    description
      "Bridge MAC address operational data";
    leaf mac-address {
      type yang:mac-address;
      description
        "MAC address associated with this MAC table entry.";
    }
    leaf-list interface {
      type string;
      ordered-by user;
      description
        "List of interface names from which the MAC address was learned.";
    }
    leaf vlan {
      type uint32;
      description
        "VLAN identifier";
    }
    leaf type {
      type bridge-ios-xe-oper:bridge-mac-type;
      description
        "Type of MAC address (static or dynamic) for this entry.";
    }
  }

  grouping bridge-entry {
    description
      "Bridge entry";
    leaf bridge-id {
      type uint32;
      description
        "Unique identifier for the bridge entry. Valid values range from 1 to 4094.";
    }
    leaf name {
      type string;
      description
        "Name of the VLAN associated with the bridge entry.";
    }
    leaf vlan {
      type uint32;
      description
        "VLAN identifier <1..4094>";
    }
    leaf routing-interface {
      type string;
      description
        "The name of VLAN routing interface";
    }
    leaf max-macs {
      type uint32;
      description
        "The maximum number of MAC addresses that can be learned by the bridge.";
    }
    leaf num-macs {
      type uint32;
      description
        "The number of MAC learned in bridge";
    }
    leaf age-time {
      type uint32;
      units "seconds";
      description
        "The aging time for MAC addresses in seconds. Valid values are 0 or from 10 to 1,000,000 seconds.";
    }
    leaf rx-packets {
      type uint64;
      description
        "The number of received packets in bridge";
    }
    leaf rx-octets {
      type uint64;
      description
        "The number of received bytes in bridge";
    }
    leaf tx-packets {
      type uint64;
      description
        "The number of transmitted packets out of bridge";
    }
    leaf tx-octets {
      type uint64;
      description
        "The number of transmitted bytes out of bridge";
    }
    leaf flood-packets {
      type uint64;
      description
        "The number of flood packets in bridge";
    }
    leaf flood-octets {
      type uint64;
      description
        "The number of flood bytes in bridge";
    }
    leaf rx-routed-packets {
      type uint64;
      description
        "Number of Layer 3 (L3) packets received by the bridge for routing.";
    }
    leaf tx-routed-packets {
      type uint64;
      description
        "Number of Layer 3 (L3) packets transmitted by the bridge after routing.";
    }
    leaf learn {
      type uint64;
      description
        "MAC learned counter in bridge";
    }
    leaf age {
      type uint64;
      description
        "MAC aging counter in bridge";
    }
    leaf move {
      type uint64;
      description
        "MAC move counter in bridge";
    }
    container bridge-intf-entries {
      description
        "Container for bridge interface member entries associated with the bridge.";
      list bridge-intf-entry {
        key "if-name";
        description
          "List of interfaces that are members of the bridge.";
        uses bridge-ios-xe-oper:bridge-intf-entry;
      }
    }
    container bridge-matm-entries {
      description
        "Container for the MAC address table (MAT) entries associated with the bridge.";
      list bridge-matm-entry {
        key "mac-address";
        description
          "List of MAC address table entries learned by the bridge.";
        uses bridge-ios-xe-oper:bridge-matm-entry;
      }
    }
  }

  container bridge-instances {
    config false;
    description
      "This is top level container for bridge table. It can have one
       or more bridge entry.";
    list bridge-entry {
      key "bridge-id";
      description
        "An ordered list of bridge entries. Each bridge entry contains
         a list of bridge interface members and associated bridge
         attributes.";
      uses bridge-ios-xe-oper:bridge-entry;
    }
  }
}
