module Cisco-IOS-XE-wireless-wat-cfg {
  yang-version 1.1;
  namespace "http://cisco.com/ns/yang/Cisco-IOS-XE-wireless-wat-cfg";
  prefix ios-xe-wat-cfg;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     global Wireless Active Testing (WAT) configuration data.
     Copyright (c) 2025-2026 by Cisco Systems, Inc.
     All rights reserved.";

  revision 2026-08-01 {
    description
      "- Updated descriptions for wat-cfg-data container and te-conn-str leaf
       - Added new WAT profile configuration
       - Added a 'must' constraint for wat-profile enable leaf to disallow test-wired and test-wireless from being enabled simultaneously";
    reference
      "1.1.0";
    cisco-semver:module-version "1.1.0";
  }
  revision 2025-07-01 {
    description
      "Initial revision";
    reference
      "1.0.0";
    cisco-semver:module-version "1.0.0";
  }

  grouping wat-config {
    description
      "Wireless Active Testing Configuration";
    leaf wat-enable {
      type boolean;
      default "true";
      description
        "Indicates whether WAT Wireless Testing is globally enabled for all WAT
         Profiles and APs enabled through the Radio Profile applied to an RF
         Tag. When disabled, WAT Wireless Testing will be disabled for all APs,
         and any APs which were already enabled will reboot or reload.";
    }
    leaf te-conn-str {
      type string {
        length "0..196" {
          error-message "ThousandEyes connection string must not be greater than 196 characters";
          error-app-tag "must-violation";
        }
        pattern '[A-Za-z0-9/+-_=.]*' {
          error-message "ThousandEyes connection string can only have Base64 characters";
          error-app-tag "pattern-violation";
        }
      }
      default "";
      description
        "Connection string used by the ThousandEyes Endpoint Agent
         to communicate with the ThousandEyes Platform in the cloud";
    }
    leaf te-download-url {
      type string {
        length "0..196" {
          error-message "ThousandEyes Download URL must not be greater than 196 characters";
          error-app-tag "must-violation";
        }
        pattern '(((https?)://[A-Za-z0-9@.:/?=%,&-]+)|(((([0-1]?[0-9]{1,2})|([2]?[0-5]{1,2})|([2]?[0-4][0-9]))[.]){3}(([0-1]?[0-9]{1,2})|([2]?[0-5]{1,2})|([2]?[0-4][1-9]))))*' {
          error-message "ThousandEyes download URL must be a valid https or http URL";
          error-app-tag "pattern-violation";
        }
      }
      default "https://downloads.thousandeyes.com/endpointagent/iox/arm64/latest.tar";
      description
        "ThousandEyes endpoint URL from which the WAT manager download the
         ThousandEyes agent IOx container";
    }
    leaf wat-wired-enable {
      type boolean;
      default "true";
      description
        "Indicates whether WAT Wired Testing is globally enabled for all WAT
         Profiles. When disabled, WAT Wired Testing will be disabled for all APs.";
    }
  }

  grouping wat-profile {
    description
      "Wireless Active Testing (WAT) profile configuration";
    leaf profile-name {
      type string {
        length "1..32" {
          error-message "WAT Profile Name should not be greater than 32 characters";
          error-app-tag "must-violation";
        }
        pattern '[!-~]([ -~]*[!-~])?' {
          error-message
            "WAT profile name must use printable ASCII characters and must not
             contain leading or trailing spaces, and cannot be empty";
          error-app-tag "pattern-violation";
        }
      }
      description
        "Wireless Active Testing (WAT) profile name";
    }
    leaf desc {
      type string {
        length "0..64";
        pattern '([!-~]([ -~]*[!-~])?)?';
      }
      default "";
      description
        "Description of Wireless Active Testing (WAT) profile, can only
         contain printable ASCII characters with no leading or trailing
         spaces, and can be empty";
    }
    leaf enable {
      type boolean;
      must "(../enable = 'false') or
            not((../test-wired = 'true') and (../test-wireless = 'true'))" {
        error-message
          "test-wired and test-wireless cannot be simultaneously enabled on a
           wat-profile for Wireless Active Testing (WAT).";
        error-app-tag "must-violation";
      }
      default "false";
      description
        "Indicates whether Wireless Active Testing (WAT) is enabled for this WAT profile;
         true enables WAT, false disables it.";
    }
    leaf test-wired {
      type boolean;
      default "false";
      description
        "Indicates whether WAT Wired Testing is enabled. When modified, the AP
         will not reboot or reload and can continue to serve clients.";
    }
    leaf test-wireless {
      type boolean;
      default "false";
      description
        "Indicates whether WAT Wireless Testing is enabled on all radio slots.
         This disables broadcasting WLANs/SSIDs and serving clients on the AP.
         Enabling this for the first time will cause the AP to reboot/reload.";
    }
  }

  container wat-cfg-data {
    description
      "Wireless Active Testing (WAT) global configuration data";
    container wat-config {
      presence "wat-config";
      description
        "Wireless Active Testing (WAT) ThousandEyes configurations";
      uses ios-xe-wat-cfg:wat-config;
    }
    container wat-profiles {
      description
        "Wireless Active Testing (WAT) configuration profiles for APs";
      list wat-profile {
        key "profile-name";
        description
          "Wireless Active Testing (WAT) configuration profile for an AP";
        uses ios-xe-wat-cfg:wat-profile;
      }
    }
  }
}
