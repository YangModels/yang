module Cisco-IOS-XE-controller-vdsl-oper {
  yang-version 1.1;
  namespace "http://cisco.com/ns/yang/Cisco-IOS-XE-controller-vdsl-oper";
  prefix vdsl-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for monitoring controller VDSL operational information.
     Copyright (c) 2018-2020, 2026 by Cisco Systems, Inc.
     All rights reserved.";

  revision 2026-08-01 {
    description
      "Updated descriptions of several model elements to clarify their meaning and purpose";
    reference
      "1.5.1";
    cisco-semver:module-version "1.5.1";
  }
  revision 2022-11-01 {
    description
      "Update yang-version to 1.1";
    reference
      "1.5.0";
    cisco-semver:module-version "1.5.0";
  }
  revision 2021-03-01 {
    description
      "Added DSL SFP local info for Titan DSL";
    reference
      "1.4.0";
    cisco-semver:module-version "1.4.0";
  }
  revision 2020-03-01 {
    description
      "Added VDSL Layer 1 statistics and GFast specific counters";
    reference
      "1.3.0";
    cisco-semver:module-version "1.3.0";
  }
  revision 2019-05-01 {
    description
      "Added semantic version";
    reference
      "1.2.0";
    cisco-semver:module-version "1.2.0";
  }
  revision 2018-10-29 {
    description
      "Cleaned up spelling errors in descriptions.";
    reference
      "1.1.0";
    cisco-semver:module-version "1.1.0";
  }
  revision 2018-01-31 {
    description
      "Initial revision";
    reference
      "1.0.0";
    cisco-semver:module-version "1.0.0";
  }

  typedef idb-states {
    type enumeration {
      enum down {
        value 0;
        description
          "Interface down";
      }
      enum going-down {
        value 1;
        description
          "Interface going down";
      }
      enum init {
        value 2;
        description
          "Interface initialization";
      }
      enum testing {
        value 3;
        description
          "Interface testing";
      }
      enum up {
        value 4;
        description
          "Interface up";
      }
      enum reset {
        value 5;
        description
          "Interface reset";
      }
      enum admindown {
        value 6;
        description
          "Interface admindown";
      }
      enum deleted {
        value 7;
        description
          "Interface deleted";
      }
    }
    description
      "Interface state";
  }

  typedef modem-status-states {
    type enumeration {
      enum modem-status-line-not-initialized {
        value 0;
        description
          "Line not initialized";
      }
      enum modem-status-line-exception {
        value 1;
        description
          "Line exception";
      }
      enum modem-status-idle-request {
        value 2;
        description
          "Idle request";
      }
      enum modem-status-idle {
        value 3;
        description
          "Modem status idle";
      }
      enum modem-status-silent-request {
        value 4;
        description
          "Silent-request";
      }
      enum modem-status-line-silent {
        value 5;
        description
          "Line silent";
      }
      enum modem-status-handshake {
        value 6;
        description
          "Handshake";
      }
      enum modem-status-line-full-initialization {
        value 7;
        description
          "Line full initialization";
      }
      enum modem-status-discovery {
        value 8;
        description
          "Discovery";
      }
      enum modem-status-training {
        value 9;
        description
          "Training";
      }
      enum modem-status-analysis {
        value 10;
        description
          "Analysis";
      }
      enum modem-status-exchange {
        value 11;
        description
          "Exchange";
      }
      enum modem-status-no-sync {
        value 12;
        description
          "No synchronization";
      }
      enum modem-status-tc-sync-showtime {
        value 13;
        description
          "TC synchronization (Showtime!)";
      }
      enum modem-status-fast-restrain {
        value 14;
        description
          "Fast restrain";
      }
      enum modem-status-low-power-l2 {
        value 15;
        description
          "Low power L2";
      }
      enum modem-status-loop-diagnostics-active {
        value 16;
        description
          "Loop diagnostics active";
      }
      enum modem-status-loop-diagnostics-data-exchange {
        value 17;
        description
          "Loop diagnostics data exchange";
      }
      enum modem-status-loop-diagnostics-data-request {
        value 18;
        description
          "Loop diagnostics data request";
      }
      enum modem-status-loop-diagnostics-data-complete {
        value 19;
        description
          "Loop diagnostics data complete";
      }
      enum modem-status-resync {
        value 20;
        description
          "Resync";
      }
      enum modem-status-test {
        value 21;
        description
          "Modem status test";
      }
      enum modem-status-test-loop {
        value 22;
        description
          "Test loop";
      }
      enum modem-status-test-reverb {
        value 23;
        description
          "Test reverb";
      }
      enum modem-status-test-medley {
        value 24;
        description
          "Test medley";
      }
      enum modem-status-low-power-l3 {
        value 25;
        description
          "Low power L3";
      }
      enum modem-status-unknown {
        value 26;
        description
          "Unknown modem status";
      }
    }
    description
      "Modem status states";
  }

  typedef trained-modes {
    type enumeration {
      enum trained-mode-not-known {
        value 0;
        description
          "Unknown trained mode";
      }
      enum trained-mode-ansi-t1-413-1998 {
        value 1;
        description
          "ANSI T1.413-1998";
      }
      enum trained-mode-etsi-annex-c-of-ts-101-388-v1-3-1 {
        value 2;
        description
          "ETSI Annex C of TS 101 388 v1.3.1";
      }
      enum trained-mode-g-992-1-adsl-annex-a {
        value 3;
        description
          "G.992.1 (ADSL) Annex A";
      }
      enum trained-mode-g-992-1-adsl-annex-b {
        value 4;
        description
          "G.992.1 (ADSL) Annex B";
      }
      enum trained-mode-g-lite-annex-ab {
        value 5;
        description
          "G.lite Annex AB";
      }
      enum trained-mode-g-992-3-adsl2-annex-m {
        value 6;
        description
          "G.992.3 (ADSL2) Annex M";
      }
      enum trained-mode-g-992-3-adsl2-annex-j {
        value 7;
        description
          "G.992.3 (ADSL2) Annex J";
      }
      enum trained-mode-g-992-3-adsl2-annex-a {
        value 8;
        description
          "G.992.3 (ADSL2) Annex A";
      }
      enum trained-mode-g-992-3-adsl2-annex-b {
        value 9;
        description
          "G.992.3 (ADSL2) Annex B";
      }
      enum trained-mode-g-992-3-adsl2-annex-l {
        value 10;
        description
          "G.992.3 (ADSL2) Annex L";
      }
      enum trained-mode-g-992-5-adsl2plus-annex-m {
        value 11;
        description
          "G.992.5 (ADSL2+) Annex M";
      }
      enum trained-mode-g-992-5-adsl2plus-annex-j {
        value 12;
        description
          "G.992.5 (ADSL2+) Annex J";
      }
      enum trained-mode-g-992-5-adsl2plus-annex-a {
        value 13;
        description
          "G.992.5 (ADSL2+) Annex A";
      }
      enum trained-mode-g-992-5-adsl2plus-annex-b {
        value 14;
        description
          "G.992.5 (ADSL2+) Annex B";
      }
      enum trained-mode-g-993-2-vdsl2-profile-8a {
        value 15;
        description
          "G.993.2 (VDSL2) Profile 8-a";
      }
      enum trained-mode-g-993-2-vdsl2-profile-8b {
        value 16;
        description
          "G.993.2 (VDSL2) Profile 8-b";
      }
      enum trained-mode-g-993-2-vdsl2profile-8c {
        value 17;
        description
          "G.993.2 (VDSL2) Profile 8-c";
      }
      enum trained-mode-g-993-2-vdsl2-profile-8d {
        value 18;
        description
          "G.993.2 (VDSL2) Profile 8-d";
      }
      enum trained-mode-g-993-2-vdsl2-profile-12a {
        value 19;
        description
          "G.993.2 (VDSL2) Profile 12-a";
      }
      enum trained-mode-g-993-2-vdsl2-profile-12b {
        value 20;
        description
          "G.993.2 (VDSL2) Profile 12-b";
      }
      enum trained-mode-g-993-2-vdsl2-profile-17a {
        value 21;
        description
          "G.993.2 (VDSL2) Profile 17-a";
      }
      enum trained-mode-g-993-2-vdsl2-profile-30a {
        value 22;
        description
          "G.993.2 (VDSL2) Profile 30-a";
      }
      enum trained-mode-g-993-2-vdsl2-profile-35b {
        value 23;
        description
          "G.993.2 (VDSL2) Profile 35-b";
      }
      enum trained-mode-g-993-2-vdsl2-unknown-profile {
        value 24;
        description
          "G.993.2 (VDSL2) unknown profile";
      }
      enum trained-mode-g-9701-gfast-profile-106a {
        value 25;
        description
          "G.9701 (GFAST) Profile 106-a";
      }
      enum trained-mode-g-9701-gfast-profile-106b {
        value 26;
        description
          "G.9701 (GFAST) Profile 106-b";
      }
      enum trained-mode-g-9701-gfast-unknown-profile {
        value 27;
        description
          "G.9701 (GFAST) unknown profile";
      }
    }
    description
      "Trained modes";
  }

  typedef mode-tc {
    type enumeration {
      enum ptm {
        value 0;
        description
          "MODE Ethernet";
      }
      enum atm {
        value 1;
        description
          "MODE Atm";
      }
      enum mode-ptm-bonded {
        value 2;
        description
          "MODE Ethernet bonded";
      }
      enum mode-unknown {
        value 3;
        description
          "MODE Unknown";
      }
    }
    description
      "Operation Mode";
  }

  typedef trellis-states {
    type enumeration {
      enum trellis-state-off {
        value 0;
        description
          "Trellis state off";
      }
      enum trellis-state-on {
        value 1;
        description
          "Trellis state on";
      }
    }
    description
      "Trellis states";
  }

  typedef dsl-config-modes {
    type enumeration {
      enum dsl-config-mode-auto {
        value 0;
        description
          "DSL configuration mode Auto";
      }
      enum dsl-config-mode-ansi {
        value 1;
        description
          "DSL configuration mode ANSI";
      }
      enum dsl-config-mode-etsi {
        value 2;
        description
          "DSL configuration mode ETSI";
      }
      enum dsl-config-mode-adsl1 {
        value 3;
        description
          "DSL configuration mode ADSL1";
      }
      enum dsl-config-mode-adsl2 {
        value 4;
        description
          "DSL configuration mode ADSL2";
      }
      enum dsl-config-mode-adsl2plus {
        value 5;
        description
          "DSL configuration mode ADSL2+";
      }
      enum dsl-config-mode-vdsl2 {
        value 6;
        description
          "DSL configuration mode VDSL2";
      }
      enum dsl-config-mode-unknown {
        value 7;
        description
          "Unknown DSL configuration mode";
      }
    }
    description
      "DSL configuration modes";
  }

  typedef vdsl-link-state {
    type enumeration {
      enum vdsl-link-down {
        value 0;
        description
          "Link state down";
      }
      enum vdsl-link-up {
        value 1;
        description
          "Link state up";
      }
    }
    description
      "Link states";
  }

  typedef delt-states {
    type enumeration {
      enum delt-state-not-running {
        value 0;
        description
          "Double ended line testing not running";
      }
      enum delt-state-successful {
        value 1;
        description
          "Double ended line testing successful";
      }
      enum delt-state-in-progress {
        value 2;
        description
          "Double ended line testing in progress";
      }
    }
    description
      "Double ended line testing states";
  }

  typedef training-logs-states {
    type enumeration {
      enum training-logs-stopped {
        value 0;
        description
          "Training logs have stopped";
      }
      enum training-logs-started {
        value 1;
        description
          "Training logs are running";
      }
    }
    description
      "Training logs states";
  }

  grouping slot-info-key {
    description
      "Key information";
    leaf slot-num {
      type uint32;
      description
        "Specifies the slot number of the VDSL controller in the chassis.";
    }
    leaf subslot-num {
      type uint32;
      description
        "Specifies the subslot number of the VDSL controller within the chassis
         slot.";
    }
  }

  grouping dsl-sfp-local-info {
    description
      "DSL SFP local information";
    leaf sfp-vendor-pid {
      type string;
      description
        "Specifies the Product Identifier (PID) of the SFP module vendor.";
    }
    leaf sfp-serial-number {
      type string;
      description
        "Specifies the serial number assigned to the SFP module.";
    }
    leaf embed-fw-ver {
      type string;
      description
        "SFP firmware version in IOS-XE image";
    }
    leaf run-fw-ver {
      type string;
      description
        "Current running firmware version of the SFP module.";
    }
    leaf mgmt-lnk-state {
      type vdsl-ios-xe-oper:vdsl-link-state;
      description
        "SFP management link status";
    }
    leaf dsl-status {
      type string;
      description
        "Operational status of the DSL interface on the SFP module.";
    }
    leaf int-info {
      type vdsl-ios-xe-oper:training-logs-states;
      description
        "Status of the internal information dump for the SFP module.";
    }
    leaf dying-gasp-armed {
      type boolean;
      description
        "SFP Dying Gasp Status";
    }
    leaf delt-state {
      type vdsl-ios-xe-oper:delt-states;
      description
        "Status of Double Ended Line Testing information for the SFP module.";
    }
  }

  grouping line-specific-info-cpe {
    description
      "Line specific information of CPE";
    leaf trellis-state {
      type vdsl-ios-xe-oper:trellis-states;
      description
        "Indicates whether trellis coding is enabled or disabled on the
         customer premises equipment (CPE) side of the VDSL line.";
    }
    leaf sra-enabled {
      type boolean;
      description
        "Seamless rate adaptation status";
    }
    leaf sra-count {
      type uint32;
      description
        "Seamless rate adaptation counter";
    }
    leaf bit-swap-enabled {
      type boolean;
      description
        "Indicates whether bit swapping is enabled for the customer premises
         equipment (CPE) line, allowing dynamic adjustment of bit allocation
         to maintain line stability.";
    }
    leaf bit-swap-count {
      type uint32;
      description
        "Bit swap counter";
    }
    leaf line-attenuation {
      type decimal64 {
        fraction-digits 2;
      }
      units "dB";
      description
        "Line attenuation in decibels";
    }
    leaf signal-attenuation {
      type decimal64 {
        fraction-digits 2;
      }
      units "dB";
      description
        "Signal attenuation in decibels";
    }
    leaf noise-margin {
      type decimal64 {
        fraction-digits 2;
      }
      units "dB";
      description
        "Noise margin in decibels";
    }
    leaf attainable-rate {
      type uint32;
      units "kbps";
      description
        "Attainable rate in kilobits per sec";
    }
    leaf actual-power {
      type decimal64 {
        fraction-digits 2;
      }
      units "dBm";
      description
        "Actual power in decibel-milliwatts";
    }
    leaf total-fecc {
      type uint32;
      description
        "Total forward error correction counter";
    }
    leaf total-es {
      type uint32;
      description
        "Total errored seconds";
    }
    leaf total-ses {
      type uint32;
      description
        "Total severely errored seconds";
    }
    leaf total-loss {
      type uint32;
      description
        "Total loss of signal seconds";
    }
    leaf total-uas {
      type uint32;
      description
        "Total unavailable seconds";
    }
    leaf total-lprs {
      type uint32;
      description
        "Total loss of power seconds";
    }
    leaf total-lofs {
      type uint32;
      description
        "Total loss of frame seconds";
    }
    leaf total-lols {
      type uint32;
      description
        "Total loss of link seconds";
    }
    leaf speed {
      type uint32;
      units "kbps";
      description
        "Speed in kilobits per sec";
    }
    leaf sra-previous-speed {
      type uint32;
      units "kbps";
      description
        "Seamless rate adaptation previous speed in kilobits per sec";
    }
    leaf previous-speed {
      type uint32;
      units "kbps";
      description
        "Previous speed field represents previous speed for ADSL and VDSL, bit swap previous speed for GFAST";
    }
    leaf reed-solomon-ec {
      type uint32;
      description
        "Reed solomon error correction counter";
    }
    leaf crc-errors {
      type uint32;
      description
        "Cyclic redundancy check errors";
    }
    leaf header-errors {
      type uint32;
      description
        "Counter for the number of header errors detected in the received data
         frames on the line.";
    }
    leaf interleave {
      type decimal64 {
        fraction-digits 2;
      }
      units "milliseconds";
      description
        "Inter-leave time";
    }
    leaf actual-inp {
      type decimal64 {
        fraction-digits 2;
      }
      description
        "Actual value of impulse noise protection applied to the line,
         indicating the system's ability to correct for impulse noise events.";
    }
    leaf gfast-fra-count {
      type uint32;
      description
        "Gfast specific field for fast rate adaptation counter";
    }
    leaf gfast-rpa-count {
      type uint32;
      description
        "Gfast specific field for robust management channel parameter adjustment counter";
    }
    leaf gfast-tiga-count {
      type uint32;
      description
        "Counter for the number of transmitter-initiated gain adjustments on
         the Gfast line.";
    }
    leaf gfast-rtx-uc {
      type uint32;
      description
        "Gfast specific field for counter for retransmissions that are uncorrected";
    }
    leaf gfast-rtx-tx {
      type uint32;
      description
        "Gfast specific field for retransmissions counter";
    }
    leaf gfast-attainable-exp-thru {
      type uint32;
      description
        "Gfast specific field for attainable expected throughput";
    }
    leaf gfast-error-free-thru {
      type uint32;
      description
        "Gfast specific field for error free throughput";
    }
    leaf vdsl2-la-band-d1 {
      type decimal64 {
        fraction-digits 2;
      }
      units "dB";
      description
        "VDSL2 specific field for line attenuation of downstream band one";
    }
    leaf vdsl2-la-band-d2 {
      type decimal64 {
        fraction-digits 2;
      }
      units "dB";
      description
        "VDSL2 specific field for line attenuation of downstream band two";
    }
    leaf vdsl2-la-band-d3 {
      type decimal64 {
        fraction-digits 2;
      }
      units "dB";
      description
        "VDSL2 specific field for line attenuation of downstream band three";
    }
    leaf vdsl2-sa-band-d1 {
      type decimal64 {
        fraction-digits 2;
      }
      units "dB";
      description
        "VDSL2 specific field for signal attenuation of downstream band one";
    }
    leaf vdsl2-sa-band-d2 {
      type decimal64 {
        fraction-digits 2;
      }
      units "dB";
      description
        "VDSL2 specific field for signal attenuation of downstream band two";
    }
    leaf vdsl2-sa-band-d3 {
      type decimal64 {
        fraction-digits 2;
      }
      units "dB";
      description
        "VDSL2 specific field for signal attenuation of downstream band three";
    }
    leaf vdsl2-snr-band-d1 {
      type decimal64 {
        fraction-digits 2;
      }
      units "dB";
      description
        "VDSL2 specific field for noise margin of downstream band one";
    }
    leaf vdsl2-snr-band-d2 {
      type decimal64 {
        fraction-digits 2;
      }
      units "dB";
      description
        "VDSL2 specific field for noise margin of downstream band two";
    }
    leaf vdsl2-snr-band-d3 {
      type decimal64 {
        fraction-digits 2;
      }
      units "dB";
      description
        "VDSL2 specific field for noise margin of downstream band three";
    }
    leaf atm-total-cells {
      type uint32;
      description
        "ATM TC mode specific total cells field";
    }
    leaf atm-user-cells {
      type uint32;
      description
        "ATM TC mode specific user cells field";
    }
  }

  grouping line-specific-info-co {
    description
      "Line specific information of central office";
    leaf trellis-state {
      type vdsl-ios-xe-oper:trellis-states;
      description
        "Indicates whether trellis coding is enabled or disabled on the
         central office (CO) side of the VDSL line.";
    }
    leaf sra-enabled {
      type boolean;
      description
        "Seamless rate adaptation status";
    }
    leaf sra-count {
      type uint32;
      description
        "Seamless rate adaptation counter";
    }
    leaf bit-swap-enabled {
      type boolean;
      description
        "Indicates whether bit swapping is enabled for the central office line,
         allowing dynamic adjustment of bit allocation to maintain line stability.";
    }
    leaf bit-swap-count {
      type uint32;
      description
        "Bit swap counter";
    }
    leaf line-attenuation {
      type decimal64 {
        fraction-digits 2;
      }
      units "dB";
      description
        "Line attenuation in decibels";
    }
    leaf signal-attenuation {
      type decimal64 {
        fraction-digits 2;
      }
      units "dB";
      description
        "Signal attenuation in decibels";
    }
    leaf noise-margin {
      type decimal64 {
        fraction-digits 2;
      }
      units "dB";
      description
        "Noise margin in decibels";
    }
    leaf attainable-rate {
      type uint32;
      units "kbps";
      description
        "Attainable rate in kilobits per sec";
    }
    leaf actual-power {
      type decimal64 {
        fraction-digits 2;
      }
      units "dBm";
      description
        "Actual power in decibel-milliwatts";
    }
    leaf total-fecc {
      type uint32;
      description
        "Total forward error correction counter";
    }
    leaf total-es {
      type uint32;
      description
        "Total errored seconds";
    }
    leaf total-ses {
      type uint32;
      description
        "Total severely errored seconds";
    }
    leaf total-loss {
      type uint32;
      description
        "Total loss of signal seconds";
    }
    leaf total-uas {
      type uint32;
      description
        "Total unavailable seconds";
    }
    leaf total-lprs {
      type uint32;
      description
        "Total loss of power seconds";
    }
    leaf total-lofs {
      type uint32;
      description
        "Total loss of frame seconds";
    }
    leaf total-lols {
      type uint32;
      description
        "Total loss of link seconds";
    }
    leaf speed {
      type uint32;
      units "kbps";
      description
        "Speed in kilobits per sec";
    }
    leaf sra-previous-speed {
      type uint32;
      units "kbps";
      description
        "Seamless rate adaptation previous speed in kilobits per sec";
    }
    leaf previous-speed {
      type uint32;
      units "kbps";
      description
        "Previous speed field represents previous speed for ADSL and VDSL, bit swap previous speed for GFAST";
    }
    leaf reed-solomon-ec {
      type uint32;
      description
        "Reed solomon error correction counter";
    }
    leaf crc-errors {
      type uint32;
      description
        "Cyclic redundancy check errors";
    }
    leaf header-errors {
      type uint32;
      description
        "Counter for the number of header errors detected in the received data
         frames on the line.";
    }
    leaf interleave {
      type decimal64 {
        fraction-digits 2;
      }
      description
        "Inter-leave time in milli seconds";
    }
    leaf actual-inp {
      type decimal64 {
        fraction-digits 2;
      }
      description
        "Actual value of impulse noise protection applied on the
         central office line, typically measured in DMT symbols.";
    }
    leaf gfast-fra-count {
      type uint32;
      description
        "Gfast specific field for fast rate adaptation counter";
    }
    leaf gfast-rpa-count {
      type uint32;
      description
        "Gfast specific field for robust management channel parameter adjustment counter";
    }
    leaf gfast-tiga-count {
      type uint32;
      description
        "Counter for the number of transmitter-initiated gain adjustments on
         the Gfast line.";
    }
    leaf gfast-rtx-uc {
      type uint32;
      description
        "Gfast specific field for counter for retransmissions that are uncorrected";
    }
    leaf gfast-rtx-tx {
      type uint32;
      description
        "Gfast specific field for retransmissions counter";
    }
    leaf gfast-attainable-exp-thru {
      type uint32;
      description
        "Gfast specific field for attainable expected throughput";
    }
    leaf gfast-error-free-thru {
      type uint32;
      description
        "Gfast specific field for error free throughput";
    }
    leaf vdsl2-la-band-u0 {
      type decimal64 {
        fraction-digits 2;
      }
      units "dB";
      description
        "VDSL2 specific field for line attenuation of upstream band zero";
    }
    leaf vdsl2-la-band-u1 {
      type decimal64 {
        fraction-digits 2;
      }
      units "dB";
      description
        "VDSL2 specific field for line attenuation of upstream band one";
    }
    leaf vdsl2-la-band-u2 {
      type decimal64 {
        fraction-digits 2;
      }
      units "dB";
      description
        "VDSL2 specific field for line attenuation of upstream band two";
    }
    leaf vdsl2-la-band-u3 {
      type decimal64 {
        fraction-digits 2;
      }
      units "dB";
      description
        "VDSL2 specific field for line attenuation of upstream band three";
    }
    leaf vdsl2-sa-band-u0 {
      type decimal64 {
        fraction-digits 2;
      }
      units "dB";
      description
        "VDSL2 specific field for signal attenuation of upstream band zero";
    }
    leaf vdsl2-sa-band-u1 {
      type decimal64 {
        fraction-digits 2;
      }
      units "dB";
      description
        "VDSL2 specific field for signal attenuation of upstream band one";
    }
    leaf vdsl2-sa-band-u2 {
      type decimal64 {
        fraction-digits 2;
      }
      units "dB";
      description
        "VDSL2 specific field for signal attenuation of upstream band two";
    }
    leaf vdsl2-sa-band-u3 {
      type decimal64 {
        fraction-digits 2;
      }
      units "dB";
      description
        "VDSL2 specific field for signal attenuation of upstream band three";
    }
    leaf vdsl2-snr-band-u0 {
      type decimal64 {
        fraction-digits 2;
      }
      units "dB";
      description
        "VDSL2 specific field for noise margin of upstream band zero";
    }
    leaf vdsl2-snr-band-u1 {
      type decimal64 {
        fraction-digits 2;
      }
      units "dB";
      description
        "VDSL2 specific field for noise margin of upstream band one";
    }
    leaf vdsl2-snr-band-u2 {
      type decimal64 {
        fraction-digits 2;
      }
      units "dB";
      description
        "VDSL2 specific field for noise margin of upstream band two";
    }
    leaf vdsl2-snr-band-u3 {
      type decimal64 {
        fraction-digits 2;
      }
      units "dB";
      description
        "VDSL2 specific field for noise margin of upstream band three";
    }
    leaf atm-total-cells {
      type uint32;
      description
        "ATM TC mode specific total cells field";
    }
    leaf atm-user-cells {
      type uint32;
      description
        "ATM TC mode specific user cells field";
    }
  }

  grouping vdsl-line-specific-info {
    description
      "VDSL line specific information";
    leaf line-num {
      type uint16;
      description
        "Specifies the identifier for the VDSL line within the controller.";
    }
    leaf modem-status {
      type vdsl-ios-xe-oper:modem-status-states;
      description
        "Current status of the VDSL modem.";
    }
    leaf trained-mode {
      type vdsl-ios-xe-oper:trained-modes;
      description
        "Indicates the trained mode of the VDSL modem (e.g., ADSL2+, VDSL2
         profile).";
    }
    leaf profile-30a-enabled {
      type boolean;
      description
        "Profile thirty-a status";
    }
    container cpe-line-specific-info {
      description
        "Line specific information of customer premises equipment";
      uses vdsl-ios-xe-oper:line-specific-info-cpe;
    }
    container co-line-specific-info {
      description
        "Line specific information of central office";
      uses vdsl-ios-xe-oper:line-specific-info-co;
    }
  }

  grouping vdsl-line-stats {
    description
      "Line specific information";
    leaf chip-vendor {
      type string;
      description
        "Chip vendor ID";
    }
    leaf line-attenuation {
      type string;
      status deprecated;
      description
        "Line attenuation in decibels";
    }
    leaf noise-margin {
      type string;
      status deprecated;
      description
        "Noise margin in decibels";
    }
    leaf attainable-rate {
      type uint32;
      status deprecated;
      description
        "Attainable rate in kilobits per sec";
    }
    leaf actual-power {
      type string;
      status deprecated;
      description
        "Actual power in decibel-milliwatts";
    }
    leaf speed {
      type uint32;
      status deprecated;
      description
        "Speed in kilobits per sec";
    }
    leaf modem-serial {
      type string;
      description
        "Modem serial number";
    }
    leaf chip-vendor-specific {
      type string;
      description
        "Vendor-specific information or identifiers provided by the chip
         manufacturer for the central office VDSL chipset.";
    }
    leaf chip-vendor-country {
      type string;
      description
        "Chip vendor country";
    }
    leaf modem-vendor-id {
      type string;
      description
        "Modem vendor id";
    }
    leaf modem-vendor-specific {
      type string;
      description
        "Vendor-specific information or identifiers provided by the modem
         manufacturer for the central office VDSL modem.";
    }
    leaf modem-vendor-country {
      type string;
      description
        "Specifies the country of origin or manufacture for the modem vendor
         associated with the customer-premises equipment.";
    }
    leaf modem-version {
      type string;
      description
        "Indicates the version identifier of the modem firmware or hardware for
         the customer-premises equipment.";
    }
  }

  grouping vdsl-line-bonding-specific-info {
    description
      "VDSL line bonding specific information";
    leaf ports-supported {
      type uint32;
      description
        "Number of ports supported";
    }
    leaf port-0-link-status {
      type vdsl-ios-xe-oper:vdsl-link-state;
      description
        "Port 0 link status";
    }
    leaf port-1-link-status {
      type vdsl-ios-xe-oper:vdsl-link-state;
      description
        "Port 1 link status";
    }
    leaf aggregate-us-rate {
      type uint32;
      units "kbps";
      description
        "Aggregate upstream rate";
    }
    leaf aggregate-ds-rate {
      type uint32;
      units "kbps";
      description
        "Aggregate downstream rate";
    }
  }

  grouping controller-info {
    description
      "VDSL Controller information";
    leaf state {
      type vdsl-ios-xe-oper:idb-states;
      description
        "Controller database state";
    }
    leaf mode {
      type vdsl-ios-xe-oper:mode-tc;
      description
        "Operational mode";
    }
    leaf modem-status {
      type string;
      status deprecated;
      description
        "Current status of the VDSL modem.";
    }
    leaf trained-mode {
      type string;
      status deprecated;
      description
        "Indicates the trained mode of the VDSL modem (e.g., ADSL2+, VDSL2 profile),
         this is deprecated, use VDSL line specific information trained mode.";
    }
    leaf firmware-version {
      type string;
      description
        "Firmware version";
    }
    leaf phy-version {
      type string;
      description
        "PHY version";
    }
    container cpe-stats {
      description
        "XTU-R customer-premises equipment statistics";
      uses vdsl-ios-xe-oper:vdsl-line-stats;
    }
    container co-stats {
      description
        "XTU-C central office statistics";
      uses vdsl-ios-xe-oper:vdsl-line-stats;
    }
    leaf dsl-config-mode {
      type vdsl-ios-xe-oper:dsl-config-modes;
      description
        "DSL configuration mode";
    }
    leaf delt-configuration-enabled {
      type boolean;
      description
        "Double ended line testing configuration state";
    }
    leaf delt-state {
      type vdsl-ios-xe-oper:delt-states;
      description
        "Status of Double Ended Line Testing information for the SFP module.";
    }
    container vdsl-line-bonding {
      description
        "VDSL line bonding info";
      uses vdsl-ios-xe-oper:vdsl-line-bonding-specific-info;
    }
    leaf failed-full-inits {
      type uint32;
      description
        "Failed full initializations counter";
    }
    leaf short-inits {
      type uint32;
      description
        "Short initializations counter";
    }
    leaf failed-short-inits {
      type uint32;
      description
        "Count of failed short initialization attempts on the line.";
    }
    leaf modem-phy-source {
      type string;
      description
        "Source of the modem PHY firmware, for example embedded in the
         system or loaded from a firmware directory/package.";
    }
    list vdsl-line-specific-info {
      key "line-num";
      description
        "VDSL line specific information";
      uses vdsl-ios-xe-oper:vdsl-line-specific-info;
    }
    leaf training-log-state {
      type vdsl-ios-xe-oper:training-logs-states;
      description
        "Indicates the current state (e.g., running or stopped) of the VDSL
         training logs, which record line training events and diagnostics.";
    }
    leaf training-log-filename {
      type string;
      description
        "Filename where the VDSL training logs are stored, containing records
         of line training events and diagnostics.";
    }
    leaf dsl-sfp-support {
      type empty;
      description
        "Indicates whether the controller supports DSL SFP (Small Form-factor
         Pluggable) modules.";
    }
    container sfp-local-info {
      when 'boolean(../dsl-sfp-support)';
      description
        "DSL SFP local information";
      uses vdsl-ios-xe-oper:dsl-sfp-local-info;
    }
  }

  container vdsl-oper-data {
    config false;
    description
      "Container for operational data related to all VDSL controllers on the
       device, including status, statistics, and configuration state.";
    list vdsl-info {
      key "slot-num subslot-num";
      description
        "List of VDSL controllers present on the device, providing operational
         status and detailed statistics for each controller.";
      uses vdsl-ios-xe-oper:controller-info;
      uses vdsl-ios-xe-oper:slot-info-key;
    }
  }
}
