module Cisco-IOS-XE-sdwan-ipsec-oper {
  yang-version 1.1;
  namespace "http://cisco.com/ns/yang/Cisco-IOS-XE-sdwan-ipsec-oper";
  prefix sdwan-ipsec-xe-oper;

  import Cisco-IOS-XE-sdwan-types {
    prefix ios-xe-sdwan-types;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for SDWAN IPSec IOS operational data.
     Copyright (c) 2025-2026 by Cisco Systems, Inc.
     All rights reserved.";

  revision 2026-08-01 {
    description
      "Updated descriptions for several model elements to clarify their meaning and purpose";
    reference
      "1.0.1";
    cisco-semver:module-version "1.0.1";
  }
  revision 2026-02-01 {
    description
      "Initial revision";
    reference
      "1.0.0";
    cisco-semver:module-version "1.0.0";
  }

  typedef iosd-encr-algo-enum {
    type enumeration {
      enum enc-none {
        value 0;
        description
          "No encryption";
      }
      enum enc-aes-gcm-256 {
        value 1;
        description
          "Represents the AES-GCM-256 encryption algorithm.";
      }
    }
    description
      "SDWAN encryption algorithm";
  }

  typedef iosd-auth-algo-enum {
    type enumeration {
      enum ath-none {
        value 0;
        description
          "No authentication";
      }
      enum ath-sha1 {
        value 1;
        description
          "Represents the SHA1 authentication algorithm.";
      }
    }
    description
      "SDWAN authentication algorithm";
  }

  typedef iosd-int-algo-enum {
    type enumeration {
      enum int-none {
        value 0;
        description
          "No integrity";
      }
      enum int-esp {
        value 1;
        description
          "ESP integrity";
      }
      enum int-ip-udp-esp {
        value 2;
        description
          "IP, UDP and ESP integrity";
      }
      enum int-ip-udp-esp-no-id {
        value 3;
        description
          "IP, UDP and ESP without ID integrity";
      }
    }
    description
      "SDWAN integrity algorithm";
  }

  grouping local-sa-key {
    description
      "Display IPsec local SA key";
    leaf tloc-addr {
      type inet:ip-address;
      description
        "Specifies the TLOC address.";
    }
    leaf tloc-color {
      type ios-xe-sdwan-types:sdwan-color-enum;
      description
        "Indicates the color attribute of the TLOC";
    }
    leaf spi {
      type uint32;
      description
        "Specifies the Security Parameter Index (SPI) used in the Security Association.";
    }
    leaf tloc-idx {
      type uint32;
      description
        "Specifies the index of the TLOC in the local TLOC table";
    }
  }

  grouping local-sa-obj {
    description
      "Display IPsec local SA object";
    leaf ip {
      type inet:ip-address;
      description
        "Specifies the IPv4 address associated with the local SA";
    }
    leaf port {
      type uint16;
      description
        "Specifies the UDP port number used by the local SA";
    }
    leaf encrypt-key-hash {
      type string;
      description
        "Specifies the hash of the encryption key used for the local Security Association.";
    }
    leaf auth-key-hash {
      type string;
      description
        "Specifies the hash of the authentication key used for the local Security Association.";
    }
    leaf ipv6 {
      type inet:ipv6-address;
      description
        "Specifies the IPv6 address associated with the local SA";
    }
  }

  grouping inb-conn-key {
    description
      "Display IPsec inbound connections key";
    leaf local-tloc-addr {
      type inet:ip-address;
      description
        "Specifies the local TLOC address.";
    }
    leaf local-tloc-color {
      type ios-xe-sdwan-types:sdwan-color-enum;
      description
        "Indicates the color attribute of the local TLOC.";
    }
    leaf remote-tloc-addr {
      type inet:ip-address;
      description
        "Specifies the remote TLOC address.";
    }
    leaf remote-tloc-color {
      type ios-xe-sdwan-types:sdwan-color-enum;
      description
        "Indicates the color attribute of the remote TLOC,";
    }
  }

  grouping inb-conn-obj {
    description
      "Display IPsec inbound connections object";
    leaf local-tloc-idx {
      type uint32;
      description
        "Specifies the flow identifier for the local Security Association (SA) in the inbound connection.";
    }
    leaf remote-tloc-idx {
      type uint32;
      description
        "Specifies the flow identifier for the remote Security Association (SA) in the inbound connection.";
    }
    leaf src-ip {
      type inet:ip-address;
      description
        "Specifies the source IP address for the inbound IPsec connection.";
    }
    leaf src-port {
      type uint16;
      description
        "Specifies the source port number for the inbound IPsec connection.";
    }
    leaf dst-ip {
      type inet:ip-address;
      description
        "Specifies the destination IP address for the inbound IPsec connection.";
    }
    leaf dst-port {
      type uint16;
      description
        "Specifies the destination port number for the inbound IPsec connection.";
    }
    leaf neg-encr-algo {
      type sdwan-ipsec-xe-oper:iosd-encr-algo-enum;
      description
        "Negotiated encryption algorithm";
    }
    leaf spi-per-tun {
      type uint32;
      description
        "Specifies the number of Traffic Control Security Parameter Index (SPI) entries per tunnel.";
    }
  }

  grouping outb-conn-key {
    description
      "Display IPsec outbound connections key";
    leaf local-tloc-addr {
      type inet:ip-address;
      description
        "Specifies the local TLOC address.";
    }
    leaf local-tloc-color {
      type ios-xe-sdwan-types:sdwan-color-enum;
      description
        "Indicates the color attribute of the local TLOC,";
    }
    leaf remote-tloc-addr {
      type inet:ip-address;
      description
        "Specifies the remote TLOC address.";
    }
    leaf remote-tloc-color {
      type ios-xe-sdwan-types:sdwan-color-enum;
      description
        "Indicates the color attribute of the remote TLOC,";
    }
  }

  grouping outb-conn-obj {
    description
      "Display IPsec outbound connections object";
    leaf src-ip {
      type inet:ip-address;
      description
        "Specifies the source IP address for the outbound IPsec connection.";
    }
    leaf src-port {
      type uint16;
      description
        "Specifies the UDP source port number used by the outbound IPsec connection.";
    }
    leaf dst-ip {
      type inet:ip-address;
      description
        "Specifies the destination IP address for the outbound IPsec connection.";
    }
    leaf dst-port {
      type uint16;
      description
        "Specifies the UDP destination port number used by the outbound IPsec connection.";
    }
    leaf spi {
      type uint32;
      description
        "Specifies the Security Parameter Index (SPI) used in the Security Association.";
    }
    leaf tunnel-mtu {
      type uint32;
      description
        "Specifies the Maximum Transmission Unit (MTU) for the outbound IPsec tunnel.";
    }
    leaf auth-used {
      type sdwan-ipsec-xe-oper:iosd-auth-algo-enum;
      description
        "Specifies the authentication algorithm used for the outbound IPsec connection.";
    }
    leaf encrypt-key-hash {
      type string;
      description
        "Specifies the hash of the encryption key used for the outbound IPsec connection.";
    }
    leaf auth-key-hash {
      type string;
      description
        "Specifies the hash of the authentication key used for the outbound IPsec connection.";
    }
    leaf neg-algo {
      type sdwan-ipsec-xe-oper:iosd-encr-algo-enum;
      description
        "Negotiated encryption algorithm";
    }
    leaf int-used {
      type sdwan-ipsec-xe-oper:iosd-int-algo-enum;
      description
        "Specifies the integrity algorithm used for the outbound IPsec connection.";
    }
    leaf spi-per-tun {
      type uint32;
      description
        "Specifies the number of Traffic Control Security Parameter Index (SPI) entries per tunnel.";
    }
  }

  grouping pwk-local-sa-key {
    description
      "Display Pairwise Key IPsec local SA Key";
    leaf tloc-addr {
      type inet:ip-address;
      description
        "Specifies the TLOC address.";
    }
    leaf tloc-color {
      type ios-xe-sdwan-types:sdwan-color-enum;
      description
        "Indicates the color attribute of the TLOC,";
    }
    leaf spi {
      type uint32;
      description
        "Specifies the Security Parameter Index (SPI) used in the Security Association.";
    }
    leaf tloc-idx {
      type uint32;
      description
        "Specifies the index of the TLOC in the local TLOC table.";
    }
  }

  grouping pwk-local-sa-obj {
    description
      "Display Pairwise Key IPsec local SA object";
    leaf ip {
      type inet:ip-address;
      description
        "Specifies the IP address associated with the local pairwise key Security Association.";
    }
    leaf port {
      type uint16;
      description
        "Specifies the UDP port number used by the local pairwise key Security Association.";
    }
    leaf sa-idx {
      type uint32;
      description
        "Specifies the index of the inbound Security Association (SA) for the pairwise key.";
    }
    leaf pkey-id {
      type uint32;
      description
        "Specifies the identifier for the pairwise key used in the Security Association.";
    }
    leaf nonce-hash {
      type string;
      description
        "Specifies the hash value of the nonce used in the Pairwise Key IPsec local Security Association for cryptographic operations.";
    }
    leaf pkey-hash {
      type string;
      description
        "Specifies the hash of the pairwise key public key.";
    }
  }

  grouping pwk-inb-conn-key {
    description
      "Display Pairwise Key IPsec inbound connections key";
    leaf local-tloc-addr {
      type inet:ip-address;
      description
        "Specifies the local TLOC address.";
    }
    leaf local-tloc-color {
      type ios-xe-sdwan-types:sdwan-color-enum;
      description
        "Indicates the color attribute of the local TLOC,";
    }
    leaf remote-tloc-addr {
      type inet:ip-address;
      description
        "Specifies the remote TLOC address.";
    }
    leaf remote-tloc-color {
      type ios-xe-sdwan-types:sdwan-color-enum;
      description
        "Indicates the color attribute of the remote TLOC,";
    }
  }

  grouping pwk-inb-conn-obj {
    description
      "Display Pairwise Key IPsec inbound connections object";
    leaf local-tloc-idx {
      type uint32;
      description
        "Specifies the flow identifier for the local Security Association (SA) in the Pairwise Key IPsec inbound connection.";
    }
    leaf remote-tloc-idx {
      type uint32;
      description
        "Specifies the flow identifier for the remote Security Association (SA) in the Pairwise Key IPsec inbound connection.";
    }
    leaf src-ip {
      type inet:ip-address;
      description
        "Specifies the source IP address for the Pairwise Key IPsec inbound connection.";
    }
    leaf src-port {
      type uint16;
      description
        "Specifies the source port number for the Pairwise Key IPsec inbound connection.";
    }
    leaf dst-ip {
      type inet:ip-address;
      description
        "Specifies the destination IP address for the Pairwise Key IPsec inbound connection.";
    }
    leaf dst-port {
      type uint16;
      description
        "Specifies the destination port number for the Pairwise Key IPsec inbound connection.";
    }
    leaf pwk-spi {
      type uint32;
      description
        "Specifies the Security Parameter Index (SPI) for the Pairwise Key IPsec inbound connection.";
    }
    leaf sa-idx {
      type uint32;
      description
        "Specifies the index of the inbound Security Association (SA) for the pairwise key.";
    }
    leaf pkey-id {
      type uint32;
      description
        "Specifies the identifier for the pairwise key used in the Security Association.";
    }
    leaf nonce-hash {
      type string;
      description
        "Specifies the hash value of the nonce used in the Pairwise Key IPsec inbound connection for cryptographic operations.";
    }
    leaf pkey-hash {
      type string;
      description
        "Specifies the hash of the pairwise key public key.";
    }
    leaf ss-hash {
      type string;
      description
        "Specifies the hash of the pairwise key shared secret.";
    }
    leaf d-key-hash {
      type string;
      description
        "Specifies the hash of the pairwise key IPsec decryption key.";
    }
    leaf is-ah-auth {
      type boolean;
      description
        "Indicates whether the Pairwise Key IPsec inbound connection is using AH (Authentication Header) authentication.";
    }
  }

  grouping pwk-outb-conn-key {
    description
      "Display Pairwise Key IPsec outbound connections key";
    leaf local-tloc-addr {
      type inet:ip-address;
      description
        "Specifies the local TLOC address.";
    }
    leaf local-tloc-color {
      type ios-xe-sdwan-types:sdwan-color-enum;
      description
        "Indicates the color attribute of the local TLOC,";
    }
    leaf remote-tloc-addr {
      type inet:ip-address;
      description
        "Specifies the remote TLOC address.";
    }
    leaf remote-tloc-color {
      type ios-xe-sdwan-types:sdwan-color-enum;
      description
        "Indicates the color attribute of the remote TLOC,";
    }
  }

  grouping pwk-outb-conn-obj {
    description
      "Display Pairwise Key IPsec outbound connections object";
    leaf src-ip {
      type inet:ip-address;
      description
        "Specifies the source IP address for the Pairwise Key IPsec outbound connection.";
    }
    leaf src-port {
      type uint16;
      description
        "Specifies the UDP source port number for the Pairwise Key IPsec outbound connection.";
    }
    leaf dst-ip {
      type inet:ip-address;
      description
        "Specifies the destination IP address for the Pairwise Key IPsec outbound connection.";
    }
    leaf dst-port {
      type uint16;
      description
        "Specifies the UDP destination port number for the Pairwise Key IPsec outbound connection.";
    }
    leaf spi {
      type uint32;
      description
        "Specifies the Security Parameter Index (SPI) used in the Security Association.";
    }
    leaf tloc-idx {
      type uint32;
      description
        "Specifies the index of the TLOC in the local TLOC table.";
    }
    leaf local-tloc-idx {
      type uint32;
      description
        "Specifies the flow identifier of the local Security Association (SA).";
    }
    leaf remote-tloc-idx {
      type uint32;
      description
        "Specifies the flow identifier of the remote Security Association (SA).";
    }
    leaf pwk-spi {
      type uint32;
      description
        "Specifies the Security Parameter Index (SPI) for the Pairwise Key IPsec outbound connection.";
    }
    leaf sa-idx {
      type uint32;
      description
        "Specifies the index of the outbound Security Association (SA).";
    }
    leaf pkey-id {
      type uint32;
      description
        "Specifies the identifier for the pairwise key used in the Security Association.";
    }
    leaf nonce-hash {
      type string;
      description
        "Specifies the hash of the nonce value used in the Pairwise Key outbound connection.";
    }
    leaf pkey-hash {
      type string;
      description
        "Specifies the hash of the pairwise key public key.";
    }
    leaf ss-hash {
      type string;
      description
        "Specifies the hash of the pairwise key shared secret.";
    }
    leaf e-key-hash {
      type string;
      description
        "Pairwise Key IPsec Encryption Key Hash";
    }
    leaf is-ah-auth {
      type boolean;
      description
        "Indicates whether the pairwise key IPsec outbound connection is using AH (Authentication Header) authentication.";
    }
  }

  container sdwan-ipsec-oper-data {
    config false;
    description
      "SDWAN IPSec IOS operational data";
    list local-sa {
      key "tloc-addr tloc-color spi tloc-idx";
      description
        "List of local Security Associations (SAs) for SDWAN IPsec, including TLOC, Security Parameter Index (SPI), and key information.";
      uses sdwan-ipsec-xe-oper:local-sa-key;
      uses sdwan-ipsec-xe-oper:local-sa-obj;
    }
    list inbound-con {
      key "local-tloc-addr local-tloc-color remote-tloc-addr remote-tloc-color";
      description
        "List of inbound IPsec connections, each representing an active Security Association (SA) from a remote TLOC to the local device.";
      uses sdwan-ipsec-xe-oper:inb-conn-key;
      uses sdwan-ipsec-xe-oper:inb-conn-obj;
    }
    list outbound-con {
      key "local-tloc-addr local-tloc-color remote-tloc-addr remote-tloc-color";
      description
        "List of outbound IPsec connections, each representing an active Security Association (SA) from the local device to a remote TLOC.";
      uses sdwan-ipsec-xe-oper:outb-conn-key;
      uses sdwan-ipsec-xe-oper:outb-conn-obj;
    }
    list pwk-local-sa {
      key "tloc-addr tloc-color spi tloc-idx";
      description
        "List of local Security Associations (SAs) that use pairwise keys for IPsec tunnels.";
      uses sdwan-ipsec-xe-oper:pwk-local-sa-key;
      uses sdwan-ipsec-xe-oper:pwk-local-sa-obj;
    }
    list pwk-inbound-con {
      key "local-tloc-addr local-tloc-color remote-tloc-addr remote-tloc-color";
      description
        "List of inbound IPsec connections that use pairwise keys.";
      uses sdwan-ipsec-xe-oper:pwk-inb-conn-key;
      uses sdwan-ipsec-xe-oper:pwk-inb-conn-obj;
    }
    list pwk-outbound-con {
      key "local-tloc-addr local-tloc-color remote-tloc-addr remote-tloc-color";
      description
        "List of outbound IPsec connections that use pairwise keys.";
      uses sdwan-ipsec-xe-oper:pwk-outb-conn-key;
      uses sdwan-ipsec-xe-oper:pwk-outb-conn-obj;
    }
  }
}
