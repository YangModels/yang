module Cisco-IOS-XE-checkpoint-archive-oper {
  yang-version 1.1;
  namespace "http://cisco.com/ns/yang/Cisco-IOS-XE-checkpoint-archive-oper";
  prefix checkpoint-archive-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     monitoring the checkpoint archives in a Network Element.
     Copyright (c) 2016-2017, 2019, 2022, 2026 by Cisco Systems, Inc.
     All rights reserved.";

  revision 2026-08-01 {
    description
      "Improved descriptions for archives container and archive list";
    reference
      "2.3.1";
    cisco-semver:module-version "2.3.1";
  }
  revision 2022-11-01 {
    description
      "Update yang-version to 1.1";
    reference
      "2.3.0";
    cisco-semver:module-version "2.3.0";
  }
  revision 2019-05-01 {
    description
      "Added semantic version";
    reference
      "2.2.0";
    cisco-semver:module-version "2.2.0";
  }
  revision 2018-10-29 {
    description
      "Cleaned up spelling errors in descriptions.";
    reference
      "2.1.0";
    cisco-semver:module-version "2.1.0";
  }
  revision 2017-04-01 {
    description
      "Top level container name change";
    reference
      "2.0.0";
    cisco-semver:module-version "2.0.0";
  }
  revision 2017-02-07 {
    description
      "Initial revision";
    reference
      "1.0.0";
    cisco-semver:module-version "1.0.0";
  }

  grouping archive {
    description
      "Archive information";
    leaf number {
      type uint16;
      description
        "The archive number";
    }
    leaf name {
      type string;
      description
        "The name of the archive";
    }
  }

  grouping checkpoint-archive {
    description
      "Checkpoint archive information";
    leaf max {
      type uint8;
      description
        "The maximum number of archives";
    }
    leaf current {
      type uint8;
      description
        "The current number of archives";
    }
    leaf recent {
      type string;
      description
        "The most recent archive";
    }
    container archives {
      description
        "Container for the list of checkpoint archive entries, each representing a saved configuration state.";
      list archive {
        key "number";
        description
          "A list of checkpoint archive entry containing details about a specific saved configuration checkpoint.";
        uses checkpoint-archive-ios-xe-oper:archive;
      }
    }
  }

  container checkpoint-archives {
    config false;
    description
      "Contents of the checkpoint archive information base";
    uses checkpoint-archive-ios-xe-oper:checkpoint-archive;
  }
}
