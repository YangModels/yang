module Cisco-IOS-XE-aaa-types {
  yang-version 1.1;
  namespace "http://cisco.com/ns/yang/Cisco-IOS-XE-aaa-types";
  prefix aaa-types;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains type definitions for AAA Types.
     Copyright (c) 2019-2021, 2024 by Cisco Systems, Inc.
     All rights reserved.";

  revision 2024-11-01 {
    description
      "- Added Meraki AAA attributes";
    reference
      "1.9.0";
    cisco-semver:module-version "1.9.0";
  }
  revision 2023-03-01 {
    description
      "- Added new enum for location capable attribute
       - Added new enum for Role-based Access-list IP version update";
    reference
      "1.8.0";
    cisco-semver:module-version "1.8.0";
  }
  revision 2022-11-01 {
    description
      "Update yang-version to 1.1";
    reference
      "1.7.0";
    cisco-semver:module-version "1.7.0";
  }
  revision 2022-07-01 {
    description
      "- Added new enums for location attributes";
    reference
      "1.6.0";
    cisco-semver:module-version "1.6.0";
  }
  revision 2022-03-01 {
    description
      "- Added new enums(push-id, policy-version-id, report-config-type) as RADIUS attributes for TrustSec Push-ID feature
       - Added MAC address of VM Bridge Host";
    reference
      "1.5.0";
    cisco-semver:module-version "1.5.0";
  }
  revision 2021-07-01 {
    description
      "- Added MAC randomization device unique identifier
       - Added an enum value for MDNS location ID attribute in aaa-attribute-type-tdl
       - Added new enum values for 5G Packet Core Gateway in aaa-attribute-type-tdl
       - Added new enum values for rogue-ap-state and rogue-ap-class AV-Pair attributes";
    reference
      "1.4.0";
    cisco-semver:module-version "1.4.0";
  }
  revision 2021-03-01 {
    description
      "- Added FQDN Redirect ACL, Auth Survivability, and WLAN Profile Name attributes
       - Added Easy PSK and Suite B attributes
       - Added Operator name attribute";
    reference
      "1.3.0";
    cisco-semver:module-version "1.3.0";
  }
  revision 2020-11-01 {
    description
      "- Added new enums to support RADIUS attributes for Boingo and Syniverse vendors";
    reference
      "1.2.0";
    cisco-semver:module-version "1.2.0";
  }
  revision 2020-03-01 {
    description
      "- Added Server list AAA attributes";
    reference
      "1.1.0";
    cisco-semver:module-version "1.1.0";
  }
  revision 2019-11-01 {
    description
      "Initial revision";
    reference
      "1.0.0";
    cisco-semver:module-version "1.0.0";
  }

  typedef protocol-type {
    type enumeration {
      enum aaa-protocol-type-none {
        value 0;
        description
          "AAA protocol type None";
      }
      enum aaa-protocol-type-invalid {
        value 1;
        description
          "AAA protocol type Invalid";
      }
      enum aaa-protocol-type-lcp {
        value 2;
        description
          "AAA protocol type LCP";
      }
      enum aaa-protocol-type-ip {
        value 3;
        description
          "AAA protocol type IP";
      }
      enum aaa-protocol-type-ipsec {
        value 4;
        description
          "AAA protocol IPSec";
      }
      enum aaa-protocol-type-ipx {
        value 5;
        description
          "AAA protocol type IPX";
      }
      enum aaa-protocol-type-atalk {
        value 6;
        description
          "AAA protocol type ATALK";
      }
      enum aaa-protocol-type-xremote {
        value 7;
        description
          "AAA protocol type XRemote";
      }
      enum aaa-protocol-type-tn3270 {
        value 8;
        description
          "AAA protocol type TN3270";
      }
      enum aaa-protocol-type-telnet {
        value 9;
        description
          "AAA protocol type Telnet";
      }
      enum aaa-protocol-type-tcp-clear {
        value 10;
        description
          "AAA protocol type TCP Clear";
      }
      enum aaa-protocol-type-rlogin {
        value 11;
        description
          "AAA protocol type RLogin";
      }
      enum aaa-protocol-type-lat {
        value 12;
        description
          "AAA protocol type LAT";
      }
      enum aaa-protocol-type-pad {
        value 13;
        description
          "AAA protocol type PAD";
      }
      enum aaa-protocol-type-osicp {
        value 14;
        description
          "AAA protocol type OSICP";
      }
      enum aaa-protocol-type-tagcp {
        value 15;
        description
          "AAA protocol type TAGCP";
      }
      enum aaa-protocol-type-bacp {
        value 16;
        description
          "AAA protocol type BACP";
      }
      enum aaa-protocol-type-decnet {
        value 17;
        description
          "AAA protocol type Decnet";
      }
      enum aaa-protocol-type-ccp {
        value 18;
        description
          "AAA protocol type CCP";
      }
      enum aaa-protocol-type-cdp {
        value 19;
        description
          "AAA protocol type CDP";
      }
      enum aaa-protocol-type-bridging {
        value 20;
        description
          "AAA protocol type Bridging";
      }
      enum aaa-protocol-type-nbf {
        value 21;
        description
          "AAA protocol type NBF";
      }
      enum aaa-protocol-type-bap {
        value 22;
        description
          "AAA protocol type BAP";
      }
      enum aaa-protocol-type-multilink {
        value 23;
        description
          "AAA protocol type Multilink";
      }
      enum aaa-protocol-type-h323 {
        value 24;
        description
          "AAA protocol type H323";
      }
      enum aaa-protocol-type-unknown {
        value 25;
        description
          "AAA protocol type Unknown";
      }
      enum aaa-protocol-type-call-accept {
        value 26;
        description
          "AAA protocol type Accept";
      }
      enum aaa-protocol-type-vpdn-session {
        value 27;
        description
          "AAA protocol type VPDN Session";
      }
      enum aaa-protocol-type-rm-call-status {
        value 28;
        description
          "AAA protocol type RM Call Status";
      }
      enum aaa-protocol-type-rm-nas-status {
        value 29;
        description
          "AAA protocol type RM NAS status";
      }
      enum aaa-protocol-type-dial-in {
        value 30;
        description
          "AAA protocol type Dial-In";
      }
      enum aaa-protocol-type-dial-out {
        value 31;
        description
          "AAA protocol type Dial-Out";
      }
      enum aaa-protocol-type-ss7 {
        value 32;
        description
          "AAA protocol type SS7";
      }
      enum aaa-protocol-type-rms-stop {
        value 33;
        description
          "AAA protocol type RMS Stop";
      }
      enum aaa-protocol-type-rms-start {
        value 34;
        description
          "AAA protocol type RMS Start";
      }
      enum aaa-protocol-type-vpdn {
        value 35;
        description
          "AAA protocol type VPDN";
      }
      enum aaa-protocol-type-sss {
        value 36;
        description
          "AAA protocol type SSS";
      }
      enum aaa-protocol-type-subscriber {
        value 37;
        description
          "AAA protocol type Subscriber";
      }
      enum aaa-protocol-type-atm {
        value 38;
        description
          "AAA protocol type ATM";
      }
      enum aaa-protocol-type-ssh {
        value 39;
        description
          "AAA protocol type SSH";
      }
      enum aaa-protocol-type-ipv6 {
        value 40;
        description
          "AAA protocol type IPv6";
      }
      enum aaa-protocol-type-pppoe {
        value 41;
        description
          "AAA protocol type PPPoE";
      }
      enum aaa-protocol-type-cdma {
        value 42;
        description
          "AAA protocol type CDMA";
      }
      enum aaa-protocol-type-crb {
        value 43;
        description
          "AAA protocol type CRB";
      }
      enum aaa-protocol-type-template {
        value 44;
        description
          "AAA protocol type Template";
      }
      enum aaa-protocol-type-aaa {
        value 45;
        description
          "AAA protocol type AAA";
      }
      enum aaa-protocol-type-mac {
        value 46;
        description
          "AAA protocol type MAC";
      }
      enum aaa-protocol-type-leap {
        value 47;
        description
          "AAA protocol type LEAP";
      }
      enum aaa-protocol-type-aironet {
        value 48;
        description
          "AAA protocol type Aironet";
      }
      enum aaa-protocol-type-entity {
        value 49;
        description
          "AAA protocol type Entity";
      }
      enum aaa-protocol-type-epd {
        value 50;
        description
          "AAA protocol type EPD";
      }
      enum aaa-protocol-type-igmp {
        value 51;
        description
          "AAA protocol type IGMP";
      }
      enum aaa-protocol-type-webvpn {
        value 52;
        description
          "AAA protocol type WEBVPN";
      }
      enum aaa-protocol-type-cts {
        value 53;
        description
          "AAA protocol type CTS";
      }
      enum aaa-protocol-type-radius {
        value 54;
        description
          "AAA protocol type RADIUS";
      }
      enum aaa-protocol-type-evc {
        value 55;
        description
          "AAA protocol type EVC";
      }
      enum aaa-protocol-type-elmi {
        value 56;
        description
          "AAA protocol type ELMI";
      }
      enum aaa-protocol-type-dot1x {
        value 57;
        description
          "AAA protocol type 802.1x";
      }
      enum aaa-protocol-type-dtp {
        value 58;
        description
          "AAA protocol type DTP";
      }
      enum aaa-protocol-type-lacp {
        value 59;
        description
          "AAA protocol type LACP";
      }
      enum aaa-protocol-type-pagp {
        value 60;
        description
          "AAA protocol type PAGP";
      }
      enum aaa-protocol-type-stp {
        value 61;
        description
          "AAA protocol type STP";
      }
      enum aaa-protocol-type-vtp {
        value 62;
        description
          "AAA protocol type VTP";
      }
      enum aaa-protocol-type-ethernet-mac-tunnel {
        value 63;
        description
          "AAA protocol type Ethernet MAC Tunnel";
      }
      enum aaa-protocol-type-bridge-domain {
        value 64;
        description
          "AAA protocol type Bridge Domain";
      }
      enum aaa-protocol-type-ethernet-cfm {
        value 65;
        description
          "AAA protocol type Ethernet CFM";
      }
      enum aaa-protocol-type-ethernet-service-instance {
        value 66;
        description
          "AAA protocol type Ethernet Service Instance";
      }
      enum aaa-protocol-type-service-group {
        value 67;
        description
          "AAA protocol type Service Group";
      }
      enum aaa-protocol-type-ip-dhcp-snooping {
        value 68;
        description
          "AAA protocol type IP DHCP Snooping";
      }
      enum aaa-protocol-type-ip-source-guard {
        value 69;
        description
          "AAA protocol type IP Source Guard";
      }
      enum aaa-protocol-type-error-disable {
        value 70;
        description
          "AAA protocol type Error Disable";
      }
      enum aaa-protocol-type-cmac-bridge-domain {
        value 71;
        description
          "AAA protocol type CMAC Bridge Domain";
      }
      enum aaa-protocol-type-mac-in-mac-tunnel {
        value 72;
        description
          "AAA protocol type MAC-IN-MAC Tunnel";
      }
      enum aaa-protocol-type-l2vpn {
        value 73;
        description
          "AAA protocol type L2VPN";
      }
      enum aaa-protocol-type-snmp {
        value 74;
        description
          "AAA protocol type SNMP";
      }
      enum aaa-protocol-type-vnid {
        value 75;
        description
          "AAA protocol type VNID";
      }
    }
    description
      "Protocol Type";
  }

  typedef serv-type {
    type enumeration {
      enum aaa-service-type-none {
        value 0;
        description
          "AAA service type None";
      }
      enum aaa-service-type-invalid {
        value 1;
        description
          "AAA service type Invalid";
      }
      enum aaa-service-type-shell {
        value 2;
        description
          "AAA service type Shell";
      }
      enum aaa-service-type-arap {
        value 3;
        description
          "AAA service type ARAP";
      }
      enum aaa-service-type-ppp {
        value 4;
        description
          "AAA service type PPP";
      }
      enum aaa-service-type-slip {
        value 5;
        description
          "AAA service type Slip";
      }
      enum aaa-service-type-system {
        value 6;
        description
          "AAA service type System";
      }
      enum aaa-service-type-resource {
        value 7;
        description
          "AAA service type Resource";
      }
      enum aaa-service-type-connection {
        value 8;
        description
          "AAA service type Connection";
      }
      enum aaa-service-type-tty-daemon {
        value 9;
        description
          "AAA service type TTY Daemon";
      }
      enum aaa-service-type-vpdn {
        value 10;
        description
          "AAA service type VPDN";
      }
      enum aaa-service-type-vpdn-out {
        value 11;
        description
          "AAA service type VPDN Out";
      }
      enum aaa-service-type-raccess {
        value 12;
        description
          "AAA service type Remote-Access";
      }
      enum aaa-service-type-h323 {
        value 13;
        description
          "AAA service type H323";
      }
      enum aaa-service-type-outbound {
        value 14;
        description
          "AAA service type Outbound";
      }
      enum aaa-service-type-mobile-ip {
        value 15;
        description
          "AAA service type Mobile-IP";
      }
      enum aaa-service-type-auth-proxy {
        value 16;
        description
          "AAA service type Auth-Proxy";
      }
      enum aaa-service-type-eou {
        value 17;
        description
          "AAA service type EOU";
      }
      enum aaa-service-type-ike {
        value 18;
        description
          "AAA service type IKE";
      }
      enum aaa-service-type-resource-management {
        value 19;
        description
          "AAA service type Resource Management";
      }
      enum aaa-service-type-callback {
        value 20;
        description
          "AAA service type Callback";
      }
      enum aaa-service-type-gprs {
        value 21;
        description
          "AAA service type GPRS";
      }
      enum aaa-service-type-gprs-pdp-context {
        value 22;
        description
          "AAA service type GPRS PDP Context";
      }
      enum aaa-service-type-preauth {
        value 23;
        description
          "AAA service type Pre-Auth";
      }
      enum aaa-service-type-translate {
        value 24;
        description
          "AAA service type Translate";
      }
      enum aaa-service-type-pki {
        value 25;
        description
          "AAA service type PKI";
      }
      enum aaa-service-type-ca {
        value 26;
        description
          "AAA service type CA";
      }
      enum aaa-service-type-tti {
        value 27;
        description
          "AAA service type Trusted Transitive Introduction";
      }
      enum aaa-service-type-multicast {
        value 28;
        description
          "AAA service type Multicast";
      }
      enum aaa-service-type-encryption {
        value 29;
        description
          "AAA service type Encryption";
      }
    }
    description
      "Service Type";
  }

  typedef aaa-req-status {
    type enumeration {
      enum aaa-req-status-begin {
        value 0;
        description
          "AAA Request Status Begin";
      }
      enum aaa-req-status-sent {
        value 1;
        description
          "AAA Request Status Sent";
      }
      enum aaa-req-status-pass {
        value 2;
        description
          "AAA Request Status Pass";
      }
      enum aaa-req-status-fail {
        value 3;
        description
          "AAA Request Fail";
      }
      enum aaa-req-status-fail-no-retries {
        value 4;
        description
          "AAA Request Status Fail No Retries";
      }
      enum aaa-req-status-failover-retry {
        value 5;
        description
          "AAA Request Status Failover Retry";
      }
      enum aaa-req-status-user-nopassword {
        value 6;
        description
          "AAA Request Status User Nopassword";
      }
      enum aaa-req-status-get-user {
        value 7;
        description
          "AAA Request Status Get User";
      }
      enum aaa-req-status-get-password {
        value 8;
        description
          "AAA Request Status Get Password";
      }
      enum aaa-req-status-get-data {
        value 9;
        description
          "AAA Request Status Get Data";
      }
      enum aaa-req-status-cancelled {
        value 10;
        description
          "AAA Request Status Cancelled";
      }
      enum aaa-req-status-get-challenge-response {
        value 11;
        description
          "AAA Request Status Get Challenge Response";
      }
      enum aaa-req-status-get-new-password {
        value 12;
        description
          "AAA Request Status Get New Password";
      }
      enum aaa-req-status-get-challenge-resp-noecho {
        value 13;
        description
          "AAA Request Status Get Challenge Response Noecho";
      }
    }
    description
      "AAA Request Status";
  }

  typedef aaa-attribute-type-tdl {
    type enumeration {
      enum aaa-at-invalid {
        value 0;
        description
          "Invalid attribute";
      }
      enum aaa-at-abort-cause {
        value 1;
        description
          "Extended disconnect cause reasons";
      }
      enum aaa-at-acct-status-type {
        value 2;
        description
          "The type of accounting request";
      }
      enum aaa-at-acct-tunnel-packets-lost {
        value 3;
        description
          "The number of packets lost on a given link";
      }
      enum aaa-at-acl {
        value 4;
        description
          "An access list";
      }
      enum aaa-at-authorized-services {
        value 5;
        description
          "Services authorized by server";
      }
      enum aaa-at-auto-logon-service {
        value 6;
        description
          "SG replacement for Service Selection Gateway vsa";
      }
      enum aaa-at-azn-tag {
        value 7;
        description
          "Identifies the translate-tag";
      }
      enum aaa-at-ipv4-address {
        value 8;
        description
          "The IPv4 address for the user";
      }
      enum aaa-at-svc-assigned-ipv4-address {
        value 9;
        description
          "Service assigned IP address for the user";
      }
      enum aaa-at-ipv6-address {
        value 10;
        description
          "The IPv6 address for the user";
      }
      enum aaa-at-address-pool {
        value 11;
        description
          "The IP address pool to obtain address from";
      }
      enum aaa-at-ip-subscriber-route {
        value 12;
        description
          "IP Subscriber routes configuration";
      }
      enum aaa-at-async-map {
        value 13;
        description
          "Async control character map";
      }
      enum aaa-at-authentic {
        value 14;
        description
          "Method of authentication";
      }
      enum aaa-at-autocommand {
        value 15;
        description
          "Automatic command to run at startup";
      }
      enum aaa-at-autocommand-ip-prompt {
        value 16;
        description
          "Automatic command to run at IP prompt";
      }
      enum aaa-at-authen-status {
        value 17;
        description
          "Indicates the authenticated status";
      }
      enum aaa-at-authen-method {
        value 18;
        description
          "Indicates the negotiated authentication protocol";
      }
      enum aaa-at-authen-strength {
        value 19;
        description
          "Indicates strength of authentication protocol [128 bit | 40 bit..]";
      }
      enum aaa-at-callback {
        value 20;
        description
          "Callback dial string";
      }
      enum aaa-at-callback-line {
        value 21;
        description
          "Per-username line for callback";
      }
      enum aaa-at-callback-no-verify {
        value 22;
        description
          "Does not require authentication after callback";
      }
      enum aaa-at-callback-rotary {
        value 23;
        description
          "Per-username rotary group for callback";
      }
      enum aaa-at-call-drops {
        value 24;
        description
          "Call drop rate";
      }
      enum aaa-at-call-type {
        value 25;
        description
          "Call type";
      }
      enum aaa-at-force-local-chap {
        value 26;
        description
          "Force local CHAP flag";
      }
      enum aaa-at-call-origin-endpoint {
        value 27;
        description
          "The leg-2 endpoint value";
      }
      enum aaa-at-call-origin-endpoint-type {
        value 28;
        description
          "The leg-2 endpoint info type";
      }
      enum aaa-at-chap-challenge {
        value 29;
        description
          "CHAP challenge";
      }
      enum aaa-at-chap-id {
        value 30;
        description
          "CHAP id";
      }
      enum aaa-at-chap-response {
        value 31;
        description
          "CHAP response";
      }
      enum aaa-at-chap-authen-user {
        value 32;
        description
          "CHAP authentication user key";
      }
      enum aaa-at-connect-info {
        value 33;
        description
          "Nature of the connection";
      }
      enum aaa-at-user-data {
        value 34;
        description
          "User data";
      }
      enum aaa-at-server-data {
        value 35;
        description
          "Server data";
      }
      enum aaa-at-clid {
        value 36;
        description
          "Calling station identifier";
      }
      enum aaa-at-formatted-clid {
        value 37;
        description
          "Formatted calling station identifier";
      }
      enum aaa-at-circuit-id {
        value 38;
        description
          "Circuit-Id Tag";
      }
      enum aaa-at-remote-id {
        value 39;
        description
          "Remote-Id Tag";
      }
      enum aaa-at-vendor-class-id {
        value 40;
        description
          "Vendor-Class-Id Tag";
      }
      enum aaa-at-caller-type-of-num {
        value 41;
        description
          "ISDN caller type of number";
      }
      enum aaa-at-clid-mac-addr {
        value 42;
        description
          "The MAC address from where the call came";
      }
      enum aaa-at-session-limit {
        value 43;
        description
          "Session limit per port";
      }
      enum aaa-at-mac-address {
        value 44;
        description
          "MAC address of client";
      }
      enum aaa-at-epd-peer-version {
        value 45;
        description
          "EPD peer version";
      }
      enum aaa-at-epd-peer-mode {
        value 46;
        description
          "EPD peer mode";
      }
      enum aaa-at-epd-peer-keepalive {
        value 47;
        description
          "EPD peer keepalive";
      }
      enum aaa-at-epd-peer-inform-owner-on-pull {
        value 48;
        description
          "EPD peer inform Owner On Pull";
      }
      enum aaa-at-epd-acct-flows {
        value 49;
        description
          "Number of EPD accounting flows";
      }
      enum aaa-at-epd-acct-flows-duration {
        value 50;
        description
          "EPD accounting flow duration";
      }
      enum aaa-at-actual-rate-up {
        value 51;
        description
          "Actual Data-Rate Upstream";
      }
      enum aaa-at-actual-rate-down {
        value 52;
        description
          "Actual Data-Rate Downstream";
      }
      enum aaa-at-min-rate-up {
        value 53;
        description
          "Minimum Data-Rate Upstream";
      }
      enum aaa-at-min-rate-down {
        value 54;
        description
          "Minimum Data-Rate Downstream";
      }
      enum aaa-at-attainable-rate-up {
        value 55;
        description
          "Attainable Data-Rate Upstream";
      }
      enum aaa-at-attainable-rate-down {
        value 56;
        description
          "Attainable Data-Rate Downstream";
      }
      enum aaa-at-max-rate-up {
        value 57;
        description
          "Maximum Data-Rate Upstream";
      }
      enum aaa-at-max-rate-down {
        value 58;
        description
          "Maximum Data-Rate Downstream";
      }
      enum aaa-at-min-rate-up-lp {
        value 59;
        description
          "Minimum Data-Rate Upstream-Low-Power";
      }
      enum aaa-at-min-rate-down-lp {
        value 60;
        description
          "Minimum Data-Rate Downstream Low Power";
      }
      enum aaa-at-max-inter-delay-up {
        value 61;
        description
          "Maximum Interleaving Delay Upstream";
      }
      enum aaa-at-max-inter-delay-down {
        value 62;
        description
          "Maximum Interleaving Delay Downstream";
      }
      enum aaa-at-actual-inter-delay-up {
        value 63;
        description
          "Actual Interleaving Delay Upstream";
      }
      enum aaa-at-actual-inter-delay-down {
        value 64;
        description
          "Actual Interleaving Delay Downstream";
      }
      enum aaa-at-iwf-tag {
        value 65;
        description
          "Interworking Functionality Tag";
      }
      enum aaa-at-access-loop-encapsulation {
        value 66;
        description
          "Access Loop Encapsulation";
      }
      enum aaa-at-epd-reporting-reason {
        value 67;
        description
          "EPD reporting reason";
      }
      enum aaa-at-dsl-type {
        value 68;
        description
          "DSL type";
      }
      enum aaa-at-ancp-line-rate {
        value 69;
        description
          "Line rate of Digital Subscriber Line Access Multiplex client";
      }
      enum aaa-at-data-rate-kbps {
        value 70;
        description
          "Rate of data received in kbps";
      }
      enum aaa-at-xmit-rate-kbps {
        value 71;
        description
          "The kbps rate which packets are being sent to the user";
      }
      enum aaa-at-ancp-access-loop-cir-id {
        value 72;
        description
          "Access Node Control Protocol access loop cir-id";
      }
      enum aaa-at-command {
        value 73;
        description
          "Command";
      }
      enum aaa-at-command-arg {
        value 74;
        description
          "Command argument";
      }
      enum aaa-at-conn-prog {
        value 75;
        description
          "Connection progress";
      }
      enum aaa-at-connect-rx-speed {
        value 76;
        description
          "Connection RX speed";
      }
      enum aaa-at-connect-tx-speed {
        value 77;
        description
          "Connection TX speed";
      }
      enum aaa-at-data-rate {
        value 78;
        description
          "Rate of data received";
      }
      enum aaa-at-data-service {
        value 79;
        description
          "Type of data service for outgoing call";
      }
      enum aaa-at-dial-number {
        value 80;
        description
          "Number to dial for outgoing call";
      }
      enum aaa-at-trunkgroup {
        value 81;
        description
          "The trunk-group to be used for the outgoing call";
      }
      enum aaa-at-dnis {
        value 82;
        description
          "Destination station identifier";
      }
      enum aaa-at-dns-server {
        value 83;
        description
          "Primary and Secondary DNS Servers";
      }
      enum aaa-at-auto-update {
        value 84;
        description
          "Client Url Revision";
      }
      enum aaa-at-dns-server-primary {
        value 85;
        description
          "Primary DNS server address";
      }
      enum aaa-at-dns-server-secondary {
        value 86;
        description
          "Secondary DNS server address";
      }
      enum aaa-at-eap-message {
        value 87;
        description
          "Extended Access Protocol (EAP) packet encapsulation";
      }
      enum aaa-at-eap-session-id {
        value 88;
        description
          "EAP Session ID for CAK name derivation";
      }
      enum aaa-at-dns-client-assign {
        value 89;
        description
          "Assign client with DNS attributes";
      }
      enum aaa-at-email-server-ack-flag {
        value 90;
        description
          "Email server ack flag";
      }
      enum aaa-at-event {
        value 91;
        description
          "Specifies the event requested by the NAD";
      }
      enum aaa-at-reason {
        value 92;
        description
          "Reason information";
      }
      enum aaa-at-fax-account-id-origin {
        value 93;
        description
          "Fax account id origin";
      }
      enum aaa-at-fax-auth-status {
        value 94;
        description
          "Fax authentication status";
      }
      enum aaa-at-fax-connect-speed {
        value 95;
        description
          "Fax connect speed";
      }
      enum aaa-at-fax-cover-page-flag {
        value 96;
        description
          "Fax cover page flag";
      }
      enum aaa-at-fax-dsn-address {
        value 97;
        description
          "Fax Delivery Status Notification address";
      }
      enum aaa-at-fax-dsn-flag {
        value 98;
        description
          "Flag for fax Delivery Status Notification";
      }
      enum aaa-at-fax-mdn-address {
        value 99;
        description
          "Fax Message Disposition Notifications address";
      }
      enum aaa-at-fax-mdn-flag {
        value 100;
        description
          "Fax Message Disposition Notifications flag";
      }
      enum aaa-at-fax-msg-id {
        value 101;
        description
          "Fax message ID";
      }
      enum aaa-at-fax-modem-time {
        value 102;
        description
          "Fax modem time";
      }
      enum aaa-at-fax-pages {
        value 103;
        description
          "Fax pages";
      }
      enum aaa-at-fax-abort-cause {
        value 104;
        description
          "Fax abort cause";
      }
      enum aaa-at-email-server-address {
        value 105;
        description
          "Email server address";
      }
      enum aaa-at-fax-process-abort-flag {
        value 106;
        description
          "Fax process abort flag";
      }
      enum aaa-at-fax-recipient-count {
        value 107;
        description
          "Fax recipient count";
      }
      enum aaa-at-fltsv-cache-refresh {
        value 108;
        description
          "Filter cache timer";
      }
      enum aaa-at-fltsv-cache-time {
        value 109;
        description
          "Time which filter profile should remain cached";
      }
      enum aaa-at-fltsv-required {
        value 110;
        description
          "Requires a filter profile";
      }
      enum aaa-at-framed-protocol {
        value 111;
        description
          "The framed protocol";
      }
      enum aaa-at-framed-mtu {
        value 112;
        description
          "The MTU available on the link";
      }
      enum aaa-at-force-56 {
        value 113;
        description
          "Whether the NAS should use only 56 KB";
      }
      enum aaa-at-gateway-id {
        value 114;
        description
          "Gateway ID";
      }
      enum aaa-at-ggsn-grouped {
        value 115;
        description
          "Grouped Gateway GPRS Support Node Attributes";
      }
      enum aaa-at-h323-billing-model {
        value 116;
        description
          "H323 billing model";
      }
      enum aaa-at-h323-call-origin {
        value 117;
        description
          "H323 call origin";
      }
      enum aaa-at-h323-call-type {
        value 118;
        description
          "H323 call type";
      }
      enum aaa-at-h323-conf-id {
        value 119;
        description
          "H323 conference ID";
      }
      enum aaa-at-h323-connect-time {
        value 120;
        description
          "H323 connection time";
      }
      enum aaa-at-h323-credit-amount {
        value 121;
        description
          "H323 credit amount";
      }
      enum aaa-at-h323-credit-time {
        value 122;
        description
          "H323 credit time";
      }
      enum aaa-at-h323-currency-type {
        value 123;
        description
          "H323 currency type";
      }
      enum aaa-at-h323-disconnect-cause {
        value 124;
        description
          "H323 disconnect cause";
      }
      enum aaa-at-h323-disconnect-time {
        value 125;
        description
          "H323 disconnect time";
      }
      enum aaa-at-h323-gw-id {
        value 126;
        description
          "H323 gateway ID";
      }
      enum aaa-at-h323-incoming-conf-id {
        value 127;
        description
          "H323 incoming conference ID";
      }
      enum aaa-at-h323-ivr-in {
        value 128;
        description
          "H323 Interactive Voice Response in";
      }
      enum aaa-at-h323-ivr-out {
        value 129;
        description
          "H323 Interactive Voice Response out";
      }
      enum aaa-at-h323-preferred-lang {
        value 130;
        description
          "H323 preferred language";
      }
      enum aaa-at-h323-prompt-id {
        value 131;
        description
          "H323 prompt ID";
      }
      enum aaa-at-h323-redirect-ip-address {
        value 132;
        description
          "H323 redirect ip address";
      }
      enum aaa-at-h323-redirect-number {
        value 133;
        description
          "H323 redirect number";
      }
      enum aaa-at-h323-remote-address {
        value 134;
        description
          "H323 remote address";
      }
      enum aaa-at-h323-remote-id {
        value 135;
        description
          "H323 remote ID";
      }
      enum aaa-at-h323-return-code {
        value 136;
        description
          "H323 return code";
      }
      enum aaa-at-h323-setup-time {
        value 137;
        description
          "H323 setup time";
      }
      enum aaa-at-h323-time-and-day {
        value 138;
        description
          "H323 time and day";
      }
      enum aaa-at-h323-voice-quality {
        value 139;
        description
          "H323 voice quality";
      }
      enum aaa-at-h323-subscriber {
        value 140;
        description
          "H323 subscriber";
      }
      enum aaa-at-release-source {
        value 141;
        description
          "Originator of the call release";
      }
      enum aaa-at-idle-timeout {
        value 142;
        description
          "Idle seconds before disconnect";
      }
      enum aaa-at-call-in-acl {
        value 143;
        description
          "A call ingress access list";
      }
      enum aaa-at-in-acl {
        value 144;
        description
          "An ingress access list";
      }
      enum aaa-at-input-giga-words {
        value 145;
        description
          "Number of times that Acct-Input-Octets has wrapped";
      }
      enum aaa-at-input-octets {
        value 146;
        description
          "Bytes received from a port";
      }
      enum aaa-at-input-packets {
        value 147;
        description
          "Packets received from a port";
      }
      enum aaa-at-input-giga-words-ipv6 {
        value 148;
        description
          "Number of times that Acct-Input-Octets-IPv6 has wrapped";
      }
      enum aaa-at-input-octets-ipv6 {
        value 149;
        description
          "Bytes received from a port for IPv6 sessions";
      }
      enum aaa-at-input-packets-ipv6 {
        value 150;
        description
          "IPv6 Packets received from a port";
      }
      enum aaa-at-tariff-input-giga-words {
        value 151;
        description
          "Number of times that tariff-input-octets has wrapped";
      }
      enum aaa-at-tariff-input-octets {
        value 152;
        description
          "Per Tariff bytes received for a session";
      }
      enum aaa-at-tariff-input-packets {
        value 153;
        description
          "Per Tariff Packets received for a session";
      }
      enum aaa-at-tariff-input-giga-words-ipv6 {
        value 154;
        description
          "Number of times that tariff-input-octets-ipv6 has wrapped";
      }
      enum aaa-at-tariff-input-octets-ipv6 {
        value 155;
        description
          "Per tariff IPv6 bytes received for a session";
      }
      enum aaa-at-tariff-input-packets-ipv6 {
        value 156;
        description
          "Per Tariff IPv6 Packets received for a session";
      }
      enum aaa-at-tariff-output-giga-words {
        value 157;
        description
          "Number of times that tariff-output-octets has wrapped";
      }
      enum aaa-at-tariff-output-octets {
        value 158;
        description
          "Per Tariff bytes sent for a session";
      }
      enum aaa-at-tariff-output-packets {
        value 159;
        description
          "Per Tariff Packets sent for a session";
      }
      enum aaa-at-tariff-output-giga-words-ipv6 {
        value 160;
        description
          "Number of times that tariff-output-octets-ipv6 has wrapped";
      }
      enum aaa-at-tariff-output-octets-ipv6 {
        value 161;
        description
          "Per tariff IPv6 bytes sent for a session";
      }
      enum aaa-at-tariff-output-packets-ipv6 {
        value 162;
        description
          "Per Tariff IPv6 Packets sent for a session";
      }
      enum aaa-at-idmgr-data {
        value 163;
        description
          "ID MGR data";
      }
      enum aaa-at-idmgr-svc-key {
        value 164;
        description
          "Key to identify a service; session-handle + service-name";
      }
      enum aaa-at-pppoe-unique-key {
        value 165;
        description
          "Unique key identifier for pppoe session";
      }
      enum aaa-at-session-guid {
        value 166;
        description
          "Global identifier for a session";
      }
      enum aaa-at-nas-identifier {
        value 167;
        description
          "A string identifying the NAS sending the Access-Request";
      }
      enum aaa-at-charged-units {
        value 168;
        description
          "Charged units";
      }
      enum aaa-at-disconnect-text {
        value 169;
        description
          "Disconnect text";
      }
      enum aaa-at-info-type {
        value 170;
        description
          "Information type";
      }
      enum aaa-at-logical-if-index {
        value 171;
        description
          "Interface from which call was made";
      }
      enum aaa-at-peer-address {
        value 172;
        description
          "The number this call was connected to";
      }
      enum aaa-at-peer-id {
        value 173;
        description
          "Id value of the peer table entry this call was made to";
      }
      enum aaa-at-peer-if-index {
        value 174;
        description
          "Index value of peer table entry the call was made to";
      }
      enum aaa-at-acom-level {
        value 175;
        description
          "Telephony VSA level";
      }
      enum aaa-at-tx-duration {
        value 176;
        description
          "Duration of transmit path open from this peer to gateway";
      }
      enum aaa-at-voice-tx-duration {
        value 177;
        description
          "Duration of voice packets transmitted";
      }
      enum aaa-at-noise-level {
        value 178;
        description
          "The average noise level in dBm";
      }
      enum aaa-at-codec-bytes {
        value 179;
        description
          "Codec bytes";
      }
      enum aaa-at-coder-type-rate {
        value 180;
        description
          "Coder type rate";
      }
      enum aaa-at-early-packets {
        value 181;
        description
          "Packets received too early to store in jitter buffer";
      }
      enum aaa-at-late-packets {
        value 182;
        description
          "Packets arrive too late for CODEC";
      }
      enum aaa-at-lost-packets {
        value 183;
        description
          "Number of packets lost";
      }
      enum aaa-at-gapfill-w-itpol {
        value 184;
        description
          "Gap fill with interpolation";
      }
      enum aaa-at-gapfill-w-predt {
        value 185;
        description
          "Gap fill with prediction";
      }
      enum aaa-at-gapfill-w-rdncy {
        value 186;
        description
          "Gap fill with redundancy";
      }
      enum aaa-at-gapfill-w-silen {
        value 187;
        description
          "Gap fill with silence";
      }
      enum aaa-at-lowater-playout-delay {
        value 188;
        description
          "Low-water play-out delay";
      }
      enum aaa-at-hiwater-playout-delay {
        value 189;
        description
          "Hi-water play-out delay";
      }
      enum aaa-at-ontime-rv-playout {
        value 190;
        description
          "Duration of a call play-out since data received on time";
      }
      enum aaa-at-receive-delay {
        value 191;
        description
          "Average voice play-out FIFO-delay plus decoder-delay";
      }
      enum aaa-at-round-trip-delay {
        value 192;
        description
          "The voice packet round trip delay";
      }
      enum aaa-at-remote-udp-port {
        value 193;
        description
          "Remote system UDP listener port";
      }
      enum aaa-at-session-protocol {
        value 194;
        description
          "Session protocol used for Internet call through IP";
      }
      enum aaa-at-vad-enable {
        value 195;
        description
          "Whether or not Voice Activity Detection enabled";
      }
      enum aaa-at-in-area {
        value 196;
        description
          "Zone ID for H323 call or originating domain for SIP";
      }
      enum aaa-at-out-area {
        value 197;
        description
          "Zone ID for H323 call or terminating domain for SIP";
      }
      enum aaa-at-in-if-desc {
        value 198;
        description
          "Description field of voice port for a incoming call";
      }
      enum aaa-at-out-if-desc {
        value 199;
        description
          "Description field of voice port for a outgoing call";
      }
      enum aaa-at-service-descriptor {
        value 200;
        description
          "Routing and accounting information from the route server";
      }
      enum aaa-at-in-carrier-id {
        value 201;
        description
          "The incoming carrier identifier";
      }
      enum aaa-at-out-carrier-id {
        value 202;
        description
          "The outgoing carrier identifier";
      }
      enum aaa-at-in-tg-label {
        value 203;
        description
          "The incoming trunk group label";
      }
      enum aaa-at-out-tg-label {
        value 204;
        description
          "The outgoing trunk group label";
      }
      enum aaa-at-alert-time {
        value 205;
        description
          "Alert time point";
      }
      enum aaa-at-gw-rxd-cdn {
        value 206;
        description
          "Gateway received called number";
      }
      enum aaa-at-gw-rxd-cgn {
        value 207;
        description
          "Gateway received calling number";
      }
      enum aaa-at-gw-rxd-ocn {
        value 208;
        description
          "Gateway received original called number";
      }
      enum aaa-at-gw-rxd-cnn {
        value 209;
        description
          "Gateway received alias called number";
      }
      enum aaa-at-gw-rxd-rdn {
        value 210;
        description
          "Gateway received redirecting number";
      }
      enum aaa-at-final-cdn {
        value 211;
        description
          "Gateway sent final translated called number";
      }
      enum aaa-at-final-cgn {
        value 212;
        description
          "Gateway sent final translated calling number";
      }
      enum aaa-at-final-rdn {
        value 213;
        description
          "Gateway sent final translated redirecting number";
      }
      enum aaa-at-gk-xlated-cdn {
        value 214;
        description
          "Gatekeeper sent e164 alias called number";
      }
      enum aaa-at-gk-xlated-cgn {
        value 215;
        description
          "Gatekeeper sent e164 alias calling number";
      }
      enum aaa-at-gw-coll-cdn {
        value 216;
        description
          "Gateway appl collected called number";
      }
      enum aaa-at-orig-cic {
        value 217;
        description
          "Gateway sent final originating translated called number";
      }
      enum aaa-at-term-cic {
        value 218;
        description
          "Gateway sent final terminating translated called number";
      }
      enum aaa-at-termination-action {
        value 219;
        description
          "An indication for termination";
      }
      enum aaa-at-aaa-unique-id {
        value 220;
        description
          "The AAA unique id";
      }
      enum aaa-at-interface {
        value 221;
        description
          "Name of the interface that is in use";
      }
      enum aaa-at-interface-config {
        value 222;
        description
          "Configuration commands for an interface";
      }
      enum aaa-at-interface-parent {
        value 223;
        description
          "Parent interface that is in use";
      }
      enum aaa-at-interface-parent-type {
        value 224;
        description
          "Type of the parent interface that is in use";
      }
      enum aaa-at-interface-type {
        value 225;
        description
          "Type of the interface that is in use";
      }
      enum aaa-at-interim-interval {
        value 226;
        description
          "Accounting interim interval";
      }
      enum aaa-at-ip-addresses {
        value 227;
        description
          "IP addresses of the home gateway";
      }
      enum aaa-at-ip-address-limits {
        value 228;
        description
          "Session limits for IP addresses of the home gateway";
      }
      enum aaa-at-key-exchange {
        value 229;
        description
          "Key exchange";
      }
      enum aaa-at-vpdn-template {
        value 230;
        description
          "Name of vpdn-template to use";
      }
      enum aaa-at-l2f-cm-retransmit-retries {
        value 231;
        description
          "Number of retries before tearing down a Layer-2 Forwarding tunnel";
      }
      enum aaa-at-l2f-init-retransmit-retries {
        value 232;
        description
          "Layer-2 Forwarding initial retries before placing HGW on busy list";
      }
      enum aaa-at-l2f-tunnel-timeout-setup {
        value 233;
        description
          "Time permitted to setup a Layer-2 Forwarding tunnel";
      }
      enum aaa-at-l2f-busy-list-timeout {
        value 234;
        description
          "How long an address is on the Layer-2 Forwarding busy list";
      }
      enum aaa-at-l2tp-busy-disconnect {
        value 235;
        description
          "L2TP busy disconnect";
      }
      enum aaa-at-l2tp-framing-cap {
        value 236;
        description
          "L2TP framing capabilities";
      }
      enum aaa-at-l2tp-bearer-cap {
        value 237;
        description
          "L2TP bearer capabilities";
      }
      enum aaa-at-l2tp-cm-local-window-size {
        value 238;
        description
          "L2TP CM local window size";
      }
      enum aaa-at-l2tp-cm-max-timeout {
        value 239;
        description
          "L2TP CM max timeout";
      }
      enum aaa-at-l2tp-cm-min-timeout {
        value 240;
        description
          "L2TP CM min timeout";
      }
      enum aaa-at-l2tp-init-max-timeout {
        value 241;
        description
          "Maximum Start Control Connection Request timeout";
      }
      enum aaa-at-l2tp-init-min-timeout {
        value 242;
        description
          "Minimum Start Control Connection Request timeout";
      }
      enum aaa-at-l2tp-init-retransmit-retries {
        value 243;
        description
          "Start Control Connection Request retries before placing L2TP Network Server on busy list";
      }
      enum aaa-at-l2tp-busy-list-timeout {
        value 244;
        description
          "How long an address is on the L2TP busy list";
      }
      enum aaa-at-l2tp-drop-out-of-order {
        value 245;
        description
          "L2TP drop out of order";
      }
      enum aaa-at-l2tp-hello-interval {
        value 246;
        description
          "L2TP hello interval";
      }
      enum aaa-at-l2tp-hidden-avp {
        value 247;
        description
          "L2TP hidden Attribute-Value Pair";
      }
      enum aaa-at-l2tp-rx-speed {
        value 248;
        description
          "L2TP configurable rx speed";
      }
      enum aaa-at-l2tp-tx-speed {
        value 249;
        description
          "L2TP configurable tx speed";
      }
      enum aaa-at-l2tp-ignore-connect-speed {
        value 250;
        description
          "L2TP ignore Attribute-Value Pair 24";
      }
      enum aaa-at-l2tp-max-ato {
        value 251;
        description
          "L2TP max Adaptive Time-Out";
      }
      enum aaa-at-l2tp-no-session-timeout {
        value 252;
        description
          "L2TP no session timeout";
      }
      enum aaa-at-l2tp-relay-group-name {
        value 253;
        description
          "PPPoE bba-group to be used for relay";
      }
      enum aaa-at-l2tp-queue-size {
        value 254;
        description
          "L2TP queue size";
      }
      enum aaa-at-l2tp-receive-window {
        value 255;
        description
          "L2TP receive window";
      }
      enum aaa-at-l2tp-cm-retransmit-retries {
        value 256;
        description
          "L2TP CM retransmit retries";
      }
      enum aaa-at-l2tp-sequencing {
        value 257;
        description
          "L2TP sequencing";
      }
      enum aaa-at-l2tp-static-rtt {
        value 258;
        description
          "L2TP static RTT";
      }
      enum aaa-at-l2tp-tunnel-authen {
        value 259;
        description
          "L2TP tunnel authentication";
      }
      enum aaa-at-l2tp-tunnel-acct {
        value 260;
        description
          "L2TP tunnel accounting";
      }
      enum aaa-at-l2tp-tunnel-password {
        value 261;
        description
          "L2TP tunnel password";
      }
      enum aaa-at-l2tp-tunnel-timeout-setup {
        value 262;
        description
          "L2TP tunnel timeout setup";
      }
      enum aaa-at-l2tp-clid-mask-method {
        value 263;
        description
          "Method to mask CLID in L2TP Attribute-Value Pair 22 of Incoming Call Request";
      }
      enum aaa-at-l2tp-udp-checksum {
        value 264;
        description
          "L2TP UDP checksum";
      }
      enum aaa-at-l2tp-security-ip-address-check {
        value 265;
        description
          "LAC to verify outgoing/incoming IP to/from L2TP Network Server";
      }
      enum aaa-at-l2tp-security-required {
        value 266;
        description
          "Security required for L2TP tunnel";
      }
      enum aaa-at-l2tp-security-teardown-conn {
        value 267;
        description
          "IKE phase 1 Security Association on L2TP tunnel teardown";
      }
      enum aaa-at-l2tp-resync-packets {
        value 268;
        description
          "L2TP tunnel resync packets";
      }
      enum aaa-at-link-compression {
        value 269;
        description
          "Link compression";
      }
      enum aaa-at-map-class {
        value 270;
        description
          "Map class for outgoing call";
      }
      enum aaa-at-epd-error-cause {
        value 271;
        description
          "EPD error cause";
      }
      enum aaa-at-error-cause {
        value 272;
        description
          "Dynamic-author error cause";
      }
      enum aaa-at-message {
        value 273;
        description
          "A reply message for the user";
      }
      enum aaa-at-message-authenticator {
        value 274;
        description
          "Used to sign Access-Requests to prevent spoof";
      }
      enum aaa-at-mlp-links-current {
        value 275;
        description
          "Current number of multilink links";
      }
      enum aaa-at-mlp-links-max {
        value 276;
        description
          "Maximum allowable links in multilink call";
      }
      enum aaa-at-mlp-session-id {
        value 277;
        description
          "Multilink session identifier";
      }
      enum aaa-at-modem-on-hold {
        value 278;
        description
          "Per-call configuration of V.92 modem on hold";
      }
      enum aaa-at-modem-script {
        value 279;
        description
          "Chat scripts for session";
      }
      enum aaa-at-mobile-ip-spi {
        value 280;
        description
          "Mobile IP Security Association";
      }
      enum aaa-at-mobile-ip-stat-ip-pool {
        value 281;
        description
          "Mobile IP static IP pool";
      }
      enum aaa-at-mobile-ip-stat-adr {
        value 282;
        description
          "Mobile IP static IP address";
      }
      enum aaa-at-mobile-ip-dyn-pool {
        value 283;
        description
          "Mobile IP dynamic IP pool";
      }
      enum aaa-at-mobile-ip-dyn-adr {
        value 284;
        description
          "Mobile IP dynamic address";
      }
      enum aaa-at-mobile-ip-stat-pool-defenition {
        value 285;
        description
          "Mobile IP static address authorization";
      }
      enum aaa-at-mobile-ip-stat-pool {
        value 286;
        description
          "IP addresses for mobile-ip static address authorization";
      }
      enum aaa-at-mobileip-rf-swact {
        value 287;
        description
          "Mobile IP RF Switch of Activity";
      }
      enum aaa-at-dhcp-server {
        value 288;
        description
          "DHCP server address";
      }
      enum aaa-at-mobile-ip-dhcp-server {
        value 289;
        description
          "Mobile IP DHCP server";
      }
      enum aaa-at-dhcp-class {
        value 290;
        description
          "DHCP class name";
      }
      enum aaa-at-config-source-dpm {
        value 291;
        description
          "Configuration sourced by DHCP Policy Module";
      }
      enum aaa-at-multicast-client {
        value 292;
        description
          "Multicast client";
      }
      enum aaa-at-multicast-rlimit {
        value 293;
        description
          "Multicast rate limit";
      }
      enum aaa-at-multilink-idle {
        value 294;
        description
          "Multilink idle threshold";
      }
      enum aaa-at-multilink-load {
        value 295;
        description
          "Multilink load threshold";
      }
      enum aaa-at-multilink-max {
        value 296;
        description
          "Multilink maximum links";
      }
      enum aaa-at-multilink-min {
        value 297;
        description
          "Multilink minimum links";
      }
      enum aaa-at-multilink-negotiate {
        value 298;
        description
          "Multilink negotiate";
      }
      enum aaa-at-nas-description {
        value 299;
        description
          "NAS description";
      }
      enum aaa-at-nbns-primary-server {
        value 300;
        description
          "Primary NetBIOS Name Server";
      }
      enum aaa-at-nbns-secondary-server {
        value 301;
        description
          "Secondary NetBIOS Name Server";
      }
      enum aaa-at-num-sessions {
        value 302;
        description
          "Number of sessions";
      }
      enum aaa-at-ipv4-netmask {
        value 303;
        description
          "The IP netmask for the user";
      }
      enum aaa-at-no-escape {
        value 304;
        description
          "No escape";
      }
      enum aaa-at-no-hangup {
        value 305;
        description
          "No hangup";
      }
      enum aaa-at-old-password {
        value 306;
        description
          "The old password for a change password protocol";
      }
      enum aaa-at-old-prompts {
        value 307;
        description
          "The old prompt for a change password protocol";
      }
      enum aaa-at-call-out-acl {
        value 308;
        description
          "A call egress access list";
      }
      enum aaa-at-output-giga-words {
        value 309;
        description
          "Number of times that Acct-Output-Octets has wrapped";
      }
      enum aaa-at-out-acl {
        value 310;
        description
          "An egress access list";
      }
      enum aaa-at-output-octets {
        value 311;
        description
          "The number of bytes sent to a port";
      }
      enum aaa-at-output-packets {
        value 312;
        description
          "The number of packets sent to a port";
      }
      enum aaa-at-output-giga-words-ipv6 {
        value 313;
        description
          "Number of times that Acct-Output-Octets-ipv6 has wrapped";
      }
      enum aaa-at-output-octets-ipv6 {
        value 314;
        description
          "The number of bytes sent to a port in an IPv6 session";
      }
      enum aaa-at-output-packets-ipv6 {
        value 315;
        description
          "The number of IPv6 packets sent to a port";
      }
      enum aaa-at-ip-port-bundle-hdl {
        value 316;
        description
          "Unique identifier for a L4 redirect session";
      }
      enum aaa-at-nativeip-vrf {
        value 317;
        description
          "combination of native IP address and VRF";
      }
      enum aaa-at-domainip-vrf {
        value 318;
        description
          "combination of domain IP address and VRF";
      }
      enum aaa-at-system-script {
        value 319;
        description
          "System script for a particular session";
      }
      enum aaa-at-user-password {
        value 320;
        description
          "The password of the user to be authenticated";
      }
      enum aaa-at-pool-definition {
        value 321;
        description
          "IP pool definition";
      }
      enum aaa-at-pool-addr {
        value 322;
        description
          "Subnet from AR to be used by ODAP for DHCP leases";
      }
      enum aaa-at-pool-mask {
        value 323;
        description
          "Subnet mask to/from AR to specify subnet size";
      }
      enum aaa-at-pool-timeout {
        value 324;
        description
          "IP Pool timeout";
      }
      enum aaa-at-port {
        value 325;
        description
          "The port for reverse-access authorization";
      }
      enum aaa-at-port-limit {
        value 326;
        description
          "Number of ports that can be allocated to this call";
      }
      enum aaa-at-port-used {
        value 327;
        description
          "Port used";
      }
      enum aaa-at-ppp-vj-slot {
        value 328;
        description
          "PPP VJ slot compression";
      }
      enum aaa-at-ppp-disc-cause {
        value 329;
        description
          "PPP disconnect cause";
      }
      enum aaa-at-presession-octets-in {
        value 330;
        description
          "The bytes sent from the station before authentication";
      }
      enum aaa-at-presession-octets-out {
        value 331;
        description
          "The bytes sent to the station before authentication";
      }
      enum aaa-at-presession-packets-in {
        value 332;
        description
          "The packets sent from the station before authentication";
      }
      enum aaa-at-presession-packets-out {
        value 333;
        description
          "The packets sent to the station before authentication";
      }
      enum aaa-at-presession-time {
        value 334;
        description
          "The seconds a user was connected before authentication";
      }
      enum aaa-at-privilege-level {
        value 335;
        description
          "The privilege level the user has";
      }
      enum aaa-at-view {
        value 336;
        description
          "The view the user has";
      }
      enum aaa-at-protocol {
        value 337;
        description
          "AAA protocol";
      }
      enum aaa-at-proxy-acl {
        value 338;
        description
          "Proxy access list";
      }
      enum aaa-at-auth-required {
        value 339;
        description
          "Further authentication required";
      }
      enum aaa-at-auth-type {
        value 340;
        description
          "Authentication protocol that will be applied to the peer";
      }
      enum aaa-at-wlan-nas-location {
        value 341;
        description
          "Dot11 NAS location";
      }
      enum aaa-at-wlan-algo-type {
        value 342;
        description
          "Dot11 authentication algorithm type";
      }
      enum aaa-at-wlan-vlan-id {
        value 343;
        description
          "Dot11 VLAN identifier";
      }
      enum aaa-at-service-type {
        value 344;
        description
          "Authorization service type";
      }
      enum aaa-at-session-key {
        value 345;
        description
          "Key to encrypt session";
      }
      enum aaa-at-service-set-id {
        value 346;
        description
          "Dot11 Service Set ID";
      }
      enum aaa-at-aironet-extention {
        value 347;
        description
          "Dot11 Aironet Admin Capabilities";
      }
      enum aaa-at-modem-service {
        value 348;
        description
          "Pre-auth modem service";
      }
      enum aaa-at-redirect-number {
        value 349;
        description
          "The 800 number the user called";
      }
      enum aaa-at-reload-user {
        value 350;
        description
          "The name of user issuing the reload command";
      }
      enum aaa-at-reload-reason {
        value 351;
        description
          "The reason that the box was reloaded or restarted";
      }
      enum aaa-at-ios-version {
        value 352;
        description
          "The IOS version running on the box";
      }
      enum aaa-at-shared-profile-enable {
        value 353;
        description
          "Sharing user profile";
      }
      enum aaa-at-resource-service {
        value 354;
        description
          "Resource service requested from server";
      }
      enum aaa-at-rm-call-count {
        value 355;
        description
          "Resource Manager call count";
      }
      enum aaa-at-rm-call-handle {
        value 356;
        description
          "Resource Manager call handle";
      }
      enum aaa-at-rm-call-treatment {
        value 357;
        description
          "Resource Manager call treatment";
      }
      enum aaa-at-rm-call-type {
        value 358;
        description
          "Resource Manager call type";
      }
      enum aaa-at-rm-cp-name {
        value 359;
        description
          "Resource Manager CP name";
      }
      enum aaa-at-rm-dnis-group-name {
        value 360;
        description
          "Resource Manager DNIS group name";
      }
      enum aaa-at-rm-link-type {
        value 361;
        description
          "Resource Manager link type";
      }
      enum aaa-at-rm-mlp-id {
        value 362;
        description
          "Resource Manager multilink id";
      }
      enum aaa-at-rm-nas-state {
        value 363;
        description
          "Resource Manager NAS state";
      }
      enum aaa-at-rm-port-descripiton {
        value 364;
        description
          "Resource Manager port description";
      }
      enum aaa-at-rm-request-type {
        value 365;
        description
          "Resource Manager request type";
      }
      enum aaa-at-rm-response-code {
        value 366;
        description
          "Resource Manager response code";
      }
      enum aaa-at-rm-rg-application {
        value 367;
        description
          "Resource Manager application";
      }
      enum aaa-at-rm-rg-name {
        value 368;
        description
          "Resource Manager RG name";
      }
      enum aaa-at-rm-rg-service {
        value 369;
        description
          "Resource Manager RG service";
      }
      enum aaa-at-rm-rg-service-name {
        value 370;
        description
          "Resource Manager RG service name";
      }
      enum aaa-at-rm-server-state {
        value 371;
        description
          "Resource Manager server state";
      }
      enum aaa-at-rm-template-name {
        value 372;
        description
          "Resource Manager template name";
      }
      enum aaa-at-rm-version {
        value 373;
        description
          "Resource Manager protocol version";
      }
      enum aaa-at-rm-vpdn-tunnel-status {
        value 374;
        description
          "Resource Manager VPDN tunnel status";
      }
      enum aaa-at-rm-overflow {
        value 375;
        description
          "Resource Manager overflow flag";
      }
      enum aaa-at-negotiated-route {
        value 376;
        description
          "Negotiated Routing information for a user session";
      }
      enum aaa-at-route {
        value 377;
        description
          "Routing information for a user session";
      }
      enum aaa-at-pw-lifetime {
        value 378;
        description
          "Password lifetime";
      }
      enum aaa-at-ppp-vj-slot-comp {
        value 379;
        description
          "PPP VJ slot compression";
      }
      enum aaa-at-route-ip {
        value 380;
        description
          "Route IP address";
      }
      enum aaa-at-tunnel-private-group-id {
        value 381;
        description
          "Tunnel private group id";
      }
      enum aaa-at-state {
        value 382;
        description
          "State information";
      }
      enum aaa-at-class {
        value 383;
        description
          "Class information";
      }
      enum aaa-at-route-filter-in {
        value 384;
        description
          "Route filter IN";
      }
      enum aaa-at-route-filter-out {
        value 385;
        description
          "Route filter OUT";
      }
      enum aaa-at-routing {
        value 386;
        description
          "Framed routing";
      }
      enum aaa-at-sap {
        value 387;
        description
          "Service Access Point";
      }
      enum aaa-at-sap-filter-in {
        value 388;
        description
          "SAP filter IN";
      }
      enum aaa-at-sap-filter-out {
        value 389;
        description
          "SAP filter OUT";
      }
      enum aaa-at-send-auth {
        value 390;
        description
          "Authentication protocol for peer";
      }
      enum aaa-at-send-name {
        value 391;
        description
          "Name of local host dialing out";
      }
      enum aaa-at-tunnel-tos-reflect {
        value 392;
        description
          "Tunnel TOS reflect";
      }
      enum aaa-at-tunnel-tos-setting {
        value 393;
        description
          "Tunnel TOS setting";
      }
      enum aaa-at-tunnel-pmtu {
        value 394;
        description
          "Tunnel Path MTU enabled";
      }
      enum aaa-at-tunnel-renego-lcp {
        value 395;
        description
          "LCP renegotiation option";
      }
      enum aaa-at-tunnel-ip-mtu-adjust {
        value 396;
        description
          "IP MTU adjust flag";
      }
      enum aaa-at-remote-name {
        value 397;
        description
          "Name of remote host to dial-out and pre-auth dial-in to";
      }
      enum aaa-at-send-secret {
        value 398;
        description
          "Name of the secret to be used for authentication";
      }
      enum aaa-at-server-admin-msg {
        value 399;
        description
          "Server admin message";
      }
      enum aaa-at-server-key {
        value 400;
        description
          "Server key";
      }
      enum aaa-at-server-name {
        value 401;
        description
          "Server name";
      }
      enum aaa-at-service {
        value 402;
        description
          "AAA service";
      }
      enum aaa-at-service-name {
        value 403;
        description
          "Service name to be advertised to client";
      }
      enum aaa-at-parent-session-id {
        value 404;
        description
          "Session id of the parent session";
      }
      enum aaa-at-cisco-service-type {
        value 405;
        description
          "Specifies the service requested by the NAD";
      }
      enum aaa-at-cisco-event-type {
        value 406;
        description
          "Specifies the event requested by the NAD";
      }
      enum aaa-at-cisco-auto-smart-port {
        value 407;
        description
          "Specifies the smartport definition to applied";
      }
      enum aaa-at-session-id {
        value 408;
        description
          "The id that identifies a pair of start and stop records";
      }
      enum aaa-at-session-handle {
        value 409;
        description
          "Handle for session";
      }
      enum aaa-at-acct-record-number {
        value 410;
        description
          "Unique number for every accounting record";
      }
      enum aaa-at-acct-record-type {
        value 411;
        description
          "Accounting record type";
      }
      enum aaa-at-string-session-id {
        value 412;
        description
          "The string id that identifies a pair of start and stop records";
      }
      enum aaa-at-subscriber-label {
        value 413;
        description
          "Subscriber Label for Session";
      }
      enum aaa-at-session-time {
        value 414;
        description
          "The number of seconds a session has been active";
      }
      enum aaa-at-override-session-time {
        value 415;
        description
          "Override the number of seconds a session can been active";
      }
      enum aaa-at-vrrs {
        value 416;
        description
          "Redundancy group name, used for VRRS accounting";
      }
      enum aaa-at-source-ip-address {
        value 417;
        description
          "Source IP address";
      }
      enum aaa-at-start-time {
        value 418;
        description
          "The time the session started";
      }
      enum aaa-at-stop-time {
        value 419;
        description
          "The time the session stopped";
      }
      enum aaa-at-sub-policy-in {
        value 420;
        description
          "Upstream policy to be applied on subscriber side";
      }
      enum aaa-at-sub-qos-policy-in {
        value 421;
        description
          "Upstream QoS policy to be applied on subscriber side";
      }
      enum aaa-at-sub-policy-out {
        value 422;
        description
          "Downstream policy to be applied on subscriber side";
      }
      enum aaa-at-sub-qos-policy-out {
        value 423;
        description
          "Downstream QoS policy to be applied on subscriber side";
      }
      enum aaa-at-acct-policy-map {
        value 424;
        description
          "Session accounting policy map";
      }
      enum aaa-at-acct-policy-in {
        value 425;
        description
          "Upstream Accounting Policy for Subscriber";
      }
      enum aaa-at-acct-policy-out {
        value 426;
        description
          "Downstream Accounting Policy for Subscriber";
      }
      enum aaa-at-vc-qos-policy-in {
        value 427;
        description
          "Upstream QoS policy to be applied on a ATM VC";
      }
      enum aaa-at-vc-qos-policy-out {
        value 428;
        description
          "Downstream QoS policy to be applied on a ATM VC";
      }
      enum aaa-at-vc-weight {
        value 429;
        description
          "Weight to be applied on a ATM VC";
      }
      enum aaa-at-vc-q-lwm {
        value 430;
        description
          "Queue depth low watermark to be applied on a ATM VC";
      }
      enum aaa-at-vc-q-hwm {
        value 431;
        description
          "Queue depth high watermark to be applied on a ATM VC";
      }
      enum aaa-at-sub-param-qos-policy-in {
        value 432;
        description
          "Upstream para-metered QoS policy to be applied on subscriber side";
      }
      enum aaa-at-sub-param-qos-policy-out {
        value 433;
        description
          "Downstream para-metered QoS policy to be applied on subscriber side";
      }
      enum aaa-at-terminate-cause {
        value 434;
        description
          "How the session was terminated";
      }
      enum aaa-at-timeout {
        value 435;
        description
          "The maximum number of seconds a user can be connected";
      }
      enum aaa-at-timezone {
        value 436;
        description
          "Timezone";
      }
      enum aaa-at-tunnel-client-endpoint {
        value 437;
        description
          "Tunnel client endpoint";
      }
      enum aaa-at-tunnel-client-auth-id {
        value 438;
        description
          "The authentication name of the tunnel initiator";
      }
      enum aaa-at-tunnel-server-auth-id {
        value 439;
        description
          "The authentication name of the tunnel terminator";
      }
      enum aaa-at-tunnel-medium-type {
        value 440;
        description
          "The protocol over which the tunnel runs";
      }
      enum aaa-at-tunnel-password {
        value 441;
        description
          "Tunnel password to authenticate with tunnel remote end";
      }
      enum aaa-at-tunnel-preference {
        value 442;
        description
          "Tunnel preference of the tunnel settings";
      }
      enum aaa-at-tunnel-server-endpoint {
        value 443;
        description
          "Tunnel server endpoint";
      }
      enum aaa-at-tunnel-connection-id {
        value 444;
        description
          "Tunnel connection id";
      }
      enum aaa-at-event-timestamp {
        value 445;
        description
          "Event timestamp";
      }
      enum aaa-at-tunnel-direction {
        value 446;
        description
          "Tunnel direction";
      }
      enum aaa-at-tunnel-application-type {
        value 447;
        description
          "VPDN tunnel application type";
      }
      enum aaa-at-tunnel-type {
        value 448;
        description
          "Tunnel protocols";
      }
      enum aaa-at-user-max-links {
        value 449;
        description
          "User max-links";
      }
      enum aaa-at-user-name {
        value 450;
        description
          "The name of the user";
      }
      enum aaa-at-vpdn-active-sessions {
        value 451;
        description
          "The number of VPDN active sessions";
      }
      enum aaa-at-v92-info {
        value 452;
        description
          "V.92 modem connection info";
      }
      enum aaa-at-vpdn-logging-info {
        value 453;
        description
          "VPDN logging information";
      }
      enum aaa-at-vpdn-dialout-type {
        value 454;
        description
          "VPDN dial-out type";
      }
      enum aaa-at-vpdn-domain {
        value 455;
        description
          "The name of VPDN domain";
      }
      enum aaa-at-vpdn-group {
        value 456;
        description
          "VPDN group to use";
      }
      enum aaa-at-vpdn-domain-list {
        value 457;
        description
          "List of domains used for VPDN pre-authorization";
      }
      enum aaa-at-vpdn-lac-dialer {
        value 458;
        description
          "VPDN LAC dialer";
      }
      enum aaa-at-vpdn-rotary-group {
        value 459;
        description
          "VPDN dialer rotary group number";
      }
      enum aaa-at-vpdn-pool-member {
        value 460;
        description
          "VPDN dialer pool member";
      }
      enum aaa-at-vpdn-profile {
        value 461;
        description
          "VPDN profile";
      }
      enum aaa-at-vpdn-scal-vtemplate {
        value 462;
        description
          "VPDN virtual template number";
      }
      enum aaa-at-vpdn-vtemplate {
        value 463;
        description
          "Virtual template number for VPDN tunnel authorization";
      }
      enum aaa-at-vpdn-redirect-id {
        value 464;
        description
          "VPDN call redirection identifier string";
      }
      enum aaa-at-sss-policy-directive {
        value 465;
        description
          "Subscriber policy directive type";
      }
      enum aaa-at-sss-subscriber-keepalive {
        value 466;
        description
          "Subscriber session keepalive";
      }
      enum aaa-at-linksec-security-policy {
        value 467;
        description
          "LinkSec security policy type";
      }
      enum aaa-at-proxy-method-list {
        value 468;
        description
          "Method list to proxy Radius packets";
      }
      enum aaa-at-proxy-acct-method-list {
        value 469;
        description
          "Accounting Method list to proxy Radius packets";
      }
      enum aaa-at-sss-service-type {
        value 470;
        description
          "Subscriber profile directive type";
      }
      enum aaa-at-tunnel-vpn-id {
        value 471;
        description
          "Tunnel VPN-ID string";
      }
      enum aaa-at-tunnel-vpn-vrf {
        value 472;
        description
          "Tunnel VPN VRF string";
      }
      enum aaa-at-wins-server {
        value 473;
        description
          "WINS server";
      }
      enum aaa-at-leap-session-key {
        value 474;
        description
          "Key to encrypt LEAP session";
      }
      enum aaa-at-wins-server-primary {
        value 475;
        description
          "WINS server primary";
      }
      enum aaa-at-client-password-local {
        value 476;
        description
          "ikev2 sign password";
      }
      enum aaa-at-client-password-remote {
        value 477;
        description
          "ikev2 verify password";
      }
      enum aaa-at-wins-server-secondary {
        value 478;
        description
          "WINS server secondary";
      }
      enum aaa-at-atm-qos-pcr {
        value 479;
        description
          "ATM Peak Cell Rate";
      }
      enum aaa-at-atm-qos-scr {
        value 480;
        description
          "ATM Sustainable Cell Rate";
      }
      enum aaa-at-xmit-rate {
        value 481;
        description
          "The rate which packets are being sent to the user";
      }
      enum aaa-at-zone-list {
        value 482;
        description
          "Zone list";
      }
      enum aaa-at-login-service {
        value 483;
        description
          "Exec login connection service";
      }
      enum aaa-at-sg-service {
        value 484;
        description
          "SG service";
      }
      enum aaa-at-sg-rule {
        value 485;
        description
          "SG rule";
      }
      enum aaa-at-sg-condition {
        value 486;
        description
          "SG condition";
      }
      enum aaa-at-sg-action {
        value 487;
        description
          "SG action";
      }
      enum aaa-at-ssg-account-info {
        value 488;
        description
          "Service Selection Gateway account info";
      }
      enum aaa-at-ssg-service-info {
        value 489;
        description
          "Service Selection Gateway service info";
      }
      enum aaa-at-ssg-command-code {
        value 490;
        description
          "Service Selection Gateway command code";
      }
      enum aaa-at-ssg-control-info {
        value 491;
        description
          "Service Selection Gateway control info";
      }
      enum aaa-at-ssg-cookie {
        value 492;
        description
          "Service Selection Gateway cookie";
      }
      enum aaa-at-cdma-user-class {
        value 493;
        description
          "CDMA user class";
      }
      enum aaa-at-cdma-realm {
        value 494;
        description
          "CDMA realm";
      }
      enum aaa-at-mobileip-mn-ipaddr {
        value 495;
        description
          "Mobile IP MN Address";
      }
      enum aaa-at-mobileip-mn-lifetime {
        value 496;
        description
          "Mobile IP MN lifetime";
      }
      enum aaa-at-mobileip-mn-flags {
        value 497;
        description
          "Mobile IP MN flags";
      }
      enum aaa-at-mobileip-mn-reject-code {
        value 498;
        description
          "Mobile IP MN Registration reject code";
      }
      enum aaa-at-mobileip-mn-local-timezone {
        value 499;
        description
          "Mobile IP MN Local Timezone Flag";
      }
      enum aaa-at-mobile-ip-prohibited {
        value 500;
        description
          "Is the Mobile prohibited from creating binding";
      }
      enum aaa-at-mobileip-vrf-ha-ip-addr {
        value 501;
        description
          "Mobile IP HA IP Address for VRF";
      }
      enum aaa-at-mobileip-reg-source-addr {
        value 502;
        description
          "Mobile IP Registration Source IP Address";
      }
      enum aaa-at-cdma-preshared-secret {
        value 503;
        description
          "CDMA pre-shared secret";
      }
      enum aaa-at-cdma-container {
        value 504;
        description
          "CDMA container";
      }
      enum aaa-at-cdma-correlation-id {
        value 505;
        description
          "CDMA correlation id";
      }
      enum aaa-at-cdma-always-on {
        value 506;
        description
          "CDMA always-on";
      }
      enum aaa-at-cdma-rn-pdit {
        value 507;
        description
          "CDMA Radio-Access Network Packet Data Inactivity Timer";
      }
      enum aaa-at-cdma-session-continue {
        value 508;
        description
          "CDMA session continue";
      }
      enum aaa-at-cdma-begin-session {
        value 509;
        description
          "CDMA begin session";
      }
      enum aaa-at-cdma-ha-ip-addr {
        value 510;
        description
          "CDMA HA IP address";
      }
      enum aaa-at-cdma-ike-preshared-secret-request {
        value 511;
        description
          "CDMA IPSec pre-shared secret request";
      }
      enum aaa-at-cdma-ipsec-security-level {
        value 512;
        description
          "CDMA IPSec security";
      }
      enum aaa-at-cdma-reverse-tnl-spec {
        value 513;
        description
          "CDMA reverse Tunnel specification";
      }
      enum aaa-at-cdma-pcf-ip-addr {
        value 514;
        description
          "CDMA PCF IP address";
      }
      enum aaa-at-cdma-bs-msc-addr {
        value 515;
        description
          "CDMA BS MSC address";
      }
      enum aaa-at-cdma-user-id {
        value 516;
        description
          "CDMA User id";
      }
      enum aaa-at-cdma-forward-mux {
        value 517;
        description
          "CDMA forward mux";
      }
      enum aaa-at-cdma-reverse-mux {
        value 518;
        description
          "CDMA reverse mux";
      }
      enum aaa-at-cdma-forward-rate {
        value 519;
        description
          "CDMA forward rate";
      }
      enum aaa-at-cdma-reverse-rate {
        value 520;
        description
          "CDMA reverse rate";
      }
      enum aaa-at-cdma-service-option {
        value 521;
        description
          "CDMA service option";
      }
      enum aaa-at-cdma-forward-type {
        value 522;
        description
          "CDMA forward type";
      }
      enum aaa-at-cdma-reverse-type {
        value 523;
        description
          "CDMA reverse type";
      }
      enum aaa-at-cdma-frame-size {
        value 524;
        description
          "CDMA fundamental frame size";
      }
      enum aaa-at-cdma-forward-rc {
        value 525;
        description
          "CDMA forward return code";
      }
      enum aaa-at-cdma-reverse-rc {
        value 526;
        description
          "CDMA reverse return code";
      }
      enum aaa-at-cdma-ip-tech {
        value 527;
        description
          "CDMA ip tech";
      }
      enum aaa-at-cdma-comp-flag {
        value 528;
        description
          "CDMA computational flag";
      }
      enum aaa-at-cdma-reason-ind {
        value 529;
        description
          "CDMA reason ind";
      }
      enum aaa-at-cdma-dcch-frame-size {
        value 530;
        description
          "CDMA Dedicated Control Channel frame size";
      }
      enum aaa-at-cdma-bad-frame-count {
        value 531;
        description
          "CDMA bad frame count";
      }
      enum aaa-at-cdma-active-time {
        value 532;
        description
          "CDMA active time";
      }
      enum aaa-at-cdma-num-active {
        value 533;
        description
          "CDMA num active";
      }
      enum aaa-at-cdma-sdb-input-octets {
        value 534;
        description
          "CDMA short data burst input octets";
      }
      enum aaa-at-cdma-sdb-output-octets {
        value 535;
        description
          "CDMA short data burst output octets";
      }
      enum aaa-at-cdma-numsdb-input {
        value 536;
        description
          "CDMA numeric short data burst input";
      }
      enum aaa-at-cdma-numsdb-output {
        value 537;
        description
          "CDMA numeric short data burst output";
      }
      enum aaa-at-cdma-hdlc-layer-bytes-in {
        value 538;
        description
          "CDMA hdlc layer bytes in";
      }
      enum aaa-at-cdma-moip-inbound {
        value 539;
        description
          "CDMA mobile-ip inbound count";
      }
      enum aaa-at-cdma-moip-outbound {
        value 540;
        description
          "CDMA mobile-ip outbound count";
      }
      enum aaa-at-cdma-last-user-activity {
        value 541;
        description
          "CDMA last user activity";
      }
      enum aaa-at-cdma-ip-qos {
        value 542;
        description
          "CDMA IP QoS";
      }
      enum aaa-at-cdma-airlink-qos {
        value 543;
        description
          "CDMA air-link QoS";
      }
      enum aaa-at-cdma-diff-svc-class-opt {
        value 544;
        description
          "CDMA diff svc class option";
      }
      enum aaa-at-cdma-rp-session-id {
        value 545;
        description
          "CDMA rp session id";
      }
      enum aaa-at-cdma-esn {
        value 546;
        description
          "CDMA ESN";
      }
      enum aaa-at-cdma-mn-ha-spi {
        value 547;
        description
          "CDMA mn ha spi";
      }
      enum aaa-at-cdma-mn-ha-shared-key {
        value 548;
        description
          "CDMA mn ha shared key";
      }
      enum aaa-at-cdma-mn-aaa-removal-ind {
        value 549;
        description
          "CDMA MN AAA Removal Indication";
      }
      enum aaa-at-cdma-sess-term-capability {
        value 550;
        description
          "CDMA session termination capability";
      }
      enum aaa-at-cdma-prepaid-accounting-quota {
        value 551;
        description
          "CDMA prepaid accounting quota";
      }
      enum aaa-at-cdma-prepaid-accounting-capability {
        value 552;
        description
          "CDMA prepaid accounting capability";
      }
      enum aaa-at-cdma-disconnect-reason {
        value 553;
        description
          "CDMA disconnect reason";
      }
      enum aaa-at-cdma-prepaid-tariff-switching {
        value 554;
        description
          "CDMA prepaid tariff switching";
      }
      enum aaa-at-cdma-allowed-differentiated-services-marking {
        value 555;
        description
          "CDMA allowed differentiated service marking";
      }
      enum aaa-at-cdma-forward-pdch-rc {
        value 556;
        description
          "CDMA forward Packet Data Channel return code";
      }
      enum aaa-at-cdma-service-ref-id {
        value 557;
        description
          "CDMA service reference id";
      }
      enum aaa-at-cdma-meid {
        value 558;
        description
          "CDMA mobile equipment identifier";
      }
      enum aaa-at-cdma-dns-server-ip-address {
        value 559;
        description
          "CDMA DNS server IP address";
      }
      enum aaa-at-cdma-dns-update-required {
        value 560;
        description
          "CDMA DNS update required";
      }
      enum aaa-at-cdma-dns-update-capability {
        value 561;
        description
          "CDMA DNS update capability";
      }
      enum aaa-at-cdma-rf-swact {
        value 562;
        description
          "CDMA RF Switch of activity";
      }
      enum aaa-at-verizon-mip-key-update-req {
        value 563;
        description
          "MIP key update req";
      }
      enum aaa-at-verizon-mip-key-data {
        value 564;
        description
          "MIP key data";
      }
      enum aaa-at-verizon-aaa-authenticator {
        value 565;
        description
          "AAA authenticator";
      }
      enum aaa-at-verizon-public-key-invalid {
        value 566;
        description
          "Public key invalid";
      }
      enum aaa-at-login-tcp-port {
        value 567;
        description
          "TCP port used for connection";
      }
      enum aaa-at-login-ip-addr-host {
        value 568;
        description
          "Login IP address host";
      }
      enum aaa-at-login-ipv6-addr-host {
        value 569;
        description
          "Login IPv6 address host";
      }
      enum aaa-at-login-ip-host {
        value 570;
        description
          "Cisco VSA to pass Login-IP-Host in string format";
      }
      enum aaa-at-crb-auth-reason {
        value 571;
        description
          "Authorization reason passed with (re)authorization";
      }
      enum aaa-at-crb-user-id {
        value 572;
        description
          "Technology specific User-id";
      }
      enum aaa-at-crb-session-id {
        value 573;
        description
          "Realtime session id";
      }
      enum aaa-at-crb-service-id {
        value 574;
        description
          "Identify the service which the subscriber is using";
      }
      enum aaa-at-crb-entity-type {
        value 575;
        description
          "CRB Entity type";
      }
      enum aaa-at-crb-duration {
        value 576;
        description
          "IN - Duration quota, OUT - Duration used since the last quota";
      }
      enum aaa-at-crb-total-volume {
        value 577;
        description
          "IN - Total volume quota in octets, OUT - Total volume in octets used since the last quota";
      }
      enum aaa-at-crb-uplink-volume {
        value 578;
        description
          "IN - UP volume quota in octets, OUT - UP volume in octets used since the last quota";
      }
      enum aaa-at-crb-downlink-volume {
        value 579;
        description
          "IN - DOWN volume quota in octets, OUT - DOWN volume in octets used since the last quota";
      }
      enum aaa-at-crb-total-packets {
        value 580;
        description
          "IN - Total pkts quota, OUT - Total pkts used since the last quota";
      }
      enum aaa-at-crb-uplink-packets {
        value 581;
        description
          "IN - Total UP pkts quota, OUT - Total UP pkts used since quota";
      }
      enum aaa-at-crb-downlink-packets {
        value 582;
        description
          "IN - Total DOWN pkts quota, OUT - Total DOWN pkts used since quota";
      }
      enum aaa-at-crb-terminate-cause {
        value 583;
        description
          "CRB termination cause";
      }
      enum aaa-at-cert-application {
        value 584;
        description
          "Determines the valid application domain for a certificate";
      }
      enum aaa-at-cert-trustpoint {
        value 585;
        description
          "Valid trustpoint label for the cert";
      }
      enum aaa-at-cert-serial {
        value 586;
        description
          "Serial number of the certificate";
      }
      enum aaa-at-cert-serial-not {
        value 587;
        description
          "Serial number of the certificate to reject";
      }
      enum aaa-at-cert-lifetime-end {
        value 588;
        description
          "Valid Lifetime end date of cert - Overrides actual cert lifetime end date";
      }
      enum aaa-at-tti-subjectname {
        value 589;
        description
          "Subject name used by Certificate Server";
      }
      enum aaa-at-tti-iosconfig1 {
        value 590;
        description
          "Trusted Transitive Introduction IOS configuration 1";
      }
      enum aaa-at-tti-iosconfig2 {
        value 591;
        description
          "Trusted Transitive Introduction IOS configuration 2";
      }
      enum aaa-at-tti-iosconfig3 {
        value 592;
        description
          "Trusted Transitive Introduction IOS configuration 3";
      }
      enum aaa-at-tti-iosconfig4 {
        value 593;
        description
          "Trusted Transitive Introduction IOS configuration 4";
      }
      enum aaa-at-tti-iosconfig5 {
        value 594;
        description
          "Trusted Transitive Introduction IOS configuration 5";
      }
      enum aaa-at-tti-iosconfig6 {
        value 595;
        description
          "Trusted Transitive Introduction IOS configuration 6";
      }
      enum aaa-at-tti-iosconfig7 {
        value 596;
        description
          "Trusted Transitive Introduction IOS configuration 7";
      }
      enum aaa-at-tti-iosconfig8 {
        value 597;
        description
          "Trusted Transitive Introduction IOS configuration 8";
      }
      enum aaa-at-tti-iosconfig9 {
        value 598;
        description
          "Trusted Transitive Introduction IOS configuration 9";
      }
      enum aaa-at-tti-privilege {
        value 599;
        description
          "Trusted Transitive Introduction privilege: admin or user";
      }
      enum aaa-at-nas-ip-address {
        value 600;
        description
          "The IP address of the NAS";
      }
      enum aaa-at-delay-time {
        value 601;
        description
          "Accounting record delay time";
      }
      enum aaa-at-em-header {
        value 602;
        description
          "EM header";
      }
      enum aaa-at-called-party-number {
        value 603;
        description
          "Called party number";
      }
      enum aaa-at-call-termination-cause {
        value 604;
        description
          "Call termination cause";
      }
      enum aaa-at-related-call-billing-correlation-id {
        value 605;
        description
          "Related call billing correlation ID";
      }
      enum aaa-at-mta-udp-portnum {
        value 606;
        description
          "Mail Transfer Agent UDP port number";
      }
      enum aaa-at-sf-id {
        value 607;
        description
          "Service flow ID";
      }
      enum aaa-at-qos-descriptor {
        value 608;
        description
          "QoS descriptor";
      }
      enum aaa-at-time-adjustment {
        value 609;
        description
          "Time adjustment";
      }
      enum aaa-at-sdp-upstream {
        value 610;
        description
          "SDP upstream";
      }
      enum aaa-at-sdp-downstream {
        value 611;
        description
          "SDP downstream";
      }
      enum aaa-at-ccc-id {
        value 612;
        description
          "CCC ID";
      }
      enum aaa-at-feid {
        value 613;
        description
          "Financial entity ID";
      }
      enum aaa-at-flow-direction {
        value 614;
        description
          "Flow direction";
      }
      enum aaa-at-gate-usage-info {
        value 615;
        description
          "Gate usage information";
      }
      enum aaa-at-element-req-qos {
        value 616;
        description
          "Element requested QoS";
      }
      enum aaa-at-qos-release-reason {
        value 617;
        description
          "QoS release reason";
      }
      enum aaa-at-gate-time-info {
        value 618;
        description
          "Gate time information";
      }
      enum aaa-at-threegenpp-imsi {
        value 619;
        description
          "3GPP International Mobile Subscriber Id";
      }
      enum aaa-at-threegenpp-charging-id {
        value 620;
        description
          "3GPP Charging ID";
      }
      enum aaa-at-threegenpp-pdp-type {
        value 621;
        description
          "3GPP PDP type";
      }
      enum aaa-at-threegenpp-cg-address {
        value 622;
        description
          "3GPP Charging Gateway Address";
      }
      enum aaa-at-threegenpp-gprs-qos-profile {
        value 623;
        description
          "3GPP GPRS QoS Profile";
      }
      enum aaa-at-threegenpp-sgsn-address {
        value 624;
        description
          "3GPP Serving GPRS Support Node address";
      }
      enum aaa-at-threegenpp-ggsn-address {
        value 625;
        description
          "3GPP Gateway GPRS Support Node address";
      }
      enum aaa-at-threegenpp-imsi-mcc-mnc {
        value 626;
        description
          "3GPP IMSI MCC MNC";
      }
      enum aaa-at-threegenpp-ggsn-mcc-mnc {
        value 627;
        description
          "3GPP Gateway GPRS Support Node MCC MNC";
      }
      enum aaa-at-threegenpp-nsapi {
        value 628;
        description
          "3GPP Network Service Access Point Identifier of the PDP";
      }
      enum aaa-at-threegenpp-sess-stop-ind {
        value 629;
        description
          "3GPP Session Stop Ind";
      }
      enum aaa-at-threegenpp-selection-mode {
        value 630;
        description
          "3GPP Selection Mode";
      }
      enum aaa-at-threegenpp-charging-characteristics {
        value 631;
        description
          "3GPP Charging Characteristics";
      }
      enum aaa-at-threegenpp-sgsn-mcc-mnc {
        value 632;
        description
          "3GPP Serving GPRS Support Node MCC MNC";
      }
      enum aaa-at-threegenpp-cg-ipv6-address {
        value 633;
        description
          "3GPP Charging gateway IPv6 address";
      }
      enum aaa-at-threegenpp-sgsn-ipv6-address {
        value 634;
        description
          "3GPP Serving GPRS Support Node IPv6 address";
      }
      enum aaa-at-threegenpp-ggsn-ipv6-address {
        value 635;
        description
          "3GPP Gateway GPRS Support Node IPv6 address";
      }
      enum aaa-at-threegenpp-ipv6-dns {
        value 636;
        description
          "3GPP IPv6 DNS server";
      }
      enum aaa-at-threegenpp-imeisv {
        value 637;
        description
          "3GPP International Mobile Equipment Identity-Software Version";
      }
      enum aaa-at-access-technology-type {
        value 638;
        description
          "Access technology type";
      }
      enum aaa-at-threegenpp-user-location-info {
        value 639;
        description
          "3GPP User Location Information";
      }
      enum aaa-at-threegenpp-ms-timezone {
        value 640;
        description
          "3GPP Mobile station timezone";
      }
      enum aaa-at-threegenpp-camel-charging-info {
        value 641;
        description
          "3GPP Camel Charge Information Container";
      }
      enum aaa-at-teardown-indicator {
        value 642;
        description
          "Teardown indicator to be present in Disconnect-Request";
      }
      enum aaa-at-md-addr {
        value 643;
        description
          "IP address of the Mediation Device";
      }
      enum aaa-at-md-port {
        value 644;
        description
          "UDP port of the Mediation Device";
      }
      enum aaa-at-intercept-action {
        value 645;
        description
          "Intercept action";
      }
      enum aaa-at-intercept-id {
        value 646;
        description
          "Intercept identifier";
      }
      enum aaa-at-charging-profile-index {
        value 647;
        description
          "Charging profile to be applied for the user";
      }
      enum aaa-at-billing-plan {
        value 648;
        description
          "Billing Rule to be applied for this user";
      }
      enum aaa-at-quota-server {
        value 649;
        description
          "Quota Server information from Gateway GPRS Support Node";
      }
      enum aaa-at-im-entry-allowed {
        value 650;
        description
          "Indicates whether the MS is allowed to enter Idle Mode";
      }
      enum aaa-at-downlink-nexthop-address {
        value 651;
        description
          "Next Hop address to use by CSG for CSG->QS communication";
      }
      enum aaa-at-gtp-pdp-session {
        value 652;
        description
          "GTP functionality for a PDP session";
      }
      enum aaa-at-apn {
        value 653;
        description
          "APN name";
      }
      enum aaa-at-sslvpn-http-proxy-server {
        value 654;
        description
          "SSLVPN back-end proxy server name";
      }
      enum aaa-at-sslvpn-http-proxy-server-port {
        value 655;
        description
          "SSLVPN back-end proxy server port";
      }
      enum aaa-at-mschap-error {
        value 656;
        description
          "MS-CHAP error";
      }
      enum aaa-at-mschap-nt-enc-pw1 {
        value 657;
        description
          "MS-CHAP NT encrypted password 1";
      }
      enum aaa-at-mschap-nt-enc-pw2 {
        value 658;
        description
          "MS-CHAP NT encrypted password 2";
      }
      enum aaa-at-mschap-nt-enc-pw3 {
        value 659;
        description
          "MS-CHAP NT encrypted password 3";
      }
      enum aaa-at-mschap-mppe-keys {
        value 660;
        description
          "LM and NT sessions keys for Microsoft Point-to-Point Encryption";
      }
      enum aaa-at-ms-mppe-send-key {
        value 661;
        description
          "Send session key for Microsoft Point-to-Point Encryption";
      }
      enum aaa-at-ms-mppe-recv-key {
        value 662;
        description
          "Receive session key for Microsoft Point-to-Point Encryption";
      }
      enum aaa-at-rad-sg-serv {
        value 663;
        description
          "Radius server host in server group";
      }
      enum aaa-at-rad-sg-vrf {
        value 664;
        description
          "VRF to be used to access the servers";
      }
      enum aaa-at-rad-sg-source-if {
        value 665;
        description
          "Source interface to use to access the servers";
      }
      enum aaa-at-rad-sg-filter {
        value 666;
        description
          "Radius filter list name for server group";
      }
      enum aaa-at-ppp-authen-list {
        value 667;
        description
          "PPP authentication method-list";
      }
      enum aaa-at-ppp-authen-type {
        value 668;
        description
          "PPP authentication protocols";
      }
      enum aaa-at-ppp-author-list {
        value 669;
        description
          "PPP authorization method-list";
      }
      enum aaa-at-ppp-account-list {
        value 670;
        description
          "PPP accounting method-list";
      }
      enum aaa-at-ip-vrf {
        value 671;
        description
          "VRF Information";
      }
      enum aaa-at-ip-addr {
        value 672;
        description
          "IP address";
      }
      enum aaa-at-ip-unnumbered {
        value 673;
        description
          "IP unnumbered";
      }
      enum aaa-at-peer-ip-pool {
        value 674;
        description
          "Local IP pool address";
      }
      enum aaa-at-rad-attr44 {
        value 675;
        description
          "Include radius attribute 44 in access-req";
      }
      enum aaa-at-account-delay {
        value 676;
        description
          "Accounting delay start";
      }
      enum aaa-at-acct-send-stop-authen-failure {
        value 677;
        description
          "Send accounting information even with failure";
      }
      enum aaa-at-acct-send-stop-accept-remote {
        value 678;
        description
          "Send accounting for remote authenticated users";
      }
      enum aaa-at-cfg-template {
        value 679;
        description
          "Name of template to be applied";
      }
      enum aaa-at-mschap-v2-success {
        value 680;
        description
          "MSCHAPv2 response string";
      }
      enum aaa-at-mschap-v2-cpw {
        value 681;
        description
          "MSCHAPv2 change password on expiry";
      }
      enum aaa-at-call-id {
        value 682;
        description
          "Call-id for a voip call";
      }
      enum aaa-at-cust-biz-grp-id {
        value 683;
        description
          "Customer business group ID for a voip call";
      }
      enum aaa-at-ip-hop {
        value 684;
        description
          "VIA header information from INVITE message";
      }
      enum aaa-at-nas-ipv6-address {
        value 685;
        description
          "The IPv6 address of the NAS";
      }
      enum aaa-at-ipv6-interfaceid {
        value 686;
        description
          "The IPv6 Interface Id for the user";
      }
      enum aaa-at-ipv6-prefix {
        value 687;
        description
          "IPv6 Prefix information for a user session";
      }
      enum aaa-at-ipv6-prefix-len {
        value 688;
        description
          "IPv6 prefix length";
      }
      enum aaa-at-delegated-ipv6-prefix {
        value 689;
        description
          "Delegated IPv6 prefix information for a user session";
      }
      enum aaa-at-delegated-ipv6-pool {
        value 690;
        description
          "DHCP pool name for assigning user session IPv6 prefix";
      }
      enum aaa-at-ipv6-dns-servers {
        value 691;
        description
          "The IPv6 address of a DNS server";
      }
      enum aaa-at-session-type {
        value 692;
        description
          "Type of PPP stack session - IPv4/v6 or dual stack";
      }
      enum aaa-at-remote-media-address {
        value 693;
        description
          "Remote media gateway IP address";
      }
      enum aaa-at-carrier-id {
        value 694;
        description
          "ISDN User Part carrier id";
      }
      enum aaa-at-calling-party-category {
        value 695;
        description
          "Calling party category";
      }
      enum aaa-at-orig-line-info {
        value 696;
        description
          "Originating line information";
      }
      enum aaa-at-charge-number {
        value 697;
        description
          "Charge number";
      }
      enum aaa-at-trans-med-req {
        value 698;
        description
          "Transmission medium request";
      }
      enum aaa-at-rdt-number {
        value 699;
        description
          "Redirecting number";
      }
      enum aaa-at-backward-call-ind {
        value 700;
        description
          "Backward call indicators";
      }
      enum aaa-at-remote-media-udp-port {
        value 701;
        description
          "Remote media gateway UDP port";
      }
      enum aaa-at-remote-media-id {
        value 702;
        description
          "Remote media gateway DNS name";
      }
      enum aaa-at-supp-svc-xfer-by {
        value 703;
        description
          "Transferor who initiates a call-transfer";
      }
      enum aaa-at-faxrelay-start-time {
        value 704;
        description
          "Fax relay start time";
      }
      enum aaa-at-faxrelay-max-jit-buf-depth {
        value 705;
        description
          "Fax relay maximum jitter buffer depth";
      }
      enum aaa-at-faxrelay-jit-buf-ovflow {
        value 706;
        description
          "Fax relay jitter buffer overflow";
      }
      enum aaa-at-faxrelay-mr-hs-mod {
        value 707;
        description
          "Fax relay most recent high speed modulation";
      }
      enum aaa-at-faxrelay-init-hs-mod {
        value 708;
        description
          "Fax relay initial high speed modulation";
      }
      enum aaa-at-faxrelay-num-pages {
        value 709;
        description
          "Fax relay number of pages transmitted";
      }
      enum aaa-at-faxrelay-direction {
        value 710;
        description
          "Fax relay direction";
      }
      enum aaa-at-faxrelay-ecm-status {
        value 711;
        description
          "Fax relay ECM status";
      }
      enum aaa-at-faxrelay-encap-prot {
        value 712;
        description
          "Fax relay encapsulation protocol";
      }
      enum aaa-at-faxrelay-nsf-country-code {
        value 713;
        description
          "Fax relay NSF country code";
      }
      enum aaa-at-faxrelay-nsf-manuf-code {
        value 714;
        description
          "Fax relay NSF manufacture code";
      }
      enum aaa-at-faxrelay-fax-success {
        value 715;
        description
          "Fax relay fax success";
      }
      enum aaa-at-faxrelay-tx-packets {
        value 716;
        description
          "Fax relay number of transmitted packets";
      }
      enum aaa-at-faxrelay-rx-packets {
        value 717;
        description
          "Fax relay number of received packets";
      }
      enum aaa-at-faxrelay-pkt-conceal {
        value 718;
        description
          "Fax relay packet concealment";
      }
      enum aaa-at-voice-feature {
        value 719;
        description
          "Voice call feature name";
      }
      enum aaa-at-feature-operation {
        value 720;
        description
          "Voice call feature operation name";
      }
      enum aaa-at-feature-op-status {
        value 721;
        description
          "Voice call feature operation status";
      }
      enum aaa-at-feature-op-time {
        value 722;
        description
          "Voice call feature operation time";
      }
      enum aaa-at-feature-id {
        value 723;
        description
          "Voice call feature ID";
      }
      enum aaa-at-feature-vsa {
        value 724;
        description
          "Gateway invoked feature information";
      }
      enum aaa-at-ip-phone-info {
        value 725;
        description
          "Details about the IP Phone";
      }
      enum aaa-at-ip-pbx-mode {
        value 726;
        description
          "Mode of the CME";
      }
      enum aaa-at-peer-sub-address {
        value 727;
        description
          "The sub number this call was connected to";
      }
      enum aaa-at-faxrelay-stop-time {
        value 728;
        description
          "Fax relay stop time";
      }
      enum aaa-at-internal-error-code {
        value 729;
        description
          "Internally detected error causing call to be released";
      }
      enum aaa-at-account-code {
        value 730;
        description
          "Account code input from telephony call leg";
      }
      enum aaa-at-vrf-id {
        value 731;
        description
          "The Virtual Route Forwarder ID";
      }
      enum aaa-at-allow-subvai {
        value 732;
        description
          "Allow virtual-access sub-interface with interface-config attribute";
      }
      enum aaa-at-idb-description {
        value 733;
        description
          "Interface description";
      }
      enum aaa-at-sg-service-type {
        value 734;
        description
          "The type of ISG service";
      }
      enum aaa-at-subscriber-policy-name {
        value 735;
        description
          "The name of policy to be provisioned on external device";
      }
      enum aaa-at-service-group {
        value 736;
        description
          "The SG Service Group Name";
      }
      enum aaa-at-isakmp-phase1-id {
        value 737;
        description
          "The Phase 1 Identifier presented by a peer in ISAKMP";
      }
      enum aaa-at-isakmp-initiator-v4-ip {
        value 738;
        description
          "The IPv4 Address of the ISAKMP Initiator";
      }
      enum aaa-at-isakmp-initiator-v6-ip {
        value 739;
        description
          "The IPv6 Address of the ISAKMP Initiator";
      }
      enum aaa-at-isakmp-group-id {
        value 740;
        description
          "The group ID of the ISAKMP Initiator";
      }
      enum aaa-at-l4-redirect {
        value 741;
        description
          "Layer 4 redirect details";
      }
      enum aaa-at-ip-portbundle {
        value 742;
        description
          "IP Port-bundle Configuration";
      }
      enum aaa-at-traffic-class {
        value 743;
        description
          "Traffic Class Configuration";
      }
      enum aaa-at-client-flash {
        value 744;
        description
          "Total flash space in remote client";
      }
      enum aaa-at-client-available-flash {
        value 745;
        description
          "Available flash space in remote client";
      }
      enum aaa-at-client-platform {
        value 746;
        description
          "Platform of remote client";
      }
      enum aaa-at-client-image {
        value 747;
        description
          "Image Version of remote client";
      }
      enum aaa-at-client-hostname {
        value 748;
        description
          "Remote client host name";
      }
      enum aaa-at-client-serial {
        value 749;
        description
          "Processor board serial number of remote client";
      }
      enum aaa-at-client-memory {
        value 750;
        description
          "Total DRAM in remote client";
      }
      enum aaa-at-client-available-memory {
        value 751;
        description
          "Available DRAM in remote client";
      }
      enum aaa-at-client-config-version {
        value 752;
        description
          "Configuration snippet version of remote client";
      }
      enum aaa-at-wispr-location-id {
        value 753;
        description
          "WiFi Wireless Internet Service Provider roaming location ID";
      }
      enum aaa-at-wispr-location-name {
        value 754;
        description
          "WiFi Wireless Internet Service Provider roaming location name";
      }
      enum aaa-at-subscriber-acct-list {
        value 755;
        description
          "Subscriber accounting method-list";
      }
      enum aaa-at-reauthenticate-type {
        value 756;
        description
          "Type of re-authenticate command";
      }
      enum aaa-at-method {
        value 757;
        description
          "Type of authentication method";
      }
      enum aaa-at-precedence {
        value 758;
        description
          "Precedence of the profile or template being applied";
      }
      enum aaa-at-activation-mode {
        value 759;
        description
          "Directive to set activation mode of user profile or service template";
      }
      enum aaa-at-sg-version {
        value 760;
        description
          "The version of the SG";
      }
      enum aaa-at-policy-route {
        value 761;
        description
          "Peruser policy route";
      }
      enum aaa-at-default-domain {
        value 762;
        description
          "Default VPN domain";
      }
      enum aaa-at-user-realm {
        value 763;
        description
          "The domain/realm name of the user";
      }
      enum aaa-at-sla-profile-name {
        value 764;
        description
          "The Service Level Agreement profile name of the user";
      }
      enum aaa-at-group-lock {
        value 765;
        description
          "VPN group lock";
      }
      enum aaa-at-configuration-url {
        value 766;
        description
          "URL to the client configuration file";
      }
      enum aaa-at-configuration-version {
        value 767;
        description
          "version of configuration";
      }
      enum aaa-at-crypto-pfs {
        value 768;
        description
          "Propose Crypto PFS";
      }
      enum aaa-at-crypto-metric {
        value 769;
        description
          "Virtual Tunnel Interface Route Metric";
      }
      enum aaa-at-access-restrict {
        value 770;
        description
          "VPN group access";
      }
      enum aaa-at-include-local-lan {
        value 771;
        description
          "Include Local LAN";
      }
      enum aaa-at-user-include-local-lan {
        value 772;
        description
          "Include Local LAN per user";
      }
      enum aaa-at-firewall-are-u-there {
        value 773;
        description
          "Is Firewall present";
      }
      enum aaa-at-cpp-policy {
        value 774;
        description
          "CPP policy name";
      }
      enum aaa-at-browser-proxy {
        value 775;
        description
          "Browser-proxy settings";
      }
      enum aaa-at-cfg-banner {
        value 776;
        description
          "Xauth banner";
      }
      enum aaa-at-save-password {
        value 777;
        description
          "Save Password";
      }
      enum aaa-at-user-save-password {
        value 778;
        description
          "Save Password per user";
      }
      enum aaa-at-route-set-interface {
        value 779;
        description
          "Route set interface";
      }
      enum aaa-at-route-accept {
        value 780;
        description
          "Route accept with tag and distance";
      }
      enum aaa-at-smartcard-removal-disconnect {
        value 781;
        description
          "Smartcard removal disconnect";
      }
      enum aaa-at-user-smartcard-removal-disconnect {
        value 782;
        description
          "Smartcard removal disconnect per user";
      }
      enum aaa-at-group-dhcp-server {
        value 783;
        description
          "VPN DHCP Server";
      }
      enum aaa-at-dhcp-timeout {
        value 784;
        description
          "VPN DHCP Timeout";
      }
      enum aaa-at-dhcp-giaddr {
        value 785;
        description
          "VPN DHCP GI address";
      }
      enum aaa-at-split-dns {
        value 786;
        description
          "VPN Split DNS";
      }
      enum aaa-at-ipv4-group-netmask {
        value 787;
        description
          "IPv4 netmask";
      }
      enum aaa-at-user-vpn-group {
        value 788;
        description
          "VPN Group for User";
      }
      enum aaa-at-backup-gateway {
        value 789;
        description
          "IPSec backup gateway";
      }
      enum aaa-at-max-users {
        value 790;
        description
          "Maximum users";
      }
      enum aaa-at-max-logins {
        value 791;
        description
          "Maximum logins per user";
      }
      enum aaa-at-ipv6-subnet-acl {
        value 792;
        description
          "IPv6 Subnet ACL";
      }
      enum aaa-at-ipv6-address-pool {
        value 793;
        description
          "The local IPv6 address pool name";
      }
      enum aaa-at-ipsec-flow-limit {
        value 794;
        description
          "IPSec flow limit per multi-SA dynamic virtual tunnel interfaces session";
      }
      enum aaa-at-max-bit-rate {
        value 795;
        description
          "Max bit rate used in a call";
      }
      enum aaa-at-qos-class-name {
        value 796;
        description
          "Name for the session QoS classmap";
      }
      enum aaa-at-qos-policy-name {
        value 797;
        description
          "Name for the session QoS policy-map";
      }
      enum aaa-at-time-quota {
        value 798;
        description
          "Time quota in seconds";
      }
      enum aaa-at-volume-quota {
        value 799;
        description
          "Volume quota in bytes";
      }
      enum aaa-at-giga-words-volume-quota {
        value 800;
        description
          "Number of times that volume-quota has wrapped";
      }
      enum aaa-at-tariff-time {
        value 801;
        description
          "Time for tariff switch in seconds";
      }
      enum aaa-at-post-tariff-volume-quota {
        value 802;
        description
          "Volume quota after tariff switch in bytes";
      }
      enum aaa-at-giga-words-post-tariff-volume-quota {
        value 803;
        description
          "Number of times that post-tariff-volume-quota has wrapped";
      }
      enum aaa-at-idle {
        value 804;
        description
          "If the session is idle";
      }
      enum aaa-at-volume-threshold {
        value 805;
        description
          "Volume threshold before which re-authorization will be issued";
      }
      enum aaa-at-time-threshold {
        value 806;
        description
          "Time threshold before which re-authorization will be issued";
      }
      enum aaa-at-prepaid-config {
        value 807;
        description
          "Name of the prepaid config that is referred for this session";
      }
      enum aaa-at-prepaid-idle-timeout {
        value 808;
        description
          "Prepaid idle timeout";
      }
      enum aaa-at-prepaid-absolute-timeout {
        value 809;
        description
          "Prepaid absolute timeout";
      }
      enum aaa-at-drop-at-quota-reached {
        value 810;
        description
          "Drop prepaid traffic when volume quota is reached";
      }
      enum aaa-at-volume-monitor-dropping {
        value 811;
        description
          "Drop all prepaid traffic";
      }
      enum aaa-at-dhcp-vendor-class {
        value 812;
        description
          "Hex-encoded version of the DHCP vendor class option no 60";
      }
      enum aaa-at-dhcp-client-id {
        value 813;
        description
          "Hex-encoded version of the DHCP client-id option no 61";
      }
      enum aaa-at-dhcp-relay-info {
        value 814;
        description
          "Hex-encoded version of the DHCP relay info option no 80";
      }
      enum aaa-at-session-duration {
        value 815;
        description
          "Maximum duration of session in seconds";
      }
      enum aaa-at-epd-session-notify-changes {
        value 816;
        description
          "Inform external policy device of changes in session";
      }
      enum aaa-at-subscriber-service-monitor {
        value 817;
        description
          "Turn on service monitoring on external policy device";
      }
      enum aaa-at-subscriber-command {
        value 818;
        description
          "ISG command code type";
      }
      enum aaa-at-audit-session-id {
        value 819;
        description
          "Session ID used for Audit scenarios";
      }
      enum aaa-at-status-query-timeout {
        value 820;
        description
          "Status Query Timeout Period";
      }
      enum aaa-at-url-redirect {
        value 821;
        description
          "URL Redirect User Sessions";
      }
      enum aaa-at-url-redirect-acl {
        value 822;
        description
          "URL Redirect ACL";
      }
      enum aaa-at-url-redirect-acl-no-match {
        value 823;
        description
          "URL Redirect ACL No Match";
      }
      enum aaa-at-url-redirect-acl-one-time {
        value 824;
        description
          "URL Redirect ACL One Time";
      }
      enum aaa-at-posture-token {
        value 825;
        description
          "Posture Token for the user Device";
      }
      enum aaa-at-ciscosecure-defined-acl {
        value 826;
        description
          "Specifies the ACL name for the Downloadable ACL";
      }
      enum aaa-at-banner {
        value 827;
        description
          "Browser banner for the group";
      }
      enum aaa-at-home-page {
        value 828;
        description
          "Default home page";
      }
      enum aaa-at-urllist-name {
        value 829;
        description
          "URL list name";
      }
      enum aaa-at-sslvpn-acl-name {
        value 830;
        description
          "SSLVPN ACL name";
      }
      enum aaa-at-nbnslist-name {
        value 831;
        description
          "NetBIOS Name Service list name";
      }
      enum aaa-at-file-browse {
        value 832;
        description
          "Enable / Disable Common Internet File System Network browsing";
      }
      enum aaa-at-file-entry {
        value 833;
        description
          "Enable / Disable Common Internet File System file entry";
      }
      enum aaa-at-file-access {
        value 834;
        description
          "Enable / Disable Common Internet File System file access";
      }
      enum aaa-at-port-forward-name {
        value 835;
        description
          "Port forwarding instance name";
      }
      enum aaa-at-port-forward-auto {
        value 836;
        description
          "Port forwarding auto applet download";
      }
      enum aaa-at-port-forward-http-proxy {
        value 837;
        description
          "Port forwarding http proxy";
      }
      enum aaa-at-port-forward-http-proxy-url {
        value 838;
        description
          "Port forwarding http proxy URL";
      }
      enum aaa-at-svc-enabled {
        value 839;
        description
          "Enable / Disable SSLVPN client";
      }
      enum aaa-at-svc-required {
        value 840;
        description
          "Enable / Disable SSLVPN client required option";
      }
      enum aaa-at-hide-urlbar {
        value 841;
        description
          "Enable / Disable hide-url-bar option";
      }
      enum aaa-at-maskurls {
        value 842;
        description
          "Mask host/port portion of mangled URLs";
      }
      enum aaa-at-dpd-client-timeout {
        value 843;
        description
          "Dead Peer Detection client-side timeout";
      }
      enum aaa-at-dpd-gateway-timeout {
        value 844;
        description
          "Dead Peer Detection gateway-side timeout";
      }
      enum aaa-at-keep-svc-installed {
        value 845;
        description
          "Keep SVC installed option";
      }
      enum aaa-at-rekey-interval {
        value 846;
        description
          "Re-key interval";
      }
      enum aaa-at-lease-duration {
        value 847;
        description
          "IP address lease duration";
      }
      enum aaa-at-svc-ie-proxy-policy {
        value 848;
        description
          "Microsoft Internet Explorer proxy server policy";
      }
      enum aaa-at-ie-proxy-server {
        value 849;
        description
          "Microsoft Internet Explorer proxy server";
      }
      enum aaa-at-ie-proxy-exception {
        value 850;
        description
          "Microsoft Internet Explorer proxy server exception list";
      }
      enum aaa-at-split-include {
        value 851;
        description
          "Include networks in tunnel";
      }
      enum aaa-at-split-exclude {
        value 852;
        description
          "Exclude networks from tunnel";
      }
      enum aaa-at-cifsurllist-name {
        value 853;
        description
          "Common Internet File System URL list name";
      }
      enum aaa-at-sso-server-name {
        value 854;
        description
          "SSO Server Name";
      }
      enum aaa-at-webvpn-context {
        value 855;
        description
          "Webvpn virtual context";
      }
      enum aaa-at-webvpn-client-ip {
        value 856;
        description
          "WEBVPN Client IP address";
      }
      enum aaa-at-anyconnect-profile {
        value 857;
        description
          "Anyconnect profile name";
      }
      enum aaa-at-dsp-id {
        value 858;
        description
          "DSP used for the leg";
      }
      enum aaa-at-mcast-source-v4 {
        value 859;
        description
          "IPv4 multicast group source address";
      }
      enum aaa-at-mcast-source-v6 {
        value 860;
        description
          "IPv6 multicast group source address";
      }
      enum aaa-at-mcast-group-v4 {
        value 861;
        description
          "IPv4 multicast group identifier address";
      }
      enum aaa-at-mcast-group-v6 {
        value 862;
        description
          "IPv6 multicast group identifier address";
      }
      enum aaa-at-local-hostname {
        value 863;
        description
          "Local Hostname in Multi-Homed Environment";
      }
      enum aaa-at-authz-directive {
        value 864;
        description
          "Specifies the directive as open or default";
      }
      enum aaa-at-method-list {
        value 865;
        description
          "AAA Method list";
      }
      enum aaa-at-template-name {
        value 866;
        description
          "Template name";
      }
      enum aaa-at-timer-name {
        value 867;
        description
          "Timer name";
      }
      enum aaa-at-timer-value {
        value 868;
        description
          "Timer value";
      }
      enum aaa-at-nas-port-sub-id-type {
        value 869;
        description
          "NAS Port Sub Id Type";
      }
      enum aaa-at-identity-policy-name {
        value 870;
        description
          "Specifies the identity policy name for local policy application";
      }
      enum aaa-at-media-type {
        value 871;
        description
          "Media type";
      }
      enum aaa-at-protocol-type {
        value 872;
        description
          "Protocol type";
      }
      enum aaa-at-domain {
        value 873;
        description
          "Session Domain";
      }
      enum aaa-at-unauthen-domain {
        value 874;
        description
          "Un-authenticate Domain";
      }
      enum aaa-at-unauthen-username {
        value 875;
        description
          "Un-authenticate Username";
      }
      enum aaa-at-nas-port {
        value 876;
        description
          "NAS Port";
      }
      enum aaa-at-tunnel-name {
        value 877;
        description
          "Tunnel Name";
      }
      enum aaa-at-if-handle {
        value 878;
        description
          "Interface Handle";
      }
      enum aaa-at-parent-if-handle {
        value 879;
        description
          "Parent interface handle";
      }
      enum aaa-at-tag-name {
        value 880;
        description
          "Tag attribute received from ACS";
      }
      enum aaa-at-supplicant-group {
        value 881;
        description
          "Supplicant-Group attribute received from ACS";
      }
      enum aaa-at-vpdn-dsl-line-info-forwarding {
        value 882;
        description
          "VPDN DSL Line Info Forwarding";
      }
      enum aaa-at-gk-operation {
        value 883;
        description
          "Gatekeeper RAS operation";
      }
      enum aaa-at-supplicant-name {
        value 884;
        description
          "Supplicant-Name attribute received from ACS";
      }
      enum aaa-at-device-traffic-class {
        value 885;
        description
          "The type of client device that is being authenticated";
      }
      enum aaa-at-identity-request {
        value 886;
        description
          "Request for additional keys";
      }
      enum aaa-at-termination-action-modifier {
        value 887;
        description
          "Extensions to IETF defined Termination Actions";
      }
      enum aaa-at-ntlm-client-cred {
        value 888;
        description
          "NT LAN Manager credentials like NT LAN Manager type 1 and 3 messages";
      }
      enum aaa-at-ntlm-server-cred {
        value 889;
        description
          "NT LAN Manager credentials like NT LAN Manager type 2 messages";
      }
      enum aaa-at-cts-pac-opaque {
        value 890;
        description
          "Include CTS PAC Opaque";
      }
      enum aaa-at-cts-capabilities {
        value 891;
        description
          "Advertise authenticator's CTS capabilities";
      }
      enum aaa-at-cts-supp-caps {
        value 892;
        description
          "Supplicant's CTS capabilities";
      }
      enum aaa-at-security-group-tag {
        value 893;
        description
          "Security group tag to apply to local device or peer";
      }
      enum aaa-at-trusted-device {
        value 894;
        description
          "Trust SGT's from the peer";
      }
      enum aaa-at-rbacl-source-list-outbound {
        value 895;
        description
          "Role-Based ACL source list name";
      }
      enum aaa-at-rbacl-destination-list-outbound {
        value 896;
        description
          "Role-Based ACL destination list name";
      }
      enum aaa-at-rbacl-any-any-outbound {
        value 897;
        description
          "Role-Based ACL any source and any destination list name";
      }
      enum aaa-at-rbacl-src-dst-list-inbound {
        value 898;
        description
          "Role-Based ACL source or destination list name";
      }
      enum aaa-at-rbacl-list-name-outbound {
        value 899;
        description
          "Role-Based ACL list name to request for ACEs";
      }
      enum aaa-at-rbacl-list-name-inbound {
        value 900;
        description
          "Role-Based ACL name and gen ID being requested";
      }
      enum aaa-at-rbacl-ace-inbound {
        value 901;
        description
          "Role-Based ACL ACEs being requested";
      }
      enum aaa-at-server-list-inbound {
        value 902;
        description
          "Server list name and generation number";
      }
      enum aaa-at-server-list-outbound {
        value 903;
        description
          "Server list name";
      }
      enum aaa-at-server {
        value 904;
        description
          "Server in a server list, format <AID>:<IP addr>:<port>";
      }
      enum aaa-at-authorization-expiry {
        value 905;
        description
          "Number of seconds before policy expires";
      }
      enum aaa-at-environment-data-outbound {
        value 906;
        description
          "Environment Data";
      }
      enum aaa-at-imt-traffic-policy-get {
        value 907;
        description
          "CTS tunnel traffic policy download";
      }
      enum aaa-at-imt-traffic-policy-inbound {
        value 908;
        description
          "CTS tunnel traffic policy name and generation number";
      }
      enum aaa-at-imt-traffic-policy-outbound {
        value 909;
        description
          "CTS tunnel traffic policy send";
      }
      enum aaa-at-imt-tunnel-default-sgt {
        value 910;
        description
          "Implicit Tunnel default SGT";
      }
      enum aaa-at-imt-reverse-check-fail-drop {
        value 911;
        description
          "Implicit Tunnel reverse check fail drop flag";
      }
      enum aaa-at-imt-tunnel-gateway {
        value 912;
        description
          "CTS Tunnel Gateway, format <IP addr>";
      }
      enum aaa-at-imt-tunnel-unicast-address {
        value 913;
        description
          "CTS Tunnel unicast address, format <IP addr>:<mask>";
      }
      enum aaa-at-imt-tunnel-multicast-group-address {
        value 914;
        description
          "CTS Tunnel multicast group address, format <src IP addr>:<dst group address>";
      }
      enum aaa-at-mcast-group-sgt-table-inbound {
        value 915;
        description
          "Multicast group SGT table name and generation number";
      }
      enum aaa-at-mcast-group-sgt-table-outbound {
        value 916;
        description
          "Multicast group SGT table name";
      }
      enum aaa-at-mcast-sgt {
        value 917;
        description
          "SGT for the multicast address, format <multicast IP>-<sgt>";
      }
      enum aaa-at-imt-current-group-key-outbound {
        value 918;
        description
          "Implicit Tunnel current group key";
      }
      enum aaa-at-imt-next-group-key-outbound {
        value 919;
        description
          "Implicit Tunnel next group key";
      }
      enum aaa-at-imt-group-spi {
        value 920;
        description
          "Implicit Tunnel Group SPI value";
      }
      enum aaa-at-imt-group-algorithm {
        value 921;
        description
          "Implicit Tunnel Group Algorithm";
      }
      enum aaa-at-imt-gcm-sequence-range {
        value 922;
        description
          "GCM cipher sequence number range";
      }
      enum aaa-at-imt-encapsulation-protocol-number {
        value 923;
        description
          "Protocol number for C-ESP encapsulated packets, value = 50 or 99";
      }
      enum aaa-at-imt-group-key-expiry {
        value 924;
        description
          "Number of seconds before CIT group key and SPI expire";
      }
      enum aaa-at-imt-min-rekey-windows {
        value 925;
        description
          "Minimum number of seconds before CIT key expiration to rekey";
      }
      enum aaa-at-imt-expired-key-hold-down-time {
        value 926;
        description
          "Time in seconds after expiration that the expired key and SPI must be active";
      }
      enum aaa-at-imt-tunnel-traffic-policy-expiry {
        value 927;
        description
          "Time in seconds that the current traffic policy expires";
      }
      enum aaa-at-environment-data-expiry {
        value 928;
        description
          "Number of seconds before environment data expires";
      }
      enum aaa-at-peer-authorization-token-outbound {
        value 929;
        description
          "Device's authorization token";
      }
      enum aaa-at-l2tp-silent-switchover {
        value 930;
        description
          "Is L2TP silent switchover enabled";
      }
      enum aaa-at-gk-endp-addr {
        value 931;
        description
          "Call Signaling address of endpoint";
      }
      enum aaa-at-gk-endp-alias {
        value 932;
        description
          "Comma separated list of endpoint's h323 id and e164 aliases";
      }
      enum aaa-at-keywrap-key {
        value 933;
        description
          "Key wrap key";
      }
      enum aaa-at-keywrap-nonce {
        value 934;
        description
          "Key wrap randomize";
      }
      enum aaa-at-keywrap-message-auth-code {
        value 935;
        description
          "Key wrap message authenticator code";
      }
      enum aaa-at-in-lpcor-grp {
        value 936;
        description
          "Logical partition class of restriction group of an incoming call leg";
      }
      enum aaa-at-out-lpcor-grp {
        value 937;
        description
          "Logical partition class of restriction group of an outgoing call leg";
      }
      enum aaa-at-evc-service-id {
        value 938;
        description
          "Service instance values for Ethernet VC";
      }
      enum aaa-at-bsn-vap-id {
        value 939;
        description
          "WLAN-ID";
      }
      enum aaa-at-bsn-qos-level {
        value 940;
        description
          "QoS Level";
      }
      enum aaa-at-bsn-dscp {
        value 941;
        description
          "Differentiated Services Code Point";
      }
      enum aaa-at-bsn-8021-p-type {
        value 942;
        description
          "802.1P Type";
      }
      enum aaa-at-bsn-vlan-interface-name {
        value 943;
        description
          "Vlan interface name";
      }
      enum aaa-at-bsn-acl-name {
        value 944;
        description
          "Wlan ACL name";
      }
      enum aaa-at-bsn-data-bw-average-contract {
        value 945;
        description
          "Data Bandwidth Average Contract";
      }
      enum aaa-at-bsn-real-time-bw-average-contract {
        value 946;
        description
          "RealTime Bandwidth Average Contract";
      }
      enum aaa-at-bsn-data-bw-burst-contract {
        value 947;
        description
          "Data Bandwidth Burst Contract";
      }
      enum aaa-at-bsn-real-time-bw-burst-contract {
        value 948;
        description
          "RealTime Bandwidth Burst Contract";
      }
      enum aaa-at-bsn-guest-role-name {
        value 949;
        description
          "Guest Role Name";
      }
      enum aaa-at-hwidb {
        value 950;
        description
          "IOS Hardware IDB";
      }
      enum aaa-at-swidb {
        value 951;
        description
          "IOS Software IDB";
      }
      enum aaa-at-iif-id {
        value 952;
        description
          "IIF ID 64 bits";
      }
      enum aaa-at-auth-profile {
        value 953;
        description
          "Auth profile name";
      }
      enum aaa-at-auth-domain {
        value 954;
        description
          "Authentication domain";
      }
      enum aaa-at-auth-mgr-ctx-state {
        value 955;
        description
          "State of the Auth Manager Context";
      }
      enum aaa-at-service-template {
        value 956;
        description
          "Profile being downloaded is a service-template";
      }
      enum aaa-at-aaa-authen-type {
        value 957;
        description
          "Authentication type required for AAA APIs";
      }
      enum aaa-at-aaa-author-type {
        value 958;
        description
          "Authorization type required for AAA APIs";
      }
      enum aaa-at-aaa-authen-service {
        value 959;
        description
          "Authentication Service type required for AAA APIs";
      }
      enum aaa-at-aaa-author-service {
        value 960;
        description
          "Authorization Service type required for AAA APIs";
      }
      enum aaa-at-arp-probe {
        value 961;
        description
          "Enable ARP Probe functionality";
      }
      enum aaa-at-arp-probe-timeout {
        value 962;
        description
          "ARP probe timeout period";
      }
      enum aaa-at-iaf-local-db {
        value 963;
        description
          "IAF local DB attribute";
      }
      enum aaa-at-authz-fail-reason {
        value 964;
        description
          "The reason for a failure from an authorization feature";
      }
      enum aaa-at-vlan-id {
        value 965;
        description
          "Virtual LAN Identifier";
      }
      enum aaa-at-nas-update {
        value 966;
        description
          "Indicator of change of subscriber's NAS";
      }
      enum aaa-at-sam-account-name {
        value 967;
        description
          "Logon name for older versions";
      }
      enum aaa-at-employee-type {
        value 968;
        description
          "Job category of employee";
      }
      enum aaa-at-contact-info {
        value 969;
        description
          "Meeting contact information";
      }
      enum aaa-at-telephone-number {
        value 970;
        description
          "Primary telephone number";
      }
      enum aaa-at-encapsulation-untagged {
        value 971;
        description
          "Encapsulation as untagged for Ethernet service";
      }
      enum aaa-at-encapsulation-default {
        value 972;
        description
          "Encapsulation as default for Ethernet service";
      }
      enum aaa-at-encapsulation-priority-tagged {
        value 973;
        description
          "Encapsulation as priority tagged for Ethernet service";
      }
      enum aaa-at-efp-session-name {
        value 974;
        description
          "EFP Session name";
      }
      enum aaa-at-stag-type {
        value 975;
        description
          "Vlan type associated with EFP encapsulation";
      }
      enum aaa-at-idmgr-mask {
        value 976;
        description
          "The netmask to be used in id-manager for subnet session";
      }
      enum aaa-at-fac-digits {
        value 977;
        description
          "Input FAC digits of a leg";
      }
      enum aaa-at-fac-status {
        value 978;
        description
          "Authenticated fac status of a leg";
      }
      enum aaa-at-dynamic-vrf-service-type {
        value 979;
        description
          "Specifies type of vrf service : mapping or transfer";
      }
      enum aaa-at-media-protocol-state {
        value 980;
        description
          "Specifies the state of media protocol";
      }
      enum aaa-at-stag-vlanid {
        value 981;
        description
          "Outer vlan ids associated with EFP encapsulation";
      }
      enum aaa-at-stag-cos {
        value 982;
        description
          "Outer COS associated with EFP encapsulation";
      }
      enum aaa-at-ctag-vlanid {
        value 983;
        description
          "Inner vlan ids associated with EFP encapsulation";
      }
      enum aaa-at-ctag-cos {
        value 984;
        description
          "Inner COS associated with EFP encapsulation";
      }
      enum aaa-at-payload-etype {
        value 985;
        description
          "Ether type of the payload associated with EFP";
      }
      enum aaa-at-encapsulation-match-exact {
        value 986;
        description
          "Encapsulation matching criteria is for exact match";
      }
      enum aaa-at-rewrite-ingress {
        value 987;
        description
          "Rewrite ingress direction";
      }
      enum aaa-at-rewrite-ingress-stag-type {
        value 988;
        description
          "Vlan ethertype for vlan push and translation operation";
      }
      enum aaa-at-rewrite-ingress-tag-operation {
        value 989;
        description
          "Rewrite ingress vlan tag operation";
      }
      enum aaa-at-rewrite-ingress-stag-vlanid {
        value 990;
        description
          "Rewrite ingress stag vlanid";
      }
      enum aaa-at-rewrite-ingress-ctag-vlanid {
        value 991;
        description
          "Rewrite ingress C-Tag vlanid";
      }
      enum aaa-at-rewrite-ingress-symmetric {
        value 992;
        description
          "Symmetric operation needed for vlan translation";
      }
      enum aaa-at-rewrite-egress {
        value 993;
        description
          "Rewrite egress direction";
      }
      enum aaa-at-rewrite-egress-stag-type {
        value 994;
        description
          "Vlan ethertype for vlan push and translation operation";
      }
      enum aaa-at-rewrite-egress-tag-operation {
        value 995;
        description
          "Rewrite egress vlan tag operation";
      }
      enum aaa-at-rewrite-egress-stag-vlanid {
        value 996;
        description
          "Rewrite egress stag vlanid";
      }
      enum aaa-at-rewrite-egress-ctag-vlanid {
        value 997;
        description
          "Rewrite egress c-tag vlanid";
      }
      enum aaa-at-rewrite-egress-symmetric {
        value 998;
        description
          "Symmetric operation needed for vlan translation";
      }
      enum aaa-at-service-instance-description {
        value 999;
        description
          "Textual description associated with EFP";
      }
      enum aaa-at-snmp-ifindex-persist {
        value 1000;
        description
          "SNMP index is persistent or need to clear";
      }
      enum aaa-at-evc-name {
        value 1001;
        description
          "EVC name to be attached with ethernet services instance";
      }
      enum aaa-at-ce-vlan-map {
        value 1002;
        description
          "CE-VLAN to EVC map for a particular UNI";
      }
      enum aaa-at-redundancy-group {
        value 1003;
        description
          "Defines the redundancy group of PE";
      }
      enum aaa-at-elmi-vlan-map-untagged {
        value 1004;
        description
          "Vlan map encapsulation as untagged";
      }
      enum aaa-at-elmi-vlan-map-default {
        value 1005;
        description
          "Vlan map encapsulation as default";
      }
      enum aaa-at-service-group-id {
        value 1006;
        description
          "Service group number newly created EFP should be member";
      }
      enum aaa-at-subscriber-id {
        value 1007;
        description
          "Subscriber ID";
      }
      enum aaa-at-port-security-enabled {
        value 1008;
        description
          "SNMP index is persistent or need to clear";
      }
      enum aaa-at-static-mac-address {
        value 1009;
        description
          "Static mac address for EFP";
      }
      enum aaa-at-static-mac-address-drop {
        value 1010;
        description
          "Static mac address to be dropped";
      }
      enum aaa-at-static-mac-address-autolearn {
        value 1011;
        description
          "Static mac address to be auto learn";
      }
      enum aaa-at-static-mac-address-disable-snooping {
        value 1012;
        description
          "Static mac address with snooping disable";
      }
      enum aaa-at-recovery-mac-sec-time-interval {
        value 1013;
        description
          "Recovery time interval for mac-security cause";
      }
      enum aaa-at-l2protocol-pdu-action {
        value 1014;
        description
          "L2 protocol PDU action";
      }
      enum aaa-at-mac-tunnel-id {
        value 1015;
        description
          "MAC tunnel ID";
      }
      enum aaa-at-mac-tunnel-description {
        value 1016;
        description
          "Textual description associated with MAC tunnel";
      }
      enum aaa-at-btag-type {
        value 1017;
        description
          "B-Vlan type associated with ethernet mac encapsulation";
      }
      enum aaa-at-btag-vlan-id {
        value 1018;
        description
          "Backbone Vlan-id required for defining matching criteria";
      }
      enum aaa-at-default-destination-mac {
        value 1019;
        description
          "Default destination mac";
      }
      enum aaa-at-itag {
        value 1020;
        description
          "I-Tag value under EFP";
      }
      enum aaa-at-mac-flush-proto {
        value 1021;
        description
          "Protocol used for MAC flush";
      }
      enum aaa-at-mac-flush-cos-value {
        value 1022;
        description
          "Cos value used for MAC flush";
      }
      enum aaa-at-bridge-domain-id {
        value 1023;
        description
          "Bridge domain to be used";
      }
      enum aaa-at-split-horizon-group {
        value 1024;
        description
          "Bridge domain split horizon group";
      }
      enum aaa-at-bridge-domain-type {
        value 1025;
        description
          "Bridge domain type";
      }
      enum aaa-at-max-mac-addr {
        value 1026;
        description
          "Bridge domain max address";
      }
      enum aaa-at-mac-learning {
        value 1027;
        description
          "Bridge domain mac learning enable";
      }
      enum aaa-at-snmp-context {
        value 1028;
        description
          "Bridge domain snmp context";
      }
      enum aaa-at-bridge-domain-member {
        value 1029;
        description
          "Bridge domain member";
      }
      enum aaa-at-bridge-domain-profile {
        value 1030;
        description
          "Bridge domain profile";
      }
      enum aaa-at-mac-security-enabled {
        value 1031;
        description
          "MAC security enabled";
      }
      enum aaa-at-permit-mac-addr-list {
        value 1032;
        description
          "Permit address list (white list)";
      }
      enum aaa-at-deny-mac-addr-list {
        value 1033;
        description
          "Deny address list (black list)";
      }
      enum aaa-at-max-mac-addr-limit {
        value 1034;
        description
          "Per service instance max address limit";
      }
      enum aaa-at-mac-security-sticky {
        value 1035;
        description
          "MAC security sticky address enable";
      }
      enum aaa-at-mac-security-violation-mode {
        value 1036;
        description
          "MAC security violation mode";
      }
      enum aaa-at-mac-security-aging-inactive {
        value 1037;
        description
          "MAC security aging timer for inactive type";
      }
      enum aaa-at-mac-security-aging-absolute {
        value 1038;
        description
          "MAC security aging timer for absolute type";
      }
      enum aaa-at-mac-security-aging-sticky {
        value 1039;
        description
          "Aging for sticky address enable";
      }
      enum aaa-at-mac-security-aging-static {
        value 1040;
        description
          "Aging for static address enable";
      }
      enum aaa-at-uni-count {
        value 1041;
        description
          "Total number of uni on a given evc";
      }
      enum aaa-at-multi-point {
        value 1042;
        description
          "Uni count of 2 is multipoint";
      }
      enum aaa-at-oam-protocol {
        value 1043;
        description
          "Protocol used for MAC flush";
      }
      enum aaa-at-cfm-svlan-id {
        value 1044;
        description
          "CFM Vlan id for CFM protocol";
      }
      enum aaa-at-cfm-vlan-id {
        value 1045;
        description
          "Maintainance association of format vlan id";
      }
      enum aaa-at-service-text {
        value 1046;
        description
          "Maintainance association of format text";
      }
      enum aaa-at-domain-name {
        value 1047;
        description
          "Domain name associated with CFM";
      }
      enum aaa-at-service-profile {
        value 1048;
        description
          "Service profile for CFM";
      }
      enum aaa-at-service-instance-id {
        value 1049;
        description
          "Service instance id";
      }
      enum aaa-at-service-direction {
        value 1050;
        description
          "Service direction of MEP(default is up)";
      }
      enum aaa-at-mip-level {
        value 1051;
        description
          "Identify MIP level";
      }
      enum aaa-at-mep-domain {
        value 1052;
        description
          "MEP domain name";
      }
      enum aaa-at-mep-mpid {
        value 1053;
        description
          "Attribute specify MEP id";
      }
      enum aaa-at-mep-cos {
        value 1054;
        description
          "Attribute specify COS priority for MEP";
      }
      enum aaa-at-mep-alarm-notification {
        value 1055;
        description
          "Attribute specify MEP alarm notification";
      }
      enum aaa-at-mep-alarm-delay {
        value 1056;
        description
          "Attribute specify MEP alarm delay time";
      }
      enum aaa-at-mep-alarm-reset {
        value 1057;
        description
          "Attribute specify MEP alarm reset time";
      }
      enum aaa-at-mip-auto-create-level {
        value 1058;
        description
          "MIP level for mips to be auto created";
      }
      enum aaa-at-mip-auto-create-evc {
        value 1059;
        description
          "EVC name for mips to be auto created";
      }
      enum aaa-at-mip-auto-create-lower-mep-only {
        value 1060;
        description
          "MIPs to be auto created only if active lower level";
      }
      enum aaa-at-mip-auto-create-sender-id {
        value 1061;
        description
          "MIP auto create sensor ID";
      }
      enum aaa-at-service-short-ma-name {
        value 1062;
        description
          "Maintainance association name under domain";
      }
      enum aaa-at-service-fmt {
        value 1063;
        description
          "Service format";
      }
      enum aaa-at-service-vlanid {
        value 1064;
        description
          "Maintainance association of format vlan id";
      }
      enum aaa-at-service-number {
        value 1065;
        description
          "Maintainance association of format number";
      }
      enum aaa-at-service-vpnid {
        value 1066;
        description
          "Maintainance association of format VPN ID";
      }
      enum aaa-at-cfm-service-type {
        value 1067;
        description
          "Maintainance association type";
      }
      enum aaa-at-service-continuity-check {
        value 1068;
        description
          "Service continuity check";
      }
      enum aaa-at-service-continuity-check-interval {
        value 1069;
        description
          "Time interval at which continuity check messages transmitted";
      }
      enum aaa-at-service-continuity-check-loss-threshold {
        value 1070;
        description
          "Service continuity check loss threshold";
      }
      enum aaa-at-service-continuity-check-static-rmep {
        value 1071;
        description
          "Service continuity check received MEP id validation";
      }
      enum aaa-at-service-continuity-check-auto-traceroute {
        value 1072;
        description
          "Service continuity check auto traceroute enabled";
      }
      enum aaa-at-service-mip-autocreate {
        value 1073;
        description
          "Service mip auto create at domain maintainance level";
      }
      enum aaa-at-service-mep-mpid {
        value 1074;
        description
          "Static MEP id in MA";
      }
      enum aaa-at-service-maximum-meps {
        value 1075;
        description
          "Maximum meps supported";
      }
      enum aaa-at-service-ais {
        value 1076;
        description
          "AIS enabled or disabled for the service";
      }
      enum aaa-at-service-ais-period {
        value 1077;
        description
          "AIS transmission period for the service";
      }
      enum aaa-at-service-ais-level {
        value 1078;
        description
          "AIS transmission level for the service";
      }
      enum aaa-at-service-ais-expiry-threshold {
        value 1079;
        description
          "AIS specific expiry threshold";
      }
      enum aaa-at-service-ais-suppress-alarms {
        value 1080;
        description
          "AIS enable/disable of suppression of alarms";
      }
      enum aaa-at-service-lck {
        value 1081;
        description
          "Enable/disable LCK generation for the service";
      }
      enum aaa-at-service-lck-period {
        value 1082;
        description
          "Service transmission period for all meps";
      }
      enum aaa-at-service-lck-level {
        value 1083;
        description
          "Maintainance level to send LCK frames";
      }
      enum aaa-at-service-lck-expiry-threshold {
        value 1084;
        description
          "LCK specific expiry threshold";
      }
      enum aaa-at-service-sender-id-chassis {
        value 1085;
        description
          "Include sender id TLV in CFM packet";
      }
      enum aaa-at-forwarding-service-type {
        value 1086;
        description
          "Represents the type of forwarding service";
      }
      enum aaa-at-forwarding-service-id {
        value 1087;
        description
          "Represents the forwarding service id";
      }
      enum aaa-at-composite-key {
        value 1088;
        description
          "Composite key";
      }
      enum aaa-at-vcid {
        value 1089;
        description
          "VC-ID associated with PW";
      }
      enum aaa-at-vpnid {
        value 1090;
        description
          "VPN-ID associated with VPLS";
      }
      enum aaa-at-pw-encapsulation {
        value 1091;
        description
          "pw-class specification";
      }
      enum aaa-at-pw-classname {
        value 1092;
        description
          "pw-class name for the class defined";
      }
      enum aaa-at-preferred-path-tunnel {
        value 1093;
        description
          "Preferred path tunnel interface";
      }
      enum aaa-at-interworking {
        value 1094;
        description
          "Ethernet or IP interworking";
      }
      enum aaa-at-pw-status {
        value 1095;
        description
          "Enable PW status extension";
      }
      enum aaa-at-sequencing-type {
        value 1096;
        description
          "Sequencing type";
      }
      enum aaa-at-primary-pw {
        value 1097;
        description
          "Primary PW";
      }
      enum aaa-at-backup-delay {
        value 1098;
        description
          "Backup PW enable delay";
      }
      enum aaa-at-redundancy-enable-delay {
        value 1099;
        description
          "Redundancy enable delay interval";
      }
      enum aaa-at-redundancy-disable-delay {
        value 1100;
        description
          "Redundancy disable delay interval";
      }
      enum aaa-at-redundancy-disable-never {
        value 1101;
        description
          "Never disable redundancy";
      }
      enum aaa-at-redundancy-priority {
        value 1102;
        description
          "Redundancy PW priority";
      }
      enum aaa-at-vfi-name {
        value 1103;
        description
          "Name of the VPLS used for forwarding service";
      }
      enum aaa-at-vpls-id {
        value 1104;
        description
          "VPLS ID";
      }
      enum aaa-at-route-distinguisher {
        value 1105;
        description
          "Route distinguisher";
      }
      enum aaa-at-route-target {
        value 1106;
        description
          "Route target";
      }
      enum aaa-at-auto-route-target {
        value 1107;
        description
          "Automatically set a route target";
      }
      enum aaa-at-l2-router-id {
        value 1108;
        description
          "PE-router id";
      }
      enum aaa-at-forward-l2protocol-all {
        value 1109;
        description
          "Permit forwarding of all L2 protocol";
      }
      enum aaa-at-peer-ip-address {
        value 1110;
        description
          "Peer PE ip address";
      }
      enum aaa-at-preferred-peer {
        value 1111;
        description
          "Preferred path peer ip address";
      }
      enum aaa-at-disable-fallback {
        value 1112;
        description
          "Disable Fallback from preferred peer or path";
      }
      enum aaa-at-l2vpn-control-word {
        value 1113;
        description
          "L2VPn control word";
      }
      enum aaa-at-vccv {
        value 1114;
        description
          "Virtual Circuit Connectivity Verification";
      }
      enum aaa-at-service-id {
        value 1115;
        description
          "Service id for downloading profile";
      }
      enum aaa-at-member {
        value 1116;
        description
          "Member of a container";
      }
      enum aaa-at-l2vpn-service-type {
        value 1117;
        description
          "L2VPN service type";
      }
      enum aaa-at-mtp-isid {
        value 1118;
        description
          "I-Tag profile name for I-EFP";
      }
      enum aaa-at-bmac {
        value 1119;
        description
          "Bridge MAC Address";
      }
      enum aaa-at-cmac {
        value 1120;
        description
          "Customer MAC Address";
      }
      enum aaa-at-sgt-name-list-inbound {
        value 1121;
        description
          "SG Name list and generation number";
      }
      enum aaa-at-sgt-name-list-outbound {
        value 1122;
        description
          "SG Name list table";
      }
      enum aaa-at-sgt-name {
        value 1123;
        description
          "SG name for the SGT, format <sgt>-<sg name>";
      }
      enum aaa-at-cdp-opaque {
        value 1124;
        description
          "CDP TLV";
      }
      enum aaa-at-lldp-opaque {
        value 1125;
        description
          "LLDP TLV";
      }
      enum aaa-at-dhcp-opaque {
        value 1126;
        description
          "DHCP TLV";
      }
      enum aaa-at-mdns-opaque {
        value 1127;
        description
          "MDNS TLV";
      }
      enum aaa-at-sip-opaque {
        value 1128;
        description
          "SIP TLV";
      }
      enum aaa-at-h323-opaque {
        value 1129;
        description
          "H323 TLV";
      }
      enum aaa-at-dc-profile-name {
        value 1130;
        description
          "Device Classifier Profile Name";
      }
      enum aaa-at-dc-device-name {
        value 1131;
        description
          "Device Classifier Device Name";
      }
      enum aaa-at-dc-device-class-tag {
        value 1132;
        description
          "Device Classifier Device Class Tag";
      }
      enum aaa-at-dc-profile-tags {
        value 1133;
        description
          "Device Classifier Profile Tags";
      }
      enum aaa-at-dc-protocol-map {
        value 1134;
        description
          "Device Classifier Protocol Map";
      }
      enum aaa-at-dc-certainty-metric {
        value 1135;
        description
          "Device Classifier Certainty Metric";
      }
      enum aaa-at-dc-device-id {
        value 1136;
        description
          "Device Classifier Certainty Metric";
      }
      enum aaa-at-dc-opaque {
        value 1137;
        description
          "Device Classifier Opaque";
      }
      enum aaa-at-pmip6-domain-identifier {
        value 1138;
        description
          "Proxy Mobile IPv6 Domain name";
      }
      enum aaa-at-pmip6-spi-value {
        value 1139;
        description
          "Proxy Mobile IPv6 Security Associations";
      }
      enum aaa-at-pmip6-spi-key {
        value 1140;
        description
          "Proxy Mobile IPv6 SPI key";
      }
      enum aaa-at-pmip6-fixed-ll-address {
        value 1141;
        description
          "Proxy Mobile IPv6 fixed link local address";
      }
      enum aaa-at-pmip6-fixed-l2-address {
        value 1142;
        description
          "Proxy Mobile IPv6 fixed L2 address";
      }
      enum aaa-at-pmip6-replay-protection {
        value 1143;
        description
          "Proxy Mobile IPv6 replay protection type";
      }
      enum aaa-at-pmip6-timestamp-window {
        value 1144;
        description
          "Proxy Mobile IPv6 timestamp validity window";
      }
      enum aaa-at-pmip6-encap-type {
        value 1145;
        description
          "Proxy Mobile IPv6 tunnel encapsulation type";
      }
      enum aaa-at-pmip6-lma-identifier {
        value 1146;
        description
          "Proxy Mobile IPv6 Local Mobility Anchor name";
      }
      enum aaa-at-pmip6-lma-v4-address {
        value 1147;
        description
          "Proxy Mobile IPv6 Local Mobility Anchor IPv4 address";
      }
      enum aaa-at-pmip6-lma-v6-address {
        value 1148;
        description
          "Proxy Mobile IPv6 Local Mobility Anchor IPv6 address";
      }
      enum aaa-at-pmip6-mag-identifier {
        value 1149;
        description
          "Proxy Mobile IPv6 MAG name";
      }
      enum aaa-at-pmip6-mag-v4-address {
        value 1150;
        description
          "Proxy Mobile IPv6 MAG IPv4 address";
      }
      enum aaa-at-pmip6-mag-v6-address {
        value 1151;
        description
          "Proxy Mobile IPv6 MAG IPv6 address";
      }
      enum aaa-at-mn-identifier {
        value 1152;
        description
          "Mobile Node Identifier";
      }
      enum aaa-at-mn-multihomed {
        value 1153;
        description
          "Mobile Node multi-homed service";
      }
      enum aaa-at-mip6-feature-vector {
        value 1154;
        description
          "Mobile IPv6 feature vector";
      }
      enum aaa-at-pmip6-home-lma-identifier {
        value 1155;
        description
          "Proxy Mobile IPv6 MN's Home Local Mobility Anchor Identifier";
      }
      enum aaa-at-pmip6-visited-lma-identifier {
        value 1156;
        description
          "Proxy Mobile IPv6 MN's Visited Local Mobility Anchor Identifier";
      }
      enum aaa-at-mn-gre-encap-key {
        value 1157;
        description
          "Mobile Nodes GRE Encap Key";
      }
      enum aaa-at-mn-service {
        value 1158;
        description
          "Mobile Node's service type";
      }
      enum aaa-at-mn-max-hnp {
        value 1159;
        description
          "MN's Maximum Home Network Prefixes";
      }
      enum aaa-at-pmip6-home-lma-ipv6-address {
        value 1160;
        description
          "MN's Home Local Mobility Anchor IPv6 address";
      }
      enum aaa-at-pmip6-visited-lma-ipv6-address {
        value 1161;
        description
          "MN's Visited Local Mobility Anchor IPv6 address";
      }
      enum aaa-at-pmip6-home-lma-ipv4-address {
        value 1162;
        description
          "MN's Home Local Mobility Anchor IPv4 address";
      }
      enum aaa-at-pmip6-visited-lma-ipv4-address {
        value 1163;
        description
          "MN's Visited Local Mobility Anchor IPv4 address";
      }
      enum aaa-at-pmip6-home-hl-prefix {
        value 1164;
        description
          "MN's Home Prefix length";
      }
      enum aaa-at-pmip6-home-dhcp6-server-address {
        value 1165;
        description
          "MN's Home DHCPv6 Server address";
      }
      enum aaa-at-pmip6-visited-dhcp6-server-address {
        value 1166;
        description
          "MN's Visited DHCPv6 Server address";
      }
      enum aaa-at-pmip6-home-dhcp4-server-address {
        value 1167;
        description
          "MN's Home DHCPv4 Server address";
      }
      enum aaa-at-pmip6-visited-dhcp4-server-address {
        value 1168;
        description
          "MN's Visited DHCPv4 Server address";
      }
      enum aaa-at-pmip6-home-ipv4-hoa {
        value 1169;
        description
          "MN's Home IPv4 address";
      }
      enum aaa-at-pmip6-visited-ipv4-hoa {
        value 1170;
        description
          "MN's Visited IPv4 address";
      }
      enum aaa-at-capwap-tunnel-profile-name {
        value 1171;
        description
          "CAPWAP tunnel profile name";
      }
      enum aaa-at-ppp-ipv4-addr-save {
        value 1172;
        description
          "PPP IPv4 Address Saving";
      }
      enum aaa-at-app-attr {
        value 1173;
        description
          "Application Specific Attribute defined for Connected-Apps";
      }
      enum aaa-at-allowed-app {
        value 1174;
        description
          "Application that a user is allowed to perform";
      }
      enum aaa-at-allowed-action {
        value 1175;
        description
          "Action that an Application is allowed to perform";
      }
      enum aaa-at-auto-acct {
        value 1176;
        description
          "Whether auto accounting is enabled for a user";
      }
      enum aaa-at-fnf-monitor {
        value 1177;
        description
          "FNF Monitor Name";
      }
      enum aaa-at-fnf-sampler {
        value 1178;
        description
          "FNF Sampler Name";
      }
      enum aaa-at-fnf-direction {
        value 1179;
        description
          "Direction to apply FNF monitor";
      }
      enum aaa-at-fnf-traffic-type {
        value 1180;
        description
          "Type of traffic to apply an FNF monitor to";
      }
      enum aaa-at-fnf-subtraffic-type {
        value 1181;
        description
          "Type of sub-traffic to apply an FNF monitor to";
      }
      enum aaa-at-rpclient-source-address {
        value 1182;
        description
          "Radius Proxy Client Source address";
      }
      enum aaa-at-mn-apn {
        value 1183;
        description
          "Mobile Node Access Point Network";
      }
      enum aaa-at-mn-network {
        value 1184;
        description
          "Mobile Node Network";
      }
      enum aaa-at-idle-timeout-direction {
        value 1185;
        description
          "Direction of Idle timeout";
      }
      enum aaa-at-rem-lifetime {
        value 1186;
        description
          "Remaining Lifetime";
      }
      enum aaa-at-user-type {
        value 1187;
        description
          "Type of User";
      }
      enum aaa-at-device-capability {
        value 1188;
        description
          "Device capability";
      }
      enum aaa-at-route-set {
        value 1189;
        description
          "Route set parameters";
      }
      enum aaa-at-chargeable-user-identity {
        value 1190;
        description
          "Chargeable User Identity";
      }
      enum aaa-at-cisco-service-selection {
        value 1191;
        description
          "Service Identifier";
      }
      enum aaa-at-cisco-mobile-node-identifier {
        value 1192;
        description
          "Mobile Node Identifier";
      }
      enum aaa-at-cisco-wlan-ssid {
        value 1193;
        description
          "SSID of the Access Point";
      }
      enum aaa-at-cisco-msisdn {
        value 1194;
        description
          "Mobile Subscriber ISDN Number";
      }
      enum aaa-at-cisco-mn-service {
        value 1195;
        description
          "Mobile Node Service Type";
      }
      enum aaa-at-cisco-mpc-protocol-interface {
        value 1196;
        description
          "Protocol Interface to be used for interfacing with MPC";
      }
      enum aaa-at-cisco-multihoming-support {
        value 1197;
        description
          "Enable/Disable Multihoming support for mobile node";
      }
      enum aaa-at-cisco-uplink-gre-key {
        value 1198;
        description
          "32-bit GRE Key to be used on the uplink path";
      }
      enum aaa-at-cisco-downlink-gre-key {
        value 1199;
        description
          "32-bit GRE Key to be used on the downlink path";
      }
      enum aaa-at-cisco-url-redirect {
        value 1200;
        description
          "HTTP URL of the Captive Portal";
      }
      enum aaa-at-cisco-url-redirect-acl {
        value 1201;
        description
          "The specific Redirect rule";
      }
      enum aaa-at-cisco-home-lma-ipv6-address {
        value 1202;
        description
          "Mobile node's Home Local Mobility Anchor IPv6 address";
      }
      enum aaa-at-cisco-visited-lma-ipv6-address {
        value 1203;
        description
          "Mobile node's Visited Local Mobility Anchor IPv6 address";
      }
      enum aaa-at-cisco-home-lma-ipv4-address {
        value 1204;
        description
          "Mobile node's Home Local Mobility Anchor IPv4 address";
      }
      enum aaa-at-cisco-visited-lma-ipv4-address {
        value 1205;
        description
          "Mobile node's Visited Local Mobility Anchor IPv4 address";
      }
      enum aaa-at-cisco-home-ipv4-home-address {
        value 1206;
        description
          "Mobile node's Home IPv4 address";
      }
      enum aaa-at-cisco-visited-ipv4-home-address {
        value 1207;
        description
          "Mobile node's Visited IPv4 address";
      }
      enum aaa-at-target-scope {
        value 1208;
        description
          "The scope of the target for feature application";
      }
      enum aaa-at-roaming-info {
        value 1209;
        description
          "Information about a roaming event";
      }
      enum aaa-at-rbacl-monitor-all {
        value 1210;
        description
          "Config from server for CTS Role-Based ACL Monitor mode";
      }
      enum aaa-at-cisco-access-vrf-id {
        value 1211;
        description
          "ACCESS Virtual Route Forwarder ID";
      }
      enum aaa-at-cisco-apn-vrf-id {
        value 1212;
        description
          "APN Virtual Route Forwarder ID";
      }
      enum aaa-at-rp-eapuser-ignore-open-session {
        value 1213;
        description
          "Ignored Open Radius Accounting For Active Authenticated Session";
      }
      enum aaa-at-cisco-tunnel-if-handle {
        value 1214;
        description
          "Mobile tunnel interface handle";
      }
      enum aaa-at-cisco-mobility-core-mtu {
        value 1215;
        description
          "MTU towards Mobility core";
      }
      enum aaa-at-cisco-if-adjacency-handle {
        value 1216;
        description
          "Mobile tunnel interface adjacency";
      }
      enum aaa-at-cisco-teid-enable {
        value 1217;
        description
          "Mobile tunnel endpoint enable";
      }
      enum aaa-at-cisco-upstream-key-teid {
        value 1218;
        description
          "Mobile upstream key Tunnel endpoint identifier";
      }
      enum aaa-at-cisco-downstream-key-teid {
        value 1219;
        description
          "Mobile downstream key Tunnel endpoint identifier";
      }
      enum aaa-at-default-ipv4-gw {
        value 1220;
        description
          "The default gateway for the mobile user";
      }
      enum aaa-at-default-gw-mac-address {
        value 1221;
        description
          "MAC address of mobile node's default gateway";
      }
      enum aaa-at-mobile-ipv4-address {
        value 1222;
        description
          "The IP address for the Mobile user";
      }
      enum aaa-at-mobile-ipv4-netmask {
        value 1223;
        description
          "The IP netmask for the mobile user";
      }
      enum aaa-at-download-request {
        value 1224;
        description
          "Type of Download-request";
      }
      enum aaa-at-pmip6-visited-hn-prefix {
        value 1225;
        description
          "Visited HN Prefix";
      }
      enum aaa-at-pmip6-home-interface-id {
        value 1226;
        description
          "Home Interface ID";
      }
      enum aaa-at-pmip6-visited-interface-id {
        value 1227;
        description
          "Proxy Mobile IPv6 Visited Interface ID";
      }
      enum aaa-at-cts-local-db {
        value 1228;
        description
          "CTS local DB attribute";
      }
      enum aaa-at-mos-con {
        value 1229;
        description
          "MOS SCORE - conversational";
      }
      enum aaa-at-rtcp-jitter-buffer-nominal-delay {
        value 1230;
        description
          "Nominal delay of jitter buffer for RTP Control Protocol";
      }
      enum aaa-at-vq-total-packet-loss {
        value 1231;
        description
          "The loss rate of total packet";
      }
      enum aaa-at-vq-out-of-order {
        value 1232;
        description
          "The out of order rate";
      }
      enum aaa-at-entity-attr {
        value 1233;
        description
          "Entity attributes";
      }
      enum aaa-at-voice-vlan {
        value 1234;
        description
          "Voice plug-in attribute";
      }
      enum aaa-at-authz-directive-local {
        value 1235;
        description
          "Authorization Directive Local";
      }
      enum aaa-at-eap-msk {
        value 1236;
        description
          "EAP Master Session Key";
      }
      enum aaa-at-eap-emsk {
        value 1237;
        description
          "EAP Extended Master Session Key";
      }
      enum aaa-at-eap-session-id-fake {
        value 1238;
        description
          "EAP keys session id";
      }
      enum aaa-at-session-linksec-secured {
        value 1239;
        description
          "Link Security Status of the session";
      }
      enum aaa-at-eap-ether {
        value 1240;
        description
          "Ether passed to linksec";
      }
      enum aaa-at-reroute-ipv4 {
        value 1241;
        description
          "Reroute ipv4 details";
      }
      enum aaa-at-reroute-ipv6 {
        value 1242;
        description
          "Reroute ipv6 details";
      }
      enum aaa-at-relay-session-id {
        value 1243;
        description
          "Relay Session ID";
      }
      enum aaa-at-dhcp-option-82-str {
        value 1244;
        description
          "DHCP relay info option 82 from lease query";
      }
      enum aaa-at-mobileopt-server-ipv4addr {
        value 1245;
        description
          "IPv4 addr of the Mobile Optimization SCTP server";
      }
      enum aaa-at-mobileopt-server-port {
        value 1246;
        description
          "SCTP port of the Mobile Optimization server";
      }
      enum aaa-at-cisco-customer-identifier {
        value 1247;
        description
          "Customer Identifier for Proxy Mobile IPv6 mobile node profile";
      }
      enum aaa-at-http-opaque {
        value 1248;
        description
          "HTTP User Agent";
      }
      enum aaa-at-cisco-user-role {
        value 1249;
        description
          "Specifies the User Role";
      }
      enum aaa-at-interface-template-name {
        value 1250;
        description
          "Specifies the interface template to be applied";
      }
      enum aaa-at-frmd-ipv6-address {
        value 1251;
        description
          "The IPv6 address for the user";
      }
      enum aaa-at-identity-session-type {
        value 1252;
        description
          "Identity Session Type";
      }
      enum aaa-at-author-status {
        value 1253;
        description
          "Identity session authorization status";
      }
      enum aaa-at-security-violation-action {
        value 1254;
        description
          "Identity session security violation";
      }
      enum aaa-at-fqdn-acl-name {
        value 1255;
        description
          "Specifies the FQDN ACL Name to be used";
      }
      enum aaa-at-vlan-autoconfig {
        value 1256;
        description
          "VLAN Auto-configuration enable";
      }
      enum aaa-at-vlan-autoconfig-service-info {
        value 1257;
        description
          "VLAN Auto-configuration Service Info";
      }
      enum aaa-at-vlan-autoconfig-command {
        value 1258;
        description
          "Type of vlan-auto-config command";
      }
      enum aaa-at-vlan-autoconfig-subinterface-id {
        value 1259;
        description
          "VLAN Auto-config Sub Interface ID";
      }
      enum aaa-at-cpeid {
        value 1260;
        description
          "Common Platform Enumeration ID Tag";
      }
      enum aaa-at-cisco-config-macro {
        value 1261;
        description
          "Specifies the config macro to be applied";
      }
      enum aaa-at-client-type {
        value 1262;
        description
          "Specifies the VPN Client type";
      }
      enum aaa-at-swbidb {
        value 1263;
        description
          "Bin-OS Software IDB";
      }
      enum aaa-at-client-iif-id {
        value 1264;
        description
          "Client IIF-ID";
      }
      enum aaa-at-intf-id {
        value 1265;
        description
          "Interface index";
      }
      enum aaa-at-auth-level {
        value 1266;
        description
          "Authentication level";
      }
      enum aaa-at-is-basic {
        value 1267;
        description
          "Is Basic";
      }
      enum aaa-at-nsh-dc-tenant-id {
        value 1268;
        description
          "IKE client tenant id";
      }
      enum aaa-at-nsh-dc-source-node-id {
        value 1269;
        description
          "IKE client source node id";
      }
      enum aaa-at-nsh-dc-source-interface-id {
        value 1270;
        description
          "IKE client source interface id";
      }
      enum aaa-at-ancp-access-loop-rem-id {
        value 1271;
        description
          "Access Node Control Protocol access loop rem ID";
      }
      enum aaa-at-fqdn-webauth-acl-name {
        value 1272;
        description
          "Specifies the FQDN WebAuth ACL Name to be used";
      }
      enum aaa-at-security-group-sgt-epg-table {
        value 1273;
        description
          "Security group sgt to End Point Grouping translation table";
      }
      enum aaa-at-security-group-sgt-epg-table-outbound {
        value 1274;
        description
          "Security group sgt to End Point Grouping translation outbound table";
      }
      enum aaa-at-security-group-sg-epg-table-info {
        value 1275;
        description
          "SG-End Point Grouping Translation table entry, format <sgt>-<gen-id>-<flag>-<End Point Grouping Class-Id>-<gen-id><VRF-Name>-<gen-id>";
      }
      enum aaa-at-security-group-default-epg-table {
        value 1276;
        description
          "Security group default End Point Grouping table to derive End Point Grouping";
      }
      enum aaa-at-security-group-default-epg-table-outbound {
        value 1277;
        description
          "Security group default End Point Grouping table to derive outbound End Point Grouping";
      }
      enum aaa-at-security-group-default-epg-table-info {
        value 1278;
        description
          "Default End Point Grouping Translation table entry, format <End Point Grouping Class-Id>-<gen-id><VRF-Name>-<gen-id>";
      }
      enum aaa-at-security-group-default-sgt-table {
        value 1279;
        description
          "Security group default SGT table to derive sgt";
      }
      enum aaa-at-security-group-default-sgt-table-outbound {
        value 1280;
        description
          "Security group default SGT table to derive outbound sgt";
      }
      enum aaa-at-security-group-default-sgt-table-info {
        value 1281;
        description
          "Default SGT Translation table entry, format <sgt>-<gen-id><VRF-Name>-<gen-id>";
      }
      enum aaa-at-security-group-sg-epg-translation-return-code {
        value 1282;
        description
          "SG-End Point Grouping Translation feature status on ISE";
      }
      enum aaa-at-security-group-default-sgt-scalar {
        value 1283;
        description
          "SG-End Point Grouping Translation default SGT scalar value";
      }
      enum aaa-at-web-secure-acl {
        value 1284;
        description
          "web secure acl";
      }
      enum aaa-at-delegated-ipv4-prefix {
        value 1285;
        description
          "Delegated IPv4 Prefix";
      }
      enum aaa-at-service-selection {
        value 1286;
        description
          "Service Selection";
      }
      enum aaa-at-pmip6-mobile-node-identifier {
        value 1287;
        description
          "Mobile Node Identifier";
      }
      enum aaa-at-coa-push {
        value 1288;
        description
          "coa-push";
      }
      enum aaa-at-anchor-vlan-id {
        value 1289;
        description
          "anchor-vlan";
      }
      enum aaa-at-route-redistribute {
        value 1290;
        description
          "Redistribute routes from routing protocols";
      }
      enum aaa-at-bsn-ipv6-acl-name {
        value 1291;
        description
          "IPV6 ACL Name";
      }
      enum aaa-at-psk {
        value 1292;
        description
          "Pre-Shared Key";
      }
      enum aaa-at-psk-mode {
        value 1293;
        description
          "PSK mode";
      }
      enum aaa-at-nas-identifier-wireless {
        value 1294;
        description
          "A string identifying the NAS in Authentication and Accounting Packets";
      }
      enum aaa-at-ericssion-rtts-estm-thrhput {
        value 1295;
        description
          "Ericsson RTTS Estimated Throughput";
      }
      enum aaa-at-ericsson-rtts-result {
        value 1296;
        description
          "Ericsson RTTS Result";
      }
      enum aaa-at-ericsson-rtts-bckoff-tmr {
        value 1297;
        description
          "Ericsson RTTS Backoff Timer";
      }
      enum aaa-at-ericsson-rtts-reestm-period {
        value 1298;
        description
          "Ericsson RTTS Re-estimation Period";
      }
      enum aaa-at-ericsson-rtts-reestm-bel-thrhput {
        value 1299;
        description
          "Ericsson RTTS Re-estimate When Below Throughput";
      }
      enum aaa-at-ericsson-rtts-reestm-keepalive-num {
        value 1300;
        description
          "Ericsson RTTS Re-estimate Keepalive Number";
      }
      enum aaa-at-ericsson-rtts-early-lift-thrput-thrhold {
        value 1301;
        description
          "Ericsson RTTS Early Lift Throughput Threshold";
      }
      enum aaa-at-bsn-data-bs-average-contract-up {
        value 1302;
        description
          "Data Bandwidth Average Contract Upstream";
      }
      enum aaa-at-bsn-real-time-bw-average-contract-up {
        value 1303;
        description
          "RealTime Bandwidth Average Contract Upstream";
      }
      enum aaa-at-bsn-data-bw-burst-contract-up {
        value 1304;
        description
          "Data Bandwidth Burst Contract Upstream";
      }
      enum aaa-at-bsn-real-time-bw-burst-contract-up {
        value 1305;
        description
          "RealTime Bandwidth Burst Contract Upstream";
      }
      enum aaa-at-opendns-param {
        value 1306;
        description
          "Open DNS profiling option under wireless policy";
      }
      enum aaa-at-url-filter-preauth {
        value 1307;
        description
          "Pre-authentication URL filter";
      }
      enum aaa-at-url-filter-postauth {
        value 1308;
        description
          "Post-authentication URL filter";
      }
      enum aaa-at-primary-tgw-ip {
        value 1309;
        description
          "Primary tunnel gateway IP address";
      }
      enum aaa-at-secondary-tgw-ip {
        value 1310;
        description
          "Secondary tunnel gateway IP address";
      }
      enum aaa-at-gw-domain-name {
        value 1311;
        description
          "Tunnel gateway domain name";
      }
      enum aaa-at-eogre-vlan {
        value 1312;
        description
          "User VLAN id for EoGRE tunneling";
      }
      enum aaa-at-mdns-profile-name {
        value 1313;
        description
          "Used as mdns policy name in case of AAA override";
      }
      enum aaa-at-wfa-subscription-remediation {
        value 1314;
        description
          "WiFi Alliance subscription remediation";
      }
      enum aaa-at-wfa-ap-version {
        value 1315;
        description
          "WiFi Alliance AP version";
      }
      enum aaa-at-wfa-mobile-device-version {
        value 1316;
        description
          "WiFi Alliance mobile device version";
      }
      enum aaa-at-wfa-deauthentication-request {
        value 1317;
        description
          "WiFi Alliance deauthentication request";
      }
      enum aaa-at-wfa-session-information {
        value 1318;
        description
          "WiFi Alliance session information";
      }
      enum aaa-at-wfa-roaming-consortium {
        value 1319;
        description
          "WiFi Alliance roaming consortium information";
      }
      enum aaa-at-wfa-tc-filename {
        value 1320;
        description
          "WiFi Alliance terms and conditions filename";
      }
      enum aaa-at-wfa-tc-filtering {
        value 1321;
        description
          "WiFi Alliance terms and conditions filtering";
      }
      enum aaa-at-wfa-timestamp {
        value 1322;
        description
          "WiFi Alliance timestamp";
      }
      enum aaa-at-dhcpv6-opaque {
        value 1323;
        description
          "DHCPv6 TLV";
      }
      enum aaa-at-cts-pac-capability {
        value 1324;
        description
          "Include CTS PAC Capability";
      }
      enum aaa-at-redirect-append-client-mac {
        value 1325;
        description
          "Append client Mac Address in the URL";
      }
      enum aaa-at-url-redirect-append-switch-mac {
        value 1326;
        description
          "Append switch Mac Address in the URL";
      }
      enum aaa-at-dns-acl-preauth {
        value 1327;
        description
          "Pre-authentication DNS ACL";
      }
      enum aaa-at-dns-acl {
        value 1328;
        description
          "DNS ACL";
      }
      enum aaa-at-private-group-id {
        value 1329;
        description
          "Windows Private Network Group ID";
      }
      enum aaa-at-private-group-name {
        value 1330;
        description
          "Windows Private Network Group name";
      }
      enum aaa-at-private-group-owner {
        value 1331;
        description
          "Windows Private Network Group owner";
      }
      enum aaa-at-fqdn-domain-list {
        value 1332;
        description
          "FQDN profile list for MUD";
      }
      enum aaa-at-fqdn-domain-url {
        value 1333;
        description
          "Domain names as part of download";
      }
      enum aaa-at-fqdn-domain-acl-name {
        value 1334;
        description
          "FQDN acl for MUD";
      }
      enum aaa-at-cts-sgt-acct {
        value 1335;
        description
          "Cisco trustsec SGT for accounting";
      }
      enum aaa-at-cts-vn-acct {
        value 1336;
        description
          "Cisco trustsec VRF name for accounting";
      }
      enum aaa-at-device-analytics {
        value 1337;
        description
          "Attribute for device classification";
      }
      enum aaa-at-wfa-tc-url {
        value 1338;
        description
          "WiFi Alliance terms and conditions URL";
      }
      enum aaa-at-server-ipv4 {
        value 1339;
        description
          "Support multiple IPv4 addresses per server";
      }
      enum aaa-at-server-ipv6 {
        value 1340;
        description
          "Support multiple IPv6 addresses per server";
      }
      enum aaa-at-svr-zip-code {
        value 1341;
        description
          "Support multiple IPv6 addresses per server";
      }
      enum aaa-at-svr-device-type {
        value 1342;
        description
          "Support multiple IPv6 addresses per server";
      }
      enum aaa-at-svr-device-model-number {
        value 1343;
        description
          "Support multiple IPv6 addresses per server";
      }
      enum aaa-at-svr-lat-long {
        value 1344;
        description
          "Support multiple IPv6 addresses per server";
      }
      enum aaa-at-svr-venue-category {
        value 1345;
        description
          "Support multiple IPv6 addresses per server";
      }
      enum aaa-at-svr-network-type {
        value 1346;
        description
          "Support multiple IPv6 addresses per server";
      }
      enum aaa-at-aggregation-aaa {
        value 1347;
        description
          "Support multiple IPv6 addresses per server";
      }
      enum aaa-at-bw-venue-id {
        value 1348;
        description
          "Support multiple IPv6 addresses per server";
      }
      enum aaa-at-bw-venue-tz {
        value 1349;
        description
          "Support multiple IPv6 addresses per server";
      }
      enum aaa-at-bw-class {
        value 1350;
        description
          "Support multiple IPv6 addresses per server";
      }
      enum aaa-at-bw-value-description {
        value 1351;
        description
          "Support multiple IPv6 addresses per server";
      }
      enum aaa-at-bw-iso-country-code {
        value 1352;
        description
          "Support multiple IPv6 addresses per server";
      }
      enum aaa-at-bw-e164-country-code {
        value 1353;
        description
          "Support multiple IPv6 addresses per server";
      }
      enum aaa-at-bw-state-name {
        value 1354;
        description
          "Support multiple IPv6 addresses per server";
      }
      enum aaa-at-bw-city-name {
        value 1355;
        description
          "Support multiple IPv6 addresses per server";
      }
      enum aaa-at-bw-area-code {
        value 1356;
        description
          "Support multiple IPv6 addresses per server";
      }
      enum aaa-at-bw-user-group {
        value 1357;
        description
          "Support multiple IPv6 addresses per server";
      }
      enum aaa-at-bw-venue-name {
        value 1358;
        description
          "Support multiple IPv6 addresses per server";
      }
      enum aaa-at-bw-operator-name {
        value 1359;
        description
          "Support multiple IPv6 addresses per server";
      }
      enum aaa-at-as-supported {
        value 1360;
        description
          "Authentication Survivability Supported";
      }
      enum aaa-at-as-username {
        value 1361;
        description
          "Authentication Survivability Username";
      }
      enum aaa-at-as-credential-hash {
        value 1362;
        description
          "Authentication Survivability Credential Hash";
      }
      enum aaa-at-service-wlan-prof-name {
        value 1363;
        description
          "WLAN Profile Name";
      }
      enum aaa-at-fqdn-redirect-acl {
        value 1364;
        description
          "FQDN Redirect ACL";
      }
      enum aaa-at-cisco-bssid {
        value 1365;
        description
          "BSSID of the Access Point";
      }
      enum aaa-at-cisco-site-name {
        value 1366;
        description
          "Site tag name";
      }
      enum aaa-at-cisco-anonce {
        value 1367;
        description
          "Cisco authenticator nonce";
      }
      enum aaa-at-cisco-easy-psk-err-cause {
        value 1368;
        description
          "Cisco easy PSK error cause";
      }
      enum aaa-at-cisco-8021x-data {
        value 1369;
        description
          "Complete EAPOL M2 message";
      }
      enum aaa-at-wlan-pairwise-cipher {
        value 1370;
        description
          "WLAN pairwise cipher";
      }
      enum aaa-at-wlan-group-cipher {
        value 1371;
        description
          "WLAN group cipher";
      }
      enum aaa-at-wlan-akm-suite {
        value 1372;
        description
          "WLAN AKM suite";
      }
      enum aaa-at-wlan-group-mgmt-cipher {
        value 1373;
        description
          "WLAN group management cipher";
      }
      enum aaa-at-wlan-reason-code {
        value 1374;
        description
          "WLAN reason code";
      }
      enum aaa-at-operator-name {
        value 1375;
        description
          "Operator name";
      }
      enum aaa-at-mdns-location-id {
        value 1376;
        description
          "MDNS location id";
      }
      enum aaa-at-cisco-duid {
        value 1377;
        description
          "Device unique identifier";
      }
      enum aaa-at-cisco-5g-auth-rand {
        value 1378;
        description
          "Random Challenge";
      }
      enum aaa-at-cisco-5g-auth-autn {
        value 1379;
        description
          "Authentication Token";
      }
      enum aaa-at-cisco-5g-auth-hxres-star {
        value 1380;
        description
          "5G Hash Expected Response Star";
      }
      enum aaa-at-cisco-5g-auth-kseaf {
        value 1381;
        description
          "5G Security Anchor Function Key";
      }
      enum aaa-at-cisco-5g-auth-auts {
        value 1382;
        description
          "Authentication Token for Re-synchronization";
      }
      enum aaa-at-cisco-5g-sn-name {
        value 1383;
        description
          "Serving Network Name";
      }
      enum aaa-at-cisco-5g-dnn {
        value 1384;
        description
          "Data Network Name used in 5G";
      }
      enum aaa-at-cisco-5g-ssc-mode {
        value 1385;
        description
          "5G Session and Service Continuity Mode";
      }
      enum aaa-at-cisco-5g-s-nssai {
        value 1386;
        description
          "5G Single Network Slice Selection Assistance Information";
      }
      enum aaa-at-cisco-rogue-ap-state {
        value 1387;
        description
          "Rogue AP State";
      }
      enum aaa-at-cisco-rogue-ap-class {
        value 1388;
        description
          "Rogue AP Classification";
      }
      enum aaa-at-qos-policy-ul {
        value 1389;
        description
          "Uplink QoS Policy Name";
      }
      enum aaa-at-qos-policy-dl {
        value 1390;
        description
          "Downlink QoS Policy Name";
      }
      enum aaa-at-push-id {
        value 1391;
        description
          "Unique identification of the CoA transaction";
      }
      enum aaa-at-policy-version-id {
        value 1392;
        description
          "Policy matrix identification details for CTS change of authorisation";
      }
      enum aaa-at-report-config-type {
        value 1393;
        description
          "Various type of reporting methods for TrustSEC CoA";
      }
      enum aaa-at-vm-bridge-mac {
        value 1394;
        description
          "MAC address of VM Bridge Host";
      }
      enum aaa-at-location-info {
        value 1395;
        description
          "RFC 5580 Location Information attribute";
      }
      enum aaa-at-location-data {
        value 1396;
        description
          "RFC 5580 Location Data attribute";
      }
      enum aaa-at-location-capable {
        value 1397;
        description
          "RFC 5580 Location Capable attribute";
      }
      enum aaa-at-rbacl-ip-version {
        value 1398;
        description
          "Support CoA for Role-based ACL IP Version";
      }
      enum aaa-at-meraki-device-name {
        value 1399;
        description
          "Support Meraki device name for AAA attribute";
      }
      enum aaa-at-meraki-network-name {
        value 1400;
        description
          "Support Meraki network name for AAA attribute";
      }
      enum aaa-at-meraki-ap-name {
        value 1401;
        description
          "Support Meraki AP name for AAA attribute";
      }
      enum aaa-at-meraki-ap-tags {
        value 1402;
        description
          "Support Meraki AP tags for AAA attribute";
      }
      enum aaa-at-meraki-ipsk {
        value 1403;
        description
          "Support Meraki IPSK for AAA attribute";
      }
    }
    description
      "AAA Attribute Type";
  }

  grouping aaa-protocol-type {
    description
      "AAA Protocol Type";
    leaf protocol {
      type aaa-types:protocol-type;
      description
        "Protocol value";
    }
  }

  grouping aaa-service-type {
    description
      "AAA Service Type";
    leaf svc-type {
      type aaa-types:serv-type;
      description
        "Service value";
    }
  }
}
