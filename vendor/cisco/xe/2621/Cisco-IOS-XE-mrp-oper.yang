module Cisco-IOS-XE-mrp-oper {
  yang-version 1.1;
  namespace "http://cisco.com/ns/yang/Cisco-IOS-XE-mrp-oper";
  prefix mrp-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for MRP (Media Redundancy Protocol) operational data.
     Copyright (c) 2021-2022, 2026 by Cisco Systems, Inc.
     All rights reserved.";

  revision 2026-08-01 {
    description
      "- Updated descriptions for several model elements to clarify their meaning and purpose
       - Added a units annotation to beacon-interval leaf in mrp-ring-hw-stats grouping";
    reference
      "1.1.0";
    cisco-semver:module-version "1.1.0";
  }
  revision 2024-03-01 {
    description
      "Initial revision";
    reference
      "1.0.0";
    cisco-semver:module-version "1.0.0";
  }

  typedef mrp-port-status {
    type enumeration {
      enum mrp-port-disabled {
        value 0;
        description
          "MRP Ring port disabled";
      }
      enum mrp-port-blocked {
        value 1;
        description
          "MRP Ring port blocked";
      }
      enum mrp-port-forwarding {
        value 2;
        description
          "MRP Ring port status forwarding";
      }
      enum mrp-port-not-connected {
        value 3;
        description
          "MRP Ring port not connected";
      }
      enum mrp-port-err-disabled {
        value 4;
        description
          "MRP Ring port error disabled";
      }
      enum mrp-port-na {
        value 5;
        description
          "MRP Ring port status Not Available";
      }
    }
    description
      "MRP Ring port status";
  }

  typedef mrp-ring-mode {
    type enumeration {
      enum mrp-mode-none {
        value 0;
        description
          "MRP Ring mode Not Available";
      }
      enum mrp-mode-client {
        value 1;
        description
          "MRP Ring Client mode";
      }
      enum mrp-mode-mgr {
        value 2;
        description
          "MRP Ring Manager mode";
      }
      enum mrp-mode-auto-mgr {
        value 3;
        description
          "MRP Ring Auto Manager mode";
      }
    }
    description
      "MRP Ring mode";
  }

  typedef mrp-ring-source {
    type enumeration {
      enum mrp-src-profinet {
        value 0;
        description
          "MRP Ring configured from other protocol";
      }
      enum mrp-src-cli {
        value 1;
        description
          "MRP Ring configured from CLI";
      }
    }
    description
      "MRP Ring Config Source";
  }

  typedef mrp-ring-license {
    type enumeration {
      enum mrp-lic-na {
        value 0;
        description
          "MRP Ring License Not Applicable";
      }
      enum mrp-lic-inactive {
        value 1;
        description
          "MRP Ring License Inactive";
      }
      enum mrp-lic-active {
        value 2;
        description
          "MRP Ring License Active";
      }
    }
    description
      "MRP Ring License State";
  }

  typedef mrp-ring-gw-status {
    type enumeration {
      enum mrp-gw-disabled {
        value 0;
        description
          "MRP Ring Gateway Disabled";
      }
      enum mrp-gw-enabled {
        value 1;
        description
          "MRP Ring Gateway Enabled";
      }
    }
    description
      "MRP Ring Gateway Status";
  }

  typedef mrp-ring-packet-block-frame {
    type enumeration {
      enum mrp-frame-start {
        value 0;
        description
          "MRP Ring Start frame";
      }
      enum mrp-frame-common {
        value 1;
        description
          "MRP Ring Common frame";
      }
      enum mrp-frame-test {
        value 2;
        description
          "MRP Ring Test frame";
      }
      enum mrp-frame-topo-change {
        value 3;
        description
          "MRP Ring Topology change frame";
      }
      enum mrp-frame-link-dn {
        value 4;
        description
          "MRP Ring Link Down frame";
      }
      enum mrp-frame-link-up {
        value 5;
        description
          "MRP Ring Link Up frame";
      }
      enum mrp-frame-mgr-nack {
        value 6;
        description
          "MRP Ring Test Manager NAck frame";
      }
      enum mrp-frame-test-ppgt {
        value 7;
        description
          "MRP Ring Test Propagate frame";
      }
      enum mrp-frame-na {
        value 127;
        description
          "MRP Ring Not filtered frame";
      }
    }
    description
      "MRP Ring Packet Block frame type";
  }

  typedef mrp-ring-nw-status {
    type enumeration {
      enum mrp-nw-na {
        value 0;
        description
          "MRP Ring Network Status Not Available";
      }
      enum mrp-nw-idle {
        value 1;
        description
          "MRP Ring has Idle Network Status";
      }
      enum mrp-nw-open {
        value 2;
        description
          "MRP Ring has Open Network Status";
      }
      enum mrp-nw-closed {
        value 3;
        description
          "MRP Ring has Closed Network Status";
      }
      enum mrp-nw-unknown {
        value 4;
        description
          "MRP Ring is configured, but Network status is Unknown";
      }
    }
    description
      "MRP Ring Network Status";
  }

  typedef mrp-ring-network-topology {
    type enumeration {
      enum mrp-topo-ring {
        value 0;
        description
          "MRP Ring Ring Network Topology";
      }
    }
    description
      "MRP Ring Network Topology";
  }

  grouping mrp-ring-identity {
    description
      "MRP ring identity";
    leaf ring-id {
      type uint8;
      description
        "Unique ID of MRP ring";
    }
  }

  grouping mrp-ring-port-block {
    description
      "MRP ring port info";
    leaf name {
      type string;
      description
        "Name of port";
    }
    leaf mac-addr {
      type yang:mac-address;
      description
        "MAC address of port";
    }
    leaf if-name {
      type string;
      description
        "Interface name of port";
    }
    leaf sts {
      type mrp-ios-xe-oper:mrp-port-status;
      description
        "Status of port";
    }
  }

  grouping mrp-ring-summary {
    description
      "Summary information for the MRP ring";
    leaf prof {
      type uint16;
      description
        "Profile identifier for the MRP ring";
    }
    leaf mode {
      type mrp-ios-xe-oper:mrp-ring-mode;
      description
        "Configured mode of the MRP ring";
    }
    leaf priority {
      type uint16;
      description
        "Configured priority of the MRP ring";
    }
    leaf oper-mode {
      type mrp-ios-xe-oper:mrp-ring-mode;
      description
        "Operational mode of MRP ring";
    }
    leaf src {
      type mrp-ios-xe-oper:mrp-ring-source;
      description
        "Source of MRP ring config";
    }
    leaf lic {
      type mrp-ios-xe-oper:mrp-ring-license;
      description
        "Indicates the license state of the MRP ring";
    }
    leaf gw-sts {
      type mrp-ios-xe-oper:mrp-ring-gw-status;
      description
        "Indicates the gateway status of the MRP ring";
    }
    leaf vlan-id {
      type uint16;
      description
        "Vlan id of MRP ring";
    }
    leaf dom-name {
      type string;
      description
        "Domain name of MRP ring";
    }
    leaf dom-id {
      type string;
      description
        "Domain id of MRP ring";
    }
    leaf best-mgr-mac-addr {
      type yang:mac-address;
      description
        "Mac address of best manager in MRP ring";
    }
    leaf best-mgr-priority {
      type uint16;
      description
        "Priority of best manager in MRP ring";
    }
  }

  grouping mrp-ring-parameters {
    description
      "MRP ring parameters";
    leaf tc-req-intl-ms {
      type uint16;
      description
        "Topology change request interval in milliseconds";
    }
    leaf tc-rep-cnt {
      type uint16;
      description
        "Topology change repeat count";
    }
    leaf st-frame-intl-ms {
      type uint16;
      description
        "Short test frame interval in milliseconds";
    }
    leaf dt-frame-intl-ms {
      type uint16;
      description
        "Default test frame interval in milliseconds";
    }
    leaf ot-frame-intl-ms {
      type uint16;
      description
        "Operational test frame interval in milliseconds";
    }
    leaf tm-intl-cnt {
      type uint16;
      description
        "Test monitoring interval count";
    }
    leaf tm-ext-intl-cnt {
      type uint16;
      description
        "Test monitoring extended interval count";
    }
    leaf lndn-tmr-intl-ms {
      type uint16;
      description
        "Link down timer interval in milliseconds";
    }
    leaf lnup-tmr-intl-ms {
      type uint16;
      description
        "Link up timer interval in milliseconds";
    }
    leaf lnk-cng-cnt-ms {
      type uint16;
      description
        "Link change count in milliseconds";
    }
  }

  grouping mrp-ring-detail {
    description
      "MRP ring details";
    container info {
      description
        "Information about MRP ring";
      uses mrp-ios-xe-oper:mrp-ring-summary;
    }
    leaf nw-topo {
      type mrp-ios-xe-oper:mrp-ring-network-topology;
      description
        "Indicates the network topology of the MRP ring";
    }
    leaf nw-sts {
      type mrp-ios-xe-oper:mrp-ring-nw-status;
      description
        "Indicates the current network status of the MRP ring";
    }
    list port {
      description
        "List of ports in the MRP ring";
      uses mrp-ios-xe-oper:mrp-ring-port-block;
    }
    container params {
      description
        "Detailed parameters for MRP ring";
      uses mrp-ios-xe-oper:mrp-ring-parameters;
    }
  }

  grouping mrp-ring-port {
    description
      "MRP ring port info for two ports";
    leaf prim-port {
      type string;
      description
        "Name of primary port of MRP Ring";
    }
    leaf prim-port-sts {
      type mrp-ios-xe-oper:mrp-port-status;
      description
        "Status of primary port of MRP Ring";
    }
    leaf sec-port {
      type string;
      description
        "Name of secondary port of MRP Ring";
    }
    leaf sec-port-sts {
      type mrp-ios-xe-oper:mrp-port-status;
      description
        "Status of secondary port of MRP Ring";
    }
  }

  grouping client-events {
    description
      "MRP ring client events stats";
    leaf conf-notif-events {
      type uint32;
      description
        "Number of notification events for client";
    }
    leaf p1up-ev {
      type uint32;
      description
        "Number of ring port 1 up events";
    }
    leaf p2up-ev {
      type uint32;
      description
        "Number of ring port 2 up events";
    }
    leaf p1dn-ev {
      type uint32;
      description
        "Number of ring port 1 down events";
    }
    leaf p2dn-ev {
      type uint32;
      description
        "Number of ring port 2 down events";
    }
    leaf top-change-ev {
      type uint32;
      description
        "Number of ring topology change events";
    }
    leaf uptmr-ex-lnknret-zero-ev {
      type uint32;
      description
        "Ring link up Timer expiry event";
    }
    leaf uptmr-ex-lnknret-ps-ev {
      type uint32;
      description
        "Client node Link Up timer expired, send next Link Up packet";
    }
    leaf dntm-ex-lnknret-zero-ev {
      type uint32;
      description
        "Ring link down timer expiry event";
    }
    leaf dntm-ex-lnknret-ps-ev {
      type uint32;
      description
        "Client node Link down timer expired, send next Link Down packet";
    }
  }

  grouping auto-manager-events {
    description
      "MRP ring auto manager events stats";
    leaf am-conf-notif-events {
      type uint32;
      description
        "Number of notification events for auto manager";
    }
    leaf am-stat1-mautci-p1-up {
      type uint32;
      description
        "Primary port 1 link up event from init down state";
    }
    leaf am-stat1-mautci-p2-up {
      type uint32;
      description
        "Primary port 2 link up event from init down state";
    }
    leaf am-prm-tt-expiry {
      type uint32;
      description
        "Ring periodic test/beacon timer expiry event";
    }
    leaf am-prm-mautci-p1-dn {
      type uint32;
      description
        "In MRA mode, number of manager-ring primary-port down events in primary-ring state";
    }
    leaf am-prm-mautci-p2-up {
      type uint32;
      description
        "In MRA mode, number of manager-ring secondary-port up events in primary-ring state";
    }
    leaf am-prm-ro-rc-tr-ind-self {
      type uint32;
      description
        "In MRA mode, number of self-beacon receive events for manager ring in primary-up, ring-open, or ring-closed state";
    }
    leaf am-prm-ro-rc-tr-ind-nsnb {
      type uint32;
      description
        "In MRA mode, number of test-beacon receive events where remote priority is not better than local priority for manager ring in primary-up, ring-open, or ring-closed state";
    }
    leaf am-prm-ro-rc-lc-ind-n-at {
      type uint32;
      description
        "In MRA mode, number of link-state change events with ADD TEST disabled for manager ring in primary-up, ring-open, or ring-closed state";
    }
    leaf am-prm-ro-rc-tc-ns {
      type uint32;
      description
        "In MRA mode, number of topology-change events where TC is not self-generated for manager ring in primary-up, ring-open, or ring-closed state";
    }
    leaf am-prm-rorc-tm-nk-i-nsbnb {
      type uint32;
      description
        "MRA mode, receive nack when not better event in ring primary up/RING OPEN/RING CLOSED state for manager ring";
    }
    leaf am-prm-rorc-tm-nk-i-nsbb {
      type uint32;
      description
        "MRA mode, receive nack when better event in ring primary up/RING OPEN/RING CLOSED state for manager ring";
    }
    leaf am-ro-tt-expiry {
      type uint32;
      description
        "MRA mode, test timer expiry event in RING OPEN state for manager ring";
    }
    leaf am-ro-mautci-p1-dn {
      type uint32;
      description
        "MRA mode, primary port down event in RING OPEN state for manager ring";
    }
    leaf am-ro-mautci-p2-dn {
      type uint32;
      description
        "MRA mode, secondary port down event in RING OPEN state for manager ring";
    }
    leaf am-rc-tt-nret-gr {
      type uint32;
      description
        "MRA mode, test timer expiry or test beacon loss event in RING CLOSED state for manager ring";
    }
    leaf am-rc-tt-nret-gr-no-tc {
      type uint32;
      description
        "MRA mode, test timer expiry or test beacon loss event in RING CLOSED state for manager ring with no topology change event";
    }
    leaf am-rc-tt-nret-less {
      type uint32;
      description
        "MRA mode, test timer expiry event with n return count < max for manager ring in RING CLOSED state";
    }
    leaf am-rc-mautci-p1-dn {
      type uint32;
      description
        "MRA mode, manager ring primary port down event in RING CLOSED state";
    }
    leaf am-rc-mautci-p2-dn {
      type uint32;
      description
        "MRA mode, manager ring secondary port down event in RING CLOSED state";
    }
    leaf am-de-pt-idlett-nret-less {
      type uint32;
      description
        "MRA mode, test timer expiry event with test n return count < max for client ring in de pt idle state";
    }
    leaf am-de-pt-idlett-nret-gr {
      type uint32;
      description
        "MRA mode, test timer expiry and oper mode change to MANAGER event for client in de pt idle state";
    }
    leaf am-de-idle-mautci-p2-up {
      type uint32;
      description
        "MRA mode, client ring secondary port up event in de idle ring state";
    }
    leaf am-de-idle-mautci-p1-dn {
      type uint32;
      description
        "MRA mode, client ring primary port down event in de idle ring state";
    }
    leaf am-de-idle-tc-ind {
      type uint32;
      description
        "MRA mode, client ring topology change event in de idle ring state";
    }
    leaf am-de-idle-tc-ind-hyst {
      type uint32;
      description
        "MRP topology change event received for client with link up hysteresis timer running";
    }
    leaf am-de-idle-tr-ind-self {
      type uint32;
      description
        "MRP Test frame received by client in de idle state with current best manager priority";
    }
    leaf am-de-idle-tr-ind-nsnb {
      type uint32;
      description
        "MRP Test frame received by client in de idle state with remote priority not better";
    }
    leaf am-pt-de-idletr-ind-nsbnb {
      type uint32;
      description
        "MRA mode, remote priority not better than own priority event for client ring in pt de idle state";
    }
    leaf am-pt-de-idletr-ind-nsbb {
      type uint32;
      description
        "MRA mode, remote priority better event for client ring in pt de idle state";
    }
    leaf am-pt-de-idle-prop-nsb {
      type uint32;
      description
        "MRA mode, PROP receive event for client ring in pt de idle state";
    }
    leaf am-de-dntm-exlnknret-zero {
      type uint32;
      description
        "MRA mode, Link Down timer expiry event with 'link N return'  = 0 for client ring in de state";
    }
    leaf am-de-dntm-exlnknret-ps {
      type uint32;
      description
        "MRA mode, Link Down timer expiry event with 'link N return'  > 0 for client ring in de state";
    }
    leaf am-de-mautci-p2-up {
      type uint32;
      description
        "MRA mode, client ring secondary port up event in de state";
    }
    leaf am-de-mautci-p1-dn {
      type uint32;
      description
        "MRA mode, client ring primary port down event in de state";
    }
    leaf am-pt-de-idle-tc-ind {
      type uint32;
      description
        "MRA mode, client ring topology change events in de idle ring state";
    }
    leaf am-pt-uptm-exlnknret-zero {
      type uint32;
      description
        "MRA mode, Link Up timer expiry event with 'link N return'  = 0 for client ring in pt state";
    }
    leaf am-pt-uptm-exlnknret-ps {
      type uint32;
      description
        "MRA mode, Link Up timer expiry event with 'link N return'  > 0 for client ring in pt state";
    }
    leaf am-pt-mautci-p2-dn {
      type uint32;
      description
        "MRA mode, client ring secondary port down event in pt ring state";
    }
    leaf am-pt-mautci-p1-dn {
      type uint32;
      description
        "MRA mode, client ring primary port down event in pt ring state";
    }
    leaf am-pt-idle-mautci-p2-dn {
      type uint32;
      description
        "MRA mode, client ring secondary port down event in pt idle ring state";
    }
    leaf am-pt-idle-mautci-p1-dn {
      type uint32;
      description
        "MRA mode, client ring primary port down event in pt idle ring state";
    }
    leaf am-ring-open-cnt {
      type uint32;
      description
        "MRA mode, ring OPEN state transition count";
    }
    leaf am-ring-tx-cnt {
      type uint32;
      description
        "MRA mode, ring state transition count";
    }
  }

  grouping mrp-ring-event-stats {
    description
      "MRP ring event statistics";
    container client {
      description
        "MRP ring client event stats";
      uses mrp-ios-xe-oper:client-events;
    }
    container auto-mgr {
      description
        "MRP ring auto manager event stats";
      uses mrp-ios-xe-oper:auto-manager-events;
    }
  }

  grouping hardware-stats-block {
    description
      "Hardware stat block info";
    leaf beac-rx {
      type uint32;
      description
        "Number of received beacon frames";
    }
    leaf beac-tx {
      type uint32;
      description
        "Number of transmitted beacon frames";
    }
    leaf beac-drop {
      type uint32;
      description
        "Number of dropped beacon frames";
    }
    leaf nack-rx {
      type uint32;
      description
        "Number of received NACK frames";
    }
    leaf nack-tx {
      type uint32;
      description
        "Number of transmitted NACK frames";
    }
    leaf nack-drop {
      type uint32;
      description
        "Number of dropped NACK frames";
    }
    leaf prop-rx {
      type uint32;
      description
        "Number of received propagate frames";
    }
    leaf prop-tx {
      type uint32;
      description
        "Number of transmitted propagate frames";
    }
    leaf prop-drop {
      type uint32;
      description
        "Number of dropped propagate frames";
    }
  }

  grouping mrp-ring-hw-stats {
    description
      "MRP ring hardware statistics";
    leaf ring-state {
      type mrp-ios-xe-oper:mrp-ring-nw-status;
      description
        "Operational state of the MRP ring";
    }
    leaf beac-intl {
      type uint16;
      units "milliseconds";
      description
        "Beacon interval in milliseconds";
    }
    leaf port-one-name {
      type string;
      description
        "Name of port one";
    }
    container port-one-stats {
      description
        "Hardware stats of port one";
      uses mrp-ios-xe-oper:hardware-stats-block;
    }
    leaf port-two-name {
      type string;
      description
        "Name of port two";
    }
    container port-two-stats {
      description
        "Hardware stats of port two";
      uses mrp-ios-xe-oper:hardware-stats-block;
    }
  }

  grouping packet-block {
    description
      "Platform packet info";
    leaf stat {
      type uint32;
      description
        "Number of frames for this frame type";
    }
    leaf frame {
      type mrp-ios-xe-oper:mrp-ring-packet-block-frame;
      description
        "Frame type for platform packets";
    }
  }

  grouping mrp-ring-packet-stats {
    description
      "MRP ring packet statistics";
    leaf p1-if-name {
      type string;
      description
        "MRP Ring Port one name";
    }
    leaf p2-if-name {
      type string;
      description
        "MRP Ring Port two name";
    }
    list tx-p1-pkt {
      description
        "List of transmitted packet counters on ring port 1";
      uses mrp-ios-xe-oper:packet-block;
    }
    list tx-p2-pkt {
      description
        "List of transmitted packet counters on ring port 2";
      uses mrp-ios-xe-oper:packet-block;
    }
    list rx-p1-pkt {
      description
        "List of received packet counters on ring port 1";
      uses mrp-ios-xe-oper:packet-block;
    }
    list rx-p2-pkt {
      description
        "List of received packet counters on ring port 2";
      uses mrp-ios-xe-oper:packet-block;
    }
  }

  grouping mrp-ring-platform-stats {
    description
      "MRP ring platform statistics";
    leaf rtos-closed-to-open-cnt {
      type uint32;
      description
        "Number of ring state transitions from closed to open";
    }
    leaf rtos-open-to-closed-cnt {
      type uint32;
      description
        "Number of ring state transitions from open to closed";
    }
    leaf ring-sts {
      type mrp-ios-xe-oper:mrp-ring-nw-status;
      description
        "Current network status of the MRP ring";
    }
  }

  grouping mrp-ring-stats {
    description
      "MRP ring all statistics";
    container evnt {
      description
        "MRP ring event statistics";
      uses mrp-ios-xe-oper:mrp-ring-event-stats;
    }
    container hw {
      description
        "MRP ring hardware statistics";
      uses mrp-ios-xe-oper:mrp-ring-hw-stats;
    }
    container pkt {
      description
        "MRP ring packet statistics";
      uses mrp-ios-xe-oper:mrp-ring-packet-stats;
    }
    container plat {
      description
        "MRP ring platform statistics";
      uses mrp-ios-xe-oper:mrp-ring-platform-stats;
    }
  }

  container mrp-oper-data {
    config false;
    description
      "MRP operational data";
    list mrp-ring-detail {
      key "ring-id";
      description
        "MRP ring details";
      uses mrp-ios-xe-oper:mrp-ring-identity;
      uses mrp-ios-xe-oper:mrp-ring-detail;
    }
    list mrp-ring-port {
      key "ring-id";
      description
        "MRP ring port info";
      uses mrp-ios-xe-oper:mrp-ring-identity;
      uses mrp-ios-xe-oper:mrp-ring-port;
    }
    list mrp-ring-stats {
      key "ring-id";
      description
        "MRP ring statistics";
      uses mrp-ios-xe-oper:mrp-ring-identity;
      uses mrp-ios-xe-oper:mrp-ring-stats;
    }
  }
}
