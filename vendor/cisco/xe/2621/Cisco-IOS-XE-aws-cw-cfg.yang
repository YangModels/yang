module Cisco-IOS-XE-aws-cw-cfg {
  yang-version 1.1;
  namespace "http://cisco.com/ns/yang/Cisco-IOS-XE-aws-cw-cfg";
  prefix aws-cw-cfg;

  import Cisco-IOS-XE-aws-common-cfg {
    prefix aws-common-cfg;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for AWS Cloudwatch configurational data.
     Copyright (c) 2023-2026 by Cisco Systems, Inc.
     All rights reserved.";

  revision 2026-08-01 {
    description
      "Improved YANG descriptions for AWS CloudWatch configuration data.";
    reference
      "1.0.1";
    cisco-semver:module-version "1.0.1";
  }
  revision 2025-07-01 {
    description
      "Initial revision";
    reference
      "1.0.0";
    cisco-semver:module-version "1.0.0";
  }

  grouping cw-log-config {
    description
      "cloudwatch logs configuration data";
    leaf log-file-path {
      type string {
        length "0..200";
        pattern '[0-9a-zA-Z_/.*-]*';
      }
      must "string-length(current()) + string-length(../log-group-name | '') + string-length(../log-stream-name | '') <= 200" {
        error-message "sum of characters in log-file-path, log-group-name and log-stream-name must be equal to or less than 200";
      }
      default "";
      description
        "Log file path";
    }
    leaf log-group-name {
      type string {
        length "0..200";
        pattern '[a-zA-Z0-9_/.#-]*';
      }
      must "string-length(current()) + string-length(../log-stream-name | '') + string-length(../log-file-path | '') <= 200" {
        error-message "sum of characters in log-file-path, log-group-name and log-stream-name must be equal to or less than 200";
      }
      default "";
      description
        "Log group name for cloudwatch";
    }
    leaf log-stream-name {
      type string {
        length "0..200";
        pattern '([^	 *:][^:*]*[^	 *:])*';
      }
      must "string-length(current()) + string-length(../log-group-name | '') + string-length(../log-file-path | '') <= 200" {
        error-message "sum of characters in log-file-path, log-group-name and log-stream-name must be equal to or less than 200";
      }
      description
        "Specifies the name of the log stream within the AWS CloudWatch log group where logs will be written.";
    }
  }

  grouping cw-config {
    description
      "Cloudwatch configuration data";
    leaf cw-profile-name {
      type string {
        length "0..32";
        pattern '[0-9a-zA-Z_]*';
      }
      description
        "Unique name identifying the AWS CloudWatch profile.";
    }
    leaf cw-profile-descr {
      type string {
        length "0..200";
        pattern '([^	 ].*[^	 ])*';
      }
      default "";
      description
        "Cloudwatch profile description";
    }
    container cw-access-creds {
      description
        "AWS access credentials for cloudwatch";
      uses aws-common-cfg:aws-access-config;
    }
    container cw-proxy-config {
      description
        "proxy configuration for cloudwatch";
      uses aws-common-cfg:st-aws-proxy-config;
    }
    leaf cw-vrf {
      type aws-common-cfg:aws-vrf-name;
      default "aws-global-vrf";
      description
        "Specifies the Virtual Routing and Forwarding (VRF) instance used for AWS CloudWatch communication.";
    }
    leaf cw-region {
      type string {
        length "0..16";
        pattern '[0-9a-zA-Z-]*';
      }
      default "";
      description
        "AWS region for Cloudwatch";
    }
    leaf cw-shutdown {
      type boolean;
      must "(((current() = 'false') and (../cw-access-creds/access-key-id != '') and (../cw-access-creds/secret-access-key != '')) or (current() = 'true'))" {
        error-message "must set access-key-id and secret-access-key along with 'no shut'";
      }
      default "true";
      description
        "Shutdown variable for cloudwatch profile";
    }
    container aws-cw-logs {
      description
        "Log configuration for cloudwatch";
      list aws-cw-log {
        key "log-stream-name";
        description
          "Log configuration for cloudwatch";
        uses aws-cw-cfg:cw-log-config;
      }
    }
  }

  container aws-cw-cfg-data {
    description
      "AWS cloudwatch configuration data";
    container aws-cw-profiles {
      description
        "Cloudwatch profile data";
      list aws-cw {
        key "cw-profile-name";
        description
          "Cloudwatch profile data";
        uses aws-cw-cfg:cw-config;
      }
    }
  }
}
