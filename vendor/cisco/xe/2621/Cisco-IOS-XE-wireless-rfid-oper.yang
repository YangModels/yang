module Cisco-IOS-XE-wireless-rfid-oper {
  yang-version 1.1;
  namespace "http://cisco.com/ns/yang/Cisco-IOS-XE-wireless-rfid-oper";
  prefix wireless-rfid-ios-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Operational data model for wireless RFID (Radio Frequency Identification) systems, providing detailed information on RFID tags, associated access points, and vendor-specific parameters. This model enables monitoring, diagnostics, and analytics for RFID deployments in Cisco wireless networks.
     Copyright (c) 2016-2020, 2022 by Cisco Systems, Inc. All rights reserved.";

  revision 2026-08-01 {
    description
      "Modified the descriptions";
    reference
      "3.5.1";
    cisco-semver:module-version "3.5.1";
  }
  revision 2024-07-01 {
    description
      "Added Ekahau and Cadi Scientific RFID vendor type";
    reference
      "3.5.0";
    cisco-semver:module-version "3.5.0";
  }
  revision 2023-03-01 {
    description
      "Added support for searching the AP list for low RSSI AP.";
    reference
      "3.4.0";
    cisco-semver:module-version "3.4.0";
  }
  revision 2022-11-01 {
    description
      "Update yang-version to 1.1";
    reference
      "3.3.0";
    cisco-semver:module-version "3.3.0";
  }
  revision 2020-11-01 {
    description
      "Added new RFID vendor type enum.";
    reference
      "3.2.0";
    cisco-semver:module-version "3.2.0";
  }
  revision 2019-05-01 {
    description
      "- Removed data, renamed various leafs and changed types.
       - Added semantic version";
    reference
      "3.1.0";
    cisco-semver:module-version "3.1.0";
  }
  revision 2018-12-14 {
    description
      "- Removal of unused leaves
       - Cleaned up spelling errors in descriptions.";
    reference
      "3.0.0";
    cisco-semver:module-version "3.0.0";
  }
  revision 2018-01-24 {
    description
      "Changes done in ptl code for time format";
    reference
      "2.0.0";
    cisco-semver:module-version "2.0.0";
  }
  revision 2017-12-22 {
    description
      "Initial revision";
    reference
      "1.0.0";
    cisco-semver:module-version "1.0.0";
  }

  typedef enm-rfid-cisco-vendor-type {
    type enumeration {
      enum rfid-type-g2 {
        value 0;
        description
          "This enum value represents type of G2 vendor.";
      }
      enum rfid-type-aeroscout {
        value 1;
        description
          "This enum value represents type of aero scout vendor.";
      }
      enum rfid-type-unknown {
        value 2;
        description
          "This enum value represents unknown vendor.";
      }
      enum rfid-type-ekahau {
        value 3;
        description
          "Type of vendor Ekahau";
      }
      enum rfid-type-cadi-scientific {
        value 4;
        description
          "Type of vendor Cadi Scientific";
      }
    }
    description
      "Enumeration of Cisco-supported RFID vendor types, such as G2, Aero Scout, Ekahau, and Cadi Scientific, to identify the specific vendor implementation for Cisco RFID tags.";
  }

  typedef enm-rfid-data-type {
    type enumeration {
      enum bluesoft-rfid-data {
        value 0;
        description
          "This enum value represents type of bluesoft rfid tag.";
      }
      enum cisco-rfid-data {
        value 1;
        description
          "This enum value represents type of cisco rfid tag.";
      }
    }
    description
      "Enumeration of all supported RFID tag types, such as Bluesoft and Cisco, to identify the format and vendor of each RFID tag in the system.";
  }

  grouping st-apf-seq-control {
    description
      "Grouping for sequence control, representing both the sequence number and fragmentation number of an RFID tag packet, used for tracking and reassembly.";
    leaf seq-num {
      type uint16;
      description
        "seq_num represents sequence number of rfid tag packet.";
    }
    leaf frag-num {
      type uint16;
      description
        "frag_num represents fragmentation number of rfid tag packet.";
    }
  }

  grouping st-rfid-cisco-cont-hdr {
    description
      "Grouping for Cisco RFID content header, containing attributes such as CCX version, transmit power, channel, regulatory class, and burst length for detailed tag diagnostics.";
    leaf ccx-version {
      type uint8;
      description
        "ccx_version represents ccx version of rfid.";
    }
    leaf tx-power {
      type int8;
      description
        "tx_power represents tx power of rfid.";
    }
    leaf channel {
      type uint8;
      description
        "channel represents channel id of rfid.";
    }
    leaf reg-class {
      type uint8;
      description
        "Specifies the regulatory class of the RFID tag, which defines allowed frequency bands and power levels.";
    }
    leaf burst-len {
      type uint8;
      description
        "burst_len represents burst length of rfid.";
    }
  }

  grouping st-bluesoft-rfid-data {
    description
      "Grouping for Bluesoft RFID tag data, including the last sequence number and tag type, to support vendor-specific analytics and troubleshooting.";
    leaf last-seq-num {
      type uint8;
      description
        "last_seq_num represents last sequence number of rfid tag.";
    }
    leaf tag-type {
      type uint8;
      description
        "tag_type represents type of bluesoft rfid tag.";
    }
  }

  grouping st-ccx-payload-list {
    description
      "Grouping for CCX payload data, representing a list of bytes that make up the CCX (Cisco Compatible Extensions) payload in an RFID packet.";
    leaf-list data {
      type uint8;
      max-elements 500;
      ordered-by user;
      description
        "Data contains one byte of ccx payload data.";
    }
  }

  grouping st-cisco-rfid-data {
    description
      "Grouping for Cisco RFID tag data, including header, sequence control, payload length, CCX payload, and vendor type, to provide a comprehensive view of Cisco tag information.";
    container rfid-cisco-hdr {
      description
        "Contains header information for Cisco RFID tags, including version, power, channel, and regulatory class.";
      uses wireless-rfid-ios-oper:st-rfid-cisco-cont-hdr;
    }
    container seq-control {
      description
        "sequence control represents sequence control number of rfid tag.";
      uses wireless-rfid-ios-oper:st-apf-seq-control;
    }
    leaf payload-len {
      type uint16;
      description
        "payload_len represents payload length of rfid packet.";
    }
    container ccx-payload {
      description
        "Container for the CCX payload data of the RFID packet.";
      uses wireless-rfid-ios-oper:st-ccx-payload-list;
    }
    leaf cisco-vendor-type {
      type wireless-rfid-ios-oper:enm-rfid-cisco-vendor-type;
      description
        "Specifies the type of RFID vendor for the Cisco tag.";
    }
  }

  grouping st-vendor-spec-data {
    description
      "Vendor specific RFID packet data";
    choice type-choice {
      description
        "type choice represents type of rfid tag supported.";
      case bluesoft-rfid-data {
        container bluesoft {
          description
            "Container for vendor-specific information related to Bluesoft RFID tags.";
          uses wireless-rfid-ios-oper:st-bluesoft-rfid-data;
        }
      }
      case cisco-rfid-data {
        container cisco {
          description
            "Contains detailed information specific to Cisco RFID tags, including header and payload data.";
          uses wireless-rfid-ios-oper:st-cisco-rfid-data;
        }
      }
    }
  }

  grouping st-rfid-avg-rssi {
    description
      "Grouping for average Received Signal Strength Indicator (RSSI) values reported by access points for RFID tags, including numerator, denominator, computed value, and last sent timestamp.";
    leaf num {
      type int16;
      description
        "Numerator used in the calculation of the average RSSI value for this AP.";
    }
    leaf denom {
      type uint16;
      description
        "Denominator used in the calculation of the average RSSI value for this AP.";
    }
    leaf value {
      type int8;
      description
        "Average RSSI value calculated for this AP.";
    }
    leaf last-sent {
      type int8;
      description
        "Last RSSI value sent for this AP.";
    }
  }

  grouping st-rfid-avg-snr {
    description
      "Grouping for average Signal-to-Noise Ratio (SNR) values reported by access points for RFID tags, including numerator, denominator, and computed value.";
    leaf num {
      type int16;
      description
        "Numerator value used in calculating the signal-to-noise ratio (SNR) for the access point.";
    }
    leaf denom {
      type uint16;
      description
        "Denominator value used in calculating the signal-to-noise ratio (SNR) for the access point.";
    }
    leaf value {
      type int8;
      description
        "Calculated signal-to-noise ratio (SNR) value for the access point.";
    }
  }

  grouping rfid-ap-entry-list {
    description
      "Grouping for a list of access point (AP) entries associated with an RFID tag, with a maximum of 16 entries. Each entry contains RSSI, slot, band, SNR, timestamp, expiration status, and AP MAC address.";
    container rssi {
      description
        "RSSI parameters as measured by the AP for the received RFID packet.";
      uses wireless-rfid-ios-oper:st-rfid-avg-rssi;
    }
    leaf slot {
      type uint8;
      description
        "slot represents AP slot.";
    }
    leaf band {
      type uint8;
      description
        "Specifies the radio frequency band (such as 2.4 GHz or 5 GHz) used by the access point that received the RFID packet.";
    }
    container snr {
      description
        "Contains the signal-to-noise ratio (SNR) information for the access point that received the RFID packet.";
      uses wireless-rfid-ios-oper:st-rfid-avg-snr;
    }
    leaf time-stamp {
      type yang:date-and-time;
      description
        "time stamp represents time stamp of rfid packet received by the AP.";
    }
    leaf expired {
      type boolean;
      description
        "Indicates whether the entry for this access point is stale (true if the timestamp has expired).";
    }
    leaf ap-mac-addr {
      type yang:mac-address;
      description
        "MAC address of the access point that received the RFID packet.";
    }
  }

  grouping st-rfid-ap-highest-rssi {
    description
      "Grouping for details of the access point (AP) that reported the highest RSSI for a given RFID tag, including AP MAC address and highest RSSI value.";
    leaf ap-mac-addr {
      type yang:mac-address;
      description
        "ap mac address represents ap mac address of highest rssi AP.";
    }
    container rssi {
      description
        "rssi represents rssi value of highest rssi AP.";
      uses wireless-rfid-ios-oper:st-rfid-avg-rssi;
    }
  }

  grouping st-rfid-ap-lowest-rssi {
    description
      "Grouping for details of the access point (AP) that reported the lowest RSSI for a given RFID tag, including AP MAC address and lowest RSSI value.";
    leaf ap-mac-addr {
      type yang:mac-address;
      description
        "MAC address of the lowest RSSI AP.";
    }
    container rssi {
      description
        "Lowest reported RSSI among all APs";
      uses wireless-rfid-ios-oper:st-rfid-avg-rssi;
    }
  }

  grouping st-rfid-data {
    description
      "Grouping for RFID tag parameters, including MAC address, tag type, packet interval, bytes and packets received, last heard timestamp, vendor, highest RSSI AP, associated AP data, transmit power, timer handle, and lowest RSSI AP.";
    leaf rfid-mac-addr {
      type yang:mac-address;
      description
        "rfid mac address represents mac address of the rfid device.";
    }
    leaf rfid-type {
      type wireless-rfid-ios-oper:enm-rfid-data-type;
      description
        "Specifies the type of RFID tag associated with this entry.";
    }
    leaf rfid-auto-interval {
      type uint16;
      description
        "rfid auto interval represents rfid packet interval.";
    }
    leaf rfid-bytes-rx {
      type uint32;
      description
        "rfid bytes rx represents number of bytes received in rfid packet.";
    }
    leaf rfid-packets-rx {
      type uint32;
      description
        "rfid packets rx represents number of rfid packets received for same rfid.";
    }
    leaf rfid-last-heard-second {
      type yang:date-and-time;
      description
        "last heard represents time stamp of last rfid packet received.";
    }
    container rfid-vendor {
      description
        "rfid vendor represents vendor type of rfid received like cisco tag or bluesoft.";
      uses wireless-rfid-ios-oper:st-vendor-spec-data;
    }
    container ap-high-rssi {
      description
        "Contains information about the access point (AP) that reported the highest received signal strength indicator (RSSI) for this RFID tag.";
      uses wireless-rfid-ios-oper:st-rfid-ap-highest-rssi;
    }
    list ap-data {
      description
        "ap data represents ap information of rfid packet received.";
      uses wireless-rfid-ios-oper:rfid-ap-entry-list;
    }
    leaf tx-power {
      type int8;
      description
        "Transmit power of the access point that sent the RFID packet.";
    }
    leaf timer-handle {
      type uint64;
      description
        "Identifier for the timer associated with this RFID record.";
    }
    container ap-list-lowest-rssi {
      description
        "Parameters of the lowest RSSI AP";
      uses wireless-rfid-ios-oper:st-rfid-ap-lowest-rssi;
    }
  }

  container rfid-oper-data {
    config false;
    description
      "Container for all wireless RFID operational data, including lists of RFID tag data and associated parameters for monitoring and analytics.";
    list rfid-data {
      key "rfid-mac-addr";
      description
        "List of RFID packet data entries, each representing the parameters of a received RFID packet.";
      uses wireless-rfid-ios-oper:st-rfid-data;
    }
  }
}
