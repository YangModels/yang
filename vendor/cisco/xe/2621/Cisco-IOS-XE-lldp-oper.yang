module Cisco-IOS-XE-lldp-oper {
  yang-version 1.1;
  namespace "http://cisco.com/ns/yang/Cisco-IOS-XE-lldp-oper";
  prefix lldp-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for monitoring of Link Layer Discovery Protocol state information.
     Copyright (c) 2016-2017, 2019-2024, 2026 by Cisco Systems, Inc.
     All rights reserved.";

  revision 2026-08-01 {
    description
      "- Modified descriptions for several LLDP model elements to improve model usability";
    reference
      "1.8.1";
    cisco-semver:module-version "1.8.1";
  }
  revision 2024-07-01 {
    description
      "- Added vendor TLV list to LLDP neighbor entry
       - Deprecated media-caps and Added adv-media-cap list";
    reference
      "1.8.0";
    cisco-semver:module-version "1.8.0";
  }
  revision 2022-11-01 {
    description
      "- Update yang-version to 1.1
       - Added local-efp-id leaf to lldp entry and lldp interface entry
         indicating the service instance identifier that handles the
         received LLDP packet. Added lldp-efp-detail indicating the LLDP
         enabled service instance identifier for an interface";
    reference
      "1.7.0";
    cisco-semver:module-version "1.7.0";
  }
  revision 2022-03-01 {
    description
      "Added peer source MAC address for the neighbor entry";
    reference
      "1.6.0";
    cisco-semver:module-version "1.6.0";
  }
  revision 2020-07-01 {
    description
      "-Added Time to live leaf for the neighbor entry
       -Added new mgmt-type enum value mgmt-not-advertised indicating that a
        management address is not advertised
       -Added system cookie leaf for the neighbor entry";
    reference
      "1.5.0";
    cisco-semver:module-version "1.5.0";
  }
  revision 2020-03-01 {
    description
      "Added transmission and reception state details, neighboring device
       physical media capabilities and failure counters";
    reference
      "1.4.0";
    cisco-semver:module-version "1.4.0";
  }
  revision 2019-05-01 {
    description
      "Added semantic version";
    reference
      "1.3.0";
    cisco-semver:module-version "1.3.0";
  }
  revision 2018-11-05 {
    description
      "- Adding port VLAN ID, power details,
         media attachment unit, and auto negotiation details.
       - Cleaned up spelling errors in descriptions.";
    reference
      "1.2.0";
    cisco-semver:module-version "1.2.0";
  }
  revision 2018-06-27 {
    description
      "Entries to support open config LLDP are added";
    reference
      "1.1.0";
    cisco-semver:module-version "1.1.0";
  }
  revision 2017-02-07 {
    description
      "Initial revision";
    reference
      "1.0.0";
    cisco-semver:module-version "1.0.0";
  }

  typedef lldp-pwr-pair-type {
    type enumeration {
      enum power-pair-signal {
        value 1;
        description
          "LLDP power pair is Signal";
      }
      enum power-pair-spare {
        value 2;
        description
          "LLDP power pair is Spare";
      }
    }
    description
      "LLDP Power pair type";
  }

  typedef lldp-pwr-class-type {
    type enumeration {
      enum power-class-0 {
        value 1;
        description
          "LLDP power class 0";
      }
      enum power-class-1 {
        value 2;
        description
          "LLDP power class 1";
      }
      enum power-class-2 {
        value 3;
        description
          "LLDP power class 2";
      }
      enum power-class-3 {
        value 4;
        description
          "LLDP power class 3";
      }
      enum power-class-4 {
        value 5;
        description
          "LLDP power class 4";
      }
    }
    description
      "LLDP Power class type";
  }

  typedef lldp-pwr-device-type {
    type enumeration {
      enum power-device-type-2-pse {
        value 1;
        description
          "LLDP power device type is TYPE 2 PSE";
      }
      enum power-device-type-2-pd {
        value 2;
        description
          "LLDP power device type is TYPE 2 PD";
      }
      enum power-device-type-1-pse {
        value 3;
        description
          "LLDP power device type is TYPE 1 PSE";
      }
      enum power-device-type-1-pd {
        value 4;
        description
          "LLDP power device type is TYPE 1 PD";
      }
    }
    description
      "LLDP Power device type";
  }

  typedef lldp-pwr-source-type {
    type enumeration {
      enum power-source-pse-and-local {
        value 1;
        description
          "LLDP power source as PSE and Local";
      }
      enum power-source-reserved {
        value 2;
        description
          "LLDP power source as Reserved";
      }
      enum power-source-pse {
        value 3;
        description
          "LLDP power source as PSE";
      }
      enum power-source-unknown {
        value 4;
        description
          "LLDP power source as Unknown";
      }
    }
    description
      "LLDP Power source";
  }

  typedef lldp-pwr-priority-type {
    type enumeration {
      enum power-priority-unknown {
        value 1;
        description
          "LLDP power priority as Unknown";
      }
      enum power-priority-critical {
        value 2;
        description
          "LLDP power source as Critical";
      }
      enum power-prioirty-high {
        value 3;
        description
          "LLDP power source as High";
      }
      enum power-priority-low {
        value 4;
        description
          "LLDP power source as Low";
      }
    }
    description
      "LLDP Power priority";
  }

  typedef chid-subtype {
    type enumeration {
      enum chassis-entphyalias {
        value 1;
        description
          "chassis id sub type holds the value of entity
           MIB physical alias";
      }
      enum chassis-ifalias {
        value 2;
        description
          "chassis id subtype with value Interface alias";
      }
      enum chassis-portentphyalias {
        value 3;
        description
          "chassis id subtype with port component";
      }
      enum chassis-mac {
        value 4;
        description
          "chassis id sub type with MAC address";
      }
      enum chassis-net {
        value 5;
        description
          "chassis id sub type with Network address";
      }
      enum chassis-ifname {
        value 6;
        description
          "chassis id sub type with interface name";
      }
      enum chassis-local {
        value 7;
        description
          "chassis id subtype with locally assigned
           identifier";
      }
    }
    description
      "Chassis id sub-type";
  }

  typedef poid-type {
    type enumeration {
      enum port-ifalias {
        value 1;
        description
          "port id subtype with interface alias";
      }
      enum port-portphyalias {
        value 2;
        description
          "port id subtype with port component";
      }
      enum port-mac {
        value 3;
        description
          "Port id subtype with MAC address";
      }
      enum port-net {
        value 4;
        description
          "Port id subtype with network address";
      }
      enum port-ifname {
        value 5;
        description
          "Port id sub type with interface name";
      }
      enum port-ckt {
        value 6;
        description
          "Port id sub type with circuit";
      }
      enum port-local {
        value 7;
        description
          "Port id sub type with local";
      }
    }
    description
      "port id subtype";
  }

  typedef mgmt-type {
    type enumeration {
      enum mgmt-ip {
        value 1;
        description
          "specifies if the type of management address is
           IPv4";
      }
      enum mgmt-ipv6 {
        value 2;
        description
          "Specifies ipv6 address";
      }
      enum mgmt-decnet {
        value 3;
        description
          "Specifies decnet phase four address";
      }
      enum mgmt-ipx {
        value 4;
        description
          "Specifies ipx address";
      }
      enum mgmt-bv {
        value 5;
        description
          "Specifies banyan vine address type";
      }
      enum mgmt-at {
        value 6;
        description
          "Specifies apple talk address type";
      }
      enum mgmt-not-advertised {
        value 7;
        description
          "Indicates that the management address field is
           not advertised";
      }
    }
    description
      "Types of management address";
  }

  typedef rx-state {
    type enumeration {
      enum wait-port-oper {
        value 0;
        description
          "Transmission waits for port operation to come up";
      }
      enum tx-init {
        value 1;
        description
          "Reception is initialized";
      }
      enum wait-for-frame {
        value 2;
        description
          "Transmission waits for frame";
      }
      enum rx-frame {
        value 3;
        description
          "Transmission waits for receive frame";
      }
      enum update-info {
        value 4;
        description
          "Updates peer LLDP information for port";
      }
      enum delete-info {
        value 5;
        description
          "Deletes Peer lldp info on TTL timeout when Port
           is active";
      }
      enum delete-aged-info {
        value 6;
        description
          "Deletes Peer lldp info on TTL timeout when Port is
           NOT enabled";
      }
    }
    description
      "Reception states available in LLDP";
  }

  typedef tx-state {
    type enumeration {
      enum rx-init {
        value 0;
        description
          "LLDP Transmission is initialized";
      }
      enum idle {
        value 1;
        description
          "Reception is in IDLE state";
      }
      enum info-frame {
        value 2;
        description
          "Information frame is received";
      }
      enum shutdown-frame {
        value 3;
        description
          "Shutdown frame is received";
      }
    }
    description
      "Transmission states available in LLDP";
  }

  typedef phy-media-cap {
    type enumeration {
      enum unknown {
        value 0;
        description
          "Advertised value is not known";
      }
      enum 10baset {
        value 1;
        description
          "10 Base-T half duplex mode is advertised";
      }
      enum 10baset-fd {
        value 2;
        description
          "10 Base-T full duplex mode is advertised";
      }
      enum 100baset4 {
        value 3;
        description
          "10 Base-T4 mode is advertised";
      }
      enum 100basetx {
        value 4;
        description
          "100 Base-TX half duplex mode is advertised";
      }
      enum 100basetx-fd {
        value 5;
        description
          "100 Base-TX full duplex mode is advertised";
      }
      enum 100baset2 {
        value 6;
        description
          "100 Base-T2 half duplex mode is advertised";
      }
      enum 100baset2-fd {
        value 7;
        description
          "100 Base-T2 full duplex mode is advertised";
      }
      enum pause-fd {
        value 8;
        description
          "Pause for full duplex mode is advertised";
      }
      enum asym-pause-fd {
        value 9;
        description
          "Asymmetric pause for full duplex mode is advertised";
      }
      enum sym-pause-fd {
        value 10;
        description
          "Symmetric pause for full duplex mode is advertised";
      }
      enum symm-asym-pause-fd {
        value 11;
        description
          "Symmetric pause for full duplex mode is advertised";
      }
      enum 1000basex-hd {
        value 12;
        description
          "1000 BASE-X, -LX, -SX, -CX half duplex mode is
           advertised";
      }
      enum 1000basex-fd {
        value 13;
        description
          "1000 BASE-X, -LX, -SX, -CX full duplex mode is
           advertised";
      }
      enum 1000base-t-hd {
        value 14;
        description
          "1000 Base-T half duplex mode is advertised";
      }
      enum 1000baset-fd {
        value 15;
        description
          "1000 Base-T full duplex mode is advertised";
      }
    }
    description
      "Physical media capabilities is advertised";
  }

  typedef vendor-tlv-type {
    type enumeration {
      enum vnd-tlv-av {
        value 1;
        description
          "Specifies availability of Type(127) LLDP vendor TLV";
      }
      enum vnd-tlv-no-ad {
        value 2;
        description
          "Specifies vendor TLV not advertised";
      }
    }
    description
      "Type of vendor TLV";
  }

  grouping lldp-capabilities {
    description
      "LLDP device type";
    leaf repeater {
      type empty;
      description
        "Indicates that the LLDP neighbor device advertises repeater capability.";
    }
    leaf bridge {
      type empty;
      description
        "Indicates that the LLDP neighbor device advertises bridge capability.";
    }
    leaf access-point {
      type empty;
      description
        "Indicates that the device has wireless access point capabilities as advertised in LLDP system capabilities.";
    }
    leaf router {
      type empty;
      description
        "Indicates that the device has router capabilities as advertised in LLDP system capabilities.";
    }
    leaf telephone {
      type empty;
      description
        "Indicates that the device has telephone (VoIP phone) capabilities as advertised in LLDP system capabilities.";
    }
    leaf docsis {
      type empty;
      description
        "Indicates that the device has DOCSIS cable device capabilities as advertised in LLDP system capabilities.";
    }
    leaf station {
      type empty;
      description
        "Indicates that the device has station-only capabilities as advertised in LLDP system capabilities.";
    }
    leaf other {
      type empty;
      description
        "Indicates that the device has other, unspecified capabilities as advertised in LLDP system capabilities.";
    }
  }

  grouping lldp-auto-negotiation {
    description
      "LLDP Auto Negotiation";
    leaf enabled {
      type empty;
      description
        "Auto Negotiation is enabled";
    }
    leaf supported {
      type empty;
      description
        "Auto Negotiation is supported";
    }
  }

  grouping lldp-pwr-via-mdi {
    description
      "Holds details for LLDP Power-via-MDI";
    leaf power-pair {
      type lldp-ios-xe-oper:lldp-pwr-pair-type;
      description
        "Indicates which wire pair (signal or spare) is used for delivering power via MDI as reported by LLDP.";
    }
    leaf power-class {
      type lldp-ios-xe-oper:lldp-pwr-class-type;
      description
        "Specifies the IEEE power class (e.g., class 0-4) of the device as advertised via LLDP.";
    }
    leaf power-device-type {
      type lldp-ios-xe-oper:lldp-pwr-device-type;
      description
        "Indicates the type of power device (e.g., Power Sourcing Equipment (PSE) or Powered Device (PD), and whether it is Type 1 or Type 2) as reported via LLDP.";
    }
    leaf power-source {
      type lldp-ios-xe-oper:lldp-pwr-source-type;
      description
        "Specifies the source of power for the device (e.g., local, PSE, or both) as advertised via LLDP.";
    }
    leaf power-priority {
      type lldp-ios-xe-oper:lldp-pwr-priority-type;
      description
        "Indicates the priority level (e.g., critical, high, low, unknown) assigned to the device for power allocation as reported via LLDP.";
    }
    leaf power-requested {
      type uint32;
      units "milliWatts";
      description
        "Power requested by peer device";
    }
    leaf power-allocated {
      type uint32;
      units "milliWatts";
      description
        "Power allocated to peer device";
    }
  }

  grouping lldp-pwrt {
    description
      "LLDP Power type";
    leaf is-drawing-power {
      type empty;
      description
        "Power is drawn from the device";
    }
    container power-details {
      when 'boolean(../is-drawing-power)';
      description
        "LLDP Power-via-MDI details";
      uses lldp-ios-xe-oper:lldp-pwr-via-mdi;
    }
  }

  grouping lldp-entry-key {
    description
      "Unique LLDP entry identifier";
    leaf device-id {
      type string;
      description
        "Device ID of the link";
    }
    leaf local-interface {
      type string;
      description
        "Name of the local interface on the current device";
    }
    leaf connecting-interface {
      type string;
      description
        "Name of the connected interface to 'local-interface'";
    }
  }

  grouping lldp-entry {
    description
      "LLDP entry details";
    leaf ttl {
      type uint32;
      description
        "TTL denoting hold-time of this link entry";
    }
    container capabilities {
      description
        "Neighbor device capabilities, such as bridge, router, or access point.";
      uses lldp-ios-xe-oper:lldp-capabilities;
    }
    leaf port-vlan-id {
      type uint32;
      description
        "LLDP port VLAN ID";
    }
    leaf mau-type {
      type uint32;
      description
        "Media attachment unit type for LLDP";
    }
    container auto-neg {
      description
        "LLDP auto negotiation details";
      uses lldp-ios-xe-oper:lldp-auto-negotiation;
    }
    container power {
      description
        "LLDP Power-via-MDI details";
      uses lldp-ios-xe-oper:lldp-pwrt;
    }
    leaf local-efp-id {
      type uint32;
      description
        "EFP Identifier of the interface where
         this LLDP entry is learnt ";
    }
  }

  grouping lldp-state-entry {
    description
      "LLDP state entry details";
    leaf enabled {
      type boolean;
      description
        "Indicates whether LLDP is enabled (true) or disabled (false) on the device.";
    }
    leaf hello-timer {
      type uint64;
      description
        "Denotes the time between advertisement packets";
    }
    leaf system-name {
      type string;
      description
        "Provides the name of the system";
    }
    leaf system-desc {
      type string;
      description
        "Textual description of the local system that is advertised to LLDP neighbors.";
    }
    leaf chassis-id {
      type string;
      description
        "Provides information about the chassis";
    }
    leaf chassis-id-type {
      type lldp-ios-xe-oper:chid-subtype;
      description
        "Provides information about the subtype of
         chassis ID";
    }
    leaf frame-in {
      type uint64;
      description
        "Denotes the number of input frames";
    }
    leaf frame-out {
      type uint64;
      description
        "Denotes the number of output frames";
    }
    leaf frame-error-in {
      type uint64;
      description
        "Denotes the number of input frames containing errors";
    }
    leaf frame-discard {
      type uint64;
      description
        "Denotes the number of discarded frames";
    }
    leaf tlv-discard {
      type uint64;
      description
        "Denotes the number of discarded TLVs";
    }
    leaf tlv-unknown {
      type uint64;
      description
        "Denotes the number of unknown TLVs";
    }
    leaf entries-aged-out {
      type uint64;
      description
        "Number of aged out entries";
    }
    leaf mem-failures {
      type uint64;
      description
        "Number of memory allocation failures";
    }
    leaf encap-failures {
      type uint64;
      description
        "Number of encapsulation failures";
    }
    leaf inqueue-overflow {
      type uint64;
      description
        "Number of queue overflow failures";
    }
    leaf table-overflow {
      type uint64;
      description
        "Number of table failures";
    }
  }

  grouping lldp-efp-entry {
    description
      "Holds EFP Specific LLDP information";
    leaf efp-id {
      type uint32;
      description
        "Identifier for the Ethernet Flow Point (EFP) associated with this LLDP-enabled service instance on the interface.";
    }
  }

  grouping lldp-intf-entry {
    description
      "LLDP entry details for interface";
    leaf if-name {
      type string;
      description
        "Specifies the name of the interface for which LLDP information is being reported.";
    }
    leaf isenabled {
      type boolean;
      description
        "Indicates whether LLDP is enabled (true) or disabled (false) on the interface.";
    }
    list lldp-neighbor-details {
      key "identifier";
      description
        "List of LLDP neighbor entries discovered on this interface.";
      uses lldp-ios-xe-oper:lldp-neighbor-entry;
    }
    leaf tx {
      type lldp-ios-xe-oper:tx-state;
      description
        "LLDP transmission state on the interface";
    }
    leaf rx {
      type lldp-ios-xe-oper:rx-state;
      description
        "LLDP reception state on the interface";
    }
    list lldp-efp-detail {
      key "efp-id";
      description
        "List of EFP (Ethernet Flow Point) identifiers for service instances where LLDP is enabled on the interface.";
      uses lldp-ios-xe-oper:lldp-efp-entry;
    }
  }

  grouping lldp-mgmt {
    description
      "Holds lldp's management address";
    leaf mgmt-addr {
      type string;
      description
        "Denotes the management ip address";
    }
    leaf mgmt-addr-type {
      type lldp-ios-xe-oper:mgmt-type;
      description
        "Denotes the type of management ip address";
    }
  }

  grouping lldp-vendor-tlv {
    description
      "Holds type,length and value information about LLDP vendor-specific-tlvs";
    leaf tlv-type {
      type lldp-ios-xe-oper:vendor-tlv-type;
      description
        "Denotes type of TLV";
    }
    leaf tlv-len {
      type uint32;
      description
        "Denotes length of TLV";
    }
    leaf tlv-val {
      type string;
      description
        "Denotes value of TLV";
    }
  }

  grouping lldp-neighbor-entry {
    description
      "Holds LLDP device neighbor entry";
    leaf identifier {
      type string;
      description
        "Provides information about the system generated id";
    }
    leaf chassis-id {
      type string;
      description
        "Provides information about the chassis";
    }
    leaf chassis-id-type {
      type lldp-ios-xe-oper:chid-subtype;
      description
        "Provides information about the subtype of
         chassis ID";
    }
    leaf port-id {
      type string;
      description
        "Provides information about the port id";
    }
    leaf port-id-type {
      type lldp-ios-xe-oper:poid-type;
      description
        "Provides information about the port id's type";
    }
    leaf port-desc {
      type string;
      description
        "Provides information about the port's description";
    }
    leaf system-name {
      type string;
      description
        "Provides the name of the system";
    }
    leaf system-desc {
      type string;
      description
        "Textual description of the remote system as advertised by the LLDP neighbor device.";
    }
    leaf time-remaining {
      type uint32;
      units "seconds";
      description
        "Number of seconds remaining until the next LLDP advertisement is expected from the neighbor.";
    }
    leaf age {
      type uint32;
      units "seconds";
      description
        "Time in seconds since this LLDP neighbor entry was first created.";
    }
    leaf time-since-last-update {
      type uint32;
      units "seconds";
      description
        "Time in seconds since the last LLDP update from neighbor.";
    }
    list mgmt-addrs {
      description
        "List of management addresses advertised by the LLDP neighbor device.";
      uses lldp-ios-xe-oper:lldp-mgmt;
    }
    container system-capabilities {
      description
        "Provides LLDP device system capabilities";
      uses lldp-ios-xe-oper:lldp-capabilities;
    }
    container enabled-capabilities {
      description
        "Provides LLDP device enabled capabilities";
      uses lldp-ios-xe-oper:lldp-capabilities;
    }
    leaf media-caps {
      type lldp-ios-xe-oper:phy-media-cap;
      status deprecated;
      description
        "Deprecated. Use adv-media-cap";
    }
    leaf ttl {
      type uint32;
      units "seconds";
      description
        "The time-to-live (TTL) is a mandatory TLV which
         indicates how long information from the neighbor should be
         considered valid";
    }
    list orgtlv-detail {
      key "platform-id";
      description
        "Holds LLDP org specific TLV information";
      uses lldp-ios-xe-oper:lldp-orgtlv-entry;
    }
    leaf peer-src-mac {
      type yang:mac-address;
      description
        "Source MAC address from received LLDP packets";
    }
    leaf local-efp-id {
      type uint32;
      description
        "Local EFP identifier of interface
          where the LLDP neighbour is learnt";
    }
    list vnd-tlv {
      description
        "Holds LLDP vendor TLV information";
      uses lldp-ios-xe-oper:lldp-vendor-tlv;
    }
    leaf-list adv-media-cap {
      type lldp-ios-xe-oper:phy-media-cap;
      ordered-by user;
      description
        "Advertised physical media capabilities of peer device";
    }
  }

  grouping lldp-orgtlv-entry {
    description
      "Holds LLDP org specific TLV entry";
    leaf platform-id {
      type string;
      description
        "Provides information about the platform identifier";
    }
    leaf system-cookie {
      type string;
      description
        "Provides system cookie - the info string for
         an LLDP org specific TLV (Type=127, Subtype=1)";
    }
  }

  container lldp-entries {
    config false;
    description
      "Container for all operational data related to Link Layer Discovery Protocol (LLDP) entries on the device.";
    list lldp-entry {
      key "device-id local-interface connecting-interface";
      description
        "The list of LLDP entries";
      uses lldp-ios-xe-oper:lldp-entry-key;
      uses lldp-ios-xe-oper:lldp-entry;
    }
    container lldp-state-details {
      presence "lldp-state-details";
      description
        "Container for LLDP protocol operational state information, including global LLDP status and statistics.";
      uses lldp-ios-xe-oper:lldp-state-entry;
    }
    list lldp-intf-details {
      key "if-name";
      description
        "The list of LLDP interface entries";
      uses lldp-ios-xe-oper:lldp-intf-entry;
    }
  }
}
