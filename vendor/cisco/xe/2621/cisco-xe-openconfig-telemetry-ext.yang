module cisco-xe-openconfig-telemetry-ext {
    namespace "http://cisco.com/ns/cisco-xe-openconfig-telemetry-ext";
    prefix oc-telemetry-ext;

    import tailf-common {
        prefix tailf;
    }
    import openconfig-telemetry {
        prefix oc-telemetry;
    }

    import openconfig-telemetry-types {
        prefix oc-telemetry-types;
    }

    organization
        "Cisco Systems";
     description
        "Cisco augmentation to the oc-telemetry model";

    revision 2026-08-01 {
        description
            "Added gnmi and grpc_tlc as transport protocols for subscriptions";
         
    }

    // Add STREAM_GNMI and STREAM_GRPC_TLS as protocol options for subscriptions

    identity STREAM_GNMI  {
        base oc-telemetry-types:STREAM_PROTOCOL;
        description
            "Telemetry stream is carried over a GNMI connection";
    }
    
    identity STREAM_GRPC_TLS  {
        base oc-telemetry-types:STREAM_PROTOCOL;
        description
            "Telemetry stream is carried over via the gRPC TLS protocol";
    }

    identity STREAM_UNSPEC  {
        base oc-telemetry-types:STREAM_PROTOCOL;
        description
            "Transport protocal is unspecified for telemetry stream";
    }

    // Add ENC_KVGPB as an encoding option for subscriptions
    
    identity ENC_KVGPB {
        base oc-telemetry-types:DATA_ENCODING_METHOD;
        description
            "KVGPB encoding";
    } 

}
