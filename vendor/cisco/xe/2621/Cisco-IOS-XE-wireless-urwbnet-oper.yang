module Cisco-IOS-XE-wireless-urwbnet-oper {
  yang-version 1.1;
  namespace "http://cisco.com/ns/yang/Cisco-IOS-XE-wireless-urwbnet-oper";
  prefix wireless-oper-urwbnet;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for URWB(Ultra Reliable Wireless Backhaul) network global
     operational data.
     Copyright (c) 2026 by Cisco Systems, Inc.
     All rights reserved.";

  revision 2026-08-01 {
    description
      "- Added band, slot-id, and radio-profile-name leaves to node interface data.
       - Added Ethernet MAC address leaf to node data.
       - Updated descriptions of several model elements to clarify their meaning and purpose.
       - Added uplink and downlink byte-rate leaves and uplink/downlink MCS-rate leaves to wireless link statistics.
       - Added URWB network name table oper-data mapping.
       - Added nw-info container mappings for URWB links/routes/nodes.
       - Added subnet network-name and network-id operational leaves.
       - Added connected-device last-update timestamp leaf to URWB network operational data.";
    reference
      "2.0.0";
    cisco-semver:module-version "2.0.0";
  }
  revision 2026-02-01 {
    description
      "- Added timestamp field to URWB oper data to indicate last update time.
       - Added URWB profile name and radio MAC address.
       - Added MCS data rate and NSS information to URWB network configuration.";
    reference
      "1.1.0";
    cisco-semver:module-version "1.1.0";
  }
  revision 2025-07-01 {
    description
      "Initial revision";
    reference
      "1.0.0";
    cisco-semver:module-version "1.0.0";
  }

  typedef uar {
    type enumeration {
      enum uar-fixed {
        value 0;
        description
          "AP role fixed node";
      }
      enum uar-client-pri {
        value 1;
        description
          "AP role mobility client primary";
      }
      enum uar-client-sec {
        value 2;
        description
          "AP role mobility client secondary";
      }
      enum uar-coord {
        value 3;
        description
          "AP role Coordinator";
      }
      enum uar-coord-backup {
        value 4;
        description
          "AP role Coordinator Backup";
      }
    }
    description
      "Enum for URWB network ap role information";
  }

  typedef urr {
    type enumeration {
      enum urr-fixed-base {
        value 0;
        description
          "AP radio role fixed base";
      }
      enum urr-ptmp-prim {
        value 1;
        description
          "AP radio role PTMP primary";
      }
      enum urr-ptmp-sec {
        value 2;
        description
          "AP radio role PTMP secondary";
      }
      enum urr-fl-base {
        value 3;
        description
          "AP radio role mobility base";
      }
      enum urr-fl-client {
        value 4;
        description
          "AP radio role mobility client";
      }
    }
    description
      "Enum for URWB network radio role information";
  }

  typedef urwbnet-bw {
    type enumeration {
      enum urwbnet-bw20m {
        value 0;
        description
          "URWB network bandwidth 20MHz";
      }
      enum urwbnet-bw40m {
        value 1;
        description
          "URWB network bandwidth 40MHz";
      }
      enum urwbnet-bw80m {
        value 2;
        description
          "URWB network bandwidth 80MHz";
      }
      enum urwbnet-bw160m {
        value 3;
        description
          "URWB network bandwidth 160MHz";
      }
    }
    description
      "Enum for URWB network bandwidth information";
  }

  typedef urwb-network-mcstype {
    type enumeration {
      enum urwbnet-mcs-noht {
        value 0;
        description
          "URWB network MCS type not high throughput";
      }
      enum urwbnet-mcs-ht {
        value 1;
        description
          "URWB network MCS type high throughput (80211n)";
      }
      enum urwbnet-mcs-vht {
        value 2;
        description
          "URWB network MCS type very high throughput";
      }
      enum urwbnet-he {
        value 3;
        description
          "URWB network MCS type HE (80211ax)";
      }
    }
    description
      "Enum for URWB network MCS type information";
  }

  typedef urwb-network-gi {
    type enumeration {
      enum urwbnet-gi-gi08 {
        value 0;
        description
          "URWB network guard interval 800 nano seconds";
      }
      enum urwbnet-gi-gi04 {
        value 1;
        description
          "URWB network guard interval 400 nano seconds";
      }
      enum urwbnet-gi-gi16 {
        value 2;
        description
          "URWB network guard interval 1.6 micro seconds";
      }
      enum urwbnet-gi-gi32 {
        value 3;
        description
          "URWB network guard interval 3.2 micro seconds";
      }
    }
    description
      "Enum for URWB network guard interval information";
  }

  typedef urwb-mcs-index {
    type enumeration {
      enum mcs-0 {
        value 0;
        description
          "MCS Index 0";
      }
      enum mcs-1 {
        value 1;
        description
          "MCS Index 1";
      }
      enum mcs-2 {
        value 2;
        description
          "MCS Index 2";
      }
      enum mcs-3 {
        value 3;
        description
          "MCS Index 3";
      }
      enum mcs-4 {
        value 4;
        description
          "MCS Index 4";
      }
      enum mcs-5 {
        value 5;
        description
          "MCS Index 5";
      }
      enum mcs-6 {
        value 6;
        description
          "MCS Index 6";
      }
      enum mcs-7 {
        value 7;
        description
          "MCS Index 7";
      }
      enum mcs-8 {
        value 8;
        description
          "MCS Index 8";
      }
      enum mcs-9 {
        value 9;
        description
          "MCS Index 9";
      }
      enum mcs-10 {
        value 10;
        description
          "MCS Index 10";
      }
      enum mcs-11 {
        value 11;
        description
          "MCS Index 11";
      }
    }
    description
      "Enum for MCS index information";
  }

  typedef urwb-network-conn-type {
    type enumeration {
      enum urwb-network-conn-wired {
        value 0;
        description
          "URWB network wired link";
      }
      enum urwb-network-conn-wireless {
        value 1;
        description
          "URWB network wireless link";
      }
    }
    description
      "Enum for URWB network link type";
  }

  typedef urwb-net-band-id {
    type enumeration {
      enum urwb-net-band-invalid {
        value 0;
        description
          "Indicates that the URWB network band is invalid or unset.";
      }
      enum urwb-net-band-5ghz {
        value 2;
        description
          "Indicates that the URWB network is operating on the 5 GHz radio frequency band.";
      }
      enum urwb-net-band-6ghz {
        value 3;
        description
          "Indicates that the URWB network is operating on the 6 GHz radio frequency band.";
      }
    }
    description
      "Enumeration type identifying the radio frequency band used in a URWB network.";
  }

  grouping st-urwbnet-inaddr {
    description
      "URWB network interface address information";
    leaf addr {
      type inet:ip-address;
      description
        "URWB network interface address";
    }
  }

  grouping st-urwbnet-mesh-id {
    description
      "URWB network mesh identifier";
    leaf addr {
      type inet:ip-address;
      description
        "URWB network mesh identifier address";
    }
  }

  grouping st-urwbnet-link-id {
    description
      "URWB link identifier";
    leaf src {
      type inet:ip-address;
      description
        "Source IP address for the link identifier.";
    }
    leaf dest {
      type inet:ip-address;
      description
        "Destination IP address for the link identifier.";
    }
  }

  grouping st-urwbnet-conn-dev {
    description
      "URWB network connected devices";
    leaf ip {
      type inet:ip-address;
      description
        "IP Address of device";
    }
    leaf vlan-id {
      type uint32;
      description
        "Vlan ID of device";
    }
    leaf last-update {
      type yang:date-and-time;
      description
        "Timestamp when the connected device entry was last updated.";
    }
  }

  grouping st-urwbnet-nw-name {
    description
      "URWB network name and coordinator details.";
    leaf nw-id {
      type uint64;
      description
        "Unique identifier of the URWB network.";
    }
    leaf nw-name {
      type string;
      description
        "Configured or learned URWB network name.";
    }
    leaf coord-mac {
      type yang:mac-address;
      description
        "Coordinator MAC address for the network name.";
    }
    container coord-id {
      description
        "Coordinator mesh identifier for the network name.";
      uses wireless-oper-urwbnet:st-urwbnet-mesh-id;
    }
    leaf last-update {
      type yang:date-and-time;
      description
        "Timestamp when the network name entry was last updated.";
    }
  }

  grouping st-urwbnet-node-intf {
    description
      "URWB network node interfaces statistics";
    container intf-id {
      description
        "Identifier of the URWB network node interface.";
      uses wireless-oper-urwbnet:st-urwbnet-inaddr;
    }
    leaf intf-enabled {
      type boolean;
      description
        "URWB network node interface enable status";
    }
    leaf role {
      type wireless-oper-urwbnet:urr;
      description
        "URWB network node interface radio role";
    }
    leaf freq {
      type int32;
      units "MHz";
      description
        "URWB network node interface radio frequency";
    }
    leaf bw {
      type wireless-oper-urwbnet:urwbnet-bw;
      description
        "URWB network node interface bandwidth";
    }
    leaf tx-power {
      type int32;
      units "dBm";
      description
        "URWB network node interface tx power";
    }
    leaf is-tdma {
      type boolean;
      description
        "Indicates whether the URWB network node interface uses Time Division Multiple Access.";
    }
    leaf freq-scan {
      type boolean;
      description
        "URWB network node interface frequency scan status";
    }
    leaf band {
      type wireless-oper-urwbnet:urwb-net-band-id;
      description
        "Specifies the radio frequency band used by this URWB network node interface.";
    }
    leaf slot-id {
      type uint8;
      description
        "Indicates the slot identifier for the URWB network node interface corresponding to the hardware slot where the radio is installed.";
    }
    leaf radio-prof-name {
      type string;
      description
        "Specifies the name of the radio profile applied to this URWB network node interface.";
    }
  }

  grouping st-urwbnet-mob-link {
    description
      "List of URWB mobility link entries.";
    container id {
      description
        "Identifier for the mobility link";
      uses wireless-oper-urwbnet:st-urwbnet-link-id;
    }
    container prim-id {
      description
        "Primary mobility link identifier";
      uses wireless-oper-urwbnet:st-urwbnet-mesh-id;
    }
    leaf client-id {
      type int32;
      description
        "Identifier of the mobility client.";
    }
    leaf ho-seq-nu {
      type uint32;
      description
        "Handoff sequence number";
    }
    list sec-mesh-id {
      max-elements 16;
      description
        "List of secondary mesh identifier entries.";
      uses wireless-oper-urwbnet:st-urwbnet-mesh-id;
    }
    container nw-info {
      description
        "URWB network name information for this mobility link.";
      uses wireless-oper-urwbnet:st-urwbnet-nw-name;
    }
  }

  grouping st-urwbnet-wfm {
    description
      "URWB network wireless link waveform";
    leaf bw {
      type wireless-oper-urwbnet:urwbnet-bw;
      units "MHz";
      description
        "Wireless link waveform bandwidth";
    }
    leaf mcs {
      type wireless-oper-urwbnet:urwb-network-mcstype;
      description
        "Specifies the MCS category used by the wireless link waveform.";
    }
    leaf mcs-index {
      type uint32;
      description
        "Specifies the MCS index value used by the wireless link waveform.";
    }
    leaf gi {
      type wireless-oper-urwbnet:urwb-network-gi;
      units "microseconds";
      description
        "Specifies the guard interval duration, in microseconds, used by the wireless link waveform.";
    }
    leaf mcs-val {
      type wireless-oper-urwbnet:urwb-mcs-index;
      units "Mbps";
      description
        "Indicates the effective MCS data rate used for packet transmission/reception. Derived from the MCS index received from the access point";
    }
    leaf nss {
      type uint8;
      description
        "Indicates the number of spatial streams (NSS), representing the number of simultaneous data streams transmitted over different spatial paths. Derived from the MCS index received from the access point";
    }
  }

  grouping st-urwbnet-wl-tx {
    description
      "URWB network wireless link stats tx";
    leaf tstamp {
      type yang:date-and-time;
      description
        "Time of transmit statistics collection";
    }
    leaf sent {
      type uint64;
      units "packets";
      description
        "Tx packets sent";
    }
    leaf failed {
      type uint64;
      description
        "Tx fail count";
    }
    leaf retries {
      type uint64;
      description
        "Tx retries";
    }
    leaf bytes {
      type uint64;
      units "bytes";
      description
        "Tx bytes";
    }
    container tx-wfm {
      description
        "wireless link waveform information";
      uses wireless-oper-urwbnet:st-urwbnet-wfm;
    }
  }

  grouping st-urwbnet-wl-rx {
    description
      "URWB network wireless link stats rx";
    leaf tstamp {
      type yang:date-and-time;
      description
        "Time of receive statistics collection";
    }
    leaf rssi {
      type int32;
      units "dBm";
      description
        "Received Signal Strength";
    }
    leaf recv {
      type uint64;
      description
        "Received packet count";
    }
    leaf bytes {
      type uint64;
      units "bytes";
      description
        "Rx bytes";
    }
    container rx-wfm {
      description
        "Wireless link waveform information";
      uses wireless-oper-urwbnet:st-urwbnet-wfm;
    }
  }

  grouping st-urwbnet-wlink-stats {
    description
      "List of URWB wireless link statistics entries.";
    container link-id {
      description
        "Wireless link identifier";
      uses wireless-oper-urwbnet:st-urwbnet-link-id;
    }
    container rx-stats {
      description
        "Contains receive statistics for the wireless link.";
      uses wireless-oper-urwbnet:st-urwbnet-wl-rx;
    }
    container tx-stats {
      description
        "Wireless link tx stats";
      uses wireless-oper-urwbnet:st-urwbnet-wl-tx;
    }
    container nw-info {
      description
        "URWB network name information for this wireless link.";
      uses wireless-oper-urwbnet:st-urwbnet-nw-name;
    }
    leaf ul-rate {
      type decimal64 {
        fraction-digits 2;
      }
      units "kbps";
      description
        "Wireless link uplink rate in kilobits per second computed from TX byte delta over time.";
    }
    leaf dl-rate {
      type decimal64 {
        fraction-digits 2;
      }
      units "kbps";
      description
        "Wireless link downlink rate in kilobits per second computed from RX byte delta over time.";
    }
    leaf ul-mcs-rate {
      type decimal64 {
        fraction-digits 2;
      }
      units "Mbps";
      description
        "Wireless link uplink modulation coding scheme (MCS) rate, in Mbps.";
    }
    leaf dl-mcs-rate {
      type decimal64 {
        fraction-digits 2;
      }
      units "Mbps";
      description
        "Wireless link downlink modulation coding scheme (MCS) rate, in Mbps.";
    }
  }

  grouping st-urwbnet-fix-lnk {
    description
      "List of URWB fixed link entries.";
    container id {
      description
        "Identifier for the fixed link";
      uses wireless-oper-urwbnet:st-urwbnet-link-id;
    }
    leaf type {
      type wireless-oper-urwbnet:urwb-network-conn-type;
      description
        "Type of the link";
    }
    container nw-info {
      description
        "URWB network name information for this fixed link.";
      uses wireless-oper-urwbnet:st-urwbnet-nw-name;
    }
  }

  grouping st-urwbnet-coord-rt {
    description
      "URWB network coordinator routes";
    leaf index {
      type uint32;
      description
        "Coordinator route index";
    }
    list peer {
      max-elements 64;
      description
        "Coordinator route peer list";
      uses wireless-oper-urwbnet:st-urwbnet-mesh-id;
    }
    container nw-info {
      description
        "URWB network name information for this route.";
      uses wireless-oper-urwbnet:st-urwbnet-nw-name;
    }
  }

  grouping st-urwbnet-node {
    description
      "URWB network node statistics";
    container id {
      description
        "URWB network node id";
      uses wireless-oper-urwbnet:st-urwbnet-mesh-id;
    }
    leaf name {
      type string;
      description
        "Specifies the name of the URWB network node.";
    }
    leaf device-model {
      type string;
      description
        "Indicates the device model of the URWB network node.";
    }
    leaf role {
      type wireless-oper-urwbnet:uar;
      description
        "Specifies the role of the URWB network node.";
    }
    leaf ip-addr {
      type inet:ip-address;
      description
        "URWB network node IP address";
    }
    leaf net-mask {
      type inet:ip-address;
      description
        "URWB network node netmask";
    }
    list node-if {
      max-elements 16;
      description
        "URWB network node interface list";
      uses wireless-oper-urwbnet:st-urwbnet-node-intf;
    }
    leaf conn-dev-count {
      type uint8;
      description
        "URWB network connected device count";
    }
    leaf urwb-prof {
      type string;
      description
        "URWB profile in use for this node";
    }
    leaf radio-mac {
      type yang:mac-address;
      description
        "Radio MAC address of this URWB node";
    }
    container nw-info {
      description
        "URWB network name information for this node.";
      uses wireless-oper-urwbnet:st-urwbnet-nw-name;
    }
    leaf eth-mac {
      type yang:mac-address;
      description
        "Specifies the Ethernet MAC address assigned to this URWB node.";
    }
  }

  grouping st-urwb-node-link-id {
    description
      "Node link id list";
    container lnk-id {
      description
        "Identifier of the link entry.";
      uses wireless-oper-urwbnet:st-urwbnet-link-id;
    }
    leaf rad-role {
      type wireless-oper-urwbnet:urr;
      description
        "Specifies the radio role associated with this link entry.";
    }
    leaf last-update {
      type yang:date-and-time;
      description
        "Specifies the timestamp when this node link entry was last updated in the URWB operational telemetry data.";
    }
  }

  grouping st-urwbnet-node-g {
    description
      "URWB network node global statistics";
    container id {
      description
        "URWB network node id";
      uses wireless-oper-urwbnet:st-urwbnet-mesh-id;
    }
    container coord-id {
      description
        "Coordinator id of the network node";
      uses wireless-oper-urwbnet:st-urwbnet-mesh-id;
    }
    leaf coord-mac {
      type yang:mac-address;
      description
        "Coordinator mac address of the network node";
    }
    leaf dev-count {
      type uint32;
      description
        "Connected device count";
    }
    list urwbnet-conn-dev {
      key "ip";
      description
        "Connected device list";
      uses wireless-oper-urwbnet:st-urwbnet-conn-dev;
    }
    list urwbnet-lnk-id {
      key "src dest";
      description
        "Link id list";
      uses wireless-oper-urwbnet:st-urwbnet-link-id;
      uses wireless-oper-urwbnet:st-urwb-node-link-id;
    }
    leaf last-update {
      type yang:date-and-time;
      description
        "Specifies the timestamp when this node global entry was last updated in the URWB operational telemetry data.";
    }
  }

  grouping st-urwbnet-subnet {
    description
      "URWB network state information";
    leaf mac {
      type yang:mac-address;
      description
        "Coordinator MAC address";
    }
    container gw {
      description
        "Gateway identifier";
      uses wireless-oper-urwbnet:st-urwbnet-mesh-id;
    }
    leaf nodes-cnt {
      type uint32;
      description
        "URWB network node count";
    }
    list urwbnet-node {
      key "addr";
      description
        "List of URWB network node entries.";
      uses wireless-oper-urwbnet:st-urwbnet-mesh-id;
      uses wireless-oper-urwbnet:st-urwbnet-node;
    }
    leaf coord-rt-cnt {
      type uint32;
      description
        "URWB network coordinator route count";
    }
    list urwbnet-coord-routes {
      key "index";
      description
        "URWB network coordinator routes";
      uses wireless-oper-urwbnet:st-urwbnet-coord-rt;
    }
    leaf fix-lnk-cnt {
      type uint32;
      description
        "URWB network fixed link count";
    }
    list urwbnet-fixed-links {
      key "src dest";
      description
        "List of URWB fixed link entries.";
      uses wireless-oper-urwbnet:st-urwbnet-fix-lnk;
      uses wireless-oper-urwbnet:st-urwbnet-link-id;
    }
    leaf mob-lnk-cnt {
      type uint32;
      description
        "URWB network mobility link count";
    }
    list urwbnet-mobility-links {
      key "src dest";
      description
        "List of URWB mobility link entries.";
      uses wireless-oper-urwbnet:st-urwbnet-link-id;
      uses wireless-oper-urwbnet:st-urwbnet-mob-link;
    }
    leaf wlinks-cnt {
      type uint32;
      description
        "URWB wireless link count";
    }
    list urwbnet-wlink-stats {
      key "src dest";
      description
        "List of URWB wireless link statistics entries.";
      uses wireless-oper-urwbnet:st-urwbnet-link-id;
      uses wireless-oper-urwbnet:st-urwbnet-wlink-stats;
    }
    leaf coord-name {
      type string;
      description
        "URWB coordinator AP name";
    }
    leaf nw-name {
      type string;
      description
        "URWB network name associated with this subnet.";
    }
    leaf nw-id {
      type uint64;
      description
        "URWB network identifier associated with this subnet.";
    }
    leaf last-update {
      type yang:date-and-time;
      description
        "The timestamp when this subnet entry was last updated.";
    }
  }

  container urwbnet-oper-data {
    config false;
    description
      "URWB network operational data";
    list urwbnet-name-entry {
      key "nw-name";
      description
        "List of URWB network names and coordinator mapping.";
      uses wireless-oper-urwbnet:st-urwbnet-nw-name;
    }
    list urwbnet-stats {
      key "mac";
      description
        "List of URWB network operational data per coordinator";
      uses wireless-oper-urwbnet:st-urwbnet-subnet;
    }
    list urwbnet-node-g {
      key "addr";
      description
        "List of URWB network Nodes";
      uses wireless-oper-urwbnet:st-urwbnet-mesh-id;
      uses wireless-oper-urwbnet:st-urwbnet-node-g;
    }
  }
}
