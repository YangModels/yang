module Cisco-IOS-XE-sslproxy-rpc {
  yang-version 1.1;
  namespace "http://cisco.com/ns/yang/Cisco-IOS-XE-sslproxy-rpc";
  prefix ios-xe-sslproxy-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Copyright (c) 2023 by Cisco Systems, Inc.
     All rights reserved.";

  revision 2024-03-01 {
    description
      "Initial revision";
    reference
      "1.0.0";
    cisco-semver:module-version "1.0.0";
  }

  rpc sslproxy-update-ca-bundle {
    description
      "Update certificate authority bundle";
  }

  rpc sslproxy-update-ca-tp-label {
    description
      "Update certificate authority trustpoint label";
  }

  rpc sslproxy-update-ec-key {
    description
      "Update EC key";
  }

  rpc sslproxy-update-rsa-key {
    description
      "Update RSA key";
  }
}
