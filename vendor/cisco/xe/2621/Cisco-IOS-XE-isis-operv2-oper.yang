module Cisco-IOS-XE-isis-operv2-oper {
  yang-version 1.1;
  namespace "http://cisco.com/ns/yang/Cisco-IOS-XE-isis-operv2-oper";
  prefix isis-ios-xe-operv2;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for ISIS operational data.
     Copyright (c) 2025-2026 by Cisco Systems, Inc.
     All rights reserved.";

  revision 2026-08-01 {
    description
      "Initial revision";
    reference
      "1.0.0";
    cisco-semver:module-version "1.0.0";
  }

  typedef isis-lvl-type {
    type enumeration {
      enum level-1 {
        value 0;
        description
          "Indicates ISIS Level 1 routing within an area";
      }
      enum level-2 {
        value 1;
        description
          "Indicates ISIS Level 2 routing between areas";
      }
    }
    description
      "ISIS levels";
  }

  typedef isis-ckt-level-type {
    type enumeration {
      enum ckt-level-1 {
        value 0;
        description
          "Indicates ISIS circuit Level 1 for intra-area routing";
      }
      enum ckt-level-2 {
        value 1;
        description
          "Indicates ISIS circuit Level 2 for inter-area routing";
      }
      enum ckt-level-12 {
        value 2;
        description
          "Indicates ISIS circuit supporting both Level 1 and Level 2 routing";
      }
    }
    description
      "Circuit type of ISIS adjacency";
  }

  typedef isis-nbr-state {
    type enumeration {
      enum adj-up {
        value 0;
        description
          "Indicates that the adjacency is fully established and operational";
      }
      enum adj-down {
        value 1;
        description
          "Indicates that the adjacency is not established";
      }
      enum adj-init {
        value 2;
        description
          "Indicates that the adjacency is initializing";
      }
      enum adj-stdby {
        value 3;
        description
          "Indicates that the adjacency is in standby mode";
      }
    }
    description
      "Current state of ISIS adjacency";
  }

  typedef isis-intf-padding-state {
    type enumeration {
      enum padding-strict {
        value 0;
        description
          "Indicates that hello PDUs are always padded to the maximum frame size";
      }
      enum padding-loose {
        value 1;
        description
          "Indicates that hello PDUs are padded only until adjacency is established";
      }
      enum padding-adaptive {
        value 2;
        description
          "Indicates that hello PDU padding adapts dynamically based on network conditions";
      }
      enum padding-disable {
        value 3;
        description
          "Hello padding disabled on the interface";
      }
    }
    description
      "Padding type on the interface";
  }

  typedef isis-intf-circuit-type {
    type enumeration {
      enum ckt-p2p {
        value 0;
        description
          "Describes Point-to-point interface";
      }
      enum ckt-bcast {
        value 1;
        description
          "Describes Broadcast interface";
      }
    }
    description
      "Circuit type on the interface";
  }

  typedef isis-lsp-flag {
    type bits {
      bit lsp-part-repair {
        position 0;
        description
          "Indicates that the originator supports partition
           repair";
      }
      bit lsp-att-err {
        position 1;
        description
          "Indicates that the originator is attached to another area using the error metric";
      }
      bit lsp-att-expense {
        position 2;
        description
          "Indicates that the originator is attached to another area using the expense metric.";
      }
      bit lsp-att-delay {
        position 3;
        description
          "Indicates that the originator is attached to another area using the delay metric.";
      }
      bit lsp-att-dflt {
        position 4;
        description
          "Indicates that the originator is attached to another area using the default metric.";
      }
      bit lsp-overload {
        position 5;
        description
          "Indicates that the originator is overloaded, and must be avoided in path calculation";
      }
    }
    description
      "Flags describing operational state and capabilities of LSP";
  }

  grouping isis-lsp-db-rec {
    description
      "Details of the LSP database";
    leaf lspid {
      type string;
      description
        "Unique identifier of the Link State PDU";
    }
    leaf max-area-addr {
      type uint8;
      description
        "Maximum area addresses";
    }
    leaf ver {
      type uint8;
      description
        "ISIS protocol version number of the LSP";
    }
    leaf id-len {
      type uint8;
      units "octets";
      description
        "System ID length in octets";
    }
    leaf pdu-type {
      type isis-ios-xe-operv2:isis-lvl-type;
      description
        "ISIS level associated with this LSP";
    }
    leaf seq-num {
      type uint32;
      description
        "Sequence number of the LSP for version tracking";
    }
    leaf checksum {
      type uint16;
      description
        "LSP checksum";
    }
    leaf pdu-len {
      type uint16;
      units "octets";
      description
        "Total length of the LSP PDU in octets";
    }
    leaf is-type {
      type isis-ios-xe-operv2:isis-lvl-type;
      description
        "ISIS level of this LSP";
    }
    leaf flag {
      type isis-ios-xe-operv2:isis-lsp-flag;
      description
        "Active attribute flags for this LSP";
    }
  }

  grouping isis-nbr-key {
    description
      "Compound key that identifies a unique neighbor within an ISIS tag";
    leaf system-id {
      type yang:phys-address;
      description
        "System ID of the neighbor";
    }
    leaf level {
      type isis-ios-xe-operv2:isis-lvl-type;
      description
        "Level of the adjacency formed";
    }
    leaf if-name {
      type string;
      description
        "Interface name on which adjacency is formed";
    }
  }

  grouping isis-nbr-rec {
    description
      "Details of the adjacency formed";
    leaf nbr-ipv4-addr {
      type inet:ip-address;
      description
        "IPv4 Address of the neighbor";
    }
    leaf nbr-ipv6-addr {
      type inet:ipv6-address;
      description
        "IPv6 Address of the neighbor";
    }
    leaf adj-state {
      type isis-ios-xe-operv2:isis-nbr-state;
      description
        "Current state of the adjacency";
    }
    leaf nbr-snpa {
      type yang:mac-address;
      description
        "ISIS Neighbor SNPA (Sub-network Point Of Attachment) address";
    }
    leaf local-ext-ckt-id {
      type uint32;
      description
        "Local extended circuit ID";
    }
    leaf nbr-ext-ckt-id {
      type uint32;
      description
        "Neighbor extended circuit ID";
    }
    leaf pri {
      type uint8;
      description
        "Designated Intermediate System election priority of the neighbor";
    }
    leaf dis-system-id {
      type string;
      description
        "System ID of the Designated Intermediate System on the LAN";
    }
    leaf nbr-ckt-type {
      type isis-ios-xe-operv2:isis-ckt-level-type;
      description
        "Received ISIS circuit type";
    }
    leaf adj-type {
      type isis-ios-xe-operv2:isis-ckt-level-type;
      description
        "Formed ISIS adjacency type";
    }
    leaf up-time {
      type yang:date-and-time;
      description
        "Time at which adjacency transitioned into UP state";
    }
    leaf restart-support {
      type boolean;
      description
        "True if the neighbor supports ISIS graceful restart; otherwise false";
    }
    leaf restart-status {
      type boolean;
      description
        "True if this router is assisting the neighbor during graceful restart; otherwise false";
    }
    leaf-list nlpid {
      type uint8;
      ordered-by user;
      description
        "List of supported network layer protocol identifiers (values from TLV 129)";
    }
    leaf multi-topo {
      type boolean;
      description
        "True if the neighbor supports ISIS multi-topology routing; otherwise false";
    }
    leaf-list topo {
      type uint32;
      ordered-by user;
      description
        "List of ISIS multi-topology (MT) IDs supported by the neighbor
             MT ID 0: Equivalent to the standard topology
             MT ID 1: IPv4 in-band management purposes
             MT ID 2: IPv6 routing topology
             MT ID 3: IPv4 multicast routing topology
             MT ID 4: IPv6 multicast routing topology
             MT ID 5: IPv6 in-band management purposes
             MT ID 6-3995: Reserved for IETF consensus";
    }
    leaf-list area-addr {
      type yang:phys-address;
      ordered-by user;
      description
        "List of ISIS area addresses";
    }
  }

  grouping isis-intf-state {
    description
      "List of interfaces for a specific tag";
    leaf if-name {
      type string;
      description
        "Interface name";
    }
    leaf is-enabled {
      type boolean;
      description
        "Indicates whether the interface is enabled for ISIS";
    }
    leaf is-passive {
      type boolean;
      description
        "Indicates whether the interface is passive";
    }
    leaf hello-padding {
      type isis-ios-xe-operv2:isis-intf-padding-state;
      description
        "Defines hello-padding type on this interface";
    }
    leaf circuit-type {
      type isis-ios-xe-operv2:isis-intf-circuit-type;
      description
        "Defines ISIS interface type";
    }
  }

  grouping isis-level-rec {
    description
      "Details of ISIS levels";
    leaf level {
      type isis-ios-xe-operv2:isis-lvl-type;
      description
        "ISIS routing level for this entry";
    }
    list isis-lsp-db {
      key "lspid";
      description
        "List of LSP for this level";
      uses isis-ios-xe-operv2:isis-lsp-db-rec;
    }
  }

  grouping isis-inst-rec {
    description
      "Each entry contains information of single IS-IS instance";
    leaf tag {
      type string;
      description
        "IS-IS router tag";
    }
    list isis-level {
      key "level";
      description
        "List of levels for a specific tag";
      uses isis-ios-xe-operv2:isis-level-rec;
    }
    list isis-intf {
      key "if-name";
      description
        "Operational state information for an ISIS interface";
      uses isis-ios-xe-operv2:isis-intf-state;
    }
    list isis-nbr {
      key "system-id level if-name";
      description
        "List of neighbors for a specific tag";
      uses isis-ios-xe-operv2:isis-nbr-rec;
      uses isis-ios-xe-operv2:isis-nbr-key;
    }
  }

  container isis-operv2-oper-data {
    config false;
    description
      "Operational state of the IS-IS subsystem";
    list isis-inst-rec {
      key "tag";
      description
        "List of ISIS routers";
      uses isis-ios-xe-operv2:isis-inst-rec;
    }
  }
}
