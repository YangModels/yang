module Cisco-IOS-XE-vxlan {
  yang-version 1.1;
  namespace "http://cisco.com/ns/yang/Cisco-IOS-XE-vxlan";
  prefix ios-vxlan;

  import cisco-semver {
    prefix cisco-semver;
  }
  import Cisco-IOS-XE-native {
    prefix ios;
  }
  import ietf-inet-types {
    prefix inet;
  }
  import Cisco-IOS-XE-types {
    prefix ios-types;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Virtual Extensible Local Area Network (VXLAN) Yang Model.
     Copyright (c) 2018-2019 by Cisco Systems, Inc.
     All rights reserved.";

  revision 2022-11-01 {
    description
      "- Update yang-version to 1.1";
    cisco-semver:module-version "1.3.0";
  }
  revision 2020-11-01 {
    description
      "- Add default-mac-source in vxlan route profile";
    cisco-semver:module-version "1.2.0";
  }
  revision 2020-03-01 {
    description
      "Add vxlan static route support";
    cisco-semver:module-version "1.1.0";
  }
  revision 2019-07-01 {
    description
      "Establish semantic version baseline";
    cisco-semver:module-version "1.0.0";
  }
  revision 2019-02-25 {
    description
      "Initial revision";
  }

  typedef vxlan-source-port-hash-type {
    type enumeration {
      enum 3-tuple {
        description
          "UDP source port hash with 3 tuples";
      }
      enum 3-tuple-for-fragments {
        description
          "UDP source port hash with 3 tuples for fragments and 5 tuples for non-fragments";
      }
    }
  }

  typedef vxlan-tunnel-mode-type {
    type enumeration {
      enum vxlan-default-mac {
        description
          "Configure vxlan default mac mode for VxLAN route profile";
      }
      enum vxlan-gpe {
        description
          "Configure vxlan gpe mode for VxLAN route profile";
      }
    }
  }

  grouping vxlan-source-port-range-grouping {
    container range {
      leaf start {
        description
          "Source port range start";
        type uint16 {
          range "1..65535";
        }
      }
      leaf end {
        description
          "Source port range end";
        type uint16 {
          range "1..65535";
        }
      }
    }
  }

  grouping vxlan-route-profile-grouping {
    description
      "Configure VxLAN route profile for static route";
    leaf dscp {
      description
        "Configure dscp for VxLAN route profile";
      type uint8 {
        range "0..63";
      }
      default "0";
    }
    leaf dst-port {
      description
        "Configure dst port for VxLAN route profile";
      type uint16 {
        range "1..65535";
      }
      default "4789";
    }
    leaf persistent {
      description
        "Configure persistent for VxLAN route profile";
      type empty;
    }
    container tunnel {
      description
        "Configure per tunnel parameters for VxLAN route profile";
      leaf mode {
        description
          "Configure encapsulate mode for VxLAN route profile";
        type vxlan-tunnel-mode-type;
      }
      leaf mtu {
        description
          "Configure mtu for VxLAN route profile";
        type uint16 {
          range "64..9216";
        }
        default "1450";
      }
      container source {
        description
          "Configure source for VxLAN route profile";
        container interface {
          description
            "Configure source interface for VxLAN route profile";
          leaf Loopback {
            description
              "Loopback interface";
            type leafref {
              path "/ios:native/ios:interface/ios:Loopback/ios:name";
            }
          }
        }
      }
      leaf source-port-hash {
        description
          "Configure source port hash tuples for VxLAN route profile";
        type vxlan-source-port-hash-type;
      }
      container source-port-range {
        description
          "Configure source port range for VxLAN route profile";
        uses vxlan-source-port-range-grouping;
      }
    }
    container vxlan-reserved-word-1 {
      description
        "Configure reserved word 1 for VxLAN route profile";
      leaf hex-string {
        description
          "Vxlan reserved word 1 with two bytes in hex value, range [0, 65535]";
        type string {
          pattern '([0-9a-fA-F]{1,4})';
        }
      }
    }
    container vxlan-reserved-word-2 {
      description
        "Configure reserved word 2 for VxLAN route profile";
      leaf hex-string {
        description
          "Vxlan reserved word 2 with one byte in hex value, range [0, 255]";
        type string {
          pattern '([0-9a-fA-F]{1,2})';
        }
      }
    }
    leaf default-mac-source {
      description
        "Configure default mac source for VxLAN route profile";
      type ios-types:cisco-mac-address-type;
    }
  }

  grouping vxlan-sr-option-persistent-grouping {
    leaf persistent {
      description
        "Configure persistent for VxLAN static route, save in startup";
      type empty;
    }
  }

  grouping vxlan-static-route-options-grouping {
    container vxlan-sr-option {
      leaf persistent {
        description
          "Configure persistent for VxLAN static route, save in startup";
        type empty;
      }
      container symmetric {
        uses vxlan-sr-option-persistent-grouping;
      }
    }
  }

  grouping vxlan-static-route-profile-grouping {
    list route-profile {
      description
        "Configure route profile for VxLAN static route prefix";
      key "name";
      leaf name {
        type string;
      }
      uses vxlan-static-route-options-grouping;
    }
  }

  grouping vxlan-static-route-dst-mac-grouping {
    list dst-mac-list {
      key "dst-mac";
      leaf dst-mac {
        description
          "Configure inner dst mac for VxLAN static route prefix";
        type ios-types:cisco-mac-address-type;
      }
      uses vxlan-static-route-profile-grouping;
    }
    uses vxlan-static-route-profile-grouping;
  }

  grouping vxlan-static-route-nh-grouping {
    list nh-list {
      description
        "global vrf next-hop address for this route";
      key "nh-address";
      leaf nh-address {
        description
          "A.B.C.D or X:X:X:X::X";
        type union {
          type inet:ipv4-address;
          type inet:ipv6-address;
        }
      }
      uses vxlan-static-route-dst-mac-grouping;
    }
  }

  grouping vxlan-static-route-vni-grouping {
    list vni-list {
      key "vni";
      leaf vni {
        description
          "Configure vni for VxLAN static route prefix";
        type uint32 {
          range "1..16777215";
        }
      }
      uses vxlan-static-route-nh-grouping;
    }
  }

  grouping vxlan-static-route-entry-grouping {
    list vxlan-static-route-prefix {
      description
        "The address and prefix length";
      key "prefix";
      leaf prefix {
        description
          "A.B.C.D/nn or X:X:X:X::X/<0-128> or A.B.C.D";
        type union {
          type ios-types:ipv4-address-slash-prefix-len;
          type ios-types:ipv6-prefix;
          type inet:ipv4-address;
        }
      }
      container vxlan-static-route-vni {
        list ipv4-addr-mask {
          key "mask";
          leaf mask {
            description
              "A.B.C.D  IP prefix mask";
            type inet:ipv4-address;
          }
          uses vxlan-static-route-vni-grouping;
        }
        uses vxlan-static-route-vni-grouping;
      }
    }
  }

  grouping vxlan-static-route-grouping {
    list vrf {
      key "name";
      leaf name {
        must '(/ios:native/ios:vrf/ios:definition[ios:name=current()] and /ios:native/ios:vrf/ios:definition[ios:name=current()]/ios:address-family/ios:ipv4) or /ios:native/ios:ip/ios:vrf[ios:name=current()]' {
          error-message "Please create vrf first, and delete the last";
        }
        type string;
      }
      uses vxlan-static-route-entry-grouping;
    }
  }

  grouping vxlan-static-route-police-rate-grouping {
    leaf rate {
      description
        "Configure police rate for VNI ranges";
      type uint64 {
        range "8000..67000000000";
      }
    }
  }

  grouping vxlan-static-route-police-vni-grouping {
    choice vni-choice {
      case vni-single {
        leaf rate {
          description
            "Configure police rate for VNI ranges";
          type uint64 {
            range "8000..67000000000";
          }
        }
      }
      case vni-range {
        container vni-range {
          leaf vni-range-end {
            description
              "VNI end number for vni range";
            type uint32 {
              range "1..16777215";
            }
          }
          uses vxlan-static-route-police-rate-grouping;
        }
      }
    }
  }

  grouping vxlan-static-route-policy-out-vrf-grouping {
    container police {
      description
        "Configure vxlan static route policy per vrf police";
      container match {
        description
          "Configure vxlan static route policy per vrf match criteria";
        container any {
          description
            "Configure vxlan static route policy per vrf match any";
          list vni-range-list {
            description
              "Specify at most 5 vni ranges one line, i.e. 1 , 2 , 3 , 5 - 10, 100 - 200";
            key "vni";
            leaf vni {
              description
                "Specify single vni number or vni start number";
              type uint32 {
                range "1..16777215";
              }
            }
            uses vxlan-static-route-police-vni-grouping;
          }
        }
      }
    }
  }

  grouping vxlan-static-route-policy-out-grouping {
    list vrf {
      key "name";
      leaf name {
        must '(/ios:native/ios:vrf/ios:definition[ios:name=current()] and /ios:native/ios:vrf/ios:definition[ios:name=current()]/ios:address-family/ios:ipv4) or /ios:native/ios:ip/ios:vrf[ios:name=current()]' {
          error-message "Please create vrf first, and delete the last";
        }
        type string;
      }
      uses vxlan-static-route-policy-out-vrf-grouping;
    }
  }

  grouping config-vxlan-grouping {
    container udp {
      leaf port {
        description
          "VxLAN dataplane UDP destination port for global";
        type uint16 {
          range "1024..65535";
        }
      }
    }
    leaf dummy-l2-tunnel-udp-port {
      description
        "UDP destination port for vxlan dummy l2 tunnel (default is 4789)";
      type uint16 {
        range "1024..65535";
      }
    }
    leaf gpe-tunnel-udp-port {
      description
        "UDP destination port for vxlan gpe tunnel (default is 4790)";
      type uint16 {
        range "1024..65535";
      }
    }
    list route-profile {
      description
        "Configure VxLAN route profile for static route";
      key "name";
      leaf name {
        type string;
      }
      uses vxlan-route-profile-grouping;
    }
    container source-port-hash {
      description
        "UDP source port hash";
      leaf dummy-l2-tunnel {
        description
          "UDP source port hash for vxlan dummy-l2 tunnel";
        type vxlan-source-port-hash-type;
      }
      leaf gpe-tunnel {
        description
          "UDP source port hash for vxlan gpe tunnel";
        type vxlan-source-port-hash-type;
      }
    }
    container source-port-range {
      description
        "UDP  source port range for vxlan/vxlan-gpe/vxlan-dummy-l2";
      container dummy-l2-tunnel-udp {
        description
          "UDP source port range for vxlan dummy l2 tunnel";
        uses vxlan-source-port-range-grouping;
      }
      container gpe-tunnel-udp {
        description
          "UDP source port range for vxlan gpe tunnel";
        uses vxlan-source-port-range-grouping;
      }
      container udp {
        description
          "UDP source port range for vxlan";
        uses vxlan-source-port-range-grouping;
      }
    }
    container static-route {
      description
        "Configure VxLAN static route";
      container accounting-policing {
        description
          "Configure VxLAN static route accounting policing bind option";
        container bind {
          description
            "Configure VxLAN static route accounting policing bind";
          leaf p2p-tunnel {
            description
              "Configure VxLAN static route accounting policing bind with p2p-tunnel";
            type empty;
          }
        }
      }
      container auto-tunnel {
        description
          "Configure VxLAN static route auto-tunnel";
        container range {
          description
            "Configure VxLAN static route auto-tunnel range";
          leaf start {
            description
              "Auto tunnel range start";
            type uint32 {
              range "1..2147483647";
            }
          }
          leaf end {
            description
              "Auto tunnel range end";
            type uint32 {
              range "1..2147483647";
            }
          }
        }
      }
      container policy {
        description
          "Configure VxLAN static route policy";
        container output {
          description
            "Configure VxLAN static route output policy";
          uses vxlan-static-route-policy-out-grouping;
        }
      }
      container route-list {
        uses vxlan-static-route-grouping;
      }
    }
  }

  augment "/ios:native/ios:vxlan" {
    uses config-vxlan-grouping;
  }
}
