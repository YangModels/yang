module Cisco-IOS-XE-rib-oper {
  yang-version 1.1;
  namespace "http://cisco.com/ns/yang/Cisco-IOS-XE-rib-oper";
  prefix rib-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for IOS-XE Routing Information Base (RIB) operational data.
     Copyright (c) 2026 by Cisco Systems, Inc.
     All rights reserved.";

  revision 2026-08-01 {
    description
      "Improved descriptions for rib-ipv4-ni-entry and
       rib-ipv6-ni-entry grouping";
    reference
      "1.0.1";
    cisco-semver:module-version "1.0.1";
  }
  revision 2026-02-01 {
    description
      "Initial revision";
    reference
      "1.0.0";
    cisco-semver:module-version "1.0.0";
  }

  grouping rib-ipv4-ni-entry {
    description
      "IPv4 RIB Network Instance";
    leaf ni-name {
      type string;
      description
        "Name identifying the network instance associated with
         this IPv4 RIB entry";
    }
    leaf num-entries {
      type uint32;
      description
        "Number of IPv4 RIB entries in the Network Instance";
    }
  }

  grouping rib-ipv6-ni-entry {
    description
      "IPv6 RIB Network Instance";
    leaf ni-name {
      type string;
      description
        "Name identifying the network instance associated with
         this IPv6 RIB entry";
    }
    leaf num-entries {
      type uint32;
      description
        "Number of IPv6 RIB entries in the Network Instance";
    }
  }

  container rib-oper-data {
    config false;
    description
      "IOS RIB operational data";
    list rib-ipv4-ni {
      key "ni-name";
      description
        "RIB IPv4 Network Instance Table";
      uses rib-ios-xe-oper:rib-ipv4-ni-entry;
    }
    list rib-ipv6-ni {
      key "ni-name";
      description
        "RIB IPv6 Network Instance Table";
      uses rib-ios-xe-oper:rib-ipv6-ni-entry;
    }
  }
}
