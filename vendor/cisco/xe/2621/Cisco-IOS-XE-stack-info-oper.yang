module Cisco-IOS-XE-stack-info-oper {
  yang-version 1.1;
  namespace "http://cisco.com/ns/yang/Cisco-IOS-XE-stack-info-oper";
  prefix stack-info-ios-xe-oper;

  import Cisco-IOS-XE-common-types {
    prefix common-types-ios-xe;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for operational data of the stack nodes and their ports specifically on Cisco Catalyst 9350 series switches
     Copyright (c) 2025 by Cisco Systems, Inc.
     All rights reserved.";

  revision 2026-08-01 {
    description
      "- Added stack adapter presence, authentication status, and serial number to stack node info
       - Updated descriptions of several model elements to improve description quality";
    reference
      "1.1.0";
    cisco-semver:module-version "1.1.0";
  }
  revision 2026-02-01 {
    description
      "Initial revision";
    reference
      "1.0.0";
    cisco-semver:module-version "1.0.0";
  }

  typedef bss-stack-node-state {
    type enumeration {
      enum bss-state-conf {
        value 0;
        description
          "The node has been configured in the stack but has not yet begun joining";
      }
      enum bss-state-wait {
        value 1;
        description
          "The node is waiting to join or re-join the stack";
      }
      enum bss-state-prog {
        value 2;
        description
          "The node is in the process of joining the stack";
      }
      enum bss-state-init {
        value 3;
        description
          "The node is initializing its stack membership and resources";
      }
      enum bss-state-ready {
        value 4;
        description
          "The node has successfully joined the stack and is fully operational";
      }
      enum bss-state-master-reinit {
        value 5;
        description
          "The master node is re-initializing its stack state and resources";
      }
      enum bss-state-feature-mismatch {
        value 6;
        description
          "Node state feature mismatch";
      }
      enum bss-state-ver-mismatch {
        value 7;
        description
          "Node state version mismatch";
      }
      enum bss-state-license-mismatch {
        value 8;
        description
          "Node state license mismatch";
      }
      enum bss-state-plat-mismatch {
        value 9;
        description
          "Node state platform mismatch";
      }
      enum bss-state-plat-lic-mismatch {
        value 10;
        description
          "Node state platform and license mismatch";
      }
      enum bss-state-invalid {
        value 11;
        description
          "The node state is invalid or could not be determined";
      }
      enum bss-state-prov {
        value 12;
        description
          "The node is provisioned in the stack configuration but not currently present";
      }
      enum bss-state-removed {
        value 13;
        description
          "The node has been removed from the stack";
      }
      enum bss-state-unprov {
        value 14;
        description
          "The node is not provisioned in the stack configuration";
      }
      enum bss-state-os-mismatch {
        value 15;
        description
          "Node state OS mismatch";
      }
    }
    description
      "Defines the operational status of a stack node";
  }

  typedef bss-stack-node-role {
    type enumeration {
      enum node-role-active {
        value 0;
        description
          "The primary switch controlling the stack";
      }
      enum node-role-standby {
        value 1;
        description
          "A backup switch ready to take over if the active switch fails";
      }
      enum node-role-member {
        value 2;
        description
          "A regular stack member switch participating in the stack but not controlling it";
      }
    }
    description
      "The role assigned to a node within a stack configuration";
  }

  typedef bss-stacking-mode {
    type enumeration {
      enum mode-sw-rear {
        value 0;
        description
          "Switches are physically connected using dedicated rear stack ports to form a single logical switch";
      }
      enum mode-active-standby {
        value 1;
        description
          "Redundancy mode where one device actively handles traffic while the other waits to take over if needed";
      }
      enum mode-sw-geo {
        value 2;
        description
          "Stack mode that enables geographically dispersed switches to be stacked over long distances using ethernet links";
      }
      enum mode-sw-virt {
        value 3;
        description
          "Stackwise virtual mode that combines two physical switches into one logical virtual switch with a unified control plane and distributed forwarding";
      }
    }
    description
      "Represents stack mode of the switch";
  }

  typedef bss-stack-port-state {
    type enumeration {
      enum link-down {
        value 0;
        description
          "The stack port link is down";
      }
      enum link-up {
        value 1;
        description
          "The stack port link is up";
      }
      enum link-no-cable {
        value 2;
        description
          "Indicates the port has no cable connected";
      }
    }
    description
      "The current operational state of the stack port";
  }

  typedef bss-stack-cable-presence {
    type enumeration {
      enum stack-cable-invalid {
        value 0;
        description
          "Invalid or unsupported stack cable detected";
      }
      enum stack-cable-absent {
        value 1;
        description
          "Stack cable not connected";
      }
      enum stack-cable-present {
        value 2;
        description
          "Stack cable connected";
      }
    }
    description
      "Indicates the presence status of the stack cable";
  }

  typedef bss-stack-cable-auth-status {
    type enumeration {
      enum cable-auth-unknown {
        value 0;
        description
          "Stack cable authentication unknown";
      }
      enum cable-auth-pass {
        value 1;
        description
          "Stack cable authentication pass";
      }
      enum cable-auth-fail {
        value 2;
        description
          "Stack cable authentication fail";
      }
    }
    description
      "Indicates the authentication status of the stack cable";
  }

  typedef bss-stack-adapter-presence {
    type enumeration {
      enum bst-pres-invalid {
        value 0;
        description
          "Indicates that the stack adapter presence state is invalid or unsupported";
      }
      enum bst-pres-not-present {
        value 1;
        description
          "Indicates that the stack adapter is not physically connected";
      }
      enum bst-pres-present {
        value 2;
        description
          "Indicates that the stack adapter is physically connected";
      }
    }
    description
      "Indicates the presence status of the stack adapter";
  }

  typedef bss-stack-adapter-auth-status {
    type enumeration {
      enum bst-auth-unknown {
        value 0;
        description
          "Indicates that the authentication status of the stack adapter cannot be determined";
      }
      enum bst-auth-pass {
        value 1;
        description
          "Indicates that the stack adapter has passed authentication";
      }
      enum bst-auth-fail {
        value 2;
        description
          "Indicates that the stack adapter has failed authentication";
      }
    }
    description
      "Indicates the authentication status of the stack adapter";
  }

  grouping bss-stack-adapter-info {
    description
      "Stack adapter presence, authentication status, and serial number";
    leaf presence {
      type stack-info-ios-xe-oper:bss-stack-adapter-presence;
      description
        "The stack adapter presence status";
    }
    leaf auth-status {
      type stack-info-ios-xe-oper:bss-stack-adapter-auth-status;
      description
        "The stack adapter authentication status";
    }
    leaf serial-num {
      type string;
      description
        "The stack adapter serial number";
    }
  }

  grouping bss-stack-port-info {
    description
      "Stack port operational data, including link state, cable details, and neighbor connectivity";
    leaf if-name {
      type string;
      description
        "Represents the stack port interface name";
    }
    leaf mac-addr {
      type yang:mac-address;
      description
        "The hardware address of the stack port";
    }
    leaf num-links {
      type uint8;
      description
        "Number of physical links aggregated in the stack";
    }
    leaf port-state {
      type stack-info-ios-xe-oper:bss-stack-port-state;
      description
        "The status of stack ports connecting switches";
    }
    leaf cable-length-cm {
      type uint16;
      units "centimeters";
      description
        "Stack cable length in centimetres";
    }
    leaf nbr-switch-num {
      type uint8;
      description
        "Neighbor switch number connected to this port";
    }
    leaf nbr-port-num {
      type uint8;
      description
        "Neighbor port number";
    }
    leaf presence {
      type stack-info-ios-xe-oper:bss-stack-cable-presence;
      description
        "The stack cable presence status";
    }
    leaf cable-auth-status {
      type stack-info-ios-xe-oper:bss-stack-cable-auth-status;
      description
        "The stack cable authentication status";
    }
    leaf cable-serial-num {
      type string;
      description
        "Serial number of the stack cable";
    }
    leaf port-in-loopback {
      type boolean;
      description
        "Indicates whether the stack port is currently operating in loopback mode";
    }
  }

  grouping bss-stack-node-info {
    description
      "Stack node data";
    leaf node-num {
      type uint8;
      description
        "Represents the node number within the stack";
    }
    leaf priority {
      type uint8;
      description
        "The priority value assigned to each switch, influencing active switch election";
    }
    leaf stack-mode {
      type stack-info-ios-xe-oper:bss-stacking-mode;
      description
        "Represents stack mode of the switch";
    }
    leaf serial-number {
      type string;
      description
        "Represents the switch serial number";
    }
    leaf role {
      type stack-info-ios-xe-oper:bss-stack-node-role;
      description
        "The role of the switch in the stack, such as Active, Standby, or Member";
    }
    leaf mac-addr {
      type yang:mac-address;
      description
        "The hardware address of each individual switch in the stack";
    }
    leaf node-state {
      type stack-info-ios-xe-oper:bss-stack-node-state;
      description
        "Represents the operational status of a stack node";
    }
    list stack-port {
      description
        "List of stack ports on this node; each entry contains operational statistics for one stack port";
      uses stack-info-ios-xe-oper:bss-stack-port-info;
    }
    container adapter-info {
      description
        "Stack adapter presence, authentication status, and serial number";
      uses stack-info-ios-xe-oper:bss-stack-adapter-info;
    }
  }

  container stack-info-oper-data {
    config false;
    description
      "This container provides operational data for the distributed stack, including information about stack nodes and overall stack status";
    list location {
      key "fru slot bay chassis node";
      description
        "A list of data provider locations";
      uses common-types-ios-xe:extended-location;
      container bss-stack-node-info {
        presence "bss-stack-node-info";
        description
          "This container holds detailed operational information for each node in the distributed stack, including node number, priority, role, and stack port statistics";
        uses stack-info-ios-xe-oper:bss-stack-node-info;
      }
    }
  }
}
