module Cisco-IOS-XE-policy-vxe-deviation {
  yang-version 1.1;
  namespace "http://cisco.com/ns/yang/Cisco-IOS-XE-policy-vxe-deviation";
  prefix ios-policy-vxe-deviate;

  import Cisco-IOS-XE-native {
    prefix ios;
  }
  import Cisco-IOS-XE-policy {
    prefix ios-policy;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Deviation Policy Map Yang model for VXE(CSR) platform.
     Copyright (c) 2019-2024 by Cisco Systems, Inc.
     All rights reserved.";

  revision 2024-11-01 {
    description
      "Initial Revision";
  }

  deviation "/ios:native/ios:policy/ios-policy:policy-map/ios-policy:class/ios-policy:action-list/ios-policy:action-param/ios-policy:shape-case/ios-policy:shape/ios-policy:average/ios-policy:average-choice/ios-policy:a/ios-policy:bit-rate" {
    deviate replace {
      type uint64 {
        range "8000..40000000000";
      }
    }
  }
}
