module Cisco-IOS-XE-wireless-raf-cfg-rpc {
  yang-version 1.1;
  namespace "http://cisco.com/ns/yang/Cisco-IOS-XE-wireless-raf-cfg-rpc";
  prefix wireless-raf-cfg-rpc;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for processing
     Regulatory Activation File(RAF)
     Copyright (c) 2026 by Cisco Systems, Inc.
     All rights reserved.";

  revision 2026-08-01 {
    description
      "Initial revision";
    reference
      "1.0.0";
    cisco-semver:module-version "1.0.0";
  }

  grouping set-raf-name {
    description
      "Configures name of the regulatory activation file";
    leaf file-name {
      type string {
        length "1..128";
        pattern '[!-~]+';
      }
      mandatory true;
      description
        "Name of the regulatory activation file to configure";
    }
  }

  grouping clear-country-ap-map {
    description
      "Clear regulatory activation country code mapping for AP";
    leaf ap-mac {
      type yang:mac-address;
      mandatory true;
      description
        "MAC address of the access point";
    }
  }

  rpc set-raf-name {
    description
      "Configures regulatory activation file name";
    input {
      uses wireless-raf-cfg-rpc:set-raf-name;
    }
  }

  rpc apply-raf-config {
    description
      "Apply regulatory activation file mapping";
  }

  rpc clear-country-map-all-ap {
    description
      "Clear regulatory activation country code mappings for all APs";
  }

  rpc clear-country-ap-map {
    description
      "Clear regulatory activation mapping for AP";
    input {
      uses wireless-raf-cfg-rpc:clear-country-ap-map;
    }
  }
}
