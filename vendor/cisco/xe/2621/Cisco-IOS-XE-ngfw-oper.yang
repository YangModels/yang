module Cisco-IOS-XE-ngfw-oper {
  yang-version 1.1;
  namespace "http://cisco.com/ns/yang/Cisco-IOS-XE-ngfw-oper";
  prefix ngfw-ios-xe-oper;

  import Cisco-IOS-XE-ngfw-common-oper {
    prefix ngfw-common-ios-xe-oper;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     Next-Generation Firewall (NGFW).
     Copyright (c) 2025-2026 by Cisco Systems, Inc.
     All rights reserved.";

  revision 2026-08-01 {
    description
      "Initial revision";
    reference
      "1.0.0";
    cisco-semver:module-version "1.0.0";
  }

  typedef ngfw-op-status-val {
    type enumeration {
      enum ngfw-op-unknown {
        value 0;
        description
          "Next-Generation Firewall (NGFW) operational status is unknown - Unable to determine status";
      }
      enum ngfw-op-green {
        value 1;
        description
          "Next-Generation Firewall (NGFW) operational status is green - Working as expected";
      }
      enum ngfw-op-yellow {
        value 2;
        description
          "Next-Generation Firewall (NGFW) operational status is yellow - Minor problem";
      }
      enum ngfw-op-red {
        value 3;
        description
          "Next-Generation Firewall (NGFW) operational status is red - Major problem";
      }
      enum ngfw-op-down {
        value 4;
        description
          "Next-Generation Firewall (NGFW) operational status is down - Communication has been lost";
      }
    }
    description
      "Next-Generation Firewall (NGFW) operation status";
  }

  grouping ngfw-ver-status {
    description
      "Next-Generation Firewall (NGFW) version status";
    leaf app-id {
      type string;
      description
        "Next-Generation Firewall (NGFW) application ID";
    }
    leaf supp-rgx {
      type string;
      description
        "Next-Generation Firewall (NGFW) version regular expression - describes version support";
    }
    leaf inst-ver {
      type string;
      description
        "Next-Generation Firewall (NGFW) version currently installed";
    }
    leaf supp {
      type boolean;
      description
        "Indicates whether the installed NGFW version is compatible with the supported version regular expression; true if compatible, false otherwise.";
    }
  }

  grouping ngfw-upd-status {
    description
      "Next-Generation Firewall (NGFW) update status";
    leaf ver {
      type string;
      description
        "Version string of the NGFW package at the time of the last update attempt.";
    }
    leaf last-upd-time {
      type yang:date-and-time;
      description
        "Time of last attempted update";
    }
    leaf last-upd-status {
      type ngfw-common-ios-xe-oper:ngfw-update-status-val;
      description
        "Status of last attempted update";
    }
    leaf last-upd-reason {
      type string;
      description
        "Reason for last attempted update failure";
    }
    leaf last-succ-upd-time {
      type yang:date-and-time;
      description
        "Time of last successful update";
    }
  }

  grouping ngfw-lsp-upd-status {
    description
      "Next-Generation Firewall (NGFW) Lightweight Security Package (LSP) update status.";
    container lsp-upd-status {
      description
        "Lightweight Security Package (LSP) update status.";
      uses ngfw-ios-xe-oper:ngfw-upd-status;
    }
  }

  grouping ngfw-vdb-upd-status {
    description
      "Next-Generation Firewall (NGFW) Vulnerability Database (VDB) update status";
    container vdb-upd-status {
      description
        "Vulnerability Database (VDB) update status";
      uses ngfw-ios-xe-oper:ngfw-upd-status;
    }
  }

  grouping ngfw-engine-inst-status {
    description
      "Next-Generation Firewall (NGFW) engine instance status";
    leaf id {
      type uint32;
      description
        "Engine instance ID";
    }
    leaf running {
      type boolean;
      description
        "Indicates whether the NGFW engine instance is currently running; true if running, false otherwise.";
    }
    leaf status {
      type ngfw-ios-xe-oper:ngfw-op-status-val;
      description
        "Engine instance status";
    }
    leaf reason {
      type string;
      description
        "Engine instance status reason";
    }
  }

  grouping ngfw-engine-status {
    description
      "Next-Generation Firewall (NGFW) engine status";
    leaf ver {
      type string;
      description
        "Engine version";
    }
    leaf profile {
      type string;
      description
        "Resource profile name in use";
    }
    leaf status {
      type ngfw-ios-xe-oper:ngfw-op-status-val;
      description
        "Aggregate operational health status of the NGFW engine.";
    }
    leaf reason {
      type string;
      description
        "Human-readable explanation of the current NGFW engine operational status, populated when the status is not green.";
    }
    leaf mem-usage {
      type decimal64 {
        fraction-digits 4;
      }
      units "percent";
      description
        "Percentage of memory used";
    }
    leaf mem-status {
      type ngfw-ios-xe-oper:ngfw-op-status-val;
      description
        "Status of memory usage";
    }
    list ngfw-engine-inst-status {
      key "id";
      description
        "Status of engine instances";
      uses ngfw-ios-xe-oper:ngfw-engine-inst-status;
    }
  }

  grouping ngfw-custom-sig-info {
    description
      "Defines custom-signature status information, including the file name, presence, last update time, and MD5 hash.";
    leaf file-name {
      type string;
      description
        "Specifies the custom-signature file name in IOS file-system format.";
    }
    leaf present {
      type boolean;
      description
        "Indicates whether the custom-signature file is present";
    }
    leaf last-upd-time {
      type yang:date-and-time;
      description
        "Specifies the time, in GMT, when the custom-signature file was last updated.";
    }
    leaf md5-hash {
      type yang:hex-string;
      description
        "Specifies the MD5 hash of the current custom-signature file as a hex string.";
    }
  }

  grouping ngfw-custom-sig-profile {
    description
      "Defines custom-signature status information for a single NGFW profile.";
    leaf name {
      type string;
      description
        "Specifies the Next-Generation Firewall (NGFW) custom-signature profile name.";
    }
    container info {
      description
        "Contains custom-signature status information for the profile.";
      uses ngfw-ios-xe-oper:ngfw-custom-sig-info;
    }
  }

  grouping ngfw-custom-sig-status {
    description
      "Defines global and per-profile custom-signature status information for NGFW.";
    container global {
      description
        "Contains the global custom-signature status.";
      uses ngfw-ios-xe-oper:ngfw-custom-sig-info;
    }
    list ngfw-custom-sig-profile {
      key "name";
      description
        "Lists custom-signature profile statuses; each entry contains the status for one custom-signature profile.";
      uses ngfw-ios-xe-oper:ngfw-custom-sig-profile;
    }
  }

  container ngfw-oper-data {
    config false;
    description
      "Next-Generation Firewall (NGFW) operational data";
    container ngfw-ver-status {
      presence "ngfw-ver-status";
      description
        "Next-Generation Firewall (NGFW) version status";
      uses ngfw-ios-xe-oper:ngfw-ver-status;
    }
    container ngfw-lsp-upd-status {
      presence "ngfw-lsp-upd-status";
      description
        "Next-Generation Firewall (NGFW) Lightweight Security Package (LSP) update status";
      uses ngfw-ios-xe-oper:ngfw-lsp-upd-status;
    }
    container ngfw-vdb-upd-status {
      presence "ngfw-vdb-upd-status";
      description
        "Next-Generation Firewall (NGFW) Vulnerability Database (VDB) update status";
      uses ngfw-ios-xe-oper:ngfw-vdb-upd-status;
    }
    container ngfw-engine-status {
      presence "ngfw-engine-status";
      description
        "Next-Generation Firewall (NGFW) engine status";
      uses ngfw-ios-xe-oper:ngfw-engine-status;
    }
    container ngfw-custom-sig-status {
      presence "ngfw-custom-sig-status";
      description
        "Contains the Next-Generation Firewall (NGFW) custom-signature status.";
      uses ngfw-ios-xe-oper:ngfw-custom-sig-status;
    }
  }
}
