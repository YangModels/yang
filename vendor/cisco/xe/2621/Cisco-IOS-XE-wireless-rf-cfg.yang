module Cisco-IOS-XE-wireless-rf-cfg {
  yang-version 1.1;
  namespace "http://cisco.com/ns/yang/Cisco-IOS-XE-wireless-rf-cfg";
  prefix wireless-rf-cfg;

  import Cisco-IOS-XE-wireless-enum-types {
    prefix wireless-enum-types;
  }
  import Cisco-IOS-XE-wireless-types {
    prefix wireless-types;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Model for managing RF(Radio-Frequency) profile configurations
     Copyright (c) 2016-2022, 2024-2026 by Cisco Systems, Inc.
     All rights reserved.";

  revision 2026-08-01 {
    description
      "- Obsoleted ATF feature and related leafs
       - Added support for DBS minimum and maximum channel widths for RF profile
       - Deprecated rf-dca-chan-width leaf and disallowed its modification
       - Enhanced descriptions for RF profile leaves including DCA channels, RSSI thresholds, band-select, trap thresholds, HSR, MCS, and Multi-BSSID profile parameters for improved clarity and consistency
       - Modified the default values of channel-width-min and channel-width-max
       - Updated channel-width-max validation to allow band-default minimum channel width with 80 MHz maximum channel width";
    reference
      "13.0.0";
    cisco-semver:module-version "13.0.0";
  }
  revision 2026-02-01 {
    description
      "- Adding constraints for basic data rate configuration
       - Deprecated ATF Policy parameters
       - Added WiFi-IOT Coexistence configuration";
    reference
      "12.0.0";
    cisco-semver:module-version "12.0.0";
  }
  revision 2025-07-01 {
    description
      "- Added AP beam state configuration
       - Added Ultra Reliable Wireless Backhaul(URWB) configuration associated with rf tag
       - Deprecated 802.11be parameters uplink downlink OFDMA and MU-MIMO";
    reference
      "11.1.0";
    cisco-semver:module-version "11.1.0";
  }
  revision 2025-03-01 {
    description
      "- Added UNII-3 low power channels support for E domain
       - Relaxed the must constraint to allow default values of channel width config under RF profile for 2.4Ghz
       - Added validation to ensure at least one rate is set as mandatory for the RF profile
       - Added Validation to ensure at least one 802.11n MCS rate is enabled to enable RF profile for 2.4GHz and 5Ghz
       - Added validation check for channel width minimum to be less than or equal to channel width maximum
       - Added validation check for client mid RSSI(dBm) to be greater than or equal to client RSSI(dBm)";
    reference
      "11.0.0";
    cisco-semver:module-version "11.0.0";
  }
  revision 2024-11-01 {
    description
      "- Modified ATF policy name length range to 0..31";
    reference
      "10.0.0";
    cisco-semver:module-version "10.0.0";
  }
  revision 2024-07-01 {
    description
      "- Added support for packet retries
       - Added preamble puncturing and 802.11be configurations";
    reference
      "9.6.0";
    cisco-semver:module-version "9.6.0";
  }
  revision 2023-11-01 {
    description
      "- Added support for 6GHz power mode enablement
       - Add block ACK window size of aggregate MAC protocol data unit";
    reference
      "9.5.0";
    cisco-semver:module-version "9.5.0";
  }
  revision 2023-03-01 {
    description
      "- Added FRA action";
    reference
      "9.4.0";
    cisco-semver:module-version "9.4.0";
  }
  revision 2022-11-01 {
    description
      "Update yang-version to 1.1";
    reference
      "9.3.0";
    cisco-semver:module-version "9.3.0";
  }
  revision 2022-07-01 {
    description
      "- Added Zero wait DFS configuration for RF profile
       - Updated the range for maximum number of clients per radio
       - Added guard interval configuration for RF profile
       - Added 6GHz specific client aware FRA thresholds";
    reference
      "9.2.0";
    cisco-semver:module-version "9.2.0";
  }
  revision 2022-03-01 {
    description
      "- Modified all 6GHz must constraints";
    reference
      "9.1.0";
    cisco-semver:module-version "9.1.0";
  }
  revision 2021-11-01 {
    description
      "- Added Spatial Reuse Group (SRG) Overlapping Basic Service Set Packet Detect (OBSS-PD) configurations
       - Updated the range for maximum number of clients per radio
       - Deprecated FILS and Unsolicited Broadcast Probe Response and added as a part of 802.11ax 6GHz specific feature
       - Updated the range for Unsolicited Broadcast Probe Response Interval
       - Added must constraint to prevent High Speed Roam (HSR) mode and client aware FRA configuration for 6 GHz RF profile
       - Modified the default value for Target Wake-up Time and Target Wake-up Time broadcast";
    reference
      "9.0.0";
    cisco-semver:module-version "9.0.0";
  }
  revision 2021-07-01 {
    description
      "- Added Multi BSSID profile and 802.11ax parameters for RF profile
       - Added radio profile configuration
       - Added preferred scanning channel bias for 6 GHz DCA
       - Added must constraint to prevent 802.11n MCS data rate configuration for 6 GHz RF profile";
    reference
      "8.1.0";
    cisco-semver:module-version "8.1.0";
  }
  revision 2021-03-01 {
    description
      "- Add ASCII 32-126 and leading/trailing spaces restriction for RF tag and profile name and ATF-policy name
       - Added Neighbor Discovery mode for AP
       - Added a default value for Rx-SOP custom threshold";
    reference
      "8.0.0";
    cisco-semver:module-version "8.0.0";
  }
  revision 2020-11-01 {
    description
      "- Added 802.11ax OBSS PD configurations
       - Added must constraints for tx-power-min, tx-power-max, client-select-threshold, client-reset-threshold";
    reference
      "7.0.0";
    cisco-semver:module-version "7.0.0";
  }
  revision 2020-07-01 {
    description
      "- Adding must constraints for data rate to mandate one rate as basic";
    reference
      "6.1.0";
    cisco-semver:module-version "6.1.0";
  }
  revision 2019-06-26 {
    description
      "- Creation of RF Profile will not need 32 mcs entries are created.
       - Added semantic version
       - Update the default values as per WLC configuration best practice.
       - Changed default value of client-network-preference to 'default'.";
    reference
      "6.0.0";
    cisco-semver:module-version "6.0.0";
  }
  revision 2019-02-19 {
    description
      "- Renaming radio type to band and removing the band variable in st_rfprofile_default
       - Cleaned up spelling errors in descriptions
       - fixed the name for load_balancing and trap_threshhold attributes
       - Removed leaf node radioType from L2 roam RF Parameters
       - Removed leaf node dot11n from RF Profile
       - Add client-aware-fra, client-select-threshold, client-reset-threshold
       - Removal of layer 2 roaming RF parameter leaves.";
    reference
      "5.0.0";
    cisco-semver:module-version "5.0.0";
  }
  revision 2018-05-03 {
    description
      "Receiver Start of Packet (RX-SOP) configuration to support custom values (-60 to -85 dbm)";
    reference
      "4.0.0";
    cisco-semver:module-version "4.0.0";
  }
  revision 2018-02-11 {
    description
      "Process Air Time Fairness(ATF) mesh stats from Access-Point(AP)";
    reference
      "3.0.0";
    cisco-semver:module-version "3.0.0";
  }
  revision 2018-01-24 {
    description
      "The first generally available version";
    reference
      "2.0.0";
    cisco-semver:module-version "2.0.0";
  }
  revision 2017-05-05 {
    description
      "Initial revision";
    reference
      "1.0.0";
    cisco-semver:module-version "1.0.0";
  }

  grouping rf-80211-nmcs {
    description
      "This container has all the configuration related to Modulation and Coding Scheme (MCS) data rates";
    leaf rf-index {
      type uint8 {
        range "0 .. 31";
      }
      must "../../../band != 'dot11-6-ghz-band'" {
        error-message "802.11n MCS data rate configuration is not applicable for 6 GHz band";
        error-app-tag "must-violation";
      }
      description
        "Identifies the Modulation and Coding Scheme (MCS) data rate for a particular RF(Radio-Frequency) profile.";
    }
    leaf rf-80211n-mcs-enable {
      type boolean;
      must "../../../band != 'dot11-6-ghz-band'" {
        error-message "802.11n MCS data rate configuration is not applicable for 6 GHz band";
        error-app-tag "must-violation";
      }
      default "true";
      description
        "Enable or disable the data rate. When this object is set to 'true' the Modulation and Coding Scheme (MCS) support is enabled.
         When this object is set to 'false' the MCS support is disabled";
    }
  }

  grouping rf-dca-allowed-chans {
    description
      "Specifies an allowed channel for Dynamic Channel Assignment (DCA) within a specific RF profile.";
    leaf channel {
      type uint32;
      description
        "Specifies the channel number to be included in the allowed Dynamic Channel Assignment (DCA) channel list for the Radio-Frequency (RF) profile.";
    }
  }

  grouping st-rf-dca-removed-chans {
    description
      "Configure the list of removed channels for the parent Radio-Frequency(rf)-profile";
    leaf channel {
      type uint32;
      description
        "Specifies the channel number to be included in the removed Dynamic Channel Assignment (DCA) channel list for the Radio-Frequency (RF) profile.";
    }
  }

  grouping rfprofile {
    description
      "This object indicates all the configurations related to Radio-Frequency(rf)-profile";
    leaf name {
      type string {
        length "1..32";
        pattern '[!-~]([ -~]*[!-~])?';
      }
      description
        "Configure the name of the Radio-Frequency(rf)-profile";
    }
    leaf description {
      type string {
        length "0..64";
      }
      description
        "Configure the brief description of each Radio-Frequency(rf)-profile";
    }
    leaf tx-power-min {
      type int8 {
        range "-10 .. 30";
      }
      units "dBm";
      must '../tx-power-min <= ../tx-power-max' {
        error-message "tx-power-min must be less than or equal to tx-power-max";
        error-app-tag "must-violation";
      }
      default "-10";
      description
        "Lower limit of transmit power in dBm. For an 802.11 network,
         the system will only accept this configuration if the Transmit Power Control(TPC) is in Auto or Run Once mode";
    }
    leaf tx-power-max {
      type int8 {
        range "-10 .. 30";
      }
      units "dBm";
      must '../tx-power-min <= ../tx-power-max' {
        error-message "tx-power-max must be greater than or equal to tx-power-min";
        error-app-tag "must-violation";
      }
      default "30";
      description
        "Upper limit of transmit power in dBm. For an 802.11 network,
         the system will only accept this configuration if the Transmit Power Control(TPC) is in Auto or Run Once mode";
    }
    leaf tx-power-v1-threshold {
      type int16 {
        range "-80 .. -50";
      }
      units "dBm";
      default "-70";
      description
        "Configure the transmit power control version 1 threshold for the radio resource management algorithm in dBm.";
    }
    leaf tx-power-v2-threshold {
      type int16 {
        range "-80 .. -50";
      }
      units "dBm";
      default "-67";
      description
        "Configure the transmit power control version 2 threshold for the radio resource management algorithm in dBm.";
    }
    leaf status {
      type boolean;
      must "((current() = 'false')
            or ((../band = 'dot11-2-dot-4-ghz-band' and (../data-rate-1m = 'apf-tx-rate-basic' or ../data-rate-2m = 'apf-tx-rate-basic' or ../data-rate-5-5m = 'apf-tx-rate-basic' or ../data-rate-11m = 'apf-tx-rate-basic' or ../data-rate-6m = 'apf-tx-rate-basic' or ../data-rate-9m = 'apf-tx-rate-basic' or ../data-rate-12m = 'apf-tx-rate-basic' or ../data-rate-18m = 'apf-tx-rate-basic' or ../data-rate-24m = 'apf-tx-rate-basic' or ../data-rate-36m = 'apf-tx-rate-basic' or ../data-rate-48m = 'apf-tx-rate-basic' or ../data-rate-54m = 'apf-tx-rate-basic'))
            or ((../band = 'dot11-5-ghz-band' or ../band = 'dot11-6-ghz-band') and (../data-rate-6m = 'apf-tx-rate-basic' or ../data-rate-9m = 'apf-tx-rate-basic' or ../data-rate-12m = 'apf-tx-rate-basic' or ../data-rate-18m = 'apf-tx-rate-basic' or ../data-rate-24m = 'apf-tx-rate-basic' or ../data-rate-36m = 'apf-tx-rate-basic' or ../data-rate-48m = 'apf-tx-rate-basic' or ../data-rate-54m = 'apf-tx-rate-basic'))))" {
        error-message "At least one data rate should be configured as basic for the active RF profile.";
        error-app-tag "must-violation";
      }
      must "((current() = 'false') or (../band = 'dot11-6-ghz-band') or (
            ((../rf-mcs-entries/rf-mcs-entry/rf-index >=  0) and (../rf-mcs-entries/rf-mcs-entry/rf-index <32))))" {
        error-message "At least one 802.11n MCS rate must be enabled to enable RF profile status";
        error-app-tag "must-violation";
      }
      must "((current() = 'false')
            or (../band = 'dot11-2-dot-4-ghz-band' and ../data-rate-1m != 'apf-tx-rate-not-applicable' and ../data-rate-2m != 'apf-tx-rate-not-applicable' and ../data-rate-5-5m != 'apf-tx-rate-not-applicable' and ../data-rate-11m != 'apf-tx-rate-not-applicable' and ../data-rate-6m != 'apf-tx-rate-not-applicable' and ../data-rate-9m != 'apf-tx-rate-not-applicable' and ../data-rate-12m != 'apf-tx-rate-not-applicable' and ../data-rate-18m != 'apf-tx-rate-not-applicable' and ../data-rate-24m != 'apf-tx-rate-not-applicable' and ../data-rate-36m != 'apf-tx-rate-not-applicable' and ../data-rate-48m != 'apf-tx-rate-not-applicable' and ../data-rate-54m != 'apf-tx-rate-not-applicable')
            or (../band != 'dot11-2-dot-4-ghz-band' and ../data-rate-6m != 'apf-tx-rate-not-applicable' and ../data-rate-9m != 'apf-tx-rate-not-applicable' and ../data-rate-12m != 'apf-tx-rate-not-applicable' and ../data-rate-18m != 'apf-tx-rate-not-applicable' and ../data-rate-24m != 'apf-tx-rate-not-applicable' and ../data-rate-36m != 'apf-tx-rate-not-applicable' and ../data-rate-48m != 'apf-tx-rate-not-applicable' and ../data-rate-54m != 'apf-tx-rate-not-applicable'))" {
        error-message "One of the basic data rate is set to apf-tx-rate-not-applicable for the RF profile";
        error-app-tag "must-violation";
      }
      default "false";
      description
        "Specifies the operational state of the Radio-Frequency (RF) profile. A value of 'true' indicates the RF profile is active; 'false' indicates it is inactive.";
    }
    leaf band {
      type wireless-types:enm-ewlc-dot11-radio-band;
      description
        "Configure the radio type for this profile.";
    }
    leaf data-rate-1m {
      type wireless-enum-types:rate-state;
      must "(../status = 'false' or (../band != 'dot11-2-dot-4-ghz-band') or (current() != 'apf-tx-rate-not-applicable'))" {
        error-message "apf-tx-rate-not-applicable is not valid configuration for active RF profile";
        error-app-tag "must-violation";
      }
      default "apf-tx-rate-basic";
      description
        "Configuration for 1 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-2m {
      type wireless-enum-types:rate-state;
      must "(../status = 'false' or (../band != 'dot11-2-dot-4-ghz-band') or (current() != 'apf-tx-rate-not-applicable'))" {
        error-message "apf-tx-rate-not-applicable is not valid configuration for active RF profile";
        error-app-tag "must-violation";
      }
      default "apf-tx-rate-basic";
      description
        "Configuration for 2 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-5-5m {
      type wireless-enum-types:rate-state;
      must "(../status = 'false' or (../band != 'dot11-2-dot-4-ghz-band') or (current() != 'apf-tx-rate-not-applicable'))" {
        error-message "apf-tx-rate-not-applicable is not valid configuration for active RF profile";
        error-app-tag "must-violation";
      }
      default "apf-tx-rate-basic";
      description
        "Configuration for 5.5 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-11m {
      type wireless-enum-types:rate-state;
      must "(../status = 'false' or (../band != 'dot11-2-dot-4-ghz-band') or (current() != 'apf-tx-rate-not-applicable'))" {
        error-message "apf-tx-rate-not-applicable is not valid configuration for active RF profile";
        error-app-tag "must-violation";
      }
      default "apf-tx-rate-basic";
      description
        "Configuration for 11 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-6m {
      type wireless-enum-types:rate-state;
      must "(../status = 'false' or (current() != 'apf-tx-rate-not-applicable'))" {
        error-message "apf-tx-rate-not-applicable is not valid configuration for active RF profile";
        error-app-tag "must-violation";
      }
      default "apf-tx-rate-not-applicable";
      description
        "Configuration for 6 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-9m {
      type wireless-enum-types:rate-state;
      must "(../status = 'false' or (current() != 'apf-tx-rate-not-applicable'))" {
        error-message "apf-tx-rate-not-applicable is not valid configuration for active RF profile";
        error-app-tag "must-violation";
      }
      default "apf-tx-rate-supported";
      description
        "Configuration for 9 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-12m {
      type wireless-enum-types:rate-state;
      must "(../status = 'false' or (current() != 'apf-tx-rate-not-applicable'))" {
        error-message "apf-tx-rate-not-applicable is not valid configuration for active RF profile";
        error-app-tag "must-violation";
      }
      default "apf-tx-rate-not-applicable";
      description
        "Configuration for 12 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-18m {
      type wireless-enum-types:rate-state;
      must "(../status = 'false' or (current() != 'apf-tx-rate-not-applicable'))" {
        error-message "apf-tx-rate-not-applicable is not valid configuration for active RF profile";
        error-app-tag "must-violation";
      }
      default "apf-tx-rate-supported";
      description
        "Configuration for 18 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-24m {
      type wireless-enum-types:rate-state;
      must "(../status = 'false' or (current() != 'apf-tx-rate-not-applicable'))" {
        error-message "apf-tx-rate-not-applicable is not valid configuration for active RF profile";
        error-app-tag "must-violation";
      }
      default "apf-tx-rate-not-applicable";
      description
        "Configuration for 24 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-36m {
      type wireless-enum-types:rate-state;
      must "(../status = 'false' or (current() != 'apf-tx-rate-not-applicable'))" {
        error-message "apf-tx-rate-not-applicable is not valid configuration for active RF profile";
        error-app-tag "must-violation";
      }
      default "apf-tx-rate-supported";
      description
        "Configuration for 36 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-48m {
      type wireless-enum-types:rate-state;
      must "(../status = 'false' or (current() != 'apf-tx-rate-not-applicable'))" {
        error-message "apf-tx-rate-not-applicable is not valid configuration for active RF profile";
        error-app-tag "must-violation";
      }
      default "apf-tx-rate-supported";
      description
        "Configuration for 48 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-54m {
      type wireless-enum-types:rate-state;
      must "(../status = 'false' or (current() != 'apf-tx-rate-not-applicable'))" {
        error-message "apf-tx-rate-not-applicable is not valid configuration for active RF profile";
        error-app-tag "must-violation";
      }
      default "apf-tx-rate-supported";
      description
        "Configuration for 54 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf coverage-data-packet-rssi-threshold {
      type int16 {
        range "-90 .. -60";
      }
      units "dBm";
      default "-80";
      description
        "Configure Received Signal Strength Indicator(RSSI) threshold value for data packets in dBm.";
    }
    leaf min-num-clients {
      type int32 {
        range "1 .. 200";
      }
      default "3";
      description
        "Specifies the minimum number of clients required before triggering an exception or alert for low client count on the radio frequency profile.";
    }
    leaf coverage-voice-packet-rssi-threshold {
      type int16 {
        range "-90 .. -60";
      }
      units "dBm";
      default "-80";
      description
        "Configure Received Signal Strength Indicator(RSSI) threshold value for voice packets in dBm.";
    }
    leaf exception-level {
      type uint16 {
        range "0 .. 100";
      }
      units "percentage";
      default "25";
      description
        "Specifies the coverage exception threshold, as a percentage, at which a coverage exception event is triggered for the RF profile.";
    }
    leaf band-select-client-rssi {
      type int16 {
        range "-90 .. -20";
      }
      units "dBm";
      default "-80";
      description
        "Configure minimum mobile station Received Signal Strength Indicator(RSSI) threshold in dBm.
         Mobile stations having RSSI below this value will not be recorded in the suppressed table.
         This configuration filters out far away mobile stations with weaker signal strength. This will limit the number of mobile stations on the table to a reasonable amount.";
    }
    leaf band-select-client-mid-rssi {
      type int16 {
        range "-90 .. -20";
      }
      units "dBm";
      must 'current() >= ../band-select-client-rssi' {
        error-message "Client mid RSSI (dBm) must be greater than or equal to client RSSI (dBm)";
        error-app-tag "must-violation";
      }
      default "-80";
      description
        "Specifies the medium RSSI threshold for mobile stations in dBm. Mobile stations with RSSI between this value and the band-select-client-rssi value will be recorded in the suppression table but not denied. Stations with RSSI stronger than this value will be recorded and denied.";
    }
    leaf band-select-cycle-count {
      type uint16 {
        range "1 .. 10";
      }
      default "2";
      description
        "Specifies the maximum number of consecutive cycles in which a mobile station does not respond before it is considered inactive for band selection purposes.";
    }
    leaf band-select-cycle-threshold {
      type uint16 {
        range "1 .. 1000";
      }
      units "milliseconds";
      default "200";
      description
        "Specifies the cycle threshold, in milliseconds, used by the band select feature to determine how often band selection decisions are made for client devices.";
    }
    leaf band-select-age-out-dual-band {
      type uint16 {
        range "10 .. 300";
      }
      units "seconds";
      default "60";
      description
        "Specifies the age-out timer, in seconds, for dual-band clients in the band select process. After this period, the client is considered inactive for band selection.";
    }
    leaf band-select-age-out-suppression {
      type uint16 {
        range "10 .. 200";
      }
      units "seconds";
      default "20";
      description
        "Specifies the suppression age-out timer, in seconds, for clients suppressed by the band select feature. After this period, suppression is lifted and the client can be considered for band selection again.";
    }
    leaf band-select-probe-response {
      type boolean;
      default "false";
      description
        "Configure Access-Point(AP)'s probe response with clients to verify whether client can associate on both 2.4 GHz and 5 Ghz spectrum.
         When set to true, AP suppresses probe response to new clients for all Service Set Identifier(SSID)'s that are not being Band Select disabled.";
    }
    leaf dca-contribution-interference {
      type boolean;
      default "true";
      description
        "Enables or disables the use of interference measurements as a factor in Dynamic Channel Assignment (DCA) decisions for RF profiles.";
    }
    leaf rf-dca-chan-width {
      type wireless-enum-types:rf-dca-chan-width;
      default "rf-dca-chan-width-best";
      status deprecated;
      description
        "Deprecated in favor of channel-width-min and channel-width-max. This leaf controlled the Dynamic Channel Assignment (DCA) channel width mode for the RF profile and will not be honoured now";
    }
    leaf load-balancing-window {
      type uint32 {
        range "0 .. 20";
      }
      default "5";
      description
        "Specifies the client count window used for load balancing decisions between Access Points (APs). Determines the acceptable difference in the number of associated clients before load balancing is triggered.";
    }
    leaf load-balancing-denial-count {
      type uint32 {
        range "1 .. 10";
      }
      default "3";
      description
        "Specifies the number of times a client association request can be denied by an Access Point (AP) as part of load balancing before the client is allowed to associate.";
    }
    leaf trap-threshold-clients {
      type uint32 {
        range "1 .. 200";
      }
      default "12";
      description
        "Configure threshold number of clients per Access-Point(AP) radio to trigger a trap.
         The trap ciscoLwappApClientThresholdNotify will be triggered once the count of clients on the AP radio reaches this limit.
         A value of zero indicates that the trap is disabled.";
    }
    leaf trap-threshold-interference {
      type uint16 {
        range "0 .. 100";
      }
      units "percentage";
      default "10";
      description
        "Specifies the interference threshold, as a percentage, at which an SNMP trap is generated when interference on the AP radio exceeds this value.";
    }
    leaf trap-threshold-noise {
      type int32 {
        range "-127 .. 0";
      }
      units "dBm";
      default "-70";
      description
        "Specifies the noise level threshold, in dBm, at which an SNMP trap is generated; valid values range from -127 to 0 dBm.";
    }
    leaf trap-threshold-utilization {
      type uint16 {
        range "0 .. 100";
      }
      units "percentage";
      default "80";
      description
        "Configure threshold of bandwidth (%) being utilized by an access-point. Traps are sent when this value is exceeded";
    }
    leaf max-radio-clients {
      type uint16 {
        range "0 .. 500";
      }
      default "200";
      description
        "Configure maximum number of radio clients per Access-Point(AP) in high density environment.";
    }
    leaf multicast-data-rate {
      type wireless-enum-types:enm-multicast-data-rate;
      default "mcast-data-rate-default";
      description
        "Configure minimum data rate at which multicast clients can associate to Access-Point(AP). A value 0 indicates that AP will automatically adjust data rates.";
    }
    leaf rx-sen-sop-threshold {
      type wireless-types:rx-sen-sop-threshold-level;
      units "dBm";
      default "rrm-ewlc-rxsensop-threshold-auto";
      description
        "Configure the Receiver Start of Packet(RX-SOP) sensitivity threshold";
    }
    leaf rx-sen-sop-custom {
      type int16 {
        range "-85 .. -60";
      }
      units "dBm";
      default "-85";
      description
        "Rx SOP custom values configured between -85 dBm (default) and -60 dBm. This configured value takes effect only when rx sop threshold is set to custom";
    }
    leaf client-network-preference {
      type wireless-types:enm-client-network-preference;
      default "default";
      description
        "Configure the client network preference. Possible values are:
         1. connectivity - Radio-Resource-Management(RRM) Algorithm has a preference on connectivity of the clients.
         2. throughput   - Radio-Resource-Management(RRM) Algorithm has a preference on high throughput of the clients.
         3. default      - Radio-Resource-Management(RRM) Algorithm has no preference on the clients.";
    }
    leaf hsr-mode {
      type boolean;
      must "((current() = 'false') or (../band != 'dot11-6-ghz-band'))" {
        error-message "High-speed roam(HSR) configuration is not applicable for 6 GHz band";
        error-app-tag "must-violation";
      }
      default "false";
      description
        "Enables or disables High-Speed Roam (HSR) for the Radio-Frequency (RF) profile.";
    }
    leaf hsr-neighbor-timeout {
      type uint16 {
        range "5 .. 60";
      }
      units "seconds";
      must "((current() = 5) or (../band != 'dot11-6-ghz-band'))" {
        error-message "hsr-neighbor-timeout configuration is not applicable for 6 GHz band";
        error-app-tag "must-violation";
      }
      default "5";
      description
        "Configure timeout interval of neighbors that will be configured for Radio-Frequency(RF) profile. Neighbor timeout factor will be five times the neighbor interval";
    }
    leaf opt-roam-rssi-treshold {
      type int16 {
        range "-127 .. 0";
      }
      units "dBm";
      default "-127";
      description
        "Configure the minimum Received Signal Strength Indicator(RSSI) threshold for optimized roaming to occur. Possible values are in the range -127 dbm to 0 dbm";
    }
    leaf opt-roam-rssi-check-enable {
      type boolean;
      default "false";
      description
        "Indicates if Received Signal Strength Indicator(RSSI) threshold is enabled before optimized roaming is enabled";
    }
    leaf atf-oper-mode {
      type wireless-enum-types:apf-ate-mode;
      default "apf-atf-mode-disable";
      status obsolete;
      description
        "ATF Mode SSID or monitor is enabled for the rf-profile; this leaf is obsolete";
    }
    leaf atf-optimization {
      type wireless-enum-types:apf-ate-stealing-policy;
      default "apf-atf-stealing-policy-disable";
      status obsolete;
      description
        "True if ATF optimization is enabled for the rf-profile; this leaf is obsolete";
    }
    leaf bridge-client-access {
      type boolean;
      default "false";
      status obsolete;
      description
        "True if Airtime Allocation feature is enabled for the rf-profile; this leaf is obsolete";
    }
    leaf airtime-allocation {
      type uint8 {
        range "5 .. 90";
      }
      units "percentage";
      default "5";
      status obsolete;
      description
        "Specifies the percentage of airtime allocated to clients or services in the Radio-Frequency (RF) profile.";
    }
    leaf client-aware-fra {
      type boolean;
      must "((current() = 'false') or (../band != 'dot11-6-ghz-band'))" {
        error-message "client aware FRA configuration is not applicable for 6 GHz band";
        error-app-tag "must-violation";
      }
      default "false";
      description
        "Client aware FRA allows the Dual band to operate on 5 Ghz or monitor mode depending on the load on the dedicated 5 Ghz radio";
    }
    leaf client-select-threshold {
      type uint8 {
        range "0 .. 100";
      }
      units "percent";
      must "((current() = 50) or (../band != 'dot11-6-ghz-band'))" {
        error-message "client-select-threshold configuration is not applicable for 6 GHz band";
        error-app-tag "must-violation";
      }
      must '../client-reset-threshold < ../client-select-threshold' {
        error-message "client-select-threshold must be greater than client-reset-threshold";
        error-app-tag "must-violation";
      }
      default "50";
      description
        "Specifies the utilization threshold, in percent, for Client Aware FRA at which the dual-band radio switches from monitor mode to client serving mode.";
    }
    leaf client-reset-threshold {
      type uint8 {
        range "0 .. 100";
      }
      must "((current() = 5) or (../band != 'dot11-6-ghz-band'))" {
        error-message "client-reset-threshold configuration is not applicable for 6 GHz band";
        error-app-tag "must-violation";
      }
      must '../client-reset-threshold < ../client-select-threshold' {
        error-message "client-reset-threshold must be less than client-select-threshold";
        error-app-tag "must-violation";
      }
      default "5";
      description
        "Client aware FRA utilization threshold value for moving Dual band radio from Client Serving mode to Monitor mode";
    }
    container rf-mcs-entries {
      description
        "Container for Modulation and Coding Scheme (MCS) configuration entries associated with a specific RF profile.";
      list rf-mcs-entry {
        key "rf-index";
        description
          "List of Modulation and Coding Scheme (MCS) configuration entries for a specific RF profile.";
        uses wireless-rf-cfg:rf-80211-nmcs;
      }
    }
    container rf-dca-allowed-channels {
      description
        "Container for specifying the list of allowed Dynamic Channel Assignment (DCA) channels for a specific RF profile.";
      list rf-dca-allowed-channel {
        key "channel";
        description
          "List of allowed Dynamic Channel Assignment (DCA) channels for a specific RF profile; each entry identifies a single channel number permitted for DCA use.";
        uses wireless-rf-cfg:rf-dca-allowed-chans;
      }
    }
    container rfdca-removed-channels {
      description
        "Configurations related to removed Dynamic Channel Assignment (DCA) channels in a named Radio-Frequency(rf)-profile";
      list rfdca-removed-channel {
        key "channel";
        description
          "A list of configurations related to removed Dynamic Channel Assignment (DCA) channels in a named Radio-Frequency(rf)-profile";
        uses wireless-rf-cfg:st-rf-dca-removed-chans;
      }
    }
    leaf he-obss-pd-enable {
      type boolean;
      default "false";
      description
        "Enable/Disable 802.11ax OBSS PD spatial reuse";
    }
    leaf he-non-srg-obss-pd-max {
      type int8 {
        range "-82 .. -62";
      }
      units "dBm";
      default "-62";
      description
        "Non-SRG OBSS PD maximum threshold in dBm";
    }
    leaf ndp-mode {
      type wireless-enum-types:enm-ndp-mode;
      default "ndp-mode-auto";
      description
        "Neighbor discovery protocol operating mode  configuration.
         Possible values are:
         auto        - AP does neighbor discovery either on serving channel or
                       off channel based on its NDP capability
         off-channel - AP does neighbor discovery on off channel";
    }
    leaf he-bcast-probe-resp {
      type boolean;
      default "false";
      status deprecated;
      description
        "Enables or disables the sending of broadcast probe responses in 802.11ax (Wi-Fi 6) extended mode.";
    }
    leaf he-bcast-probe-resp-intvl {
      type uint16 {
        range "5 .. 25";
      }
      units "seconds";
      default "20";
      description
        "Specifies the interval, in seconds, between broadcast probe responses sent in 802.11ax (Wi-Fi 6) extended mode.";
    }
    leaf he-fils-disc {
      type boolean;
      default "false";
      status deprecated;
      description
        "Enables or disables Fast Initial Link Setup (FILS) discovery in 802.11ax (Wi-Fi 6) extended mode.";
    }
    leaf mbssid-prof-name {
      type string;
      default "default-multi-bssid-profile";
      description
        "Specifies the name of the Multi BSSID profile to be used for 802.11ax (Wi-Fi 6) extended mode configurations in this RF profile.";
    }
    leaf psc-bias {
      type boolean;
      default "false";
      description
        "Enable or disable preferred scanning channel bias for 6 GHz DCA";
    }
    leaf he-srg-obss-pd-enable {
      type boolean;
      default "false";
      description
        "Enable/Disable 802.11ax SRG OBSS PD spatial reuse";
    }
    leaf he-srg-obss-pd-min {
      type int8 {
        range "-82 .. -62";
      }
      units "dBm";
      must '../he-srg-obss-pd-min <= ../he-srg-obss-pd-max' {
        error-message "SRG OBSS PD minimum must be less than or equal to SRG OBSS PD maximum";
        error-app-tag "must-violation";
      }
      default "-82";
      description
        "SRG OBSS PD minimum threshold in dBm";
    }
    leaf he-srg-obss-pd-max {
      type int8 {
        range "-82 .. -62";
      }
      units "dBm";
      must '../he-srg-obss-pd-min <= ../he-srg-obss-pd-max' {
        error-message "SRG OBSS PD maximum must be greater than or equal to SRG OBSS PD minimum";
        error-app-tag "must-violation";
      }
      default "-62";
      description
        "SRG OBSS PD maximum threshold in dBm";
    }
    leaf dot11ax-6ghz-feature {
      type wireless-enum-types:dot11ax-6ghz-feature;
      default "he-6ghz-none";
      description
        "Specifies the 802.11ax-specific feature to be enabled or configured for the 6 GHz band in the RF profile.";
    }
    leaf zerowt-dfs {
      type boolean;
      must "(../band = 'dot11-5-ghz-band' or
             ../zerowt-dfs = 'false')" {
        error-message "Zero wait DFS feature is applicable only for 5 GHz band";
        error-app-tag "must-violation";
      }
      default "false";
      description
        "Enable/Disable 802.11a Zero wait DFS feature";
    }
    leaf guard-interval-ext {
      type wireless-enum-types:enm-guard-interval-ext;
      default "guard-interval-none";
      description
        "Specifies the guard interval extension setting for the RF profile, which determines the time interval between transmitted symbols to reduce inter-symbol interference in wireless communications.";
    }
    leaf client-reset-thresh-6ghz {
      type uint8 {
        range "0 .. 100";
      }
      units "percentage";
      default "5";
      description
        "Client aware FRA utilization threshold value for moving dual band radio from 6GHz to 5GHz";
    }
    leaf client-count-reset-6ghz {
      type uint8 {
        range "1 .. 10";
      }
      default "1";
      description
        "Client aware FRA client count value for moving dual band radio from 6GHz to 5GHz";
    }
    leaf channel-width-min {
      type wireless-types:dca-ewlc-chan-width-cap;
      must "((../band != 'dot11-2-dot-4-ghz-band') or
            (current() = 'dca-ewlc-chan-width-cap-band-default'))" {
        error-message "DBS channel width min/max are not supported for 2.4GHz band";
        error-app-tag "must-violation";
      }
      must "((../band != 'dot11-5-ghz-band') or
            ((current() != 'dca-ewlc-chan-width-cap-320-mhz') and
             (current() != 'dca-ewlc-chan-width-cap-max')))" {
        error-message "5GHz band does not support width-max and 320 megahertz width selection";
        error-app-tag "must-violation";
      }
      must "((../band = 'dot11-2-dot-4-ghz-band') or
            (../band = 'dot11-5-ghz-band' and (current() = 'dca-ewlc-chan-width-cap-320-mhz' or current() = 'dca-ewlc-chan-width-cap-max')) or
            ((current() != 'dca-ewlc-chan-width-cap-band-default') or
              (../band = 'dot11-5-ghz-band' and
                ../channel-width-max != 'dca-ewlc-chan-width-cap-20-mhz') or
              (../band = 'dot11-6-ghz-band' and
                ../channel-width-max != 'dca-ewlc-chan-width-cap-20-mhz' and
                ../channel-width-max != 'dca-ewlc-chan-width-cap-40-mhz')))" {
        error-message "When channel width minimum is band-default, maximum must be 40MHz+ for 5GHz or 80MHz+ for 6GHz";
        error-app-tag "must-violation";
      }
      must "((../band = 'dot11-2-dot-4-ghz-band') or
            (current() = ../channel-width-max) or
            (current() = 'dca-ewlc-chan-width-cap-band-default') or
            (current() = 'dca-ewlc-chan-width-cap-20-mhz') or
            (../band = 'dot11-5-ghz-band' and (current() = 'dca-ewlc-chan-width-cap-320-mhz') or current() = 'dca-ewlc-chan-width-cap-max') or
            (current() = 'dca-ewlc-chan-width-cap-40-mhz' and ../channel-width-max != 'dca-ewlc-chan-width-cap-20-mhz') or
            (current() = 'dca-ewlc-chan-width-cap-80-mhz' and ../band = 'dot11-5-ghz-band' and
              ../channel-width-max != 'dca-ewlc-chan-width-cap-20-mhz' and ../channel-width-max != 'dca-ewlc-chan-width-cap-40-mhz' and
              ../channel-width-max != 'dca-ewlc-chan-width-cap-band-default') or
            (current() = 'dca-ewlc-chan-width-cap-80-mhz' and ../band = 'dot11-6-ghz-band' and
              ../channel-width-max != 'dca-ewlc-chan-width-cap-20-mhz' and ../channel-width-max != 'dca-ewlc-chan-width-cap-40-mhz') or
            (current() = 'dca-ewlc-chan-width-cap-160-mhz' and
              (../channel-width-max != 'dca-ewlc-chan-width-cap-20-mhz' and ../channel-width-max != 'dca-ewlc-chan-width-cap-40-mhz' and
              ../channel-width-max != 'dca-ewlc-chan-width-cap-80-mhz' and ../channel-width-max != 'dca-ewlc-chan-width-cap-band-default')) or
            (current() = 'dca-ewlc-chan-width-cap-max' and
              (../channel-width-max = 'dca-ewlc-chan-width-cap-160-mhz' or
               ../channel-width-max = 'dca-ewlc-chan-width-cap-320-mhz')))" {
        error-message "Channel width minimum should be lesser than or equal to channel width maximum";
        error-app-tag "must-violation";
      }
      default "dca-ewlc-chan-width-cap-band-default";
      description
        "Specifies the minimum channel width allowed for Dynamic Bandwidth Selection (DBS) in the RF profile. Supported values include 20 MHz, 40 MHz, 80 MHz, 160 MHz, 320 MHz, max, and band-default. The 320 MHz option is valid only for the 6 GHz band, and the 2.4 GHz band is restricted to band-default";
    }
    leaf channel-width-max {
      type wireless-types:dca-ewlc-chan-width-cap;
      must "((../band != 'dot11-2-dot-4-ghz-band') or
            (current() = 'dca-ewlc-chan-width-cap-band-default'))" {
        error-message "DBS channel width min/max are not supported for 2.4GHz band";
        error-app-tag "must-violation";
      }
      must "((../band != 'dot11-5-ghz-band') or
            ((current() != 'dca-ewlc-chan-width-cap-320-mhz') and
             (current() != 'dca-ewlc-chan-width-cap-max')))" {
        error-message "5GHz band does not support width-max and 320 megahertz width selection";
        error-app-tag "must-violation";
      }
      must "((../band = 'dot11-2-dot-4-ghz-band') or
            (../band = 'dot11-5-ghz-band' and (current() = 'dca-ewlc-chan-width-cap-320-mhz' or current() = 'dca-ewlc-chan-width-cap-max')) or
            ((current() != 'dca-ewlc-chan-width-cap-band-default') or
              (../band = 'dot11-5-ghz-band' and
                ../channel-width-min != 'dca-ewlc-chan-width-cap-80-mhz' and
                ../channel-width-min != 'dca-ewlc-chan-width-cap-160-mhz') or
              (../band = 'dot11-6-ghz-band' and
                ../channel-width-min != 'dca-ewlc-chan-width-cap-160-mhz' and
                ../channel-width-min != 'dca-ewlc-chan-width-cap-max' and
                ../channel-width-min != 'dca-ewlc-chan-width-cap-320-mhz')))" {
        error-message "When channel width maximum is band-default, minimum must be <= 40MHz for 5GHz and <= 80MHz for 6GHz";
        error-app-tag "must-violation";
      }
      must "((../band = 'dot11-2-dot-4-ghz-band') or
            (current() = ../channel-width-min) or
            (current() = 'dca-ewlc-chan-width-cap-band-default') or
            (current() = 'dca-ewlc-chan-width-cap-320-mhz') or
            (current() = 'dca-ewlc-chan-width-cap-max') or
            (current() = 'dca-ewlc-chan-width-cap-40-mhz' and
              ((../channel-width-min = 'dca-ewlc-chan-width-cap-20-mhz') or
                (../band = 'dot11-5-ghz-band' and ../channel-width-min = 'dca-ewlc-chan-width-cap-band-default'))) or
            (current() = 'dca-ewlc-chan-width-cap-80-mhz' and
              ../channel-width-min != 'dca-ewlc-chan-width-cap-160-mhz' and
              ../channel-width-min != 'dca-ewlc-chan-width-cap-320-mhz' and
              ../channel-width-min != 'dca-ewlc-chan-width-cap-max') or
            (current() = 'dca-ewlc-chan-width-cap-160-mhz' and
              ../channel-width-min != 'dca-ewlc-chan-width-cap-320-mhz'))" {
        error-message "Channel width maximum should be greater than or equal to channel width minimum";
        error-app-tag "must-violation";
      }
      default "dca-ewlc-chan-width-cap-band-default";
      description
        "Specifies the maximum channel width allowed for Dynamic Bandwidth Selection (DBS) in the RF profile. Supported values include 20 MHz, 40 MHz, 80 MHz, 160 MHz, 320 MHz, max, and band-default. The 320 MHz option is valid only for the 6 GHz band, and the 2.4 GHz band is restricted to band-default";
    }
    leaf std-pwr-mode-allowed {
      type boolean;
      default "false";
      description
        "Allow AP to operate in 6GHz standard power mode";
    }
    leaf fra-action {
      type wireless-enum-types:enm-fra-action-type;
      default "fra-action-default";
      description
        "Specifies the Flexible Radio Assignment (FRA) action to be applied to dual band radios, determining how the radio operates (e.g., band assignment or mode).";
    }
    leaf ampdu-window-size {
      type uint16 {
        range "1 .. 255";
      }
      default "255";
      description
        "Window size for aggregate MAC protocol data unit";
    }
    leaf preamble-puncture {
      type boolean;
      default "false";
      description
        "Enables or disables preamble puncturing as defined in the 802.11be (Wi-Fi 7) standard, allowing selective use of sub-channels within a wider channel to avoid interference.";
    }
    leaf management-retries {
      type int16 {
        range "-1 .. 255";
      }
      default "-1";
      description
        "Specifies the number of retry attempts for transmitting management frames on the radio.";
    }
    leaf aggregate-retries {
      type int16 {
        range "-1 .. 255";
      }
      default "-1";
      description
        "Specifies the number of retry attempts for transmitting aggregate frames (such as AMPDU) on the radio.";
    }
    leaf non-aggregate-retries {
      type int16 {
        range "-1 .. 255";
      }
      default "-1";
      description
        "Specifies the number of retry attempts for transmitting non-aggregate frames on the radio.";
    }
    leaf unii3-lp-channels {
      type boolean;
      must "(../band = 'dot11-5-ghz-band' or
             ../unii3-lp-channels = 'false')" {
        error-message "UNII-3 low power channels is applicable only for 5 GHz band";
        error-app-tag "must-violation";
      }
      default "false";
      description
        "Enable/Disable UNII-3 low power channels for 5 GHz band";
    }
    leaf iot-coex-mode {
      type wireless-enum-types:enm-iot-coex-mode;
      default "ap-coex-mode-disable";
      description
        "Specifies the coexistence mode for WiFi and IoT radios on the access point. This setting determines how WiFi and IoT radios operate together to minimize interference and optimize performance.";
    }
  }

  grouping rf-80211-nmcs-default {
    description
      "This object contains all the configuration related to nmcs data rates for default Radio-Frequency(rf)-profile.";
    leaf rf-index {
      type uint8 {
        range "0 .. 31";
      }
      description
        "uniquely identifies the Modulation and Coding Scheme(MCS) data rate for a particular Radio-Frequency(rf)-profile.";
    }
    leaf mcs-data-rate {
      type uint16;
      units "Mbps";
      description
        "Modulation and Coding Scheme(MCS) Data rate in Mbps.";
    }
    leaf rf-80211n-mcs-enable {
      type boolean;
      default "true";
      description
        "Enable or disable the data rate. When this object is set to 'true' the Modulation and Coding Scheme(MCS) support is enabled. When this object is set to 'false' the MCS support is disabled..";
    }
  }

  grouping rf-dca-allowed-chans-default {
    description
      "Configure list of all the allowed channels for the default Radio-Frequency(rf)-profile";
    leaf channel {
      type uint32;
      description
        "Specifies the channel number to be included in the allowed Dynamic Channel Assignment (DCA) channel list for the default Radio-Frequency (RF) profile.";
    }
  }

  grouping rf-dca-removed-chans-default {
    description
      "Configure list of all the removed channels for the default Radio-Frequency(rf)-profile";
    leaf channel {
      type uint32;
      description
        "Specifies the channel number to be included in the removed Dynamic Channel Assignment (DCA) channel list for the default Radio-Frequency (RF) profile.";
    }
  }

  grouping rfprofile-default {
    description
      "This object indicates all the configurations related to default Radio-Frequency(rf)-profile";
    leaf band {
      type wireless-types:enm-ewlc-dot11-radio-band;
      description
        "Configure the type of the radio. Possible values are either 802.11b or 802.11a.";
    }
    leaf name {
      type string;
      description
        "Configure the name of the default Radio-Frequency(rf)-profile";
    }
    leaf description {
      type string;
      description
        "Configure the brief description of default Radio-Frequency(rf)-profile";
    }
    leaf tx-power-min {
      type int8 {
        range "-10 .. 30";
      }
      units "dBm";
      must '../tx-power-min <= ../tx-power-max' {
        error-message "tx-power-min must be less than or equal to tx-power-max";
        error-app-tag "must-violation";
      }
      default "-10";
      description
        "Lower limit of transmit power in dBm. For an 802.11 network, the system will only accept this configuration if the TPC is in Auto or Run Once mode";
    }
    leaf tx-power-max {
      type int8 {
        range "-10 .. 30";
      }
      units "dBm";
      must '../tx-power-min <= ../tx-power-max' {
        error-message "tx-power-max must be greater than or equal to tx-power-min";
        error-app-tag "must-violation";
      }
      default "30";
      description
        "Upper limit of transmit power in dBm. For an 802.11 network, the system will only accept this configuration if the TPC is in Auto or Run Once mode";
    }
    leaf tx-power-v1-threshold {
      type int16 {
        range "-80 .. -50";
      }
      units "dBm";
      default "-70";
      description
        "Configure transmit power control version 1 threshold for the radio resource management algorithm.";
    }
    leaf tx-power-v2-threshold {
      type int16 {
        range "-80 .. -50";
      }
      units "dBm";
      default "-67";
      description
        "Configure transmit power control version 2 threshold for the radio resource management algorithm.";
    }
    leaf status {
      type boolean;
      default "true";
      description
        "Configure the Radio-Frequency(rf)-profile operational state. The value false indicates that the Radio-Frequency(rf)-profile is inactive, the value of true indicate the Radio-Frequency(rf)-profile is active";
    }
    leaf data-rate-1m {
      type wireless-enum-types:rate-state;
      must "(../band != 'dot11-2-dot-4-ghz-band' or
             ../data-rate-1m = 'apf-tx-rate-basic' or
             ../data-rate-2m = 'apf-tx-rate-basic' or
             ../data-rate-5-5m = 'apf-tx-rate-basic' or
             ../data-rate-11m = 'apf-tx-rate-basic' or
             ../data-rate-6m = 'apf-tx-rate-basic' or
             ../data-rate-9m = 'apf-tx-rate-basic' or
             ../data-rate-12m = 'apf-tx-rate-basic' or
             ../data-rate-18m = 'apf-tx-rate-basic' or
             ../data-rate-24m = 'apf-tx-rate-basic' or
             ../data-rate-36m = 'apf-tx-rate-basic' or
             ../data-rate-48m = 'apf-tx-rate-basic' or
             ../data-rate-54m = 'apf-tx-rate-basic')" {
        error-message "At least one data rate should be configured as basic for 2.4GHz rf profile";
        error-app-tag "must-violation";
      }
      must "(../band != 'dot11-5-ghz-band' or
             ../data-rate-6m = 'apf-tx-rate-basic' or
             ../data-rate-9m = 'apf-tx-rate-basic' or
             ../data-rate-12m = 'apf-tx-rate-basic' or
             ../data-rate-18m = 'apf-tx-rate-basic' or
             ../data-rate-24m = 'apf-tx-rate-basic' or
             ../data-rate-36m = 'apf-tx-rate-basic' or
             ../data-rate-48m = 'apf-tx-rate-basic' or
             ../data-rate-54m = 'apf-tx-rate-basic')" {
        error-message "At least one data rate should be configured as basic for 5GHz rf profile";
        error-app-tag "must-violation";
      }
      must "(../band != 'dot11-2-dot-4-ghz-band' or current() != 'apf-tx-rate-not-applicable')" {
        error-message "apf-tx-rate-not-applicable is not valid configuration";
        error-app-tag "must-violation";
      }
      default "apf-tx-rate-basic";
      description
        "Configure the 1 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-2m {
      type wireless-enum-types:rate-state;
      must "(../band != 'dot11-2-dot-4-ghz-band' or current() != 'apf-tx-rate-not-applicable')" {
        error-message "apf-tx-rate-not-applicable is not valid configuration";
        error-app-tag "must-violation";
      }
      default "apf-tx-rate-basic";
      description
        "Configure the 2 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-5-5m {
      type wireless-enum-types:rate-state;
      must "(../band != 'dot11-2-dot-4-ghz-band' or current() != 'apf-tx-rate-not-applicable')" {
        error-message "apf-tx-rate-not-applicable is not valid configuration";
        error-app-tag "must-violation";
      }
      default "apf-tx-rate-basic";
      description
        "Configure the 5.5 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-11m {
      type wireless-enum-types:rate-state;
      must "(../band != 'dot11-2-dot-4-ghz-band' or current() != 'apf-tx-rate-not-applicable')" {
        error-message "apf-tx-rate-not-applicable is not valid configuration";
        error-app-tag "must-violation";
      }
      default "apf-tx-rate-basic";
      description
        "Configure the 11 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-6m {
      type wireless-enum-types:rate-state;
      must "(current() != 'apf-tx-rate-not-applicable')" {
        error-message "apf-tx-rate-not-applicable is not valid configuration";
        error-app-tag "must-violation";
      }
      default "apf-tx-rate-not-applicable";
      description
        "Configure the 6 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-9m {
      type wireless-enum-types:rate-state;
      must "(current() != 'apf-tx-rate-not-applicable')" {
        error-message "apf-tx-rate-not-applicable is not valid configuration";
        error-app-tag "must-violation";
      }
      default "apf-tx-rate-supported";
      description
        "Configure the 9 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-12m {
      type wireless-enum-types:rate-state;
      must "(current() != 'apf-tx-rate-not-applicable')" {
        error-message "apf-tx-rate-not-applicable is not valid configuration";
        error-app-tag "must-violation";
      }
      default "apf-tx-rate-not-applicable";
      description
        "Configure the 12 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-18m {
      type wireless-enum-types:rate-state;
      must "(current() != 'apf-tx-rate-not-applicable')" {
        error-message "apf-tx-rate-not-applicable is not valid configuration";
        error-app-tag "must-violation";
      }
      default "apf-tx-rate-supported";
      description
        "Configure the 18 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-24m {
      type wireless-enum-types:rate-state;
      must "(current() != 'apf-tx-rate-not-applicable')" {
        error-message "apf-tx-rate-not-applicable is not valid configuration";
        error-app-tag "must-violation";
      }
      default "apf-tx-rate-not-applicable";
      description
        "Configure the 24 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-36m {
      type wireless-enum-types:rate-state;
      must "(current() != 'apf-tx-rate-not-applicable')" {
        error-message "apf-tx-rate-not-applicable is not valid configuration";
        error-app-tag "must-violation";
      }
      default "apf-tx-rate-supported";
      description
        "Configure the 36 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-48m {
      type wireless-enum-types:rate-state;
      must "(current() != 'apf-tx-rate-not-applicable')" {
        error-message "apf-tx-rate-not-applicable is not valid configuration";
        error-app-tag "must-violation";
      }
      default "apf-tx-rate-supported";
      description
        "Configure the 48 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-54m {
      type wireless-enum-types:rate-state;
      must "(current() != 'apf-tx-rate-not-applicable')" {
        error-message "apf-tx-rate-not-applicable is not valid configuration";
        error-app-tag "must-violation";
      }
      default "apf-tx-rate-supported";
      description
        "Configure the 54 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf coverage-data-packet-rssi-threshold {
      type int16 {
        range "-90 .. -60";
      }
      units "dBm";
      default "-80";
      description
        "Configure Received Signal Strength Indicator(RSSI) threshold value for data packets.";
    }
    leaf min-num-clients {
      type int32 {
        range "1 .. 200";
      }
      default "3";
      description
        "Specifies the minimum number of clients required before triggering an exception or alert for low client count on the radio frequency profile.";
    }
    leaf coverage-voice-packet-rssi-threshold {
      type int16 {
        range "-90 .. -60";
      }
      units "dBm";
      default "-80";
      description
        "Configure the Received Signal Strength Indicator(RSSI) threshold value for voice packets.";
    }
    leaf exception-level {
      type uint16 {
        range "0 .. 100";
      }
      units "dBm";
      default "25";
      description
        "Specifies the threshold, in dBm, for triggering a coverage exception event when the signal strength falls below this level.";
    }
    leaf band-select-client-rssi {
      type int16 {
        range "-90 .. -20";
      }
      units "dBm";
      default "-80";
      description
        "Configure the minimum mobile station Received Signal Strength Indicator(RSSI) threshold. Mobile stations having RSSI below this value will not be recorded in the suppressed table. This configuration filters out far away mobile stations with weaker signal strength. This will limit the number of mobile stations on the table to a reasonable amount.";
    }
    leaf band-select-client-mid-rssi {
      type int16 {
        range "-90 .. -20";
      }
      units "dBm";
      must 'current() >= ../band-select-client-rssi' {
        error-message "Client mid RSSI (dBm) must be greater than or equal to client RSSI (dBm)";
        error-app-tag "must-violation";
      }
      default "-80";
      description
        "Configure the medium mobile station Received Signal Strength Indicator(RSSI) threshold. Mobile station between this value and cldband_select_client_rssi will be recorded in suppressed table but will not be denied. The mobile station having RSSI stronger this value will be recorded and denied.";
    }
    leaf band-select-cycle-count {
      type uint16 {
        range "1 .. 10";
      }
      default "2";
      description
        "Specifies the maximum number of consecutive cycles in which a mobile station does not respond before it is considered inactive for band selection purposes.";
    }
    leaf band-select-cycle-threshold {
      type uint16 {
        range "1 .. 1000";
      }
      units "milliseconds";
      default "200";
      description
        "Specifies the cycle threshold, in milliseconds, used by the band select feature to determine how often band selection decisions are made for client devices.";
    }
    leaf band-select-age-out-dual-band {
      type uint16 {
        range "10 .. 300";
      }
      units "seconds";
      default "60";
      description
        "Specifies the age-out timer, in seconds, for dual-band clients in the band select process. After this period, the client is considered inactive for band selection.";
    }
    leaf band-select-age-out-suppression {
      type uint16 {
        range "10 .. 200";
      }
      units "seconds";
      default "20";
      description
        "Specifies the suppression age-out timer, in seconds, for clients suppressed by the band select feature. After this period, suppression is lifted and the client can be considered for band selection again.";
    }
    leaf band-select-probe-response {
      type boolean;
      default "false";
      description
        "Configure Access-Point(AP)'s probe response with clients to verify whether client can associate on both 2.4 GHz and 5 Ghz spectrum. When set to true, AP suppresses probe response to new clients for all Service Set Identifier(SSID)'s that are not being Band Select disabled.";
    }
    leaf dca-contribution-interference {
      type boolean;
      default "true";
      description
        "Enables or disables the use of interference measurements as a factor in Dynamic Channel Assignment (DCA) decisions for RF profiles.";
    }
    leaf rf-dca-chan-width {
      type wireless-enum-types:rf-dca-chan-width;
      default "rf-dca-chan-width-best";
      status deprecated;
      description
        "Deprecated in favor of channel-width-min and channel-width-max. This leaf controlled the Dynamic Channel Assignment (DCA) channel width mode for the default RF profile and will not be honoured now";
    }
    leaf load-balancing-window {
      type uint32 {
        range "0 .. 20";
      }
      default "5";
      description
        "Specifies the client count window used for load balancing decisions between Access Points (APs). Determines the acceptable difference in the number of associated clients before load balancing is triggered.";
    }
    leaf load-balancing-denial-count {
      type uint32 {
        range "1 .. 10";
      }
      default "3";
      description
        "Specifies the number of times a client association request can be denied by an Access Point (AP) as part of load balancing before the client is allowed to associate.";
    }
    leaf trap-threshold-clients {
      type uint32 {
        range "1 .. 200";
      }
      default "12";
      description
        "Configure threshold number of clients per Access-Point(AP) radio to trigger a trap. The trap ciscoLwappApClientThresholdNotify will be triggered once the count of clients on the AP radio reaches this limit. A value of zero indicates that the trap is disabled.";
    }
    leaf trap-threshold-interference {
      type uint16 {
        range "0 .. 100";
      }
      units "percentage";
      default "10";
      description
        "Specifies the interference threshold, as a percentage, at which an SNMP trap is generated when interference on the AP radio exceeds this value.";
    }
    leaf trap-threshold-noise {
      type int32 {
        range "-127 .. 0";
      }
      units "dBm";
      default "-70";
      description
        "Specifies the noise level threshold, in dBm, at which an SNMP trap is generated; valid values range from -127 to 0 dBm.";
    }
    leaf trap-threshold-utilization {
      type uint16 {
        range "0 .. 100";
      }
      units "percentage";
      default "80";
      description
        "Configure threshold of bandwidth (%) being utilized by an access-point. Traps are sent when this value is exceeded";
    }
    leaf max-radio-clients {
      type uint16 {
        range "0 .. 500";
      }
      default "200";
      description
        "Configure maximum number of radio clients per Access-Point(AP) in high density environment.";
    }
    leaf multicast-data-rate {
      type wireless-enum-types:enm-multicast-data-rate;
      default "mcast-data-rate-default";
      description
        "Configure minimum data rate at which multicast clients can associate to Access-Point(AP). A value 0 indicates that AP will automatically adjust data rates.";
    }
    leaf rx-sen-sop-threshold {
      type wireless-types:rx-sen-sop-threshold-level;
      units "dBm";
      default "rrm-ewlc-rxsensop-threshold-auto";
      description
        "Configure the Receiver Start of Packet (RX-SOP) sensitivity threshold";
    }
    leaf rx-sen-sop-custom {
      type int16 {
        range "-85 .. -60";
      }
      units "dBm";
      default "-85";
      description
        "Rx SOP custom values configured between -85 dBm (default) and -60 dBm. This configured value takes effect only when rx sop threshold is set to custom";
    }
    leaf client-network-preference {
      type wireless-types:enm-client-network-preference;
      default "default";
      description
        "Configure the client network preference. Possible values are:
         1. connectivity - Radio-Resource-Management(RRM) Algorithm has a preference on connectivity of the clients.
         2. throughput   - Radio-Resource-Management(RRM) Algorithm has a preference on high throughput of the clients.
         3. default      - Radio-Resource-Management(RRM) Algorithm has no preference on the clients.";
    }
    leaf hsr-mode {
      type boolean;
      default "false";
      description
        "Enables or disables High-Speed Roam (HSR) for the Radio-Frequency (RF) profile.";
    }
    leaf hsr-neighbor-timeout {
      type uint16 {
        range "5 .. 60";
      }
      default "5";
      description
        "Configure the timeout interval of neighbors that will be configured for Radio-Frequency(RF) profile. Neighbor timeout factor will be five times the neighbor interval";
    }
    leaf opt-roam-rssi-treshold {
      type int16 {
        range "-127 .. 0";
      }
      units "dBm";
      default "-127";
      description
        "Configure the minimum Received Signal Strength Indicator(RSSI) threshold for optimized roaming to occur. Possible values are in the range -127 dbm to 0 dbm";
    }
    leaf opt-roam-rssi-check-enable {
      type boolean;
      default "false";
      description
        "Configure if Received Signal Strength Indicator(RSSI) threshold is enabled before optimized roaming is enabled";
    }
    leaf atf-oper-mode {
      type wireless-enum-types:apf-ate-mode;
      status obsolete;
      description
        "ATF Mode SSID or monitor is enabled for the default-rf-profile; this leaf is obsolete";
    }
    leaf atf-optimization {
      type wireless-enum-types:apf-ate-stealing-policy;
      status obsolete;
      description
        "True if ATF optimization is enabled for the default-rf-profile; this leaf is obsolete";
    }
    leaf bridge-client-access {
      type boolean;
      default "false";
      status obsolete;
      description
        "True if Airtime Allocation feature is enabled for the default-rf-profile; this leaf is obsolete";
    }
    leaf airtime-allocation {
      type uint8 {
        range "5 .. 90";
      }
      units "percentage";
      default "5";
      status obsolete;
      description
        "Specifies the percentage of airtime allocated to clients or services in the default Radio-Frequency (RF) profile.";
    }
    leaf client-aware-fra {
      type boolean;
      default "false";
      description
        "Client Aware FRA allows the Dual band to operate on 5 Ghz or monitor mode depending on the load on the dedicated 5 Ghz radio";
    }
    leaf client-select-threshold {
      type uint8 {
        range "0 .. 100";
      }
      units "percent";
      must '../client-reset-threshold < ../client-select-threshold' {
        error-message "client-select-threshold must be greater than client-reset-threshold";
        error-app-tag "must-violation";
      }
      default "50";
      description
        "Specifies the utilization threshold, in percent, for Client Aware FRA at which the dual-band radio switches from monitor mode to client serving mode.";
    }
    leaf client-reset-threshold {
      type uint8 {
        range "0 .. 100";
      }
      must '../client-reset-threshold < ../client-select-threshold' {
        error-message "client-reset-threshold must be less than client-select-threshold";
        error-app-tag "must-violation";
      }
      default "5";
      description
        "Client aware FRA utilization threshold value for moving Dual band radio from Client Serving mode to Monitor mode";
    }
    container rf-mcs-default-entries {
      description
        "Contains default Modulation and Coding Scheme (MCS) configuration entries for the Radio-Frequency (RF) profile.";
      list rf-mcs-default-entry {
        key "rf-index";
        description
          "List of default Modulation and Coding Scheme (MCS) configuration entries for the Radio-Frequency (RF) profile.";
        uses wireless-rf-cfg:rf-80211-nmcs-default;
      }
    }
    container rf-dca-allowed-channels-default-entries {
      description
        "Configurations related to allowed Dynamic Channel Assignment (DCA) channels in default Radio-Frequency(rf)-profile";
      list rf-dca-allowed-channel-default-entry {
        key "channel";
        description
          "A list of configurations related to allowed Dynamic Channel Assignment (DCA) channels in default Radio-Frequency(rf)-profile";
        uses wireless-rf-cfg:rf-dca-allowed-chans-default;
      }
    }
    container rf-dca-removed-channels-default-entries {
      description
        "Configurations related to removed Dynamic Channel Assignment (DCA) channels in default Radio-Frequency(rf)-profile";
      list rf-dca-removed-channels-default-entry {
        key "channel";
        description
          "A list of configurations related to removed Dynamic Channel Assignment (DCA) channels in default Radio-Frequency(rf)-profile";
        uses wireless-rf-cfg:rf-dca-removed-chans-default;
      }
    }
    leaf he-obss-pd-enable {
      type boolean;
      default "false";
      description
        "Enable/Disable 802.11ax OBSS PD spatial reuse";
    }
    leaf he-non-srg-obss-pd-max {
      type int8 {
        range "-82 .. -62";
      }
      units "dBm";
      default "-62";
      description
        "Non-SRG OBSS PD maximum threshold in dBm";
    }
    leaf ndp-mode {
      type wireless-enum-types:enm-ndp-mode;
      default "ndp-mode-auto";
      description
        "Neighbor discovery protocol operating mode configuration.
         Possible values are:
         auto        - AP does neighbor discovery either on serving channel or
                       off channel based on its NDP capability
         off-channel - AP does neighbor discovery on off channel";
    }
    leaf he-srg-obss-pd-enable {
      type boolean;
      default "false";
      description
        "Enable/Disable 802.11ax SRG OBSS PD spatial reuse";
    }
    leaf he-srg-obss-pd-min {
      type int8 {
        range "-82 .. -62";
      }
      units "dBm";
      must '../he-srg-obss-pd-min <= ../he-srg-obss-pd-max' {
        error-message "SRG OBSS PD minimum must be less than or equal to SRG OBSS PD maximum";
        error-app-tag "must-violation";
      }
      default "-82";
      description
        "SRG OBSS PD minimum threshold in dBm";
    }
    leaf he-srg-obss-pd-max {
      type int8 {
        range "-82 .. -62";
      }
      units "dBm";
      must '../he-srg-obss-pd-min <= ../he-srg-obss-pd-max' {
        error-message "SRG OBSS PD maximum must be greater than or equal to SRG OBSS PD minimum";
        error-app-tag "must-violation";
      }
      default "-62";
      description
        "SRG OBSS PD maximum threshold in dBm";
    }
    leaf dot11ax-6ghz-feature {
      type wireless-enum-types:dot11ax-6ghz-feature;
      default "he-6ghz-none";
      description
        "Specifies the 802.11ax-specific feature to be enabled or configured for the 6 GHz band in the RF profile.";
    }
    leaf zerowt-dfs {
      type boolean;
      must "(../band = 'dot11-5-ghz-band' or
             ../zerowt-dfs = 'false')" {
        error-message "Zero wait DFS feature is applicable only for 5 GHz band";
        error-app-tag "must-violation";
      }
      default "false";
      description
        "Enable/Disable 802.11a Zero wait DFS feature";
    }
    leaf guard-interval-ext {
      type wireless-enum-types:enm-guard-interval-ext;
      default "guard-interval-none";
      description
        "Specifies the guard interval extension setting for the RF profile, which determines the time interval between transmitted symbols to reduce inter-symbol interference in wireless communications.";
    }
    leaf client-reset-thresh-6ghz {
      type uint8 {
        range "0 .. 100";
      }
      units "percentage";
      default "5";
      description
        "Client aware FRA utilization threshold value for moving dual band radio from 6GHz to 5GHz";
    }
    leaf client-count-reset-6ghz {
      type uint8 {
        range "1 .. 10";
      }
      default "1";
      description
        "Client aware FRA client count value for moving dual band radio from 6GHz to 5GHz";
    }
    leaf channel-width-min {
      type wireless-types:dca-ewlc-chan-width-cap;
      must "((../band != 'dot11-2-dot-4-ghz-band') or
            (current() = 'dca-ewlc-chan-width-cap-band-default'))" {
        error-message "DBS channel width min/max are not supported for 2.4GHz band";
        error-app-tag "must-violation";
      }
      must "((../band != 'dot11-5-ghz-band') or
            ((current() != 'dca-ewlc-chan-width-cap-320-mhz') and
             (current() != 'dca-ewlc-chan-width-cap-max')))" {
        error-message "5GHz band does not support width-max and 320 megahertz width selection";
        error-app-tag "must-violation";
      }
      must "((../band = 'dot11-2-dot-4-ghz-band') or
            (current() = ../channel-width-max) or
            (current() = 'dca-ewlc-chan-width-cap-band-default') or
            (current() = 'dca-ewlc-chan-width-cap-20-mhz') or
            (../band = 'dot11-5-ghz-band' and (current() = 'dca-ewlc-chan-width-cap-max' or current() = 'dca-ewlc-chan-width-cap-320-mhz')) or
            (current() = 'dca-ewlc-chan-width-cap-40-mhz' and ../channel-width-max != 'dca-ewlc-chan-width-cap-20-mhz') or
            (current() = 'dca-ewlc-chan-width-cap-80-mhz' and ../band = 'dot11-5-ghz-band' and
              ../channel-width-max != 'dca-ewlc-chan-width-cap-20-mhz' and ../channel-width-max != 'dca-ewlc-chan-width-cap-40-mhz' and
              ../channel-width-max != 'dca-ewlc-chan-width-cap-band-default') or
            (current() = 'dca-ewlc-chan-width-cap-80-mhz' and ../band = 'dot11-6-ghz-band' and
              ../channel-width-max != 'dca-ewlc-chan-width-cap-20-mhz' and ../channel-width-max != 'dca-ewlc-chan-width-cap-40-mhz') or
            (current() = 'dca-ewlc-chan-width-cap-160-mhz' and
              (../channel-width-max != 'dca-ewlc-chan-width-cap-20-mhz' and ../channel-width-max != 'dca-ewlc-chan-width-cap-40-mhz' and
              ../channel-width-max != 'dca-ewlc-chan-width-cap-80-mhz' and ../channel-width-max != 'dca-ewlc-chan-width-cap-band-default')) or
            (current() = 'dca-ewlc-chan-width-cap-max' and
              (../channel-width-max = 'dca-ewlc-chan-width-cap-160-mhz' or
               ../channel-width-max = 'dca-ewlc-chan-width-cap-320-mhz')))" {
        error-message "Channel width minimum should be lesser than or equal to channel width maximum";
        error-app-tag "must-violation";
      }
      must "((../band = 'dot11-2-dot-4-ghz-band') or
            (../band = 'dot11-5-ghz-band' and (current() = 'dca-ewlc-chan-width-cap-320-mhz' or current() = 'dca-ewlc-chan-width-cap-max')) or
            (current() != 'dca-ewlc-chan-width-cap-band-default') or
            (../band = 'dot11-5-ghz-band' and
              ../channel-width-max != 'dca-ewlc-chan-width-cap-20-mhz' and
              ../channel-width-max != 'dca-ewlc-chan-width-cap-320-mhz') or
            (../band = 'dot11-6-ghz-band' and
              (../channel-width-max != 'dca-ewlc-chan-width-cap-20-mhz' and
              ../channel-width-max != 'dca-ewlc-chan-width-cap-40-mhz')))" {
        error-message "When channel width minimum is band-default, maximum must be 40MHz+ for 5GHz or 80MHz+ for 6GHz";
        error-app-tag "must-violation";
      }
      default "dca-ewlc-chan-width-cap-band-default";
      description
        "Specifies the minimum channel width allowed for Dynamic Bandwidth Selection (DBS) in the default RF profile. Supported values include 20 MHz, 40 MHz, 80 MHz, 160 MHz, 320 MHz, max, and band-default. The 320 MHz option is valid only for the 6 GHz band, and the 2.4 GHz band is restricted to band-default";
    }
    leaf channel-width-max {
      type wireless-types:dca-ewlc-chan-width-cap;
      must "((../band != 'dot11-2-dot-4-ghz-band') or
            (current() = 'dca-ewlc-chan-width-cap-band-default'))" {
        error-message "DBS channel width min/max are not supported for 2.4GHz band";
        error-app-tag "must-violation";
      }
      must "((../band != 'dot11-5-ghz-band') or
            ((current() != 'dca-ewlc-chan-width-cap-320-mhz') and
             (current() != 'dca-ewlc-chan-width-cap-max')))" {
        error-message "5GHz band does not support width-max and 320 megahertz width selection";
        error-app-tag "must-violation";
      }
      must "((../band = 'dot11-2-dot-4-ghz-band') or
            (../band = 'dot11-5-ghz-band' and (current() = 'dca-ewlc-chan-width-cap-320-mhz' or current() = 'dca-ewlc-chan-width-cap-max')) or
            ((current() != 'dca-ewlc-chan-width-cap-band-default') or
              (../band = 'dot11-5-ghz-band' and
                ../channel-width-min != 'dca-ewlc-chan-width-cap-80-mhz' and
                ../channel-width-min != 'dca-ewlc-chan-width-cap-160-mhz') or
              (../band = 'dot11-6-ghz-band' and
                ../channel-width-min != 'dca-ewlc-chan-width-cap-160-mhz' and
                ../channel-width-min != 'dca-ewlc-chan-width-cap-max' and
                ../channel-width-min != 'dca-ewlc-chan-width-cap-320-mhz')))" {
        error-message "When channel width maximum is band-default, minimum must be <= 40MHz for 5GHz and <= 80MHz for 6GHz";
        error-app-tag "must-violation";
      }
      must "((../band = 'dot11-2-dot-4-ghz-band') or
            (current() = ../channel-width-min) or
            (current() = 'dca-ewlc-chan-width-cap-band-default') or
            (current() = 'dca-ewlc-chan-width-cap-320-mhz') or
            (current() = 'dca-ewlc-chan-width-cap-max') or
            (current() = 'dca-ewlc-chan-width-cap-40-mhz' and
              ((../channel-width-min = 'dca-ewlc-chan-width-cap-20-mhz') or
                (../band = 'dot11-5-ghz-band' and ../channel-width-min = 'dca-ewlc-chan-width-cap-band-default'))) or
            (current() = 'dca-ewlc-chan-width-cap-80-mhz' and
              ../channel-width-min != 'dca-ewlc-chan-width-cap-160-mhz' and
              ../channel-width-min != 'dca-ewlc-chan-width-cap-320-mhz' and
              ../channel-width-min != 'dca-ewlc-chan-width-cap-max') or
            (current() = 'dca-ewlc-chan-width-cap-160-mhz' and
              ../channel-width-min != 'dca-ewlc-chan-width-cap-320-mhz'))" {
        error-message "Channel width maximum should be greater than or equal to channel width minimum";
        error-app-tag "must-violation";
      }
      default "dca-ewlc-chan-width-cap-band-default";
      description
        "Specifies the maximum channel width allowed for Dynamic Bandwidth Selection (DBS) in the default RF profile. Supported values include 20 MHz, 40 MHz, 80 MHz, 160 MHz, 320 MHz, max, and band-default. The 320 MHz option is valid only for the 6 GHz band, and the 2.4 GHz band is restricted to band-default";
    }
    leaf std-pwr-mode-allowed {
      type boolean;
      default "false";
      description
        "Allow AP to operate in 6GHz standard power mode";
    }
    leaf fra-action {
      type wireless-enum-types:enm-fra-action-type;
      default "fra-action-default";
      description
        "Specifies the Flexible Radio Assignment (FRA) action to be applied to dual band radios, determining how the radio operates (e.g., band assignment or mode).";
    }
    leaf ampdu-window-size {
      type uint16 {
        range "1 .. 255";
      }
      default "255";
      description
        "Window size for aggregate MAC protocol data unit";
    }
    leaf management-retries {
      type int16 {
        range "-1 .. 255";
      }
      default "-1";
      description
        "Specifies the number of retry attempts for transmitting management frames on the radio.";
    }
    leaf aggregate-retries {
      type int16 {
        range "-1 .. 255";
      }
      default "-1";
      description
        "Specifies the number of retry attempts for transmitting aggregate frames (such as AMPDU) on the radio.";
    }
    leaf non-aggregate-retries {
      type int16 {
        range "-1 .. 255";
      }
      default "-1";
      description
        "Specifies the number of retry attempts for transmitting non-aggregate frames on the radio.";
    }
    leaf unii3-lp-channels {
      type boolean;
      must "(../band = 'dot11-5-ghz-band' or
             ../unii3-lp-channels = 'false')" {
        error-message "UNII-3 low power channels is applicable only for 5 GHz band";
        error-app-tag "must-violation";
      }
      default "false";
      description
        "Enable/Disable UNII-3 low power channels for 5 GHz band";
    }
    leaf iot-coex-mode {
      type wireless-enum-types:enm-iot-coex-mode;
      default "ap-coex-mode-disable";
      description
        "Configure AP WiFi-IOT Coexistence mode";
    }
  }

  grouping st-atf-policy {
    description
      "Configurations of Air Time Fairness policy.";
    leaf atfpolicy-name {
      type string {
        length "0..31";
        pattern '[!-~]([ -~]*[!-~])?';
      }
      description
        "Configure profile name assigned to the Air Time Fairness policy. The name assigned to an ATF policy has to be unique across all the ATF policies on the controller";
    }
    leaf policy-id {
      type uint32 {
        range "0 .. 511";
      }
      description
        "Unique identifier for the Air Time Fairness (ATF) policy instance on the controller.";
    }
    leaf policy-weight {
      type uint8 {
        range "5 .. 100";
      }
      default "10";
      description
        "Configure policy weight assigned to the ATF policy";
    }
    leaf client-sharing {
      type boolean;
      default "false";
      description
        "Enables or disables client fair sharing for the associated Air Time Fairness (ATF) policy.";
    }
  }

  grouping st-rf-tag-radio-profile {
    description
      "Configure the slot specific radio profiles mapped in the (RF) Radio-Frequency tag";
    leaf radio-profile-name {
      type string;
      default "default-radio-profile";
      description
        "Name of the radio profile";
    }
  }

  grouping rf-tag {
    description
      "Contains configurations related to rf tag.";
    leaf tag-name {
      type string {
        pattern '[!-~]([ -~]*[!-~])?';
      }
      description
        "Configure the rf tag name";
    }
    leaf description {
      type string;
      default "";
      description
        "Specifies a brief user-defined description for the RF tag.";
    }
    leaf dot11a-rf-profile-name {
      type string;
      default "default_rf_5gh";
      description
        "Configure the 802.11a Radio-Frequency(rf)-profile that is associated with this rf tag";
    }
    leaf dot11b-rf-profile-name {
      type string;
      default "default_rf_24gh";
      description
        "Configure the 802.11b Radio-Frequency(rf)-profile that is associated with this rf tag";
    }
    leaf dot11-6ghz-rf-prof-name {
      type string;
      default "default-rf-profile-6ghz";
      description
        "802.11 6GHz Radio-Frequency(rf)-profile that is associated with this RF tag";
    }
    container rf-tag-radio-profiles {
      description
        "Radio profile configuration related to the RF tag";
      list rf-tag-radio-profile {
        key "slot-id band-id";
        description
          "Slot specific radio profile configuration related to the RF tag";
        uses wireless-types:st-slot-band-key;
        uses wireless-rf-cfg:st-rf-tag-radio-profile;
      }
    }
    leaf ap-beam-state {
      type wireless-enum-types:enm-ap-beam-state;
      default "ap-beam-state-boresight";
      description
        "Configures AP beam state";
    }
    container urwb {
      description
        "Ultra Reliable Wireless Backhaul(URWB) configuration associated with this rf tag";
      uses wireless-types:st-urwb-cfg;
    }
  }

  grouping multi-bssid-profile {
    description
      "802.11ax Multi BSSID profile configuration";
    leaf profile-name {
      type string {
        pattern '[!-~]([ -~]*[!-~])?';
      }
      description
        "Name of the 802.11ax Multi BSSID profile";
    }
    leaf description {
      type string;
      default "";
      description
        "Brief description of 802.11ax Multi BSSID profile";
    }
    leaf he-ofdma-downlink {
      type boolean;
      default "true";
      description
        "Enables or disables 802.11ax OFDMA (Orthogonal Frequency Division Multiple Access) downlink operation for this Multi-BSSID profile.";
    }
    leaf he-ofdma-uplink {
      type boolean;
      default "true";
      description
        "Enables or disables 802.11ax OFDMA (Orthogonal Frequency Division Multiple Access) uplink operation for this Multi-BSSID profile.";
    }
    leaf he-mumimo-downlink {
      type boolean;
      default "true";
      description
        "Enables or disables 802.11ax MU-MIMO (Multi-User Multiple Input Multiple Output) downlink operation for this Multi-BSSID profile.";
    }
    leaf he-mumimo-uplink {
      type boolean;
      default "true";
      description
        "Enables or disables 802.11ax MU-MIMO (Multi-User Multiple Input Multiple Output) uplink operation for this Multi-BSSID profile.";
    }
    leaf he-twt {
      type boolean;
      default "false";
      description
        "Enables or disables the 802.11ax Target Wake Time (TWT) feature for this Multi-BSSID profile.";
    }
    leaf he-twt-broadcast {
      type boolean;
      default "false";
      description
        "Enables or disables the broadcast of Target Wake Time (TWT) information for 802.11ax (Wi-Fi 6) clients, allowing devices to schedule wake times and improve power efficiency.";
    }
    leaf eht-ofdma-downlink {
      type boolean;
      default "true";
      status deprecated;
      description
        "Enables or disables Orthogonal Frequency Division Multiple Access (OFDMA) downlink transmissions for 802.11be (Wi-Fi 7), allowing multiple clients to receive data simultaneously on different frequency sub-carriers.";
    }
    leaf eht-ofdma-uplink {
      type boolean;
      default "true";
      status deprecated;
      description
        "Enables or disables Orthogonal Frequency Division Multiple Access (OFDMA) uplink transmissions for 802.11be (Wi-Fi 7), allowing multiple clients to transmit data simultaneously on different frequency sub-carriers.";
    }
    leaf eht-mumimo-downlink {
      type boolean;
      default "false";
      status deprecated;
      description
        "Enables or disables Multi-User Multiple Input Multiple Output (MU-MIMO) downlink transmissions for 802.11be (Wi-Fi 7), allowing the access point to send data to multiple clients simultaneously.";
    }
    leaf eht-mumimo-uplink {
      type boolean;
      default "false";
      status deprecated;
      description
        "Enables or disables Multi-User Multiple Input Multiple Output (MU-MIMO) uplink transmissions for 802.11be (Wi-Fi 7), allowing multiple clients to transmit data to the access point simultaneously.";
    }
    leaf eht-ofdma-multi-ru {
      type boolean;
      default "false";
      description
        "Enables or disables support for multiple Resource Units (RUs) in Orthogonal Frequency Division Multiple Access (OFDMA) for 802.11be (Wi-Fi 7), allowing more flexible allocation of frequency resources among clients.";
    }
  }

  container rf-cfg-data {
    description
      "This Model contains all the Radio-Frequency(rf)-profile related configurations";
    container multi-bssid-profiles {
      description
        "Container for configuration of multiple Multi-BSSID profiles used in wireless RF settings.";
      list multi-bssid-profile {
        key "profile-name";
        description
          "Configuration entry for a single Multi-BSSID profile, defining parameters for multiple BSSIDs on a wireless interface.";
        uses wireless-rf-cfg:multi-bssid-profile;
      }
    }
    container atf-policies {
      status obsolete;
      description
        "Container for configuring Air Time Fairness (ATF) policies, which manage and allocate wireless airtime among clients to optimize network performance.";
      list atf-policy {
        key "policy-id";
        unique "atfpolicy-name";
        description
          "A list of Air Time Fairness Policy objects";
        uses wireless-rf-cfg:st-atf-policy {
          refine "atfpolicy-name" {
            mandatory true;
          }
        }
      }
    }
    container rf-tags {
      description
        "Configuration related to named rf-tag";
      list rf-tag {
        key "tag-name";
        description
          "A list of configurations related to named rf-tag";
        uses wireless-rf-cfg:rf-tag;
      }
    }
    container rf-profiles {
      description
        "Configurations related to named Radio-Frequency(rf)-profile";
      list rf-profile {
        key "name";
        description
          "A list of configurations related to named Radio-Frequency(rf)-profile";
        uses wireless-rf-cfg:rfprofile;
      }
    }
    container rf-profile-default-entries {
      description
        "Configurations related to default Radio-Frequency(rf)-profile";
      list rf-profile-default-entry {
        key "band";
        unique "name";
        description
          "Configurations of default Radio-Frequency(rf)-profile";
        uses wireless-rf-cfg:rfprofile-default {
          refine "name" {
            mandatory true;
          }
        }
      }
    }
  }
}
