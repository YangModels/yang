module Cisco-IOS-XE-wireless-rogue-authz-rpc {
  yang-version 1.1;
  namespace "http://cisco.com/ns/yang/Cisco-IOS-XE-wireless-rogue-authz-rpc";
  prefix wireless-rogue-authz-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     Wireless Rogue Authz Remote Control Procedures.
     Copyright (c) 2024 by Cisco Systems, Inc.
     All rights reserved.";

  revision 2025-07-01 {
    description
      "Added import, export, & clear RPCs.
       Import RPCs for AP, Client, SSID, AKM, & Cipher.
       Export RPCs for SSID, AKM & Cipher.
       Clear RPCs for SSID, AKM & Cipher.";
    reference
      "1.1.0";
    cisco-semver:module-version "1.1.0";
  }
  revision 2025-03-01 {
    description
      "Initial revision";
    reference
      "1.0.0";
    cisco-semver:module-version "1.0.0";
  }

  grouping client-allow-list-export {
    description
      "Rogue Authz Client Allow list Export";
    leaf filename {
      type string {
        length "0..255";
      }
      mandatory true;
      description
        "Client Allow list export filename with csv extension";
    }
  }

  grouping ap-allow-list-export {
    description
      "Rogue Authz Access Point Allow list Export";
    leaf filename {
      type string {
        length "0..255";
      }
      mandatory true;
      description
        "Access Point Allow list export filename with csv extension";
    }
  }

  grouping client-allow-list-import {
    description
      "Rogue Authz Client Allow list Import";
    leaf filename {
      type string {
        length "0..255";
      }
      mandatory true;
      description
        "Client Allow list filename with csv extension";
    }
    leaf checksum {
      type string {
        length "0..64";
      }
      mandatory true;
      description
        "SHA256 hash of Access Point Allow list file";
    }
  }

  grouping ap-allow-list-import {
    description
      "Rogue Authz Access Point Allow list Import";
    leaf filename {
      type string {
        length "0..255";
      }
      mandatory true;
      description
        "Access Point Allow list filename with csv extension";
    }
    leaf checksum {
      type string {
        length "0..64";
      }
      mandatory true;
      description
        "SHA256 hash of Access Point Allow list file";
    }
  }

  grouping cipher-allow-list-export {
    description
      "Rogue Authz Cipher Allow list Export";
    leaf filename {
      type string {
        length "0..255";
      }
      mandatory true;
      description
        "Cipher Allow list export filename with csv extension";
    }
  }

  grouping akm-allow-list-export {
    description
      "Rogue Authz AKM Allow list Export";
    leaf filename {
      type string {
        length "0..255";
      }
      mandatory true;
      description
        "AKM Allow list export filename with csv extension";
    }
  }

  grouping ssid-allow-list-export {
    description
      "Rogue Authz SSID Allow list Export";
    leaf filename {
      type string {
        length "0..255";
      }
      mandatory true;
      description
        "SSID Allow list export filename with csv extension";
    }
  }

  grouping cipher-allow-list-import {
    description
      "Rogue Authz Cipher Allow list Import";
    leaf filename {
      type string {
        length "0..255";
      }
      mandatory true;
      description
        "Cipher Allow list filename with csv extension";
    }
    leaf checksum {
      type string {
        length "0..64";
      }
      mandatory true;
      description
        "SHA256 hash of Cipher Allow list file";
    }
  }

  grouping akm-allow-list-import {
    description
      "Rogue Authz AKM Allow list Import";
    leaf filename {
      type string {
        length "0..255";
      }
      mandatory true;
      description
        "AKM Allow list filename with csv extension";
    }
    leaf checksum {
      type string {
        length "0..64";
      }
      mandatory true;
      description
        "SHA256 hash of AKM Allow list file";
    }
  }

  grouping ssid-allow-list-import {
    description
      "Rogue Authz SSID Allow list Import";
    leaf filename {
      type string {
        length "0..255";
      }
      mandatory true;
      description
        "SSID Allow list filename with csv extension";
    }
    leaf checksum {
      type string {
        length "0..64";
      }
      mandatory true;
      description
        "SHA256 hash of SSID Allow list file";
    }
  }

  rpc clear-client-allow-list {
    description
      "Rogue Authz Clear Client Allow list entries Remote Control Procedure";
  }

  rpc clear-ap-allow-list {
    description
      "Rogue Authz Clear Access Point Allow list entries Remote Control Procedure";
  }

  rpc client-allow-list-export {
    description
      "Rogue Authz Export Client Allow list Remote Control Procedure";
    input {
      uses wireless-rogue-authz-rpc:client-allow-list-export;
    }
  }

  rpc ap-allow-list-export {
    description
      "Rogue Authz Export Access Point Allow list Remote Control Procedure";
    input {
      uses wireless-rogue-authz-rpc:ap-allow-list-export;
    }
  }

  rpc client-allow-list-import {
    description
      "Rogue Authz Import client allow list.";
    input {
      uses wireless-rogue-authz-rpc:client-allow-list-import;
    }
  }

  rpc ap-allow-list-import {
    description
      "Rogue Authz Import AP allow list.";
    input {
      uses wireless-rogue-authz-rpc:ap-allow-list-import;
    }
  }

  rpc clear-cipher-allow-list {
    description
      "Rogue Authz Clear cipher allow list.";
  }

  rpc clear-akm-allow-list {
    description
      "Rogue Authz Clear AKM allow list.";
  }

  rpc clear-ssid-allow-list {
    description
      "Rogue Authz Clear SSID allow list.";
  }

  rpc cipher-allow-list-export {
    description
      "Rogue Authz Export cipher allow list.";
    input {
      uses wireless-rogue-authz-rpc:cipher-allow-list-export;
    }
  }

  rpc akm-allow-list-export {
    description
      "Rogue Authz Export AKM allow list.";
    input {
      uses wireless-rogue-authz-rpc:akm-allow-list-export;
    }
  }

  rpc ssid-allow-list-export {
    description
      "Rogue Authz Export SSID allow list.";
    input {
      uses wireless-rogue-authz-rpc:ssid-allow-list-export;
    }
  }

  rpc cipher-allow-list-import {
    description
      "Rogue Authz Import cipher allow list.";
    input {
      uses wireless-rogue-authz-rpc:cipher-allow-list-import;
    }
  }

  rpc akm-allow-list-import {
    description
      "Rogue Authz Import AKM allow list.";
    input {
      uses wireless-rogue-authz-rpc:akm-allow-list-import;
    }
  }

  rpc ssid-allow-list-import {
    description
      "Rogue Authz Import SSID allow list.";
    input {
      uses wireless-rogue-authz-rpc:ssid-allow-list-import;
    }
  }
}
