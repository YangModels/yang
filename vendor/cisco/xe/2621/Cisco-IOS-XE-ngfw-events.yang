module Cisco-IOS-XE-ngfw-events {
  yang-version 1.1;
  namespace "http://cisco.com/ns/yang/Cisco-IOS-XE-ngfw-events";
  prefix ngfw-ios-xe-events;

  import Cisco-IOS-XE-common-types {
    prefix common-types-ios-xe;
  }
  import Cisco-IOS-XE-ios-common-oper {
    prefix ios-common-ios-xe-oper;
  }
  import Cisco-IOS-XE-ngfw-common-oper {
    prefix ngfw-common-ios-xe-oper;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for NGFW events operational data.
     Copyright (c) 2024-2026 by Cisco Systems, Inc.
     All rights reserved.";

  revision 2026-08-01 {
    description
      "- Added NGFW IPS alert notifications.
       - Added NGFW version notification.
       - Added NGFW update notification
       - Added NGFW FQDN destination status change alarm notification.";
    reference
      "1.1.0";
    cisco-semver:module-version "1.1.0";
  }
  revision 2025-03-01 {
    description
      "Initial revision";
    reference
      "1.0.0";
    cisco-semver:module-version "1.0.0";
  }

  typedef ngfw-event-type {
    type enumeration {
      enum ngfw-policy-error {
        value 0;
        description
          "NGFW FW Policy error.";
      }
      enum ngfw-object-error {
        value 1;
        description
          "NGFW Policy Object error.";
      }
      enum ngfw-general-error {
        value 2;
        description
          "NGFW general error.";
      }
    }
    description
      "NGFW Event type";
  }

  typedef ngfw-event-err-reason {
    type enumeration {
      enum ngfw-fw-db-error {
        value 0;
        description
          "NGFW FW DB error.";
      }
      enum ngfw-fw-memory-error {
        value 1;
        description
          "NGFW FW Memory error.";
      }
      enum ngfw-fw-config-error {
        value 2;
        description
          "NGFW FW Config error.";
      }
      enum ngfw-fw-classif-error {
        value 3;
        description
          "NGFW FW Classification error.";
      }
      enum ngfw-fw-internal-error {
        value 4;
        description
          "NGFW FW Internal error.";
      }
      enum ngfw-fw-general-error {
        value 5;
        description
          "NGFW FW general error.";
      }
    }
    description
      "NGFW event error reason";
  }

  typedef ngfw-ips-alert-action-val {
    type enumeration {
      enum ngfw-action-unknown {
        value 0;
        description
          "Next-Generation Firewall (NGFW) Intrusion Prevention System (IPS) alert action is unknown";
      }
      enum ngfw-action-alert {
        value 1;
        description
          "Next-Generation Firewall (NGFW) Intrusion Prevention System (IPS) alert action generated an alert";
      }
      enum ngfw-action-drop {
        value 2;
        description
          "Next-Generation Firewall (NGFW) Intrusion Prevention System (IPS) alert action resulted in a drop";
      }
      enum ngfw-action-wdrop {
        value 3;
        description
          "Next-Generation Firewall (NGFW) Intrusion Prevention System (IPS) alert action would have resulted in a drop if running in IPS mode";
      }
    }
    description
      "Next-Generation Firewall (NGFW) Intrusion Prevention System (IPS) alert action";
  }

  typedef ngfw-ips-alert-classification-val {
    type enumeration {
      enum ngfw-class-none {
        value 0;
        description
          "Next-Generation Firewall (NGFW) Intrusion Prevention System (IPS) alert classification is not set";
      }
      enum ngfw-class-not-susp {
        value 1;
        description
          "Next-Generation Firewall (NGFW) Intrusion Prevention System (IPS) alert classification is not suspicious traffic";
      }
      enum ngfw-class-unknown {
        value 2;
        description
          "Next-Generation Firewall (NGFW) Intrusion Prevention System (IPS) alert classification is unknown traffic";
      }
      enum ngfw-class-bad-unknown {
        value 3;
        description
          "Next-Generation Firewall (NGFW) Intrusion Prevention System (IPS) alert classification is potentially bad traffic";
      }
      enum ngfw-class-attempt-recon {
        value 4;
        description
          "Next-Generation Firewall (NGFW) Intrusion Prevention System (IPS) alert classification is attempted information leak";
      }
      enum ngfw-class-succ-recon-ltd {
        value 5;
        description
          "Next-Generation Firewall (NGFW) Intrusion Prevention System (IPS) alert classification is information leak";
      }
      enum ngfw-class-succ-recon-lsc {
        value 6;
        description
          "Next-Generation Firewall (NGFW) Intrusion Prevention System (IPS) alert classification is large scale information leak";
      }
      enum ngfw-class-attempt-dos {
        value 7;
        description
          "Next-Generation Firewall (NGFW) Intrusion Prevention System (IPS) alert classification is attempted denial of service";
      }
      enum ngfw-class-succ-dos {
        value 8;
        description
          "Next-Generation Firewall (NGFW) Intrusion Prevention System (IPS) alert classification is denial of service";
      }
      enum ngfw-class-attempt-user {
        value 9;
        description
          "Next-Generation Firewall (NGFW) Intrusion Prevention System (IPS) alert classification is attempted user privilege gain";
      }
      enum ngfw-class-unsucc-user {
        value 10;
        description
          "Next-Generation Firewall (NGFW) Intrusion Prevention System (IPS) alert classification is unsuccessful user privilege gain";
      }
      enum ngfw-class-succ-user {
        value 11;
        description
          "Next-Generation Firewall (NGFW) Intrusion Prevention System (IPS) alert classification is successful user privilege gain";
      }
      enum ngfw-class-attempt-admin {
        value 12;
        description
          "Next-Generation Firewall (NGFW) Intrusion Prevention System (IPS) alert classification is attempted administrator privilege gain";
      }
      enum ngfw-class-succ-admin {
        value 13;
        description
          "Next-Generation Firewall (NGFW) Intrusion Prevention System (IPS) alert classification is successful administrator privilege gain";
      }
      enum ngfw-class-rpc-portmap-dec {
        value 14;
        description
          "Next-Generation Firewall (NGFW) Intrusion Prevention System (IPS) alert classification is decode of an RPC query";
      }
      enum ngfw-class-shellcd-det {
        value 15;
        description
          "Next-Generation Firewall (NGFW) Intrusion Prevention System (IPS) alert classification is executable code was detected";
      }
      enum ngfw-class-string-det {
        value 16;
        description
          "Next-Generation Firewall (NGFW) Intrusion Prevention System (IPS) alert classification is a suspicious string was detected";
      }
      enum ngfw-class-susp-fname-det {
        value 17;
        description
          "Next-Generation Firewall (NGFW) Intrusion Prevention System (IPS) alert classification is a suspicious filename was detected";
      }
      enum ngfw-class-susp-login {
        value 18;
        description
          "Next-Generation Firewall (NGFW) Intrusion Prevention System (IPS) alert classification is an attempted login using a suspicious username was detected";
      }
      enum ngfw-class-sys-call-det {
        value 19;
        description
          "Next-Generation Firewall (NGFW) Intrusion Prevention System (IPS) alert classification is a system call was detected";
      }
      enum ngfw-class-tcp-conn {
        value 20;
        description
          "Next-Generation Firewall (NGFW) Intrusion Prevention System (IPS) alert classification is a TCP connection was detected";
      }
      enum ngfw-class-trojan-act {
        value 21;
        description
          "Next-Generation Firewall (NGFW) Intrusion Prevention System (IPS) alert classification is a network trojan was detected";
      }
      enum ngfw-class-unsl-cl-pconn {
        value 22;
        description
          "Next-Generation Firewall (NGFW) Intrusion Prevention System (IPS) alert classification is a client was using an unusual port";
      }
      enum ngfw-class-nw-scan {
        value 23;
        description
          "Next-Generation Firewall (NGFW) Intrusion Prevention System (IPS) alert classification is detection of a network scan";
      }
      enum ngfw-class-dos {
        value 24;
        description
          "Next-Generation Firewall (NGFW) Intrusion Prevention System (IPS) alert classification is detection of a denial of service attack";
      }
      enum ngfw-class-non-std-protoc {
        value 25;
        description
          "Next-Generation Firewall (NGFW) Intrusion Prevention System (IPS) alert classification is detection of a non-standard protocol or event";
      }
      enum ngfw-class-protoc-cmd-dec {
        value 26;
        description
          "Next-Generation Firewall (NGFW) Intrusion Prevention System (IPS) alert classification is generic protocol command decode";
      }
      enum ngfw-class-webapp-act {
        value 27;
        description
          "Next-Generation Firewall (NGFW) Intrusion Prevention System (IPS) alert classification is access to a potentially vulnerable web application";
      }
      enum ngfw-class-web-app-attack {
        value 28;
        description
          "Next-Generation Firewall (NGFW) Intrusion Prevention System (IPS) alert classification is web application attack";
      }
      enum ngfw-class-misc-act {
        value 29;
        description
          "Next-Generation Firewall (NGFW) Intrusion Prevention System (IPS) alert classification is miscellaneous activity";
      }
      enum ngfw-class-misc-attack {
        value 30;
        description
          "Next-Generation Firewall (NGFW) Intrusion Prevention System (IPS) alert classification is miscellaneous attack";
      }
      enum ngfw-class-icmp-event {
        value 31;
        description
          "Next-Generation Firewall (NGFW) Intrusion Prevention System (IPS) alert classification is generic ICMP event";
      }
      enum ngfw-class-inapp-content {
        value 32;
        description
          "Next-Generation Firewall (NGFW) Intrusion Prevention System (IPS) alert classification is inappropriate content was detected";
      }
      enum ngfw-class-pol-viol {
        value 33;
        description
          "Next-Generation Firewall (NGFW) Intrusion Prevention System (IPS) alert classification is potential corporate privacy violation";
      }
      enum ngfw-class-def-log-attempt {
        value 34;
        description
          "Next-Generation Firewall (NGFW) Intrusion Prevention System (IPS) alert classification is attempt to login by a default username and password";
      }
      enum ngfw-class-sdf {
        value 35;
        description
          "Next-Generation Firewall (NGFW) Intrusion Prevention System (IPS) alert classification is sensitive data";
      }
      enum ngfw-class-file-format {
        value 36;
        description
          "Next-Generation Firewall (NGFW) Intrusion Prevention System (IPS) alert classification is known malicious file or file based exploit";
      }
      enum ngfw-class-malware-cnc {
        value 37;
        description
          "Next-Generation Firewall (NGFW) Intrusion Prevention System (IPS) alert classification is known malware command and control traffic";
      }
      enum ngfw-class-cl-side-exploit {
        value 38;
        description
          "Next-Generation Firewall (NGFW) Intrusion Prevention System (IPS) alert classification is known client side exploit attempt";
      }
    }
    description
      "Next-Generation Firewall (NGFW) Intrusion Prevention System (IPS) alert classification";
  }

  typedef ngfw-ips-alert-priority-val {
    type enumeration {
      enum ngfw-pr-unknown {
        value 0;
        description
          "Next-Generation Firewall (NGFW) Intrusion Prevention System (IPS) alert priority is unknown";
      }
      enum ngfw-pr-emerg {
        value 1;
        description
          "Next-Generation Firewall (NGFW) Intrusion Prevention System (IPS) alert priority is emergency";
      }
      enum ngfw-pr-alert {
        value 2;
        description
          "Next-Generation Firewall (NGFW) Intrusion Prevention System (IPS) alert priority is alert";
      }
      enum ngfw-pr-crit {
        value 3;
        description
          "Next-Generation Firewall (NGFW) Intrusion Prevention System (IPS) alert priority is critical";
      }
      enum ngfw-pr-error {
        value 4;
        description
          "Next-Generation Firewall (NGFW) Intrusion Prevention System (IPS) alert priority is error";
      }
      enum ngfw-pr-warn {
        value 5;
        description
          "Next-Generation Firewall (NGFW) Intrusion Prevention System (IPS) alert priority is warning";
      }
      enum ngfw-pr-notice {
        value 6;
        description
          "Next-Generation Firewall (NGFW) Intrusion Prevention System (IPS) alert priority is notice";
      }
      enum ngfw-pr-info {
        value 7;
        description
          "Next-Generation Firewall (NGFW) Intrusion Prevention System (IPS) alert priority is info";
      }
      enum ngfw-pr-debug {
        value 8;
        description
          "Next-Generation Firewall (NGFW) Intrusion Prevention System (IPS) alert priority is debug";
      }
    }
    description
      "Next-Generation Firewall (NGFW) Intrusion Prevention System (IPS) alert priority";
  }

  typedef fqdn-destination-state {
    type enumeration {
      enum ngfw-fqdn-state-rslvd {
        value 0;
        description
          "The destination FQDN is resolved.";
      }
      enum ngfw-fqdn-state-unrslvd {
        value 1;
        description
          "The destination FQDN is unresolved.";
      }
    }
    description
      "Resolution state of the destination FQDN.";
  }

  typedef fqdn-destination-error-reason {
    type enumeration {
      enum ngfw-fqdn-rc-none {
        value 0;
        description
          "No error reason is present.";
      }
      enum ngfw-fqdn-rc-not-reg {
        value 1;
        description
          "The destination FQDN is not registered with DNS.";
      }
      enum ngfw-fqdn-rc-no-addr-rec {
        value 2;
        description
          "No address records were returned for the destination FQDN.";
      }
      enum ngfw-fqdn-rc-socket {
        value 3;
        description
          "The DNS lookup failed because of a socket error.";
      }
      enum ngfw-fqdn-rc-mem {
        value 4;
        description
          "The DNS lookup failed because of a memory allocation error.";
      }
      enum ngfw-fqdn-rc-lookup-off {
        value 5;
        description
          "The DNS lookup was disabled before completion.";
      }
      enum ngfw-fqdn-rc-other-dns {
        value 6;
        description
          "The DNS lookup failed for an implementation-specific reason.";
      }
      enum ngfw-fqdn-rc-format {
        value 7;
        description
          "The DNS server reported a format error.";
      }
      enum ngfw-fqdn-rc-server-fail {
        value 8;
        description
          "The DNS server reported a server failure.";
      }
      enum ngfw-fqdn-rc-name {
        value 9;
        description
          "The DNS server reported a name error for the destination FQDN.";
      }
      enum ngfw-fqdn-rc-not-impl {
        value 10;
        description
          "The DNS server reported that the request was not implemented.";
      }
      enum ngfw-fqdn-rc-refused {
        value 11;
        description
          "The DNS server refused the request.";
      }
      enum ngfw-fqdn-rc-res-fail {
        value 12;
        description
          "Resolution of the destination FQDN failed without a more specific DNS error.";
      }
      enum ngfw-fqdn-rc-res-pend {
        value 13;
        description
          "Resolution of the destination FQDN is still pending.";
      }
      enum ngfw-fqdn-rc-int {
        value 14;
        description
          "An internal error prevented the destination FQDN resolution state from being determined.";
      }
      enum ngfw-fqdn-rc-unknown {
        value 15;
        description
          "The destination FQDN resolution failed for an unknown reason.";
      }
    }
    description
      "Reason associated with the destination FQDN resolution state.";
  }

  grouping ngfw-notif {
    description
      "NGFW configuration event";
    leaf severity-level {
      type ios-common-ios-xe-oper:notification-severity;
      description
        "Event severity";
    }
    leaf host-name {
      type string;
      description
        "NGFW Event hostname";
    }
    leaf zp-name {
      type string;
      description
        "NGFW Event zone-pair name";
    }
    leaf policy-name {
      type string;
      description
        "NGFW Event policy-map name";
    }
    leaf event-type {
      type ngfw-ios-xe-events:ngfw-event-type;
      description
        "NGFW Event Type";
    }
    leaf err-reason {
      type ngfw-ios-xe-events:ngfw-event-err-reason;
      description
        "NGFW Event description";
    }
  }

  grouping ngfw-ips-alert {
    description
      "Next-Generation Firewall (NGFW) Intrusion Prevention System (IPS) alert";
    leaf severity-level {
      type ios-common-ios-xe-oper:notification-severity;
      description
        "Event severity";
    }
    leaf host-name {
      type string;
      description
        "Host name";
    }
    leaf system-ip {
      type inet:ip-address;
      description
        "System IP address";
    }
    leaf timestamp {
      type yang:date-and-time;
      description
        "Alert timestamp";
    }
    leaf action {
      type ngfw-ios-xe-events:ngfw-ips-alert-action-val;
      description
        "Alert action";
    }
    leaf sid {
      type uint32;
      description
        "Alert signature ID";
    }
    leaf gid {
      type uint32;
      description
        "Alert generator ID";
    }
    leaf rev {
      type uint32;
      description
        "Alert signature revision ID";
    }
    leaf class {
      type ngfw-ios-xe-events:ngfw-ips-alert-classification-val;
      description
        "Alert classification ID";
    }
    leaf msg {
      type string;
      description
        "Alert message";
    }
    leaf priority {
      type ngfw-ios-xe-events:ngfw-ips-alert-priority-val;
      description
        "Alert priority";
    }
    leaf src-ip {
      type inet:ip-address;
      description
        "Alert source IP";
    }
    leaf dst-ip {
      type inet:ip-address;
      description
        "Alert destination IP";
    }
    leaf src-port {
      type uint16;
      description
        "Alert source port";
    }
    leaf dst-port {
      type uint16;
      description
        "Alert destination port";
    }
    leaf proto {
      type uint8;
      description
        "Alert IP protocol number (IANA assigned, e.g. 6=TCP, 17=UDP, 1=ICMP)";
    }
    leaf policy-name {
      type string;
      description
        "Alert policy name";
    }
    leaf src-user {
      type string;
      description
        "Alert source user name";
    }
    leaf dst-user {
      type string;
      description
        "Alert destination user name";
    }
  }

  grouping ngfw-ver-notif {
    description
      "Next-Generation Firewall (NGFW) version notification";
    leaf severity-level {
      type ios-common-ios-xe-oper:notification-severity;
      description
        "Event severity";
    }
    leaf host-name {
      type string;
      description
        "Host name";
    }
    leaf system-ip {
      type inet:ip-address;
      description
        "System IP address";
    }
    leaf supported-regex {
      type string;
      description
        "Next-Generation Firewall (NGFW) version regular expression - describes version support";
    }
    leaf current-ver {
      type string;
      description
        "Next-Generation Firewall (NGFW) version currently active";
    }
    leaf supported {
      type boolean;
      description
        "Indicates whether the current NGFW version is compatible with the supported version regular expression; true if compatible, false otherwise.";
    }
  }

  grouping ngfw-update {
    description
      "Next-Generation Firewall (NGFW) update";
    leaf severity-level {
      type ios-common-ios-xe-oper:notification-severity;
      description
        "Event severity";
    }
    leaf host-name {
      type string;
      description
        "Host name";
    }
    leaf system-ip {
      type inet:ip-address;
      description
        "System IP address";
    }
    leaf type {
      type ngfw-common-ios-xe-oper:ngfw-update-type-val;
      description
        "Type of NGFW package update, indicating whether the update is an LSP or VDB package.";
    }
    leaf timestamp {
      type yang:date-and-time;
      description
        "Update timestamp";
    }
    leaf version {
      type string;
      description
        "Version of the NGFW package at the time of this update notification.";
    }
    leaf update-status {
      type ngfw-common-ios-xe-oper:ngfw-update-status-val;
      description
        "Outcome status of the NGFW package update, indicating whether the update succeeded, failed, or was not required.";
    }
    leaf reason {
      type string;
      description
        "Update failure reason";
    }
  }

  grouping hsl-fqdn-dst-status-change {
    description
      "NGFW destination FQDN resolution state transition alarm notification.";
    leaf severity-level {
      type ios-common-ios-xe-oper:notification-severity;
      description
        "Severity level of the NGFW FQDN destination status change alarm.";
    }
    leaf host-name {
      type string;
      description
        "Host name of the system reporting the alarm.";
    }
    leaf system-ip {
      type inet:ip-address;
      description
        "IP address of the system reporting the alarm.";
    }
    leaf fqdn {
      type string;
      description
        "Fully Qualified Domain Name (FQDN) of the destination whose resolution state changed.";
    }
    leaf ni-type {
      type common-types-ios-xe:net-inst-type;
      description
        "Network instance type. Differentiates between the default routing instance and VRFs.";
    }
    leaf ni-name {
      type string;
      description
        "Network instance name. If the type is net-inst-default, use the name default.";
    }
    leaf new-state {
      type ngfw-ios-xe-events:fqdn-destination-state;
      description
        "New resolution state of the destination FQDN.";
    }
    leaf dst-ip {
      type inet:ip-address;
      description
        "IP address resolved for the destination FQDN, when available.";
    }
    leaf dst-port {
      type uint16;
      description
        "Destination port associated with the resolved destination IP address.";
    }
    leaf error-reason {
      type ngfw-ios-xe-events:fqdn-destination-error-reason;
      description
        "Structured reason describing why the destination is unresolved; set to no-error when the destination is resolved.";
    }
  }

  notification hsl-fqdn-dst-status-change {
    description
      "NGFW FQDN destination status change alarm notification.";
    uses ngfw-ios-xe-events:hsl-fqdn-dst-status-change;
  }

  notification ngfw-event {
    description
      "NGFW Error  Notification";
    uses ngfw-ios-xe-events:ngfw-notif;
  }

  notification ngfw-ips-alert {
    description
      "Next-Generation Firewall (NGFW) Intrusion Prevention System (IPS) alert notification";
    uses ngfw-ios-xe-events:ngfw-ips-alert;
  }

  notification ngfw-ver-notif {
    description
      "Next-Generation Firewall (NGFW) version notification";
    uses ngfw-ios-xe-events:ngfw-ver-notif;
  }

  notification ngfw-update {
    description
      "Next-Generation Firewall (NGFW) update notification";
    uses ngfw-ios-xe-events:ngfw-update;
  }
}
