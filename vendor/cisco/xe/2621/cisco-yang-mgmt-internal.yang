module cisco-yang-mgmt-internal {
  yang-version 1.1;
  namespace "http://cisco.com/ns/yang/cisco-yang-mgmt-internal";
  prefix cisco-yang-mgmt-internal;

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of internal definitions
     for Cisco IOS-XE YANG infra management.
     Copyright (c) 2025 by Cisco Systems, Inc.
     All rights reserved.";

  revision 2026-02-01 {
    description
      "Initial Version.";
  }
}
