module Cisco-IOS-XE-bridge {
  yang-version 1.1;
  namespace "http://cisco.com/ns/yang/Cisco-IOS-XE-bridge";
  prefix ios-bridge;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE PnP Yang model.
     Copyright (c) 2020-2021 by Cisco Systems, Inc.
     All rights reserved.";

  revision 2022-11-01 {
    description
      "- Update yang-version to 1.1";
    cisco-semver:module-version "1.1.0";
  }
  revision 2021-07-01 {
    description
      "Added yang support for bridge routing commands";
    cisco-semver:module-version "1.0.0";
  }

  grouping config-bridge {
    container bridge {
      description
        "Bridge Group.";
      leaf irb {
        description
          "Integrated routing and bridging";
        must 'not (../crb)' {
          error-message
            "CRB(Concurrent Routing and Bridging) is already configured!
             Please deconfigure CRB first!";
        }
        type empty;
      }
      leaf crb {
        description
          "Concurrent routing and bridging";
        must 'not (../irb)' {
          error-message
            "IRB(Integrated Routing and Bridging) is already configured!
             Please deconfigure IRB first!";
        }
        type empty;
      }
    }
  }

  augment "/ios:native" {
    uses config-bridge;
  }
}
