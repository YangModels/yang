module Cisco-IOS-XE-crypto-pki-events {
  yang-version 1.1;
  namespace "http://cisco.com/ns/yang/Cisco-IOS-XE-crypto-pki-events";
  prefix crypto-pki-ios-xe-events;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for crypto PKI events data.
     Copyright (c) 2019-2020, 2022-2023 by Cisco Systems, Inc.
     All rights reserved.";

  revision 2023-11-01 {
    description
      "- Added new event type for certificate authentication failure";
    reference
      "2.3.0";
    cisco-semver:module-version "2.3.0";
  }
  revision 2022-11-01 {
    description
      "Update yang-version to 1.1";
    reference
      "2.2.0";
    cisco-semver:module-version "2.2.0";
  }
  revision 2020-11-01 {
    description
      "- Added new notification for EEM events";
    reference
      "2.1.0";
    cisco-semver:module-version "2.1.0";
  }
  revision 2020-07-01 {
    description
      "- Remove unused empty container crypto-pki-events";
    reference
      "2.0.0";
    cisco-semver:module-version "2.0.0";
  }
  revision 2019-11-01 {
    description
      "Initial revision";
    reference
      "1.0.0";
    cisco-semver:module-version "1.0.0";
  }

  typedef pki-notification-severity {
    type enumeration {
      enum pki-notification-critical {
        value 0;
        description
          "Critical severity notification";
      }
      enum pki-notification-major {
        value 1;
        description
          "Major severity notification";
      }
      enum pki-notification-minor {
        value 2;
        description
          "Minor severity notification";
      }
    }
    description
      "PKI Notification Severity";
  }

  typedef pki-event-type {
    type enumeration {
      enum pki-certificate-install {
        value 0;
        description
          "Certificate installation notification";
      }
      enum pki-certificate-delete {
        value 1;
        description
          "Certificate deletion notification";
      }
      enum pki-certificate-scep-granted {
        value 2;
        description
          "Certificate granted notification";
      }
      enum pki-certificate-scep-rejected {
        value 3;
        description
          "Certificate rejected notification";
      }
      enum pki-certificate-scep-pending {
        value 4;
        description
          "Certificate pending notification";
      }
      enum pki-certificate-failure {
        value 5;
        description
          "Certificate authentication failed";
      }
    }
    description
      "PKI Event Type";
  }

  grouping pki-certificate-expiry-update {
    description
      "Certificate expiry update";
    leaf trust-point {
      type string;
      description
        "Trustpoint name";
    }
    leaf expires-at {
      type yang:date-and-time;
      description
        "Absolute time of expiry";
    }
    leaf is-ca-cert {
      type boolean;
      description
        "Set to true if expiring certificate is a CA certificate";
    }
    leaf subject-name {
      type string;
      description
        "Subject name of expiring certificate";
    }
    leaf issuer-name {
      type string;
      description
        "Issuer name of expiring certificate";
    }
    leaf serial-number {
      type string;
      description
        "Serial number of the expiring certificate";
    }
    leaf severity {
      type crypto-pki-ios-xe-events:pki-notification-severity;
      description
        "Notification Severity";
    }
    leaf host-name {
      type string;
      description
        "Host Name";
    }
  }

  grouping pki-certificate-event-update {
    description
      "Certificate event update";
    leaf severity {
      type crypto-pki-ios-xe-events:pki-notification-severity;
      description
        "Notification Severity";
    }
    leaf host-name {
      type string;
      description
        "Host Name";
    }
    leaf trust-point {
      type string;
      description
        "Trustpoint name";
    }
    leaf event-type {
      type crypto-pki-ios-xe-events:pki-event-type;
      description
        "Event update type";
    }
    leaf valid-from {
      type yang:date-and-time;
      description
        "Certificate validity start time";
    }
    leaf expires-at {
      type yang:date-and-time;
      description
        "Absolute time of expiry";
    }
    leaf is-ca-cert {
      type boolean;
      description
        "Set to true if the certificate is a CA certificate";
    }
    leaf subject-name {
      type string;
      description
        "Subject name of the certificate";
    }
    leaf issuer-name {
      type string;
      description
        "Issuer name of the certificate";
    }
    leaf serial-number {
      type string;
      description
        "Serial number of the certificate";
    }
  }

  notification pki-certificate-expiry {
    description
      "Certificate expiry update";
    uses crypto-pki-ios-xe-events:pki-certificate-expiry-update;
  }

  notification pki-certificate-event {
    description
      "Certificate event update";
    uses crypto-pki-ios-xe-events:pki-certificate-event-update;
  }
}
