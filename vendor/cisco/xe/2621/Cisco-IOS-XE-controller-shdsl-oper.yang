module Cisco-IOS-XE-controller-shdsl-oper {
  yang-version 1.1;
  namespace "http://cisco.com/ns/yang/Cisco-IOS-XE-controller-shdsl-oper";
  prefix shdsl-ios-xe-oper;

  import Cisco-IOS-XE-controller-shdsl-common {
    prefix shdsl-ios-xe-common;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for monitoring controller SHDSL operational information.
     Copyright (c) 2019, 2026 by Cisco Systems, Inc.
     All rights reserved.";

  revision 2026-08-01 {
    description
      "Updated descriptions of several model elements to clarify their meaning and purpose";
    reference
      "1.1.1";
    cisco-semver:module-version "1.1.1";
  }
  revision 2022-11-01 {
    description
      "Update yang-version to 1.1";
    reference
      "1.1.0";
    cisco-semver:module-version "1.1.0";
  }
  revision 2020-03-01 {
    description
      "Initial revision";
    reference
      "1.0.0";
    cisco-semver:module-version "1.0.0";
  }

  grouping shdsl-controller-info {
    description
      "SHDSL Controller Information";
    leaf state {
      type shdsl-ios-xe-common:controller-state;
      description
        "Current operational state of the SHDSL controller.";
    }
    leaf hardware {
      type string;
      description
        "Hardware model or identifier for the SHDSL controller.";
    }
    leaf efm-capabilities {
      type string;
      description
        "Indicates the Ethernet First Mile capabilities supported by the SHDSL PHY,
         formatted as 'EFM: 2-wire, EFM-Bond, Annex A, Annex B, Annex F, Annex G' - EFM mode supports
         single-pair operation (2-wire), Ethernet bonding across pairs (EFM-Bond),
         and multiple SHDSL annex variants (A/B/F/G).";
    }
    leaf atm-capabilities {
      type string;
      description
        "Indicates the ATM capabilities supported by the SHDSL PHY,
         formatted as 'ATM: 2-wire, Mpair, Annex A, Annex B, Annex F, Annex G' - ATM mode supports
         single-pair operation (2-wire), multi-pair operation (Mpair),
         and multiple SHDSL annex variants (A/B/F/G).";
    }
    leaf termination {
      type shdsl-ios-xe-common:term-type;
      description
        "Type of termination configured for the SHDSL controller (e.g., CPE or
         CO).";
    }
    leaf configured-mode {
      type shdsl-ios-xe-common:mode-type;
      description
        "Operational mode configured for the SHDSL controller.";
    }
    leaf vendor {
      type string;
      description
        "Vendor name of the SHDSL controller hardware.";
    }
    leaf chipset {
      type string;
      description
        "Chipset model or identifier used in the SHDSL controller.";
    }
    leaf phy-source {
      type string;
      description
        "Specifies the physical layer (PHY) source used by the SHDSL
         controller, indicating the origin or type of PHY interface in use.";
    }
    leaf phy-firmware-files {
      type string;
      description
        "Specifies PHY firmware file used by the SHDSL controller, Possible values are,
         <empty> - This field value is empty when the embedded system PHY firmware is in use,
         'shdsl_IDC_DFE.pkg' - When the default firmware package is in use,
         <user-provided firmware package path> - The full user-provided firmware package path,
               for example 'bootflash:images/shdsl_custom.pkg', when a downloaded firmware package is in use.";
    }
    leaf idc-firmware-version {
      type string;
      description
        "Integrated Device Control Firmware version";
    }
    leaf dfe-firmware-version {
      type string;
      description
        "Digital Front End Firmware Version";
    }
    list groups-conf {
      description
        "Configuration details for SHDSL groups associated with the controller,
         including group parameters and settings.";
      uses shdsl-ios-xe-common:shdsl-configured-group;
    }
  }

  container shdsl-oper-data {
    config false;
    description
      "SHDSL controller information";
    list shdsl-info {
      key "slot-num subslot-num";
      description
        "SHDSL controller information";
      uses shdsl-ios-xe-oper:shdsl-controller-info;
      uses shdsl-ios-xe-common:shdsl-slot-info-key;
    }
  }
}
