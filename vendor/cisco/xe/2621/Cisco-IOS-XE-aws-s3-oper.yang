module Cisco-IOS-XE-aws-s3-oper {
  yang-version 1.1;
  namespace "http://cisco.com/ns/yang/Cisco-IOS-XE-aws-s3-oper";
  prefix aws-s3-oper;

  import Cisco-IOS-XE-aws-common-oper {
    prefix aws-common-oper;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for AWS S3 operational data.
     Copyright (c) 2023-2026 by Cisco Systems, Inc.
     All rights reserved.";

  revision 2026-08-01 {
    description
      "Improved YANG descriptions for AWS S3 operational data.";
    reference
      "1.0.1";
    cisco-semver:module-version "1.0.1";
  }
  revision 2025-07-01 {
    description
      "Initial revision";
    reference
      "1.0.0";
    cisco-semver:module-version "1.0.0";
  }

  grouping aws-s3-mount-config {
    description
      "S3 bucket mount configuration data";
    leaf aws-s3-bucket-name {
      type string;
      description
        "S3 bucket name";
    }
    leaf aws-s3-mount-point {
      type string;
      description
        "S3 mount point";
    }
    leaf aws-s3-region {
      type string;
      description
        "AWS S3 region";
    }
  }

  grouping aws-s3-oper {
    description
      "AWS S3 operational data";
    leaf aws-s3-profile-name {
      type string;
      description
        "S3 profile name";
    }
    leaf aws-s3-profile-descr {
      type string;
      description
        "S3 profile description";
    }
    leaf aws-s3-pid {
      type uint32;
      description
        "AWS S3 process ID";
    }
    leaf mount-time {
      when "(../aws-s3-shutdown='false')";
      type yang:date-and-time;
      description
        "Mount time";
    }
    leaf aws-s3-shutdown {
      type boolean;
      description
        "Indicates whether the AWS S3 profile is administratively shut down (true) or active (false).";
    }
    leaf aws-s3-read-write {
      type boolean;
      description
        "Indicates whether the AWS S3 mount is in read-write mode (true) or read-only mode (false).";
    }
    leaf aws-s3-state {
      type aws-common-oper:aws-agent-state;
      description
        "AWS S3 profile state";
    }
    leaf aws-s3-vrf {
      type aws-common-oper:aws-vrf-name;
      description
        "AWS S3 VRF";
    }
    container aws-s3-mount-config {
      description
        "Contains configuration data for mounting an AWS S3 bucket, including bucket name, mount point, and region.";
      uses aws-s3-oper:aws-s3-mount-config;
    }
    container aws-s3-proxy-config {
      description
        "Contains configuration data for the proxy used to access AWS S3, including proxy URLs and ports.";
      uses aws-common-oper:aws-proxy-config;
    }
    leaf aws-s3-trace {
      type aws-common-oper:aws-agent-trace;
      description
        "S3 trace level";
    }
    leaf aws-s3-retry-count {
      type uint32;
      description
        "Specifies the number of times an AWS S3 operation will be retried in case of failure.";
    }
  }

  container aws-s3-oper-data {
    config false;
    description
      "Container for operational data related to AWS S3 profiles and their status on the device";
    list aws-oper-s3fs {
      key "aws-s3-profile-name";
      description
        "List of AWS S3 profile operational data entries, each representing the state and configuration of a mounted S3 profile.";
      uses aws-s3-oper:aws-s3-oper;
    }
  }
}
