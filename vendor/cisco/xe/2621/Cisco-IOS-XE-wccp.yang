module Cisco-IOS-XE-wccp {
  yang-version 1.1;
  namespace "http://cisco.com/ns/yang/Cisco-IOS-XE-wccp";
  prefix ios-wccp;

  import cisco-semver {
    prefix cisco-semver;
  }
  import ietf-inet-types {
    prefix inet;
  }
  import Cisco-IOS-XE-native {
    prefix ios;
  }
  import Cisco-IOS-XE-types {
    prefix ios-types;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Web Cache Communication Protocol (WCCP) Yang model.
     Copyright (c) 2016 by Cisco Systems, Inc.
     All rights reserved.";

  revision 2026-08-01 {
    description
      "- Added TwoHundredGigE and FourHundredGigE interface support";
    cisco-semver:module-version "3.1.0";
  }
  revision 2026-02-01 {
    description
      "- Added must constraint in clear-key to validate type 0,6 and 7 auth key";
    cisco-semver:module-version "3.0.0";
  }
  revision 2025-07-01 {
    description
      "- Added FiftyGigabitEthernet interface support";
    cisco-semver:module-version "2.2.0";
  }
  revision 2022-11-01 {
    description
      "- Update yang-version to 1.1";
    cisco-semver:module-version "2.1.0";
  }
  revision 2022-03-01 {
    description
      "Added leaf outbound-acl-check and variable-timers, list overlay-vrf";
    cisco-semver:module-version "2.0.0";
  }
  revision 2019-07-01 {
    description
      "Establish semantic version baseline";
    cisco-semver:module-version "1.0.0";
  }
  revision 2019-01-22 {
    description
      "Added leaf for App-hosting Gigabit Ethernet interface";
  }
  revision 2017-11-27 {
    description
      "Added Change 25GE name";
  }
  revision 2017-11-14 {
    description
      "Added 2, 5, 25, 40, 100GE interfaces";
  }
  revision 2017-02-07 {
    description
      "Initial revision";
  }

  grouping ip-wccp-group-address-grouping {
    leaf group-address {
      description
        "Set the multicast group";
      type inet:ipv4-address;
    }
    leaf group-list {
      description
        "Set the access-list used to permit group membership";
      type ios-types:exp-acl-type;
    }
    leaf mode {
      description
        "Set the service mode";
      type enumeration {
        enum closed;
        enum open;
      }
    }
    leaf redirect-list {
      description
        "Set the access-list used to permit redirection";
      type ios-types:exp-acl-type;
    }
    leaf snmp-disabled {
      description
        "Disable SNMP for WCCP GRE Tunnel";
      type empty;
    }
    container password {
      description
        "Set the authentication password";
      leaf encryption {
        type enumeration {
          enum 0;
          enum 7;
          enum 6;
        }
      }
      leaf clear-key {
        type string {
          length "1..33";
        }
        must '((not(../encryption) or ../encryption = 0) and string-length(.) <= 8) or (../encryption = 6 and string-length(.) <= 33) or (../encryption = 7 and string-length(.) <=18)' {
          error-message "Cleartext should not be greater than 8 characters, AES encrypted should not be greater than 33 characters, type 7 should not be greater than 18 characters";
        }
      }
    }
  }

  grouping ip-wccp-grouping {
    list wccp-list {
      key "id";
      leaf id {
        type uint8 {
          range "0..254";
        }
      }
      leaf service-list {
        description
          "Set the service-list used to set group properties";
        type string;
      }
      uses ip-wccp-group-address-grouping;
    }
    leaf source-interface {
      description
        "Set source interface for Router ID";
      type string;
    }
    container web-cache {
      description
        "Standard web caching service";
      presence "true";
      uses ip-wccp-group-address-grouping;
    }
  }

  grouping config-ip-wccp-grouping {
    container wccp {
      description
        "Web-Cache Coordination Protocol IPv4 Commands";
      uses ip-wccp-grouping;
      container check {
        description
          "Enable a WCCP check";
        container acl {
          description
            "Enable acl check";
          leaf outbound {
            description
              "Enable acl check on original outbound interface";
            type empty;
          }
        }
        container services {
          description
            "Enable services check";
          leaf all {
            description
              "Enable all services check for redirection";
            type empty;
          }
        }
      }
      leaf variable-timers {
        description
          "Enable support for variable timers";
        default "true";
        type boolean;
      }
      list overlay-vrf {
        description
          "Overlay VRF name";
        key "name";
        leaf name {
          type string;
        }
        uses ip-wccp-grouping;
      }
      list vrf {
        description
          "Configure WCCP for a VRF";
        key "name";
        leaf name {
          type string;
        }
        list overlay-vrf {
          description
            "Overlay VRF name";
          key "name";
          leaf name {
            type string;
          }
          uses ip-wccp-grouping;
        }
        uses ip-wccp-grouping;
      }
    }
  }

  grouping interface-ip-wccp-group-listen-grouping {
    leaf group-listen {
      description
        "Listen for multicasted WCCP protocol packets";
      type empty;
    }
    container redirect {
      description
        "Set packet redirection options for the service";
      leaf in {
        description
          "Redirect to a Cache Engine appropriate inbound packets";
        type empty;
      }
      leaf out {
        description
          "Redirect to a Cache Engine appropriate outbound packets";
        type empty;
      }
    }
  }

  grouping interface-ip-wccp-grouping {
    list wccp-list {
      key "id";
      leaf id {
        type uint8 {
          range "0..254";
        }
      }
      uses interface-ip-wccp-group-listen-grouping;
    }
    container web-cache {
      description
        "Standard web caching service";
      uses interface-ip-wccp-group-listen-grouping;
    }
  }

  grouping config-interface-ip-wccp-grouping {
    container wccp {
      description
        "WCCP IPv4 interface commands";
      uses interface-ip-wccp-grouping;
      container redirect {
        description
          "Set packet redirection options";
        container exclude {
          description
            "Exclude packets from redirection";
          leaf in {
            description
              "Exclude inbound packets from outbound redirection";
            type empty;
          }
        }
      }
      list overlay-vrf {
        description
          "Configure WCCP for a overlay VRF";
        key "name";
        leaf name {
          type string;
        }
        uses interface-ip-wccp-grouping;
      }
      list vrf {
        description
          "Configure WCCP for a VRF";
        key "name";
        leaf name {
          type string;
        }
        list overlay-vrf {
          description
            "Configure WCCP for a overlay VRF";
          key "name";
          leaf name {
            type string;
          }
          uses interface-ip-wccp-grouping;
        }
        uses interface-ip-wccp-grouping;
      }
    }
  }

  augment "/ios:native/ios:ip" {
    uses config-ip-wccp-grouping;
  }

  augment "/ios:native/ios:interface/ios:FastEthernet/ios:ip" {
    uses config-interface-ip-wccp-grouping;
  }

  augment "/ios:native/ios:interface/ios:GigabitEthernet/ios:ip" {
    uses config-interface-ip-wccp-grouping;
  }

  augment "/ios:native/ios:interface/ios:TenGigabitEthernet/ios:ip" {
    uses config-interface-ip-wccp-grouping;
  }

  augment "/ios:native/ios:interface/ios:TwoGigabitEthernet/ios:ip" {
    uses config-interface-ip-wccp-grouping;
  }

  augment "/ios:native/ios:interface/ios:FiveGigabitEthernet/ios:ip" {
    uses config-interface-ip-wccp-grouping;
  }

  augment "/ios:native/ios:interface/ios:AppGigabitEthernet/ios:ip" {
    uses config-interface-ip-wccp-grouping;
  }

  augment "/ios:native/ios:interface/ios:TwentyFiveGigE/ios:ip" {
    uses config-interface-ip-wccp-grouping;
  }

  augment "/ios:native/ios:interface/ios:FortyGigabitEthernet/ios:ip" {
    uses config-interface-ip-wccp-grouping;
  }

  augment "/ios:native/ios:interface/ios:FiftyGigabitEthernet/ios:ip" {
    uses config-interface-ip-wccp-grouping;
  }

  augment "/ios:native/ios:interface/ios:HundredGigE/ios:ip" {
    uses config-interface-ip-wccp-grouping;
  }

  augment "/ios:native/ios:interface/ios:TwoHundredGigE/ios:ip" {
    uses config-interface-ip-wccp-grouping;
  }

  augment "/ios:native/ios:interface/ios:FourHundredGigE/ios:ip" {
    uses config-interface-ip-wccp-grouping;
  }

  augment "/ios:native/ios:interface/ios:Port-channel/ios:ip" {
    uses config-interface-ip-wccp-grouping;
  }

  augment "/ios:native/ios:interface/ios:Loopback/ios:ip" {
    uses config-interface-ip-wccp-grouping;
  }

  augment "/ios:native/ios:interface/ios:Tunnel/ios:ip" {
    uses config-interface-ip-wccp-grouping;
  }

  augment "/ios:native/ios:interface/ios:vasileft/ios:ip" {
    uses config-interface-ip-wccp-grouping;
  }

  augment "/ios:native/ios:interface/ios:vasiright/ios:ip" {
    uses config-interface-ip-wccp-grouping;
  }
}
