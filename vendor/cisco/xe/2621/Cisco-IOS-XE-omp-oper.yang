module Cisco-IOS-XE-omp-oper {
  yang-version 1.1;
  namespace "http://cisco.com/ns/yang/Cisco-IOS-XE-omp-oper";
  prefix omp-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     the operational data of Overlay Management Protocol (OMP).
     Copyright (c) 2024, 2026 by Cisco Systems, Inc.
     All rights reserved.";

  revision 2026-08-01 {
    description
      "Update descriptions for several lists and leaves to better explain their meaning and purpose.";
    reference
      "1.0.1";
    cisco-semver:module-version "1.0.1";
  }
  revision 2024-07-01 {
    description
      "Initial revision";
    reference
      "1.0.0";
    cisco-semver:module-version "1.0.0";
  }

  typedef loss-reason-enum {
    type enumeration {
      enum lr-none {
        value 0;
        description
          "None loss reason";
      }
      enum lr-inval {
        value 1;
        description
          "Loss reason of invalid route";
      }
      enum lr-person {
        value 2;
        description
          "Loss reason of personality";
      }
      enum lr-dist {
        value 3;
        description
          "Loss reason of distance";
      }
      enum lr-pref {
        value 4;
        description
          "Loss reason of preference";
      }
      enum lr-tloc-pref {
        value 5;
        description
          "Loss reason of TLOC preference";
      }
      enum lr-origin-prot {
        value 6;
        description
          "Loss reason of original protocol";
      }
      enum lr-origin-prot-subtype {
        value 7;
        description
          "Loss reason of origin protocol subtype";
      }
      enum lr-origin-metric {
        value 8;
        description
          "Loss reason of origin metric";
      }
      enum lr-peer-id {
        value 9;
        description
          "Loss reason of peer ID";
      }
      enum lr-tloc-id {
        value 10;
        description
          "Loss reason of TLOC ID";
      }
      enum lr-ult-tloc-id {
        value 11;
        description
          "Loss reason of ultimate TLOC ID";
      }
      enum lr-stale-entry {
        value 12;
        description
          "Loss reason of stale entry";
      }
      enum lr-site-id {
        value 13;
        description
          "Loss reason of site ID";
      }
      enum lr-omp-ver {
        value 14;
        description
          "Loss reason of OMP version";
      }
      enum lr-tloc-gen-id {
        value 15;
        description
          "Loss reason of TLOC gen ID";
      }
      enum lr-tloc-spi {
        value 16;
        description
          "TLOC SPI loss reason";
      }
      enum lr-tloc-actn {
        value 17;
        description
          "Loss reason of TLOC action";
      }
      enum lr-path-inact {
        value 18;
        description
          "Loss reason of inactive path";
      }
      enum lr-reg-id {
        value 19;
        description
          "Loss reason of region ID";
      }
      enum lr-reg-path {
        value 20;
        description
          "Loss reason of region path";
      }
      enum lr-tgw {
        value 21;
        description
          "Loss reason of transport gateway";
      }
      enum lr-aff-grp {
        value 22;
        description
          "Loss reason of affinity group";
      }
      enum lr-migr-bgp-comm {
        value 23;
        description
          "Loss reason of migration BGP community";
      }
      enum lr-as-path-length {
        value 24;
        description
          "Loss reason of AS path length";
      }
      enum lr-migr-omp-pref {
        value 25;
        description
          "Loss reason of migration OMP preference";
      }
      enum lr-sub-region-id {
        value 26;
        description
          "Loss reason of sub region ID";
      }
      enum lr-br-pref {
        value 27;
        description
          "Loss reason of border router preference";
      }
      enum lr-derived-aff-grp {
        value 28;
        description
          "Loss reason of derived affinity group number";
      }
      enum lr-indir-path {
        value 29;
        description
          "Loss reason of indirect path";
      }
    }
    description
      "The enumeration definition of best-path loss reason";
  }

  typedef service-enum {
    type enumeration {
      enum svc-vpn {
        value 0;
        description
          "VPN service";
      }
      enum svc-fw {
        value 1;
        description
          "FW service";
      }
      enum svc-ids {
        value 2;
        description
          "IDS service";
      }
      enum svc-idp {
        value 3;
        description
          "IDP service";
      }
      enum svc-netsvc1 {
        value 4;
        description
          "NET SVC 1";
      }
      enum svc-netsvc2 {
        value 5;
        description
          "NET SVC 2";
      }
      enum svc-netsvc3 {
        value 6;
        description
          "NET SVC 3";
      }
      enum svc-netsvc4 {
        value 7;
        description
          "NET SVC 4";
      }
      enum svc-te {
        value 8;
        description
          "TE service";
      }
      enum svc-sig {
        value 9;
        description
          "SIG service";
      }
      enum svc-appqoe {
        value 10;
        description
          "APPQOE";
      }
    }
    description
      "The enumeration definition of service";
  }

  typedef l2vpn-type-enum {
    type enumeration {
      enum l2vpn-type-unknown {
        value 0;
        description
          "Unknown";
      }
      enum l2vpn-type-p2p {
        value 1;
        description
          "Point to point";
      }
      enum l2vpn-type-multipoint {
        value 2;
        description
          "Point to multipoint";
      }
    }
    description
      "The enumeration definition of l2vpn type";
  }

  typedef omp-l2route-type-enum {
    type enumeration {
      enum l2route-type-invalid {
        value 0;
        description
          "Invalid";
      }
      enum l2route-type-vpn {
        value 1;
        description
          "VPN l2-route type";
      }
      enum l2route-type-mac {
        value 2;
        description
          "MAC l2-route type";
      }
      enum l2route-type-macip {
        value 3;
        description
          "MAC-IP l2-route type";
      }
      enum l2route-type-macipv6 {
        value 4;
        description
          "MAC-IPv6 l2-route type";
      }
    }
    description
      "The enumeration definition of l2-route type";
  }

  typedef omp-ris-bitmask {
    type bits {
      bit omp-ris-c {
        position 0;
        description
          "The bit of RIB in status is chosen";
      }
      bit omp-ris-i {
        position 1;
        description
          "The bit of RIB in status is installed";
      }
      bit omp-ris-red {
        position 2;
        description
          "The bit of RIB in status is redistributed";
      }
      bit omp-ris-rej {
        position 3;
        description
          "The bit of RIB in status is rejected";
      }
      bit omp-ris-l {
        position 4;
        description
          "The bit of RIB in status is looped";
      }
      bit omp-ris-r {
        position 5;
        description
          "The bit of RIB in status is resolved";
      }
      bit omp-ris-s {
        position 6;
        description
          "The bit of RIB in status is stale";
      }
      bit omp-ris-ext {
        position 7;
        description
          "The bit of RIB in status is extranet";
      }
      bit omp-ris-inv {
        position 8;
        description
          "The bit of RIB in status is invalid";
      }
      bit omp-ris-u {
        position 9;
        description
          "The bit of RIB in status is TLOC Unresolved";
      }
      bit omp-ris-stg {
        position 10;
        description
          "The bit of RIB in status is staged";
      }
      bit omp-ris-ia {
        position 11;
        description
          "The bit of RIB in status is on-demand inactive";
      }
      bit omp-ris-br-r {
        position 12;
        description
          "The bit of RIB in status is border-router re-originated";
      }
      bit omp-ris-tgw-r {
        position 13;
        description
          "The bit of RIB in status is transport-gateway re-originated";
      }
    }
    description
      "The bit definition of RIB in status bit mask";
  }

  grouping omp-l2-svc-rx-key {
    description
      "The key combination of a received layer2 service entry";
    leaf from-peer {
      type inet:ip-address;
      description
        "The remote peer of a received layer2 service entry. A special IP 0.0.0.0 means this peer is the local device itself.";
    }
    leaf path-id {
      type uint32;
      description
        "The path index of a received layer2 service entry";
    }
  }

  grouping omp-l2-svc-rx {
    description
      "The received content of a layer2 service entry";
    leaf label {
      type uint32;
      description
        "The downstream SDWAN MPLS label ID allocated per each received layer2 service entry";
    }
    leaf status {
      type omp-ios-xe-oper:omp-ris-bitmask;
      description
        "Indicates the Routing Information Base (RIB) status of a received layer2 service entry. It is represented as a bitmask showing the entry's state in the RIB.";
    }
    leaf loss-reason {
      type omp-ios-xe-oper:loss-reason-enum;
      description
        "The loss reason for failure competition among multi received paths of a same layer2 service entry";
    }
    leaf lost-to-peer {
      type inet:ip-address;
      description
        "The lost to peer IP address for failure competition among multi received paths of a same layer2 service entry";
    }
    leaf lost-to-path-id {
      type uint32;
      description
        "The lost to path index for failure competition among multi received paths of a same layer2 service entry";
    }
    leaf orig {
      type inet:ip-address;
      description
        "The originator's IP address of a layer2 service entry";
    }
    leaf remote-site-id {
      type uint32;
      description
        "The remote site ID of a received layer2 service entry. It is only valid when vpn-type is p2p.";
    }
  }

  grouping omp-l2-svc-adv {
    description
      "The advertised content of layer2 service entry";
    leaf to-peer {
      type inet:ip-address;
      description
        "The IP address of a remote peer that a layer2 service entry is advertised to.";
    }
  }

  grouping omp-l2-svc-key {
    description
      "The key combination of a layer2 service entry";
    leaf vpn-id {
      type uint32;
      description
        "The layer2 VPN ID of a layer2 service entry";
    }
    leaf service {
      type omp-ios-xe-oper:service-enum;
      description
        "The service type of a layer2 service entry";
    }
    leaf vc-id {
      type uint32;
      description
        "The virtual circuit ID of a layer2 service entry";
    }
    leaf site-id {
      type uint32;
      description
        "The site ID of a layer2 service entry";
    }
  }

  grouping omp-l2-svc {
    description
      "The content of an OMP layer2 service entry";
    leaf vpn-type {
      type omp-ios-xe-oper:l2vpn-type-enum;
      description
        "The layer2 VPN type of a layer2 service entry";
    }
    list omp-l2-svc-rx {
      key "from-peer path-id";
      description
        "List of received layer2 service entries identified by remote peer IP address and path ID. Each entry includes label, RIB status, loss reason, lost to peer and path information, originator IP address and remote site ID.";
      uses omp-ios-xe-oper:omp-l2-svc-rx-key;
      uses omp-ios-xe-oper:omp-l2-svc-rx;
    }
    list omp-l2-svc-adv {
      key "to-peer";
      description
        "List of advertised layer2 service entries identified by remote peer IP address. Each entry specifies the remote peer to which the entry is advertised.";
      uses omp-ios-xe-oper:omp-l2-svc-adv;
    }
  }

  grouping omp-l2-route-rx-key {
    description
      "The key combination of a received layer2 route entry";
    leaf from-peer {
      type inet:ip-address;
      description
        "The remote peer of a received layer2 route entry. A special IP 0.0.0.0 means this peer is the local device itself.";
    }
    leaf path-id {
      type uint32;
      description
        "The path index of a received layer2 route entry";
    }
  }

  grouping omp-l2-route-rx {
    description
      "The received content of a layer2 route entry";
    leaf label {
      type uint32;
      description
        "The downstream SDWAN MPLS label ID of a received layer2 route entry";
    }
    leaf status {
      type omp-ios-xe-oper:omp-ris-bitmask;
      description
        "Indicates the Routing Information Base (RIB) status of a received layer2 route entry. It is represented as a bitmask showing the entry's state in the RIB.";
    }
    leaf loss-reason {
      type omp-ios-xe-oper:loss-reason-enum;
      description
        "The loss reason for failure competition among multi received paths of a same layer2 route entry";
    }
    leaf lost-to-peer {
      type inet:ip-address;
      description
        "The lost to peer IP address for failure competition among multi received paths of a same layer2 route entry";
    }
    leaf lost-to-path-id {
      type uint32;
      description
        "The lost to path index for failure competition among multi received paths of a same layer2 route entry";
    }
    leaf orig {
      type inet:ip-address;
      description
        "The originator's IP address of a layer2 route entry";
    }
    leaf remote-site-id {
      type uint32;
      description
        "The remote site ID of a received layer2 route entry. It is only valid when vpn-type is p2p.";
    }
  }

  grouping omp-l2-route-adv {
    description
      "The advertised content of layer2 route entry";
    leaf to-peer {
      type inet:ip-address;
      description
        "The IP address of a remote peer that a layer2 route entry is advertised to.";
    }
  }

  grouping omp-l2-route-key {
    description
      "The key combination of a layer2 route entry";
    leaf vpn-id {
      type uint32;
      description
        "The layer2 VPN ID of a layer2 route entry";
    }
    leaf vc-id {
      type uint32;
      description
        "Virtual circuit ID of a layer2 route entry";
    }
    leaf orig {
      type inet:ip-address;
      description
        "Originator IP address of a layer2 route entry";
    }
    leaf route-type {
      type omp-ios-xe-oper:omp-l2route-type-enum;
      description
        "The route type of a layer2 route entry";
    }
    leaf mac {
      type yang:mac-address;
      description
        "A host's MAC address of a layer2 route entry.";
    }
    leaf ip {
      type inet:ip-address;
      description
        "A host's IP address of a layer2 route entry";
    }
  }

  grouping omp-l2-route {
    description
      "The content of an OMP layer2 route entry";
    leaf vpn-type {
      type omp-ios-xe-oper:l2vpn-type-enum;
      description
        "The layer2 VPN type of a layer2 route entry";
    }
    leaf site-id {
      type uint32;
      description
        "The site ID of a layer2 route entry";
    }
    list omp-l2-route-rx {
      key "from-peer path-id";
      description
        "The received content of a layer2 route entry";
      uses omp-ios-xe-oper:omp-l2-route-rx-key;
      uses omp-ios-xe-oper:omp-l2-route-rx;
    }
    list omp-l2-route-adv {
      key "to-peer";
      description
        "List of advertised layer2 route entries identified by remote peer IP address. Each entry specifies the remote peer to which the entry is advertised.";
      uses omp-ios-xe-oper:omp-l2-route-adv;
    }
  }

  container omp-oper-data {
    config false;
    description
      "The operational data of Overlay Management Protocol (OMP)";
    list omp-l2-svc {
      key "vpn-id service vc-id site-id";
      description
        "List of layer2 service entries identified by VPN ID, virtual circuit ID, service and site ID. Each entry includes VPN type, received and advertised contents.";
      uses omp-ios-xe-oper:omp-l2-svc-key;
      uses omp-ios-xe-oper:omp-l2-svc;
    }
    list omp-l2-route {
      key "vpn-id vc-id orig route-type mac ip";
      description
        "List of layer2 route entries identified by VPN ID, virtual circuit ID, originator IP address, route type, MAC address and IP address. Each entry includes VPN type, site ID, received and advertised contents.";
      uses omp-ios-xe-oper:omp-l2-route-key;
      uses omp-ios-xe-oper:omp-l2-route;
    }
  }
}
