module common-mpls-static-devs {
  namespace "http://cisco.com/ns/mpls-static/devs";
  prefix mpls-devs;

  import common-mpls-static {
    prefix ms;
  }

  organization
    "Cisco Systems, Inc.";
  contact
    " Cisco Systems, Inc.
     Customer Service

     Postal: 170 W Tasman Drive
     San Jose, CA 95134

     Tel: +1 1800 553-NETS

     E-mail: cs-yang@cisco.com";
  description
    "This module defines deviation statements for common-mpls-static module.";

  revision 2015-09-11 {
    description
      "Initial Revision";
    reference
      "RFC 6020: YANG - A Data Modeling Language for the
       Network Configuration Protocol (NETCONF)";
  }

  deviation "/ms:mpls-static/ms:mpls-static-cfg/ms:ipv4-ingress-lsps"
          + "/ms:ipv4-ingress-lsp/ms:path/ms:resolution"
          + "/ms:explicit-next-hops/ms:next-hop" {
    deviate add {
      max-elements 1;
    }
    description
      "Next hop list. Currently only one static element with key (index) '0'
       is supported.";
  }

  deviation "/ms:mpls-static/ms:mpls-static-cfg/ms:ipv4-ingress-lsps"
          + "/ms:ipv4-ingress-lsp/ms:path/ms:resolution/ms:explicit-next-hops"
          + "/ms:next-hop/ms:operations/ms:operation/ms:swap-with-label-stack"
          + "/ms:swap/ms:stack/ms:label-stack" {
    deviate add {
      max-elements 1;
    }
    description
      "Device does not support multiple label-stack";
  }

  deviation "/ms:mpls-static/ms:mpls-static-cfg/ms:interfaces" {
    deviate not-supported;
    description
      "Not supported in IOS-XE 3.17 release.";
  }

  deviation "/ms:mpls-static/ms:mpls-static-cfg/ms:ipv4-ingress-lsps"
          + "/ms:ipv4-ingress-lsp/ms:path/ms:resolution/ms:auto-next-hops" {
    deviate not-supported;
    description
      "Not supported in IOS-XE 3.17 release.";
  }

  deviation "/ms:mpls-static/ms:mpls-static-cfg/ms:ipv4-ingress-lsps"
          + "/ms:ipv4-ingress-lsp/ms:name" {
    deviate not-supported;
    description
      "Not supported in IOS-XE 3.17 release.";
  }

  deviation "/ms:mpls-static/ms:mpls-static-cfg/ms:ipv4-ingress-lsps"
          + "/ms:ipv4-ingress-lsp/ms:path/ms:resolution/ms:explicit-next-hops"
          + "/ms:next-hop/ms:protected-by" {
    deviate not-supported;
    description
      "Not supported in IOS-XE 3.17 release.";
  }

  deviation "/ms:mpls-static/ms:mpls-static-cfg/ms:ipv4-ingress-lsps"
          + "/ms:ipv4-ingress-lsp"
          + "/ms:path/ms:resolution"
          + "/ms:explicit-next-hops/ms:next-hop/ms:next-hop-type"
          + "/ms:address-type/ms:unnumberd" {
    deviate not-supported;
    description
      "Not supported in IOS-XE 3.17 release.";
  }

  deviation "/ms:mpls-static/ms:mpls-static-cfg/ms:ipv4-ingress-lsps"
          + "/ms:ipv4-ingress-lsp/ms:path/ms:resolution/ms:explicit-next-hops"
          + "/ms:next-hop/ms:next-hop-type/ms:address-type/ms:layer3-ipv6" {
    deviate not-supported;
    description
      "Not supported in IOS-XE 3.17 release.";
  }

  deviation "/ms:mpls-static/ms:mpls-static-cfg/ms:ipv4-ingress-lsps"
          + "/ms:ipv4-ingress-lsp/ms:path/ms:resolution/ms:explicit-next-hops"
          + "/ms:next-hop/ms:next-hop-type/ms:address-type/ms:layer2" {
    deviate not-supported;
    description
      "Not supported in IOS-XE 3.17 release.";
  }

  deviation "/ms:mpls-static/ms:mpls-static-cfg/ms:ipv4-ingress-lsps"
          + "/ms:ipv4-ingress-lsp/ms:path/ms:resolution/ms:explicit-next-hops"
          + "/ms:next-hop/ms:next-hop-type/ms:out-interface-name" {
    deviate not-supported;
    description
      "Not supported in IOS-XE 3.17 release.";
  }

  deviation "/ms:mpls-static/ms:mpls-static-cfg/ms:ipv4-ingress-lsps"
          + "/ms:ipv4-ingress-lsp/ms:path/ms:resolution/ms:explicit-next-hops"
          + "/ms:next-hop/ms:operations/ms:operation/ms:preserve-stack" {
    deviate not-supported;
    description
      "Not supported in IOS-XE 3.17 release.";
  }

  deviation "/ms:mpls-static/ms:mpls-static-cfg/ms:ipv4-ingress-lsps"
          + "/ms:ipv4-ingress-lsp/ms:path/ms:resolution/ms:explicit-next-hops"
          + "/ms:next-hop/ms:operations/ms:operation/ms:push-label-stack" {
    deviate not-supported;
    description
      "Not supported in IOS-XE 3.17 release.";
  }

  deviation "/ms:mpls-static/ms:mpls-static-cfg/ms:ipv4-ingress-lsps"
          + "/ms:ipv4-ingress-lsp/ms:path/ms:resolution/ms:explicit-next-hops"
          + "/ms:next-hop/ms:operations/ms:operation/ms:pop-and-forward" {
    deviate not-supported;
    description
      "Not supported in IOS-XE 3.17 release.";
  }

  deviation "/ms:mpls-static/ms:mpls-static-cfg/ms:ipv6-ingress-lsps" {
    deviate not-supported;
    description
      "Not supported in IOS-XE 3.17 release.";
  }

  deviation "/ms:mpls-static/ms:mpls-static-cfg/ms:named-lsps" {
    deviate not-supported;
    description
      "Not supported in IOS-XE 3.17 release.";
  }

  deviation "/ms:mpls-static/ms:mpls-static-cfg/ms:in-label-lsps" {
    deviate not-supported;
    description
      "Not supported in IOS-XE 3.17 release.";
  }

  deviation "/ms:mpls-static/ms:mpls-static-state" {
    deviate not-supported;
    description
      "Not supported in Polaris 16.8.1 release.";
  }
}
