module Cisco-IOS-XE-wireless-ble-mgmt-oper {
  yang-version 1.1;
  namespace "http://cisco.com/ns/yang/Cisco-IOS-XE-wireless-ble-mgmt-oper";
  prefix wireless-ble-mgmt-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for wireless Bluetooth Low Energy (BLE) management operational data.
     Copyright (c) 2018-2019, 2022 by Cisco Systems, Inc.
     All rights reserved.";

  revision 2026-08-01 {
    description
      "Updated descriptions of several model elements to clarify their meaning and purpose";
    reference
      "1.2.1";
    cisco-semver:module-version "1.2.1";
  }
  revision 2022-11-01 {
    description
      "Update yang-version to 1.1";
    reference
      "1.2.0";
    cisco-semver:module-version "1.2.0";
  }
  revision 2019-05-01 {
    description
      "Added semantic version";
    reference
      "1.1.0";
    cisco-semver:module-version "1.1.0";
  }
  revision 2018-11-23 {
    description
      "Initial revision";
    reference
      "1.0.0";
    cisco-semver:module-version "1.0.0";
  }

  typedef ble-mgmt-reason {
    type enumeration {
      enum ble-mgmt-reason-none {
        value 0;
        description
          "Not Applicable";
      }
      enum ble-mgmt-reason-unknown {
        value 1;
        description
          "Reason unknown";
      }
      enum ble-mgmt-reason-disabled {
        value 2;
        description
          "BLE Administrative state disabled";
      }
      enum ble-mgmt-reason-no-next-hop {
        value 3;
        description
          "NextHop to CMX not resolved";
      }
    }
    description
      "Enumeration of reasons for operational state down";
  }

  typedef ble-mgmt-state {
    type enumeration {
      enum ble-mgmt-state-unknown {
        value 0;
        description
          "Unknown state";
      }
      enum ble-mgmt-state-init {
        value 1;
        description
          "Initializing state";
      }
      enum ble-mgmt-state-open {
        value 2;
        description
          "Open state";
      }
      enum ble-mgmt-state-close {
        value 3;
        description
          "Closed state";
      }
    }
    description
      "Enumeration of all the supported BLE management states";
  }

  typedef ble-mgmt-interface {
    type enumeration {
      enum ble-mgmt-interface-msm1 {
        value 0;
        description
          "Integrated interface";
      }
      enum ble-mgmt-interface-s1 {
        value 1;
        description
          "Integrated interface";
      }
      enum ble-mgmt-interface-hs0 {
        value 2;
        description
          "Integrated interface";
      }
      enum ble-mgmt-interface-usb0 {
        value 3;
        description
          "USB dongle";
      }
      enum ble-mgmt-interface-xrusb0 {
        value 4;
        description
          "Integrated interface";
      }
      enum ble-mgmt-interface-h0 {
        value 5;
        description
          "Integrated interface";
      }
      enum ble-mgmt-interface-unknown {
        value 6;
        description
          "Unknown interface";
      }
    }
    description
      "Enumeration of all the supported BLE interfaces";
  }

  grouping ble-mgmt-cmx {
    description
      "BLE management data for each CMX";
    leaf cmx-id {
      type uint64;
      description
        "CMX Identifier";
    }
    leaf oper-state {
      type boolean;
      description
        "Indicates whether the BLE management connection to the CMX is currently operational (true) or not (false).";
    }
    leaf reason-down {
      when "(../oper-state = 'false')";
      type wireless-ble-mgmt-oper:ble-mgmt-reason;
      description
        "Reason for BLE operational state down";
    }
    leaf admin-state {
      type boolean;
      description
        "Indicates whether the BLE management connection to the CMX is administratively enabled (true) or disabled (false).";
    }
    leaf cmx-resolved {
      type boolean;
      description
        "Whether CMX is reachable";
    }
    leaf scan-interval {
      type uint32;
      units "seconds";
      description
        "BLE scan interval";
    }
    leaf ble-source-mac {
      when "(../oper-state = 'true')";
      type yang:mac-address;
      description
        "Source MAC used for BLE traffic from AP";
    }
  }

  grouping ble-mgmt-ap {
    description
      "BLE management data for each AP";
    leaf ap-mac {
      type yang:mac-address;
      description
        "AP MAC address";
    }
    leaf is-new {
      type boolean;
      description
        "The AP just joined the controller (other fields are invalid)";
    }
    leaf cmx-id {
      type uint64;
      description
        "ID of CMX controlling the AP";
    }
    leaf ble-interface {
      type wireless-ble-mgmt-oper:ble-mgmt-interface;
      description
        "AP BLE interface";
    }
    leaf radio-state {
      type wireless-ble-mgmt-oper:ble-mgmt-state;
      description
        "AP BLE radio state";
    }
    leaf oper-state {
      type boolean;
      description
        "AP BLE Operational state";
    }
  }

  container ble-mgmt-oper-data {
    config false;
    description
      "BLE Management operational data";
    list ble-mgmt-ap {
      key "ap-mac";
      description
        "BLE Management AP data";
      uses wireless-ble-mgmt-oper:ble-mgmt-ap;
    }
    list ble-mgmt-cmx {
      key "cmx-id";
      description
        "BLE Management CMX data";
      uses wireless-ble-mgmt-oper:ble-mgmt-cmx;
    }
  }
}
