module Cisco-IOS-XE-nd {
  yang-version 1.1;
  namespace "http://cisco.com/ns/yang/Cisco-IOS-XE-nd";
  prefix ios-nd;

  import cisco-semver {
    prefix cisco-semver;
  }
  import Cisco-IOS-XE-native {
    prefix ios;
  }
  import Cisco-IOS-XE-types {
    prefix ios-types;
  }
  import Cisco-IOS-XE-features {
    prefix ios-features;
  }
  import ietf-inet-types {
    prefix inet;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Neighbor Discovery (ND) Yang model.
     Copyright (c) 2016-2021 by Cisco Systems, Inc.
     All rights reserved.";

  revision 2026-08-01 {
    description
      "- Added TwoHundredGigE and FourHundredGigE interface support";
    cisco-semver:module-version "6.2.0";
  }
  revision 2026-02-01 {
    description
      "- Added tailf:cli-diff-delete-before to process none before vlan-name, add, all";
    cisco-semver:module-version "6.1.1";
  }
  revision 2025-07-01 {
    description
      "- Added FiftyGigabitEthernet interface support";
    cisco-semver:module-version "6.1.0";
  }
  revision 2024-11-01 {
    description
      "- Added support for ipv6 nd ra-throttler policy
       - OBSOLETE leaf server which was deprecated before 17.11 release
       - Deprecated the leaf time and refresh for ipv6 nd cache expire and added choice type";
    cisco-semver:module-version "6.0.0";
  }
  revision 2024-07-01 {
    description
      "- Obsolete raguard attach-policy
       - Added support for ipv6 nd nsf convergence
       - Added support for ipv6 nd nsf throttle
       - Added support for ipv6 nd nsf dad suppress
       - Added support for ipv6 nd resolution data limit
       - Added support for ipv6 nd dad loopback detect
       - Added support for Router Advertisement control
       - Added support for ipv6 nd raguard default config
       - Added support for advertised reachability time
       - Added support for ipv6 nd dad time and ipv6 nd ns-interval
       - Added IPv6 nd router alert configuration
       - Added support for ipv6 nd ra interval
       - Update must constraint for ipv6 nd raguard attach-policy to allow 'default' policy
       - Added support for ipv6 nd ra interval";
    cisco-semver:module-version "5.0.0";
  }
  revision 2023-11-01 {
    description
      "- Added support for routing-proxy and dad-proxy";
    cisco-semver:module-version "4.1.0";
  }
  revision 2023-07-01 {
    description
      "- Make 25 Gigabit Ethernet interface obsolete
       - Added support for routing-proxy and dad-proxy";
    cisco-semver:module-version "4.0.0";
  }
  revision 2022-11-01 {
    description
      "- Update yang-version to 1.1";
    cisco-semver:module-version "3.1.0";
  }
  revision 2022-03-01 {
    description
      "- Deprecated ra/dns/server leaf and implemented ra/dns/server-list as leaf-list
       - Added if-features around the raguard to selective enable/disable";
    cisco-semver:module-version "3.0.0";
  }
  revision 2021-11-01 {
    description
      "- Added new container for cache and ra/dns under nd module for interfaces";
    cisco-semver:module-version "2.4.0";
  }
  revision 2021-07-01 {
    description
      "- Added specific-route list for ipv6 nd router alert configuration";
    cisco-semver:module-version "2.3.0";
  }
  revision 2021-03-01 {
    description
      "- Fix the issue with device-role in raguard
       - Add support for RA guard managed-config-flag
       - Add support modes for feature nd suppress";
    cisco-semver:module-version "2.2.0";
  }
  revision 2020-11-01 {
    description
      "- Initial revision for 17.4.1
       - Adding the support for attaching policy under vlan for raguard
       - Added the missing commands to fill the gap between CLI and Yang for SISF";
    cisco-semver:module-version "2.1.1";
  }
  revision 2020-07-01 {
    description
      "- Added support for ND config in Dialer interface
       - Added 'tailf:cli-delete-container-on-delete' to the leaf
         'all' in 'ipv6 nd ra suppress all'";
    cisco-semver:module-version "2.1.0";
  }
  revision 2020-03-01 {
    description
      "- Added support for raguard config.";
    cisco-semver:module-version "2.0.0";
  }
  revision 2019-11-01 {
    description
      "- Added leaf for packet-priority to ipv6 ND grouping for interface ND
         configuration.
       - Deprecated ipv6 nd inspection policy.";
    cisco-semver:module-version "1.1.0";
  }
  revision 2019-07-01 {
    description
      "- Establish semantic version baseline
       - Added support for 'nd ns-interval' and 'ns reachable-time' options";
    cisco-semver:module-version "1.0.0";
  }
  revision 2019-01-25 {
    description
      "Added leaf for App-hosting Gigabit Ethernet interface";
  }
  revision 2018-07-26 {
    description
      "Added support for some interface ipv4 nd options";
  }
  revision 2017-11-27 {
    description
      "Added Change 25GE name";
  }
  revision 2017-11-14 {
    description
      "Add support for 40 and 100GE interfaces";
  }
  revision 2017-10-12 {
    description
      "Add support for command 'ipv6 nd suppress policy *'";
  }
  revision 2017-09-18 {
    description
      "This revision has changes for new 2gig interface addition";
  }
  revision 2017-08-16 {
    description
      "This revision has changes for new 5gig and 25gig interfaces addition";
  }
  revision 2017-04-07 {
    description
      "Add default-route";
  }
  revision 2017-02-07 {
    description
      "Initial revision";
  }

  grouping config-interface-ipv6-nd-raguard-vlan-grouping {
    container vlan {
      description
        "Configure the vlan list for which this policy applies (default: all)";
      leaf vlan-name {
        description
          "VLAN IDs of the VLANs for which this policy applies";
        type string;
      }
      leaf add {
        description
          "add VLANs to the current list";
        type string;
      }
      leaf all {
        description
          "all VLANs";
        type empty;
      }
      leaf except {
        description
          "VLAN IDs of disallowed VLANS for this policy on this port";
        type string;
      }
      leaf none {
        description
          "no VLANs";
        type empty;
      }
      leaf remove {
        description
          "Remove VLANs from the current list";
        type string;
      }
    }
  }

  grouping config-ipv6-nd-grouping {
    container inspection {
      if-feature "ios-features:inspection";
      status obsolete;
      description
        "Deprecated - NDP Inspection";
      list policy {
        status obsolete;
        description
          "Deprecated - Using device-tracking";
        key "name-nd-inspection-policy";
        leaf name-nd-inspection-policy {
          status obsolete;
          type string;
        }
        container device-role {
          status obsolete;
          description
            "Deprecated - Sets the role of the device attached to the port";
          leaf host {
            status obsolete;
            description
              "Deprecated - Attached device is a host (default)";
            type empty;
          }
          leaf monitor {
            status obsolete;
            description
              "Deprecated - Attached device is a monitor/sniffer";
            type empty;
          }
          leaf router {
            status obsolete;
            description
              "Deprecated - Attached device is a route";
            type empty;
          }
          leaf switch {
            status obsolete;
            description
              "Deprecated - Attached device is a switch";
            type empty;
          }
        }
        leaf drop-unsecure {
          status obsolete;
          description
            "Deprecated - drop unsecure (3971) messages";
          type empty;
        }
        container limit {
          status obsolete;
          description
            "Deprecated - Specifies a limit";
          leaf address-count {
            status obsolete;
            description
              "Deprecated - Configure maximum address per port";
            type uint16 {
              range "1..10000";
            }
          }
        }
        container sec-level {
          status obsolete;
          description
            "Deprecated - Specifies a minimum sec-level";
          leaf minimum {
            status obsolete;
            description
              "Deprecated - Configure minimum sec-level";
            type uint8 {
              range "1..7";
            }
          }
        }
        container tracking {
          status obsolete;
          description
            "Deprecated - Override default tracking behavior";
          container disable {
            status obsolete;
            description
              "Deprecated - Tracking off";
            presence "true";
            container stale-lifetime {
              status obsolete;
              description
                "Deprecated - Time entry is kept inactive before delete";
              leaf seconds {
                status obsolete;
                description
                  "Deprecated - Seconds";
                type uint32 {
                  range "1..86400";
                }
              }
              leaf infinite {
                status obsolete;
                description
                  "Deprecated - Keep in STALE forever";
                type empty;
              }
            }
          }
          container enable {
            status obsolete;
            description
              "Deprecated - Tracking on";
            presence "true";
            container reachable-lifetime {
              status obsolete;
              description
                "Deprecated - Time entry is kept REACHABLE";
              leaf seconds {
                status obsolete;
                description
                  "Deprecated - Seconds";
                type uint32 {
                  range "1..86400";
                }
              }
              leaf infinite {
                status obsolete;
                description
                  "Deprecated - Keep in REACHABLE forever";
                type empty;
              }
            }
          }
        }
        leaf trusted-port {
          status obsolete;
          description
            "Deprecated - setup trusted port";
          type empty;
        }
        container validate {
          status obsolete;
          description
            "Deprecated - specific validation";
          leaf source-mac {
            status obsolete;
            description
              "Deprecated - check source mac against link-layer-address";
            type empty;
          }
        }
      }
    }
    container cache {
      description
        "Cache entry";
      container expire {
        description
          "Expiry time for ND entries";
        choice expire-options {
          case time-refresh {
            container time-refresh {
              leaf time {
                description
                  "Expiry time (seconds)";
                type uint16;
              }
              leaf time_refresh {
                description
                  "Automatically refresh entry along with time";
                type empty;
              }
            }
          }
          case refresh_only {
            leaf refresh_only {
              description
                "Automatically refresh entry only";
              type empty;
            }
          }
        }
        leaf time {
          description
            "This node is deprecated and replaced by node time in expire-options choice";
          status deprecated;
          type uint16;
        }
        leaf refresh {
          description
            "This node is deprecated and replaced by node refresh-only in expire-options choice";
          status deprecated;
          type empty;
        }
      }
    }
    leaf reachable-time {
      description
        "Duration for advertised reachability intervals";
      type uint32 {
        range "0..3600000";
      }
      default "0";
      units "seconds";
    }
    container ra {
      description
        "Router Advertisement control";
      container solicited {
        description
          "Configuration for solicited Router Advertisement response method";
        leaf unicast {
          description
            "Enable or disable unicast solicited Router Advertisement responses";
          type boolean;
          default "false";
        }
      }
    }
    container nud {
      description
        "Neighbor Unreachability Detection (NUD) configuration";
      container limit {
        description
          "NUD resolutions outstanding configuration";
        leaf limitver {
          type uint32 {
            range "32..4096";
          }
          default "256";
        }
        leaf refresh {
          description
            "Refresh period for NUD resolutions (seconds)";
          type uint8 {
            range "1..10";
          }
          default "10";
        }
      }
    }
    container raguard {
      if-feature "ios-features:raguard";
      description
        "Configure RA guard";
      list policy {
        description
          "Configure a policy for feature RA guard";
        key "raguard-policy-name";
        leaf raguard-policy-name {
          type string;
        }
        container device-role {
          description
            "Sets the role of the device attached to the port";
          container device-role-choice {
            leaf role-choice {
              default "host";
              type enumeration {
                enum host;
                enum monitor;
                enum router;
                enum switch;
              }
            }
          }
          leaf host {
            status obsolete;
            description
              "Deprecated, use other leaf role-choice. Attached device is a host (default)";
            type empty;
          }
          leaf monitor {
            status obsolete;
            description
              "Deprecated, use other leaf role-choice. Attached device is a monitor/sniffer";
            type empty;
          }
          leaf router {
            status obsolete;
            description
              "Deprecated, use other leaf role-choice. Attached device is a router";
            type empty;
          }
          leaf switch {
            status obsolete;
            description
              "Deprecated, use other leaf role-choice. Attached device is a switch";
            type empty;
          }
        }
        container hop-limit {
          description
            "Enable verification of the advertised Hop count limit";
          leaf maximum {
            description
              "Maximum hop count value allowed";
            type uint8 {
              range "1..255";
            }
          }
          leaf minimum {
            description
              "Minimum hop count value allowed";
            type uint8 {
              range "1..255";
            }
          }
        }
        container managed-config-flag {
          description
            "Enable verification of the advertised M flag";
          choice flag-choice {
            leaf off {
              description
                "Verify that the advertised Managed address Configuration flag is Off";
              type empty;
            }
            leaf on {
              description
                "Verify that the advertised Managed address Configuration flag is on";
              type empty;
            }
          }
        }
        container match {
          container ipv6 {
            description
              "Match in received ND message";
            leaf access-list {
              description
                "Name of the access-list to be matched";
              type string;
            }
          }
          container ra {
            description
              "Match in received Router Advertisement";
            leaf prefix-list {
              description
                "Name of the prefix-list to be matched";
              type string;
            }
          }
        }
        container other-config-flag {
          description
            "Enable verification of the advertised O flag";
          choice config-flag-choice {
            leaf off {
              description
                "Verify that the advertised Other Stateful Configuration flag is Off";
              type empty;
            }
            leaf on {
              description
                "Verify that the advertised Other Stateful Configuration flag is on";
              type empty;
            }
          }
        }
        container router-preference {
          description
            "Enable verification of the advertised Router Preference flag";
          container maximum {
            description
              "Verify that the advertised Router preference is lower than the limit";
            choice preference-maximum-choice {
              leaf high {
                description
                  "Discard RAs with router preference greater than high";
                type empty;
              }
              leaf low {
                description
                  "Discard RAs with router preference greater than low";
                type empty;
              }
              leaf medium {
                description
                  "Discard RAs with router preference greater than medium";
                type empty;
              }
            }
          }
        }
        leaf trusted-port {
          description
            "setup trusted port";
          type empty;
        }
      }
      leaf attach-policy {
        description
          "Configure a policy for feature RA guard";
        type string;
      }
    }
    container ra-throttler {
      if-feature "ios-features:ra-throttler";
      description
        "Configure RA throttler";
      list policy {
        description
          "Configure a policy for feature RA throttler";
        key "policy-name";
        leaf policy-name {
          description
            "Name of the RA throttler policy";
          type string;
        }
        container allow {
          description
            "Cap the number of multicast RA's per router per throttle period";
          choice allow-choice {
            case inherit-opt {
              leaf inherit {
                description
                  "Inherit (coalesce) the settings between target policies";
                type empty;
              }
            }
            case custom-limit-opt {
              container custom-limit {
                leaf at-least {
                  description
                    "Guaranteed multicast RAs per router per throttle period";
                  type uint8 {
                    range "0..32";
                  }
                }
                container at-most {
                  choice limit-choice {
                    case limit-opt {
                      leaf max-limit {
                        description
                          "Cap the number of unthrottled multicast RAs per router per throttle period";
                        type uint16 {
                          range "0..256";
                        }
                      }
                    }
                    case no-limit-opt {
                      leaf no-limit {
                        description
                          "No upper bound at the router level";
                        type empty;
                      }
                    }
                  }
                }
              }
            }
          }
        }
        container interval-option {
          description
            "Adjust the behaviour on RA with RFC 3775 interval option";
          choice interval-choice {
            case ignore-opt {
              leaf ignore {
                description
                  "RFC 3775 interval option has no influence on throttling decision";
                type empty;
              }
            }
            case inherit-opt {
              leaf inherit {
                description
                  "Inherit (coalesce) the setting between target policies";
                type empty;
              }
            }
            case passthrough-opt {
              leaf passthrough {
                description
                  "All RAs with RFC 3775 interval option will be forwarded";
                type empty;
              }
            }
            case throttle-opt {
              leaf throttle {
                description
                  "All RAs with RFC 3775 interval option will be throttled";
                type empty;
              }
            }
          }
        }
        container max-through {
          description
            "Cap unthrottled multicast RAs per VLAN per throttle period";
          choice max-through-choice {
            case value-opt {
              leaf value {
                description
                  "Number of multicast RAs on vlan by which throttling is enforced";
                type uint16 {
                  range "0..256";
                }
              }
            }
            case inherit-opt {
              leaf inherit {
                description
                  "Inherit (coalesce) the setting between target policies";
                type empty;
              }
            }
            case no-limit-opt {
              leaf no-limit {
                description
                  "No upper bound at the vlan level";
                type empty;
              }
            }
          }
        }
        container medium-type {
          description
            "Override the natural medium type, wired or wireless";
          choice medium-type-choice {
            default "wifi-opt";
            case wifi-opt {
              leaf wifi {
                description
                  "End devices are reached via a WIFI Access Point";
                type empty;
              }
            }
            case wired-opt {
              leaf wired {
                description
                  "End devices are wired to this or a remote switch";
                type empty;
              }
            }
          }
        }
        container throttle-period {
          description
            "Adjust the throttle period";
          choice throttle-period-choice {
            case value-opt {
              leaf value {
                description
                  "Duration of the throttle period in seconds";
                type uint32 {
                  range "10..86400";
                }
              }
            }
            case inherit-opt {
              leaf inherit {
                description
                  "Inherit (coalesce) the setting between target policies";
                type empty;
              }
            }
          }
        }
      }
    }
    container default-route {
      list vrf {
        ordered-by user;
        key "word";
        leaf word {
          type string;
        }
        leaf limit {
          type uint8 {
            range "0..5";
          }
        }
      }
      leaf limit {
        type uint8 {
          range "0..5";
        }
      }
    }
    container suppress {
      if-feature "ios-features:suppress";
      description
        "Configure ND multicast suppress";
      list policy {
        description
          "Configure a policy for feature nd suppress";
        key "nd-suppress-policy-name";
        leaf nd-suppress-policy-name {
          type string;
        }
        container mode {
          description
            "setup mode of operations";
          leaf dad-proxy {
            description
              "Proxy Duplicate Address Resolution request";
            type empty;
          }
          leaf full-proxy {
            description
              "Proxy all resolution requests";
            type empty;
          }
          leaf mc-proxy {
            description
              "Proxy multicast resolution requests (default)";
            type empty;
          }
        }
      }
    }
    container dad {
      description
        "Duplicate Address Detection";
      container loopback {
        description
          "Response method for looped back NS(DAD) packets";
        leaf detect {
          description
            "Looped-back NS(DAD) packets detection control.";
          type boolean;
          default "true";
        }
      }
      leaf time {
        description
          "IPv6 Duplicate Address Detection Time";
        type uint32 {
          range "0 | 1..6000";
        }
        default "0";
      }
    }
    leaf ns-interval {
      description
        "Advertised NS retransmission interval";
      type uint32 {
        range "0 | 1000..30000";
      }
      default "0";
    }
    container nsf {
      description
        "Data related to Non-Stop Forwarding (NSF).";
      leaf convergence {
        description
          "Time limit for NSF convergence.";
        type uint16 {
          range "10..600";
        }
        default "120";
        units "seconds";
      }
      container dad {
        description
          "Data related to Duplicate Address Detection (DAD).";
        leaf suppress {
          description
            "Suppress DAD for a specified duration.";
          type uint16 {
            range "0..600";
          }
          default "60";
          units "seconds";
        }
      }
      leaf throttle {
        description
          "Throttle resolution requests.";
        type uint16 {
          range "128..4096";
        }
        default "512";
      }
    }
    container resolution {
      description
        "Configuration for resolution settings.";
      container data {
        description
          "Data related to resolution settings.";
        leaf limit {
          description
            "Limit on the number of packets.";
          type uint16 {
            range "16..2048";
          }
          default "16";
        }
      }
    }
  }

  grouping config-interface-ipv6-nd-grouping {
    container cache {
      description
        "Cache entry";
      leaf interface-limit {
        description
          "Number of entries";
        type uint32;
      }
      container expire {
        description
          "Expiry time for ND entries";
        leaf time {
          description
            "Expiry time (seconds)";
          type uint16;
        }
        leaf refresh {
          description
            "Automatically refresh entry";
          type empty;
        }
      }
    }
    container raguard {
      if-feature "ios-features:raguard";
      description
        "Configure RA guard on the interface";
      presence "“true”";
      list attached-policies {
        key "attach-policy";
        leaf attach-policy {
          description
            "Apply a policy for feature RA guard";
          type string;
          must "(/ios:native/ios:ipv6/ios:nd/ios-nd:raguard/ios-nd:policy[ios-nd:raguard-policy-name=current()]) or .='default'" {
            error-message "Create raguard policy first, then attach policy; Detach policy from interface before removing the policy";
          }
        }
        uses config-interface-ipv6-nd-raguard-vlan-grouping;
      }
      container default-policy {
        uses config-interface-ipv6-nd-raguard-vlan-grouping;
      }
      leaf attach-policy {
        status obsolete;
        description
          "Apply a policy for feature RA guard";
        type string;
        must '(/ios:native/ios:ipv6/ios:nd/ios-nd:raguard/ios-nd:policy[ios-nd:raguard-policy-name=current()])' {
          error-message "Create raguard policy first, then attach policy; Detach policy from interface before removing the policy";
        }
      }
    }
    container ra-throttler {
      if-feature "ios-features:ra-throttler";
      description
        "Configure RA throttler on the interface";
      presence "“true”";
      list attached-policies {
        key "attach-policy";
        leaf attach-policy {
          description
            "Apply a policy for feature RA throttler";
          type string;
          must "(/ios:native/ios:ipv6/ios:nd/ios-nd:ra-throttler/ios-nd:policy[ios-nd:policy-name=current()]) or .='default'" {
            error-message "Create RA throttler policy first, then attach policy; Detach policy from interface before removing the policy";
          }
        }
        uses config-interface-ipv6-nd-raguard-vlan-grouping;
      }
      container default-policy {
        uses config-interface-ipv6-nd-raguard-vlan-grouping;
      }
    }
    container autoconfig {
      description
        "Obtain address using autoconfiguration";
      leaf default-route {
        description
          "Insert default route";
        type empty;
      }
      leaf prefix {
        description
          "Insert auto-configured prefix";
        type empty;
      }
    }
    leaf managed-config-flag {
      description
        "Use DHCP for IPv6 address configuration";
      type empty;
    }
    leaf other-config-flag {
      description
        "Hosts should use DHCP for non-address config";
      type empty;
    }
    leaf router-preference {
      description
        "Set default router preference value";
      type enumeration {
        enum High;
        enum Medium;
        enum Low;
      }
      default "Medium";
    }
    leaf routing-proxy {
      if-feature "ios-features:routing-proxy";
      description
        "Configure Routing Proxy on the interface";
      type empty;
    }
    leaf dad-proxy {
      if-feature "ios-features:dad-proxy";
      description
        "Configure DAD Proxy on the interface";
      type empty;
    }
    container prefix {
      description
        "Configure IPv6 Routing Prefix Advertisement";
      list ipv6-prefix-list {
        description
          "IPv6 prefix x:x::y/<z>";
        key "ipv6-prefix";
        leaf ipv6-prefix {
          type ios-types:ipv6-prefix;
        }
        leaf no-advertise {
          description
            "Do not advertise prefix";
          type empty;
        }
      }
    }
    container ra {
      description
        "IPv6 nd router alert configuration";
      container interval {
        description
          "Configuration of Router Advertisement (RA) interval in seconds.";
        leaf interval_sec {
          type uint16 {
            range "4..65535";
          }
          default "200";
        }
      }
      container dns {
        description
          "Configure DNS server for a zone";
        leaf-list server-list {
          description
            "List of IPv6 server addresses";
          type inet:ipv6-address;
        }
        leaf server {
          status obsolete;
          description
            "IPv6 address. DEPRECATED, Use server-list instead";
          type inet:ipv6-address;
        }
      }
      container suppress {
        description
          "Suppress IPv6 router-alert configuration";
        presence "true";
        leaf all {
          description
            "Suppress all IPv6 RA";
          type empty;
        }
      }
      list specific-route {
        key "specific-route";
        leaf specific-route {
          type ios-types:ipv6-prefix;
        }
        leaf lifetime {
          description
            "lifetime(seconds)";
          type uint32 {
            range "0..4294967295";
          }
        }
        leaf preference {
          description
            "Set default router preference value";
          type enumeration {
            enum High;
            enum Medium;
            enum Low;
          }
          default "Medium";
        }
      }
    }
    leaf ns-interval {
      description
        "Set advertised NS retransmission interval";
      type uint32 {
        range "1000..172800000";
      }
    }
    leaf reachable-time {
      description
        "Set advertised reachability time";
      type uint32 {
        range "0..3600000";
      }
    }
    leaf packet-priority {
      description
        "Use high priority for IPv6 ND packets";
      type empty;
    }
  }

  grouping config-interface-ipv6-nd-raguard-vlan-grouping-obsolete {
    container vlan {
      status obsolete;
      description
        "Configure the vlan list for which this policy applies (default: all)";
      leaf vlan-name {
        status obsolete;
        description
          "VLAN IDs of the VLANs for which this policy applies";
        type string;
      }
      leaf add {
        status obsolete;
        description
          "add VLANs to the current list";
        type string;
      }
      leaf all {
        status obsolete;
        description
          "all VLANs";
        type empty;
      }
      leaf except {
        status obsolete;
        description
          "VLAN IDs of disallowed VLANS for this policy on this port";
        type string;
      }
      leaf none {
        status obsolete;
        description
          "no VLANs";
        type empty;
      }
      leaf remove {
        status obsolete;
        description
          "Remove VLANs from the current list";
        type string;
      }
    }
  }

  grouping config-interface-ipv6-nd-grouping-obsolete {
    container cache {
      status obsolete;
      description
        "Cache entry";
      leaf interface-limit {
        status obsolete;
        description
          "Number of entries";
        type uint32;
      }
      container expire {
        status obsolete;
        description
          "Expiry time for ND entries";
        leaf time {
          status obsolete;
          description
            "Expiry time (seconds)";
          type uint16;
        }
        leaf refresh {
          status obsolete;
          description
            "Automatically refresh entry";
          type empty;
        }
      }
    }
    container raguard {
      status obsolete;
      if-feature "ios-features:raguard";
      description
        "Configure RA guard on the interface";
      list attached-policies {
        status obsolete;
        key "attach-policy";
        leaf attach-policy {
          status obsolete;
          description
            "Apply a policy for feature RA guard";
          type string;
          must '(/ios:native/ios:ipv6/ios:nd/ios-nd:raguard/ios-nd:policy[ios-nd:raguard-policy-name=current()])' {
            error-message "Create raguard policy first, then attach policy; Detach policy from interface before removing the policy";
          }
        }
        uses config-interface-ipv6-nd-raguard-vlan-grouping-obsolete;
      }
      container default-policy {
        status obsolete;
        uses config-interface-ipv6-nd-raguard-vlan-grouping-obsolete;
      }
      leaf attach-policy {
        status obsolete;
        description
          "Apply a policy for feature RA guard";
        type string;
        must '(/ios:native/ios:ipv6/ios:nd/ios-nd:raguard/ios-nd:policy[ios-nd:raguard-policy-name=current()])' {
          error-message "Create raguard policy first, then attach policy; Detach policy from interface before removing the policy";
        }
      }
    }
    container autoconfig {
      status obsolete;
      description
        "Obtain address using autoconfiguration";
      leaf default-route {
        status obsolete;
        description
          "Insert default route";
        type empty;
      }
      leaf prefix {
        status obsolete;
        description
          "Insert auto-configured prefix";
        type empty;
      }
    }
    leaf managed-config-flag {
      status obsolete;
      description
        "Use DHCP for IPv6 address configuration";
      type empty;
    }
    leaf other-config-flag {
      status obsolete;
      description
        "Hosts should use DHCP for non-address config";
      type empty;
    }
    leaf router-preference {
      status obsolete;
      description
        "Set default router preference value";
      type enumeration {
        enum High;
        enum Medium;
        enum Low;
      }
      default "Medium";
    }
    container prefix {
      status obsolete;
      description
        "Configure IPv6 Routing Prefix Advertisement";
      list ipv6-prefix-list {
        status obsolete;
        description
          "IPv6 prefix x:x::y/<z>";
        key "ipv6-prefix";
        leaf ipv6-prefix {
          status obsolete;
          type ios-types:ipv6-prefix;
        }
        leaf no-advertise {
          status obsolete;
          description
            "Do not advertise prefix";
          type empty;
        }
      }
    }
    container ra {
      status obsolete;
      description
        "IPv6 nd router alert configuration";
      container dns {
        status obsolete;
        description
          "Configure DNS server for a zone";
        leaf-list server-list {
          status obsolete;
          description
            "List of IPv6 server addresses";
          type inet:ipv6-address;
        }
        leaf server {
          status obsolete;
          description
            "IPv6 address. DEPRECATED, Use server-list instead";
          type inet:ipv6-address;
        }
      }
      container suppress {
        status obsolete;
        description
          "Suppress IPv6 router-alert configuration";
        presence "true";
        leaf all {
          status obsolete;
          description
            "Suppress all IPv6 RA";
          type empty;
        }
      }
      list specific-route {
        status obsolete;
        key "specific-route";
        leaf specific-route {
          status obsolete;
          type ios-types:ipv6-prefix;
        }
        leaf lifetime {
          status obsolete;
          description
            "lifetime(seconds)";
          type uint32 {
            range "0..4294967295";
          }
        }
        leaf preference {
          status obsolete;
          description
            "Set default router preference value";
          type enumeration {
            enum High;
            enum Medium;
            enum Low;
          }
          default "Medium";
        }
      }
    }
    leaf ns-interval {
      status obsolete;
      description
        "Set advertised NS retransmission interval";
      type uint32 {
        range "1000..172800000";
      }
    }
    leaf reachable-time {
      status obsolete;
      description
        "Set advertised reachability time";
      type uint32 {
        range "0..3600000";
      }
    }
    leaf packet-priority {
      status obsolete;
      description
        "Use high priority for IPv6 ND packets";
      type empty;
    }
  }

  augment "/ios:native/ios:ipv6/ios:nd" {
    uses config-ipv6-nd-grouping;
  }

  augment "/ios:native/ios:interface/ios:FastEthernet/ios:ipv6/ios:nd" {
    uses config-interface-ipv6-nd-grouping;
  }

  augment "/ios:native/ios:interface/ios:GigabitEthernet/ios:ipv6/ios:nd" {
    uses config-interface-ipv6-nd-grouping;
  }

  augment "/ios:native/ios:interface/ios:TenGigabitEthernet/ios:ipv6/ios:nd" {
    uses config-interface-ipv6-nd-grouping;
  }

  augment "/ios:native/ios:interface/ios:FiveGigabitEthernet/ios:ipv6/ios:nd" {
    uses config-interface-ipv6-nd-grouping;
  }

  augment "/ios:native/ios:interface/ios:AppGigabitEthernet/ios:ipv6/ios:nd" {
    uses config-interface-ipv6-nd-grouping;
  }

  augment "/ios:native/ios:interface/ios:TwentyFiveGigE/ios:ipv6/ios:nd" {
    uses config-interface-ipv6-nd-grouping;
  }

  augment "/ios:native/ios:interface/ios:TwoGigabitEthernet/ios:ipv6/ios:nd" {
    uses config-interface-ipv6-nd-grouping;
  }

  augment "/ios:native/ios:interface/ios:FortyGigabitEthernet/ios:ipv6/ios:nd" {
    uses config-interface-ipv6-nd-grouping;
  }

  augment "/ios:native/ios:interface/ios:FiftyGigabitEthernet/ios:ipv6/ios:nd" {
    uses config-interface-ipv6-nd-grouping;
  }

  augment "/ios:native/ios:interface/ios:HundredGigE/ios:ipv6/ios:nd" {
    uses config-interface-ipv6-nd-grouping;
  }

  augment "/ios:native/ios:interface/ios:TwoHundredGigE/ios:ipv6/ios:nd" {
    uses config-interface-ipv6-nd-grouping;
  }

  augment "/ios:native/ios:interface/ios:FourHundredGigE/ios:ipv6/ios:nd" {
    uses config-interface-ipv6-nd-grouping;
  }

  augment "/ios:native/ios:interface/ios:Port-channel/ios:ipv6/ios:nd" {
    uses config-interface-ipv6-nd-grouping;
  }

  augment "/ios:native/ios:interface/ios:Virtual-Template/ios:ipv6/ios:nd" {
    uses config-interface-ipv6-nd-grouping;
  }

  augment "/ios:native/ios:interface/ios:Loopback/ios:ipv6/ios:nd" {
    uses config-interface-ipv6-nd-grouping;
  }

  augment "/ios:native/ios:interface/ios:Tunnel/ios:ipv6/ios:nd" {
    uses config-interface-ipv6-nd-grouping;
  }

  augment "/ios:native/ios:interface/ios:vasileft/ios:ipv6/ios:nd" {
    uses config-interface-ipv6-nd-grouping;
  }

  augment "/ios:native/ios:interface/ios:vasiright/ios:ipv6/ios:nd" {
    uses config-interface-ipv6-nd-grouping;
  }

  augment "/ios:native/ios:interface/ios:Vlan/ios:ipv6/ios:nd" {
    uses config-interface-ipv6-nd-grouping;
  }

  augment "/ios:native/ios:interface/ios:Dialer/ios:ipv6/ios:nd" {
    uses config-interface-ipv6-nd-grouping;
  }

  augment "/ios:native/ios:interface/ios:AppNav-Compress/ios:ipv6/ios:nd" {
    uses config-interface-ipv6-nd-grouping;
  }

  augment "/ios:native/ios:interface/ios:AppNav-UnCompress/ios:ipv6/ios:nd" {
    uses config-interface-ipv6-nd-grouping;
  }

  augment "/ios:native/ios:interface/ios:ATM/ios:ipv6/ios:nd" {
    uses config-interface-ipv6-nd-grouping;
  }

  augment "/ios:native/ios:interface/ios:ATM-subinterface/ios:ATM/ios:ipv6/ios:nd" {
    uses config-interface-ipv6-nd-grouping;
  }

  augment "/ios:native/ios:interface/ios:BDI/ios:ipv6/ios:nd" {
    uses config-interface-ipv6-nd-grouping;
  }

  augment "/ios:native/ios:interface/ios:Embedded-Service-Engine/ios:ipv6/ios:nd" {
    uses config-interface-ipv6-nd-grouping;
  }

  augment "/ios:native/ios:interface/ios:Ethernet/ios:ipv6/ios:nd" {
    uses config-interface-ipv6-nd-grouping;
  }

  augment "/ios:native/ios:interface/ios:ucse/ios:ipv6/ios:nd" {
    uses config-interface-ipv6-nd-grouping;
  }

  augment "/ios:native/ios:interface/ios:Ethernet-Internal/ios:ipv6/ios:nd" {
    uses config-interface-ipv6-nd-grouping;
  }

  augment "/ios:native/ios:interface/ios:Service-Engine/ios:ipv6/ios:nd" {
    uses config-interface-ipv6-nd-grouping;
  }

  augment "/ios:native/ios:interface/ios:TwentyFiveGigabitEthernet/ios:ipv6/ios:nd" {
    uses config-interface-ipv6-nd-grouping-obsolete;
  }

  augment "/ios:native/ios:interface/ios:LISP/ios:ipv6/ios:nd" {
    uses config-interface-ipv6-nd-grouping;
  }

  augment "/ios:native/ios:interface/ios:LISP-subinterface/ios:LISP/ios:ipv6/ios:nd" {
    uses config-interface-ipv6-nd-grouping;
  }

  augment "/ios:native/ios:interface/ios:nve/ios:ipv6/ios:nd" {
    uses config-interface-ipv6-nd-grouping;
  }

  augment "/ios:native/ios:interface/ios:Port-channel-subinterface/ios:Port-channel/ios:ipv6/ios:nd" {
    uses config-interface-ipv6-nd-grouping;
  }

  augment "/ios:native/ios:interface/ios:SM/ios:ipv6/ios:nd" {
    uses config-interface-ipv6-nd-grouping;
  }

  augment "/ios:native/ios:interface/ios:Cellular/ios:ipv6/ios:nd" {
    uses config-interface-ipv6-nd-grouping;
  }

  augment "/ios:native/ios:interface/ios:GMPLS/ios:ipv6/ios:nd" {
    uses config-interface-ipv6-nd-grouping;
  }

  augment "/ios:native/ios:interface/ios:Group-Async/ios:ipv6/ios:nd" {
    uses config-interface-ipv6-nd-grouping;
  }

  augment "/ios:native/ios:interface/ios:Multilink/ios:ipv6/ios:nd" {
    uses config-interface-ipv6-nd-grouping;
  }

  augment "/ios:native/ios:interface/ios:Serial/ios:ipv6/ios:nd" {
    uses config-interface-ipv6-nd-grouping;
  }

  augment "/ios:native/ios:interface/ios:Async/ios:ipv6/ios:nd" {
    uses config-interface-ipv6-nd-grouping;
  }

  augment "/ios:native/ios:interface/ios:Virtual-PPP/ios:ipv6/ios:nd" {
    uses config-interface-ipv6-nd-grouping;
  }

  augment "/ios:native/ios:interface/ios:VirtualPortGroup/ios:ipv6/ios:nd" {
    uses config-interface-ipv6-nd-grouping;
  }

  augment "/ios:native/ios:interface/ios:Vif/ios:ipv6/ios:nd" {
    uses config-interface-ipv6-nd-grouping;
  }

  augment "/ios:native/ios:interface/ios:Wlan-GigabitEthernet/ios:ipv6/ios:nd" {
    uses config-interface-ipv6-nd-grouping;
  }

  augment "/ios:native/ios:interface/ios:BD-VIF/ios:ipv6/ios:nd" {
    uses config-interface-ipv6-nd-grouping;
  }

  augment "/ios:native/ios:interface/ios:MFR/ios:ipv6/ios:nd" {
    uses config-interface-ipv6-nd-grouping;
  }

  augment "/ios:native/ios:interface/ios:Serial-subinterface/ios:Serial/ios:ipv6/ios:nd" {
    uses config-interface-ipv6-nd-grouping;
  }

  augment "/ios:native/ios:interface/ios:MFR-subinterface/ios:MFR/ios:ipv6/ios:nd" {
    uses config-interface-ipv6-nd-grouping;
  }
}
