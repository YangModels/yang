module Cisco-IOS-XE-mka-oper {
  yang-version 1.1;
  namespace "http://cisco.com/ns/yang/Cisco-IOS-XE-mka-oper";
  prefix mka-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for MACsec Key Agreement(MKA) protocol operational data.
     Copyright (c) 2018-2019, 2022 by Cisco Systems, Inc.
     All rights reserved.";

  revision 2026-08-01 {
    description
      "- Refined existing leaf descriptions for clarity and consistency";
    reference
      "1.1.1";
    cisco-semver:module-version "1.1.1";
  }
  revision 2022-11-01 {
    description
      "Update yang-version to 1.1";
    reference
      "1.1.0";
    cisco-semver:module-version "1.1.0";
  }
  revision 2019-05-01 {
    description
      "Added semantic version";
    reference
      "1.0.1";
    cisco-semver:module-version "1.0.1";
  }
  revision 2018-10-26 {
    description
      "Initial revision";
    reference
      "1.0.0";
    cisco-semver:module-version "1.0.0";
  }

  grouping mka-statistics {
    description
      "Grouping of per-interface statistics for the MKA protocol.";
    leaf if-name {
      type string;
      description
        "Name of the interface for which the MKA statistics are collected.";
    }
    leaf mkpdu-stats-rx {
      type uint32;
      description
        "MKPDU Validated & RX count";
    }
    leaf mkpdu-stats-rx-distsak {
      type uint32;
      description
        "MKPDU RX Distributed SAK count";
    }
    leaf mkpdu-stats-rx-distcak {
      type uint32;
      description
        "MKPDU RX Distributed CAK count";
    }
    leaf mkpdu-stats-tx {
      type uint32;
      description
        "MKPDU TX count";
    }
    leaf mkpdu-stats-tx-distsak {
      type uint32;
      description
        "MKPDU TX Distributed SAK count";
    }
    leaf mkpdu-stats-tx-distcak {
      type uint32;
      description
        "MKPDU TX Distributed CAK count";
    }
  }

  grouping mka-statistics-global {
    description
      "Grouping of global statistics related to the MKA protocol.";
    leaf mkpdu-stats-rx {
      type uint32;
      description
        "Specifies the total number of received and validated MKPDU packets on the device.";
    }
    leaf mkpdu-stats-rx-distsak {
      type uint32;
      description
        "Specifies the number of received MKPDU packets that have distributed a SAK on the device.";
    }
    leaf mkpdu-stats-rx-distcak {
      type uint32;
      description
        "Specifies the number of received MKPDU packets that have distributed a CAK on the device.";
    }
    leaf mkpdu-stats-tx {
      type uint32;
      description
        "Specifies the total number of MKPDU packets transmitted by the device.";
    }
    leaf mkpdu-stats-tx-distsak {
      type uint32;
      description
        "Specifies the number of transmitted MKPDU packets that distributed a SAK from the device.";
    }
    leaf mkpdu-stats-tx-distcak {
      type uint32;
      description
        "Specifies the number of transmitted MKPDU packets that distributed a CAK from the device.";
    }
    leaf mka-err-sak-gen {
      type uint32;
      description
        "MKA error SAK generation count";
    }
    leaf mka-err-hash-gen {
      type uint32;
      description
        "MKA error Hash Key generation count";
    }
    leaf mka-err-sak-encryption {
      type uint32;
      description
        "MKA error SAK encryption/wrap count";
    }
    leaf mka-err-sak-decryption {
      type uint32;
      description
        "MKA error SAK decryption/unwrap count";
    }
    leaf mka-err-sak-cipher-mismatch {
      type uint32;
      description
        "MKA error SAK cipher mismatch count";
    }
    leaf mkpdu-err-tx {
      type uint32;
      description
        "MKPDU TX error count ";
    }
    leaf mkpdu-err-rx-icv-verify {
      type uint32;
      description
        "MKPDU RX ICV verification error count";
    }
    leaf mkpdu-err-rx-validation {
      type uint32;
      description
        "MKPDU RX validation error count";
    }
    leaf mkpdu-err-rx-badpeer-mn {
      type uint32;
      description
        "MKPDU RX Bad peer MN error count";
    }
    leaf mkpdu-err-rx-peer-list {
      type uint32;
      description
        "MKPDU RX non-recent peer list MN error count";
    }
  }

  container mka-oper-data {
    config false;
    description
      "Operational state of MKA";
    list mka-statistics {
      key "if-name";
      description
        "List of per-interface MKA protocol statistics; each entry represents statistics collected for a single interface.";
      uses mka-ios-xe-oper:mka-statistics;
    }
    container mka-statistics-global {
      presence "mka-statistics-global";
      description
        "Container for global statistics related to the MKA protocol.";
      uses mka-ios-xe-oper:mka-statistics-global;
    }
  }
}
