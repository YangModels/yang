module Cisco-IOS-XE-ngfw-common-oper {
  yang-version 1.1;
  namespace "http://cisco.com/ns/yang/Cisco-IOS-XE-ngfw-common-oper";
  prefix ngfw-common-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     common for all NGFW operational data.
     Copyright (c) 2026 by Cisco Systems, Inc.
     All rights reserved.";

  revision 2026-08-01 {
    description
      "Initial revision";
    reference
      "1.0.0";
    cisco-semver:module-version "1.0.0";
  }

  typedef ngfw-update-type-val {
    type enumeration {
      enum ngfw-update-type-unknown {
        value 0;
        description
          "Next-Generation Firewall (NGFW) update type is unknown";
      }
      enum ngfw-update-type-lsp {
        value 1;
        description
          "Next-Generation Firewall (NGFW) update is Lightweight Security Package (LSP) update";
      }
      enum ngfw-update-type-vdb {
        value 2;
        description
          "Next-Generation Firewall (NGFW) update is Vulnerability Database (VDB) update";
      }
    }
    description
      "Next-Generation Firewall (NGFW) update type";
  }

  typedef ngfw-update-status-val {
    type enumeration {
      enum ngfw-update-status-unknown {
        value 0;
        description
          "Next-Generation Firewall (NGFW) update status is unknown";
      }
      enum ngfw-update-status-success {
        value 1;
        description
          "Next-Generation Firewall (NGFW) update successful";
      }
      enum ngfw-update-status-failure {
        value 2;
        description
          "Next-Generation Firewall (NGFW) update failed";
      }
      enum ngfw-update-status-no-update {
        value 3;
        description
          "Next-Generation Firewall (NGFW) update attempted but not required";
      }
    }
    description
      "Next-Generation Firewall (NGFW) update status";
  }
}
