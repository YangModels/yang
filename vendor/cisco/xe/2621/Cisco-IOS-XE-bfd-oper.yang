module Cisco-IOS-XE-bfd-oper {
  yang-version 1.1;
  namespace "http://cisco.com/ns/yang/Cisco-IOS-XE-bfd-oper";
  prefix bfd-ios-xe-oper;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for BFD neighbor monitoring.
     Copyright (c) 2016-2019, 2021-2022, 2026 by Cisco Systems, Inc.
     All rights reserved.";

  revision 2026-08-01 {
    description
      "Modified descriptions for several BFD model elements to improve model usability";
    reference
      "2.5.1";
    cisco-semver:module-version "2.5.1";
  }
  revision 2022-11-01 {
    description
      "Update yang-version to 1.1";
    reference
      "2.5.0";
    cisco-semver:module-version "2.5.0";
  }
  revision 2021-11-01 {
    description
      "- Added BFD session state info and session neighbor details";
    reference
      "2.4.0";
    cisco-semver:module-version "2.4.0";
  }
  revision 2021-03-01 {
    description
      "- Added session state info and session neighbor details";
    reference
      "2.3.0";
    cisco-semver:module-version "2.3.0";
  }
  revision 2019-05-01 {
    description
      "Added semantic version";
    reference
      "2.2.0";
    cisco-semver:module-version "2.2.0";
  }
  revision 2018-10-29 {
    description
      "Cleaned up spelling errors in descriptions.";
    reference
      "2.1.0";
    cisco-semver:module-version "2.1.0";
  }
  revision 2017-09-10 {
    description
      "Enumeration renaming";
    reference
      "2.0.0";
    cisco-semver:module-version "2.0.0";
  }
  revision 2017-02-07 {
    description
      "Initial revision";
    reference
      "1.0.0";
    cisco-semver:module-version "1.0.0";
  }

  typedef bfd-oper-session-type {
    type enumeration {
      enum ipv4 {
        value 0;
      }
      enum ipv6 {
        value 1;
      }
      enum vccv {
        value 2;
      }
      enum mpls-tp {
        value 3;
      }
      enum ipv4-multihop {
        value 4;
      }
      enum ipv6-multihop {
        value 5;
      }
      enum poch-ipv4 {
        value 6;
        description
          "Port Channel IPV4 client";
      }
    }
    description
      "BFD session type";
  }

  typedef bfd-remote-state-type {
    type enumeration {
      enum remote-up {
        value 0;
      }
      enum remote-down {
        value 1;
      }
      enum remote-init {
        value 2;
      }
      enum remote-admindown {
        value 3;
      }
      enum remote-invalid {
        value 4;
      }
    }
    description
      "BFD remote state type";
  }

  typedef bfd-state-type {
    type enumeration {
      enum admindown {
        value 0;
      }
      enum down {
        value 1;
      }
      enum fail {
        value 2;
      }
      enum init {
        value 3;
      }
      enum up {
        value 4;
      }
      enum invalid {
        value 5;
      }
    }
    description
      "BFD state type";
  }

  typedef bfd-lsp-type {
    type enumeration {
      enum working {
        value 0;
      }
      enum protect {
        value 1;
      }
      enum unknown {
        value 2;
      }
    }
    description
      "BFD LSP type";
  }

  typedef bfd-diag-state {
    type enumeration {
      enum bfd-diag-no-diag {
        value 0;
        description
          "No failure";
      }
      enum bfd-diag-ctrl-time-exp {
        value 1;
        description
          "Control time expired";
      }
      enum bfd-diag-echo-failed {
        value 2;
        description
          "Echo failed";
      }
      enum bfd-diag-nbr-signaled-down {
        value 3;
        description
          "Neighbor session down";
      }
      enum bfd-diag-fwd-plane-reset {
        value 4;
        description
          "Forwarding plane in the local system is reset for some reason";
      }
      enum bfd-diag-path-down {
        value 5;
        description
          "The underlying path has failed";
      }
      enum bfd-diag-concat-path-down {
        value 6;
        description
          "Forward path failure";
      }
      enum bfd-diag-admin-down {
        value 7;
        description
          "Entering the administratively down state and sending an explanatory diagnostic code";
      }
      enum bfd-diag-rev-concat-path-down {
        value 8;
        description
          "Reverse path failure";
      }
      enum bfd-diag-not-valid {
        value 9;
        description
          "Not valid diag";
      }
    }
    description
      "BFD diag state to identify failure";
  }

  typedef bfd-session-host {
    type enumeration {
      enum bfd-host-software {
        value 0;
        description
          "BFD sessions host software";
      }
      enum bfd-host-hardware {
        value 1;
        description
          "BFD sessions host hardware";
      }
      enum bfd-host-unknown {
        value 2;
        description
          "Unknown host";
      }
    }
    description
      "BFD sessions host";
  }

  grouping bfd-neighbor-params {
    description
      "BFD neighbour parameters";
    leaf ld {
      type uint32;
      description
        "Local discriminator";
    }
    leaf rd {
      type uint32;
      description
        "Remote discriminator";
    }
    leaf remote-state {
      type bfd-ios-xe-oper:bfd-remote-state-type;
      description
        "Indicates the remote state as reported by the BFD neighbor. For BFD version 0, the Remote Heard (RH) state is also mapped to up/down.";
    }
    leaf state {
      type bfd-ios-xe-oper:bfd-state-type;
      description
        "Current operational state of the BFD session (e.g., up, down, init, admin down, fail, invalid).";
    }
    leaf remote-min-tx-int {
      type uint32;
      units "microseconds";
      description
        "Configured received remote TX interval";
    }
    leaf remote-min-rx-int {
      type uint32;
      units "microseconds";
      description
        "Configured received remote RX interval";
    }
    leaf remote-multiplier {
      type uint32;
      description
        "Configured received remote multiplier value";
    }
    leaf local-min-tx-int {
      type uint32;
      units "microseconds";
      description
        "Configured transmit control packet interval";
    }
    leaf local-min-rx-int {
      type uint32;
      units "microseconds";
      description
        "Configured receive control packet interval";
    }
    leaf local-multiplier {
      type uint32;
      description
        "Configured local multiplier value";
    }
    leaf local-diag {
      type bfd-ios-xe-oper:bfd-diag-state;
      description
        "The local diagnostic code indicating the reason for the remote BFD session failure.";
    }
    leaf remote-diag {
      type bfd-ios-xe-oper:bfd-diag-state;
      description
        "The diagnostic code reported by the remote BFD neighbor indicating the reason for session failure.";
    }
    leaf session-host {
      type bfd-ios-xe-oper:bfd-session-host;
      description
        "If the hardware limit is exceeded, then the sessions are hosted in software";
    }
    leaf common-tx-interval {
      type uint32;
      units "microseconds";
      description
        "Common negotiated interval value";
    }
    leaf hold-down-interval {
      type uint32;
      units "microseconds";
      description
        "The hold-down interval, in microseconds, indicating the time after which the BFD session is considered down if no control packets are received.";
    }
  }

  grouping bfd-config-state {
    description
      "BFD config state";
    leaf if-name {
      type string;
      description
        "Interface identifier of BFD session";
    }
    leaf enabled {
      type boolean;
      description
        "BFD session enable status";
    }
    leaf ip {
      type inet:ip-address;
      description
        "Source IP address used for the BFD session";
    }
    leaf desired-min-tx-int {
      type uint32;
      units "milliseconds";
      description
        "BFD minimum transmit interval in msecs";
    }
    leaf req-min-rx {
      type uint32;
      units "milliseconds";
      description
        "BFD required minimum receive interval in msecs";
    }
    leaf detect-mult {
      type uint32;
      description
        "BFD detection interval multiplier";
    }
  }

  grouping bfd-echo {
    description
      "BFD echo state";
    leaf active {
      type boolean;
      description
        "BFD echo active state";
    }
    leaf last-pak-tx {
      type uint64;
      units "nanoseconds";
      description
        "The date and time at which the last BFD packet was transmitted for this session, expressed as the number of nanoseconds since the Unix epoch (January 1, 1970, 00:00 UTC).";
    }
    leaf last-pak-rx {
      type uint64;
      units "nanoseconds";
      description
        "The date and time at which the last BFD packet was received for this session, expressed as the number of nanoseconds since the Unix epoch (January 1, 1970, 00:00 UTC).";
    }
    leaf tx-packets {
      type uint64;
      description
        "Number of BFD echo packets transmitted";
    }
    leaf rx-packets {
      type uint64;
      description
        "Number of BFD echo packets received";
    }
    leaf up-trans {
      type uint64;
      description
        "Number of BFD session up transitions";
    }
  }

  grouping bfd-async {
    description
      "BFD Async mode";
    leaf last-pak-tx {
      type uint64;
      units "nanoseconds";
      description
        "The date and time at which the last BFD packet was transmitted for this session, expressed as the number of nanoseconds since the Unix epoch (January 1, 1970, 00:00 UTC).";
    }
    leaf last-pak-rx {
      type uint64;
      units "nanoseconds";
      description
        "The date and time at which the last BFD packet was received for this session, expressed as the number of nanoseconds since the Unix epoch (January 1, 1970, 00:00 UTC).";
    }
    leaf tx-packets {
      type uint64;
      description
        "Number of BFD control packets transmitted";
    }
    leaf rx-packets {
      type uint64;
      description
        "Number of BFD control packets received";
    }
    leaf up-trans {
      type uint64;
      description
        "Number of BFD session up transitions";
    }
  }

  grouping bfd-peer-info {
    description
      "BFD peer state";
    leaf local-addr {
      type inet:ip-address;
      description
        "BFD session source IP address";
    }
    leaf rem-addr {
      type inet:ip-address;
      description
        "BFD session remote IP address";
    }
    leaf sess-state {
      type bfd-ios-xe-oper:bfd-state-type;
      description
        "Operational state of the BFD session (e.g., up, down, init, fail, admin down, invalid).";
    }
    leaf rem-sess-state {
      type bfd-ios-xe-oper:bfd-remote-state-type;
      description
        "State of the BFD session as reported by the remote peer (e.g., remote up, remote down, remote init, remote admin down, remote invalid).";
    }
    leaf last-fail-time {
      type uint64;
      units "nanoseconds";
      description
        "The time of the last transition of the BFD session out of the UP state, expressed as the number of nanoseconds since the Unix epoch (January 1, 1970, 00:00 UTC).";
    }
    leaf fail-trans {
      type uint64;
      description
        "Number of BFD session failure transitions";
    }
    leaf local-discr {
      type uint32;
      description
        "BFD session local discriminator";
    }
    leaf rem-discr {
      type uint32;
      description
        "BFD session remote discriminator";
    }
    leaf local-diag-code {
      type bfd-ios-xe-oper:bfd-diag-state;
      description
        "BFD session local diagnostic code";
    }
    leaf rem-diag-code {
      type bfd-ios-xe-oper:bfd-diag-state;
      description
        "BFD session remote diagnostic code";
    }
    leaf rem-min-rx-int {
      type uint32;
      units "milliseconds";
      description
        "BFD session remote minimum receive interval";
    }
    leaf demand-mode-req {
      type boolean;
      description
        "BFD session demand mode requested";
    }
    leaf rem-auth-enabled {
      type boolean;
      description
        "BFD session remote authentication enabled";
    }
    leaf rem-ctrl-plane-ind {
      type boolean;
      description
        "BFD session remote control plane independent";
    }
    container echo {
      description
        "BFD session echo mode statistics";
      uses bfd-ios-xe-oper:bfd-echo;
    }
    container async {
      description
        "BFD session async mode statistics";
      uses bfd-ios-xe-oper:bfd-async;
    }
  }

  grouping bfd-peer-state {
    description
      "BFD session peer state";
    leaf local-discr {
      type uint32;
      description
        "BFD session peer local discriminator key";
    }
    container peer {
      description
        "Detailed information about the BFD session peer, including state, addresses, and statistics.";
      uses bfd-ios-xe-oper:bfd-peer-info;
    }
  }

  grouping bfd-tunnel-path-key {
    description
      "BFD tunnel Path Key";
    leaf interface {
      type string;
      description
        "Associated interface";
    }
    leaf lsp-type {
      type bfd-ios-xe-oper:bfd-lsp-type;
      description
        "LSP type";
    }
  }

  grouping bfd-circuit-key {
    description
      "BFD circuit key";
    leaf interface {
      type string;
      description
        "Associated interface";
    }
    leaf vcid {
      type uint32;
      description
        "Virtual circuit identifier";
    }
  }

  grouping bfd-nbr-key {
    description
      "BFD Neighbor key";
    leaf ip {
      type inet:ip-address;
      description
        "Neighbor IP address";
    }
    leaf interface {
      type string;
      description
        "Associated interface";
    }
  }

  grouping mhop-nbr-key {
    description
      "BFD MHOP Neighbor key";
    leaf ip {
      type inet:ip-address;
      description
        "Neighbor IP address";
    }
    leaf src-ip {
      type inet:ip-address;
      description
        "Source IP address";
    }
  }

  grouping mhop-vrf-nbr-key {
    description
      "BFD MHOP VRF Neighbor key";
    leaf ip {
      type inet:ip-address;
      description
        "Neighbor IP address";
    }
    leaf vrf {
      type string;
      description
        "Name of the VRF associated with the BFD neighbor.";
    }
    leaf src-ip {
      type inet:ip-address;
      description
        "Source IP address";
    }
  }

  grouping session-count-info {
    description
      "BFD sessions info";
    leaf max-sup-sw-sess {
      type uint32;
      description
        "Maximum supported software sessions";
    }
    leaf max-sup-hw-sess {
      type uint32;
      description
        "Maximum supported hardware sessions";
    }
    leaf total-session {
      type uint32;
      description
        "Total number of BFD sessions currently present on the device.";
    }
    leaf init-session {
      type uint32;
      description
        "Number of BFD sessions currently in the INIT state.";
    }
    leaf down-session {
      type uint32;
      description
        "Number of BFD sessions currently in the DOWN state.";
    }
    leaf up-session {
      type uint32;
      description
        "Number of BFD sessions currently in the UP state.";
    }
    leaf admin-down-session {
      type uint32;
      description
        "Number of BFD sessions currently in the administratively down (ADMIN DOWN) state.";
    }
  }

  grouping bfd-info {
    description
      "interface";
    leaf if-name {
      type string;
      description
        "BFD interface name";
    }
    container state {
      description
        "Operational state information for the BFD session on this interface, including configuration and status parameters.";
      uses bfd-ios-xe-oper:bfd-config-state;
    }
    list bfd-peer {
      key "local-discr";
      description
        "List of BFD peers associated with this interface, each representing a BFD session with a remote neighbor.";
      uses bfd-ios-xe-oper:bfd-peer-state;
    }
  }

  grouping bfd-session-v2 {
    description
      "BFD session data";
    leaf type {
      type bfd-ios-xe-oper:bfd-oper-session-type;
      description
        "Session type";
    }
    container bfd-tunnel-paths {
      description
        "BFD tunnel path information";
      list bfd-tunnel-path {
        when "../../type='mpls-tp'";
        key "interface lsp-type";
        description
          "List of BFD tunnel paths";
        uses bfd-ios-xe-oper:bfd-tunnel-path-key;
        uses bfd-ios-xe-oper:bfd-neighbor-params;
      }
    }
    container bfd-circuits {
      description
        "BFD circuit information";
      list bfd-circuit {
        when "../../type='vccv'";
        key "interface vcid";
        description
          "List of BFD circuits";
        uses bfd-ios-xe-oper:bfd-circuit-key;
        uses bfd-ios-xe-oper:bfd-neighbor-params;
      }
    }
    container bfd-nbrs {
      description
        "BFD neighbor information";
      list bfd-nbr {
        when "../../type!='mpls-tp' and ../../type!='vccv'";
        key "ip interface";
        description
          "List of BFD neighbors";
        uses bfd-ios-xe-oper:bfd-nbr-key;
        uses bfd-ios-xe-oper:bfd-neighbor-params;
      }
    }
    container bfd-mhop-nbrs {
      description
        "Multi hop neighbors for multi hop neighbor scenario
         for global VRF (no VRF)";
      list bfd-mhop-nbr {
        when "../../type='ipv4-multihop' or ../../type='ipv6-multihop'";
        key "ip src-ip";
        description
          "List of multi-hop BFD neighbor sessions.";
        uses bfd-ios-xe-oper:mhop-nbr-key;
        uses bfd-ios-xe-oper:bfd-neighbor-params;
      }
    }
    container bfd-mhop-vrf-nbrs {
      description
        "Multi hop neighbors for multi hop neighbor scenario
         with non-global VRF";
      list bfd-mhop-vrf-nbr {
        when "../../type='ipv4-multihop' or ../../type='ipv6-multihop'";
        key "ip vrf src-ip";
        description
          "List of BFD multi-hop neighbor entries associated with a specific non-global VRF.";
        uses bfd-ios-xe-oper:mhop-vrf-nbr-key;
        uses bfd-ios-xe-oper:bfd-neighbor-params;
      }
    }
  }

  container bfd-state {
    config false;
    description
      "Contains operational information about all BFD (Bidirectional Forwarding Detection) neighbors, sessions, and interfaces on the device.";
    container sessions {
      description
        "BFD neighbor session information";
      list session {
        key "type";
        description
          "List of BFD sessions";
        uses bfd-ios-xe-oper:bfd-session-v2;
      }
    }
    container bfd-session-info {
      presence "bfd-session-info";
      description
        "Provides summary state information for all BFD sessions, including counts of sessions by status (up, down, admin down, etc.) and hardware/software session support.";
      uses bfd-ios-xe-oper:session-count-info;
    }
    list bfd-if {
      key "if-name";
      description
        "BFD interface information";
      uses bfd-ios-xe-oper:bfd-info;
    }
  }
}
