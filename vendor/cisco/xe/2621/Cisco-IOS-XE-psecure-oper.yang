module Cisco-IOS-XE-psecure-oper {
  yang-version 1.1;
  namespace "http://cisco.com/ns/yang/Cisco-IOS-XE-psecure-oper";
  prefix psecure-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for monitoring of port security state information.
     Copyright (c) 2020, 2022 by Cisco Systems, Inc.
     All rights reserved.";

  revision 2026-08-01 {
    description
      "Refined existing leaf descriptions for clarity and consistency.";
    reference
      "1.2.1";
    cisco-semver:module-version "1.2.1";
  }
  revision 2022-11-01 {
    description
      "Update yang-version to 1.1";
    reference
      "1.2.0";
    cisco-semver:module-version "1.2.0";
  }
  revision 2022-03-01 {
    description
      "Deprecated port security parameter list. New port security entry
       will have support for multiple port security entries with the same
       MAC addresses and different VLANs.";
    reference
      "1.1.0";
    cisco-semver:module-version "1.1.0";
  }
  revision 2021-03-01 {
    description
      "Initial revision";
    reference
      "1.0.0";
    cisco-semver:module-version "1.0.0";
  }

  typedef psecure-type {
    type enumeration {
      enum psecure-configured {
        value 0;
        description
          "Indicates the type of port security applied.";
      }
      enum psecure-dynamic {
        value 1;
        description
          "Indicates a dynamically learned port security type.";
      }
      enum psecure-sticky {
        value 2;
        description
          "Indicates a sticky port security type.";
      }
      enum psecure-none {
        value 3;
        description
          "Indicates that no specific port security type is assigned.";
      }
    }
    description
      "Enumerates the supported port security entry types.";
  }

  grouping psecure-param {
    description
      "Defines the port security parameters associated with a local interface.";
    leaf vlan {
      type uint16;
      description
        "Identifies the VLAN associated with port security.";
    }
    leaf mac {
      type yang:mac-address;
      description
        "Specifies the secure MAC address associated with port security.";
    }
    leaf type {
      type psecure-ios-xe-oper:psecure-type;
      description
        "Indicates the type of secure MAC address used for port security.";
    }
    leaf age-remain {
      type uint32;
      units "minutes";
      description
        "Shows the remaining aging time, in minutes, for port security.";
    }
  }

  grouping psecure-entry-key {
    description
      "Defines the key fields that uniquely identify a port security entry.";
    leaf vlan {
      type uint16;
      description
        "Identifies the VLAN that uniquely keys a port security entry.";
    }
    leaf mac {
      type yang:mac-address;
      description
        "Specifies the secure MAC address associated with port security.";
    }
  }

  grouping psecure-entry {
    description
      "Defines the details associated with a port security entry.";
    leaf type {
      type psecure-ios-xe-oper:psecure-type;
      description
        "Indicates the type of secure MAC address used for port security.";
    }
  }

  grouping psecure-state {
    description
      "Contains the port security state maintained for a local interface.";
    leaf if-name {
      type string;
      description
        "Specifies the name of the local interface for which port security state is reported.";
    }
    list psecure-param {
      key "mac";
      status deprecated;
      description
        "This list is deprecated because it does not support
         multiple port security entries with same MAC address.
         Use port security entry group instead. The new list
         supports port security entries with the same MAC address
         and different VLANs.";
      uses psecure-ios-xe-oper:psecure-param;
    }
    list psecure-entry {
      key "vlan mac";
      description
        "Lists the port security entries present on the local interface.";
      uses psecure-ios-xe-oper:psecure-entry-key;
      uses psecure-ios-xe-oper:psecure-entry;
    }
  }

  container psecure-oper-data {
    config false;
    description
      "Container for data related to port security.";
    list psecure-state {
      key "if-name";
      description
        "Lists port security operational state entries for local interfaces.";
      uses psecure-ios-xe-oper:psecure-state;
    }
  }
}
