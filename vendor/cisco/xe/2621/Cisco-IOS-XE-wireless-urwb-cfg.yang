module Cisco-IOS-XE-wireless-urwb-cfg {
  yang-version 1.1;
  namespace "http://cisco.com/ns/yang/Cisco-IOS-XE-wireless-urwb-cfg";
  prefix wireless-urwb-cfg;

  import Cisco-IOS-XE-wireless-enum-types {
    prefix wireless-enum-types;
  }
  import Cisco-IOS-XE-wireless-urwb-common-types {
    prefix wireless-urwb-common-types;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Ultra Reliable Wireless Backhaul (URWB) configuration data.
     Copyright (c) 2025-2026 by Cisco Systems, Inc.
     All rights reserved.";

  revision 2026-08-01 {
    description
      "- Added URWB Ethernet configuration leaves
       - Added RADIUS server group configuration for URWB profile
       - Added URWB NAT configuration support
       - Updated descriptions for URWB profile configuration leaves and containers
       - Updated URWB passphrase constraint to allow special characters only for AES encrypted network keys
       - Updated RADIUS server group must constraint to allow unconfigured state
       - Added maximum elements constraint for URWB NAT rule list";
    reference
      "3.0.0";
    cisco-semver:module-version "3.0.0";
  }
  revision 2026-02-01 {
    description
      "- Fix model constraint for URWB profile description leaf by adding a space to the list of allowed characters
       - Added new configuration reliability parameters for URWB
       - Added passphrase type and updated passphrase pattern";
    reference
      "2.0.0";
    cisco-semver:module-version "2.0.0";
  }
  revision 2025-07-01 {
    description
      "Initial revision";
    reference
      "1.0.0";
    cisco-semver:module-version "1.0.0";
  }

  grouping st-ethertype-list {
    description
      "This contains all attributes for mpls ether type";
    leaf ethertype {
      type uint16;
      description
        "This value indicates the ether type used";
    }
  }

  grouping st-urwb-rel {
    description
      "URWB reliability configuration";
    leaf grat-arp {
      type wireless-enum-types:urwb-grat-arp;
      default "urwb-grat-arp-disable";
      description
        "Specifies the URWB gratuitous ARP management mode";
    }
    leaf grat-arp-delay {
      type uint32 {
        range "0 .. 2147483647";
      }
      units "milliseconds";
      default "150";
      description
        "Specifies the delay time before sending URWB gratuitous ARP packets";
    }
    leaf qosmap-pri-0 {
      type uint8 {
        range "0 .. 7";
      }
      default "0";
      description
        "Specifies the URWB Quality of Service (QoS) mapping for priority 0";
    }
    leaf qosmap-pri-1 {
      type uint8 {
        range "0 .. 7";
      }
      default "1";
      description
        "Specifies the URWB Quality of Service (QoS) mapping for priority 1";
    }
    leaf qosmap-pri-2 {
      type uint8 {
        range "0 .. 7";
      }
      default "2";
      description
        "Specifies the URWB Quality of Service (QoS) mapping for priority 2";
    }
    leaf qosmap-pri-3 {
      type uint8 {
        range "0 .. 7";
      }
      default "3";
      description
        "Specifies the URWB Quality of Service (QoS) mapping for priority 3";
    }
    leaf qosmap-pri-4 {
      type uint8 {
        range "0 .. 7";
      }
      default "4";
      description
        "Specifies the URWB Quality of Service (QoS) mapping for priority 4";
    }
    leaf qosmap-pri-5 {
      type uint8 {
        range "0 .. 7";
      }
      default "5";
      description
        "Specifies the URWB Quality of Service (QoS) mapping for priority 5";
    }
    leaf qosmap-pri-6 {
      type uint8 {
        range "0 .. 7";
      }
      default "6";
      description
        "Specifies the URWB Quality of Service (QoS) mapping for priority 6";
    }
    leaf qosmap-pri-7 {
      type uint8 {
        range "0 .. 7";
      }
      default "7";
      description
        "Specifies the URWB Quality of Service (QoS) mapping for priority 7";
    }
  }

  grouping st-urwb-nat-rule-list {
    description
      "URWB NAT rule list entry";
    leaf inside-ip {
      type inet:ip-address;
      must "not(starts-with(., '0.')) and not(starts-with(., '127.')) and not(starts-with(., '224.')) and not(starts-with(., '225.')) and not(starts-with(., '226.')) and not(starts-with(., '227.')) and not(starts-with(., '228.')) and not(starts-with(., '229.')) and not(starts-with(., '230.')) and not(starts-with(., '231.')) and not(starts-with(., '232.')) and not(starts-with(., '233.')) and not(starts-with(., '234.')) and not(starts-with(., '235.')) and not(starts-with(., '236.')) and not(starts-with(., '237.')) and not(starts-with(., '238.')) and not(starts-with(., '239.')) and not(starts-with(., '240.')) and not(starts-with(., '241.')) and not(starts-with(., '242.')) and not(starts-with(., '243.')) and not(starts-with(., '244.')) and not(starts-with(., '245.')) and not(starts-with(., '246.')) and not(starts-with(., '247.')) and not(starts-with(., '248.')) and not(starts-with(., '249.')) and not(starts-with(., '250.')) and not(starts-with(., '251.')) and not(starts-with(., '252.')) and not(starts-with(., '253.')) and not(starts-with(., '254.')) and not(starts-with(., '255.')) and not(. = '128.0.0.0') and not(. = '192.0.0.0')" {
        error-message "NAT rule inside IP must be a valid IPv4 address - cannot be 0.x.x.x, loopback, multicast (224.0.0.0-239.255.255.255), Class E (240.0.0.0-255.255.255.255), or reserved subnet-mask edge values (128.0.0.0, 192.0.0.0)";
        error-app-tag "must-violation";
      }
      description
        "Inside IP address for NAT translation";
    }
    leaf in-port {
      type uint16 {
        range "1 .. 65535";
      }
      description
        "Inside port number for NAT rule";
    }
  }

  grouping urwb-profile {
    description
      "URWB profile configuration";
    leaf profile-name {
      type string {
        length "1..128" {
          error-message "URWB profile-name should not be greater than 128 characters";
          error-app-tag "must-violation";
        }
        pattern '[!-~]([ -~]*[!-~])?';
        pattern '[!-~]([ -~]*[!-~])?' {
          error-message "URWB profile name must use ASCII 1-126 characters and must not contain leading or trailing spaces";
          error-app-tag "pattern-violation";
        }
      }
      description
        "Unique name identifying the URWB profile. The name must use ASCII characters (33-126) and cannot have leading or trailing spaces.";
    }
    leaf descp {
      type string {
        length "0..128";
        pattern '([!-~]([ -~]*[!-~])?)?';
      }
      default "";
      description
        "Description for URWB profile. Description may contain only printable ASCII characters with no leading or trailing spaces";
    }
    leaf enabled {
      type boolean;
      default "false";
      description
        "This value indicates whether URWB feature is enabled";
    }
    leaf passphr {
      type string {
        length "0..64";
        pattern '[	 -~]*';
      }
      must "../passphr-type = 'aes' or translate(., '|;$<>&^~`?\\', '') = ." {
        error-message "Network key must not contain special characters |;$<>&^~`?\\";
        error-app-tag "must-violation";
      }
      default "";
      description
        "Specifies the passphrase used to authenticate to the URWB network";
    }
    leaf passphr-type {
      type wireless-enum-types:crypt-type;
      default "clear";
      description
        "Indicates the encryption type for the URWB passphrase.";
    }
    container mob {
      description
        "URWB mobility configuration";
      uses wireless-urwb-common-types:st-urwb-mob;
    }
    container mpls {
      description
        "Configuration container for MPLS (Multiprotocol Label Switching) parameters within the Ultra Reliable Wireless Backhaul (URWB) profile.";
      uses wireless-urwb-common-types:st-urwb-mpls;
    }
    container mpo {
      description
        "Configuration container for MPO (Multi-Path Optimization) parameters within the Ultra Reliable Wireless Backhaul (URWB) profile.";
      uses wireless-urwb-common-types:st-urwb-mpo;
    }
    leaf mcast {
      type wireless-enum-types:urwb-mcast;
      default "urwb-mcast-dis";
      description
        "Specifies the multicast configuration mode for the URWB (Ultra Reliable Wireless Backhaul) profile.";
    }
    leaf strong-netkey {
      type boolean;
      default "false";
      description
        "Indicates whether strong network key is enabled";
    }
    container ethertype-lists {
      description
        "Configuration container for specifying a list of Ethernet types to be used in the URWB (Ultra Reliable Wireless Backhaul) profile.";
      list ethertype-list {
        key "ethertype";
        description
          "List of Ethernet type (ethertype) entries to be used in the URWB (Ultra Reliable Wireless Backhaul) profile, each entry identifies a specific ethertype value.";
        uses wireless-urwb-cfg:st-ethertype-list;
      }
    }
    container rel {
      description
        "Configuration container for reliability parameters related to the URWB (Ultra Reliable Wireless Backhaul) profile.";
      uses wireless-urwb-cfg:st-urwb-rel;
    }
    container eth {
      description
        "URWB ethernet configuration";
      uses wireless-urwb-common-types:st-urwb-eth;
    }
    container nat {
      description
        "URWB NAT configuration";
      uses wireless-urwb-common-types:st-urwb-nat;
    }
    container nat-rule-lists {
      description
        "URWB NAT rule list configuration";
      list nat-rule-list {
        key "outside-port proto";
        max-elements 100;
        description
          "URWB NAT rule entry";
        uses wireless-urwb-common-types:st-urwb-nat-rule-key;
        uses wireless-urwb-cfg:st-urwb-nat-rule-list;
      }
    }
    leaf rad-srv-grp {
      type string {
        length "1..64" {
          error-message "URWB radius-server-group name should not be greater than 64 characters";
          error-app-tag "must-violation";
        }
        pattern '[!-~]([ -~]*[!-~])?' {
          error-message "URWB radius-server-group name must use printable ASCII characters and must not contain leading or trailing spaces";
          error-app-tag "pattern-violation";
        }
      }
      must "not(.) or ../mob/role = 'urwb-mob-client'" {
        error-message "URWB radius-server-group is only valid when mobility role is client";
        error-app-tag "must-violation";
      }
      description
        "Name of the RADIUS server group used for authenticating wired 802.1X clients";
    }
  }

  container urwb-cfg-data {
    description
      "URWB backhaul configuration data";
    container urwb-profiles {
      description
        "URWB policy configuration profiles for APs";
      list urwb-profile {
        key "profile-name";
        description
          "URWB policy configuration for AP";
        uses wireless-urwb-cfg:urwb-profile;
      }
    }
  }
}
