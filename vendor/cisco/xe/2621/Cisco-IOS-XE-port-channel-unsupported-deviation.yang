module Cisco-IOS-XE-port-channel-unsupported-deviation {
  yang-version 1.1;
  namespace "http://cisco.com/ns/yang/Cisco-IOS-XE-port-channel-unsupported-deviation";
  prefix ios-ethernet-punsupported;

  import Cisco-IOS-XE-native {
    prefix ios;
  }
  import Cisco-IOS-XE-ethernet {
    prefix ios-eth;
  }

  organization
    "Cisco Systems";
  description
    "Cisco XE Native Deviation YANG module for IOS
     Copyright (c) 2024 by Cisco Systems, Inc.
     All rights reserved.";

  revision 2026-08-01 {
    description
      "- Added TwoHundredGigE and FourHundredGigE interface support";
  }
  revision 2025-07-01 {
    description
      "- Added FiftyGigabitEthernet interface support";
  }
  revision 2024-07-01 {
    description
      "Added Unsupported deviations for Port-channel";
  }

  deviation "/ios:native/ios:interface/ios:GigabitEthernet/ios-eth:channel-group/ios-eth:non-silent" {
    deviate not-supported;
  }

  deviation "/ios:native/ios:interface/ios:AppGigabitEthernet/ios-eth:channel-group/ios-eth:non-silent" {
    deviate not-supported;
  }

  deviation "/ios:native/ios:interface/ios:FastEthernet/ios-eth:channel-group/ios-eth:non-silent" {
    deviate not-supported;
  }

  deviation "/ios:native/ios:interface/ios:FiveGigabitEthernet/ios-eth:channel-group/ios-eth:non-silent" {
    deviate not-supported;
  }

  deviation "/ios:native/ios:interface/ios:FortyGigabitEthernet/ios-eth:channel-group/ios-eth:non-silent" {
    deviate not-supported;
  }

  deviation "/ios:native/ios:interface/ios:FiftyGigabitEthernet/ios-eth:channel-group/ios-eth:non-silent" {
    deviate not-supported;
  }

  deviation "/ios:native/ios:interface/ios:TenGigabitEthernet/ios-eth:channel-group/ios-eth:non-silent" {
    deviate not-supported;
  }

  deviation "/ios:native/ios:interface/ios:TwentyFiveGigE/ios-eth:channel-group/ios-eth:non-silent" {
    deviate not-supported;
  }

  deviation "/ios:native/ios:interface/ios:TwoGigabitEthernet/ios-eth:channel-group/ios-eth:non-silent" {
    deviate not-supported;
  }

  deviation "/ios:native/ios:interface/ios:HundredGigE/ios-eth:channel-group/ios-eth:non-silent" {
    deviate not-supported;
  }

  deviation "/ios:native/ios:interface/ios:TwoHundredGigE/ios-eth:channel-group/ios-eth:non-silent" {
    deviate not-supported;
  }

  deviation "/ios:native/ios:interface/ios:FourHundredGigE/ios-eth:channel-group/ios-eth:non-silent" {
    deviate not-supported;
  }

  deviation "/ios:native/ios:interface/ios:GigabitEthernet/ios-eth:channel-group/ios-eth:auto" {
    deviate not-supported;
  }

  deviation "/ios:native/ios:interface/ios:AppGigabitEthernet/ios-eth:channel-group/ios-eth:auto" {
    deviate not-supported;
  }

  deviation "/ios:native/ios:interface/ios:FastEthernet/ios-eth:channel-group/ios-eth:auto" {
    deviate not-supported;
  }

  deviation "/ios:native/ios:interface/ios:FiveGigabitEthernet/ios-eth:channel-group/ios-eth:auto" {
    deviate not-supported;
  }

  deviation "/ios:native/ios:interface/ios:FortyGigabitEthernet/ios-eth:channel-group/ios-eth:auto" {
    deviate not-supported;
  }

  deviation "/ios:native/ios:interface/ios:FiftyGigabitEthernet/ios-eth:channel-group/ios-eth:auto" {
    deviate not-supported;
  }

  deviation "/ios:native/ios:interface/ios:TenGigabitEthernet/ios-eth:channel-group/ios-eth:auto" {
    deviate not-supported;
  }

  deviation "/ios:native/ios:interface/ios:TwentyFiveGigE/ios-eth:channel-group/ios-eth:auto" {
    deviate not-supported;
  }

  deviation "/ios:native/ios:interface/ios:TwoGigabitEthernet/ios-eth:channel-group/ios-eth:auto" {
    deviate not-supported;
  }

  deviation "/ios:native/ios:interface/ios:HundredGigE/ios-eth:channel-group/ios-eth:auto" {
    deviate not-supported;
  }

  deviation "/ios:native/ios:interface/ios:TwoHundredGigE/ios-eth:channel-group/ios-eth:auto" {
    deviate not-supported;
  }

  deviation "/ios:native/ios:interface/ios:FourHundredGigE/ios-eth:channel-group/ios-eth:auto" {
    deviate not-supported;
  }

  deviation "/ios:native/ios:port-channel/ios-eth:load-balance" {
    deviate not-supported;
  }
}
