module Cisco-IOS-XE-device-tracking-cat9k-deviation {
  yang-version 1.1;
  namespace "http://cisco.com/ns/yang/Cisco-IOS-XE-device-tracking-cat9k-deviation";
  prefix ios-device-tracking-d;

  import Cisco-IOS-XE-native {
    prefix ios;
  }
  import Cisco-IOS-XE-switch {
    prefix ios-sw;
  }

  organization
    "Cisco Systems";
  description
    "Cisco XE Native Deviation YANG module for IOS
     Copyright (c) 2025 by Cisco Systems, Inc.
     All rights reserved.";

  revision 2026-08-01 {
    description
      "- Added TwoHundredGigE and FourHundredGigE interface support";
  }
  revision 2026-02-01 {
    description
      "- Adding deviation file for device-tracking in cat9k platform";
  }

  deviation "/ios:native/ios:interface/ios:FastEthernet/ios-sw:device-tracking" {
    deviate add {
      must "not (../ios:switchport-conf/ios:switchport = 'false') or (../ios:switchport-conf/ios:switchport = 'true')" {
        error-message "To configure attach device-tracking policy, set switchport-conf to true; To detach a policy, set switchport to false";
      }
    }
  }

  deviation "/ios:native/ios:interface/ios:GigabitEthernet/ios-sw:device-tracking" {
    deviate add {
      must "not (../ios:switchport-conf/ios:switchport = 'false') or (../ios:switchport-conf/ios:switchport = 'true')" {
        error-message "To configure attach device-tracking policy, set switchport-conf to true; To detach a policy, set switchport to false";
      }
    }
  }

  deviation "/ios:native/ios:interface/ios:TwoGigabitEthernet/ios-sw:device-tracking" {
    deviate add {
      must "not (../ios:switchport-conf/ios:switchport = 'false') or (../ios:switchport-conf/ios:switchport = 'true')" {
        error-message "To configure attach device-tracking policy, set switchport-conf to true; To detach a policy, set switchport to false";
      }
    }
  }

  deviation "/ios:native/ios:interface/ios:FiveGigabitEthernet/ios-sw:device-tracking" {
    deviate add {
      must "not (../ios:switchport-conf/ios:switchport = 'false') or (../ios:switchport-conf/ios:switchport = 'true')" {
        error-message "To configure attach device-tracking policy, set switchport-conf to true; To detach a policy, set switchport to false";
      }
    }
  }

  deviation "/ios:native/ios:interface/ios:AppGigabitEthernet/ios-sw:device-tracking" {
    deviate add {
      must "not (../ios:switchport-conf/ios:switchport = 'false') or (../ios:switchport-conf/ios:switchport = 'true')" {
        error-message "To configure attach device-tracking policy, set switchport-conf to true; To detach a policy, set switchport to false";
      }
    }
  }

  deviation "/ios:native/ios:interface/ios:TenGigabitEthernet/ios-sw:device-tracking" {
    deviate add {
      must "not (../ios:switchport-conf/ios:switchport = 'false') or (../ios:switchport-conf/ios:switchport = 'true')" {
        error-message "To configure attach device-tracking policy, set switchport-conf to true; To detach a policy, set switchport to false";
      }
    }
  }

  deviation "/ios:native/ios:interface/ios:TwentyFiveGigE/ios-sw:device-tracking" {
    deviate add {
      must "not (../ios:switchport-conf/ios:switchport = 'false') or (../ios:switchport-conf/ios:switchport = 'true')" {
        error-message "To configure attach device-tracking policy, set switchport-conf to true; To detach a policy, set switchport to false";
      }
    }
  }

  deviation "/ios:native/ios:interface/ios:FortyGigabitEthernet/ios-sw:device-tracking" {
    deviate add {
      must "not (../ios:switchport-conf/ios:switchport = 'false') or (../ios:switchport-conf/ios:switchport = 'true')" {
        error-message "To configure attach device-tracking policy, set switchport-conf to true; To detach a policy, set switchport to false";
      }
    }
  }

  deviation "/ios:native/ios:interface/ios:FiftyGigabitEthernet/ios-sw:device-tracking" {
    deviate add {
      must "not (../ios:switchport-conf/ios:switchport = 'false') or (../ios:switchport-conf/ios:switchport = 'true')" {
        error-message "To configure attach device-tracking policy, set switchport-conf to true; To detach a policy, set switchport to false";
      }
    }
  }

  deviation "/ios:native/ios:interface/ios:HundredGigE/ios-sw:device-tracking" {
    deviate add {
      must "not (../ios:switchport-conf/ios:switchport = 'false') or (../ios:switchport-conf/ios:switchport = 'true')" {
        error-message "To configure attach device-tracking policy, set switchport-conf to true; To detach a policy, set switchport to false";
      }
    }
  }

  deviation "/ios:native/ios:interface/ios:TwoHundredGigE/ios-sw:device-tracking" {
    deviate add {
      must "not (../ios:switchport-conf/ios:switchport = 'false') or (../ios:switchport-conf/ios:switchport = 'true')" {
        error-message "To configure attach device-tracking policy, set switchport-conf to true; To detach a policy, set switchport to false";
      }
    }
  }

  deviation "/ios:native/ios:interface/ios:FourHundredGigE/ios-sw:device-tracking" {
    deviate add {
      must "not (../ios:switchport-conf/ios:switchport = 'false') or (../ios:switchport-conf/ios:switchport = 'true')" {
        error-message "To configure attach device-tracking policy, set switchport-conf to true; To detach a policy, set switchport to false";
      }
    }
  }

  deviation "/ios:native/ios:interface/ios:Port-channel/ios-sw:device-tracking" {
    deviate add {
      must "not (../ios:switchport-conf/ios:switchport = 'false') or (../ios:switchport-conf/ios:switchport = 'true')" {
        error-message "To configure attach device-tracking policy, set switchport-conf to true; To detach a policy, set switchport to false";
      }
    }
  }
}
