module Cisco-IOS-XE-sdwan-rpc {
  yang-version 1.1;
  namespace "http://cisco.com/ns/yang/Cisco-IOS-XE-sdwan-rpc";
  prefix ios-xe-sdwan-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Copyright (c) 2022 by Cisco Systems, Inc.
     All rights reserved.";

  revision 2023-03-01 {
    description
      "Initial revision";
    reference
      "1.0.0";
    cisco-semver:module-version "1.0.0";
  }

  typedef sdwan-action-file-format-to-dump {
    type enumeration {
      enum csv-file {
        value 0;
        description
          "Option to dump routes into comma separated file";
      }
      enum json-file {
        value 1;
        description
          "Option to dump routes into file";
      }
    }
    description
      "Audit file format to create";
  }

  typedef sdwan-action-route-type-to-dump {
    type enumeration {
      enum advertised-routes {
        value 0;
        description
          "Option to dump advertised routes";
      }
      enum received-routes {
        value 1;
        description
          "Option to dump received routes";
      }
    }
    description
      "OMP routes to dump";
  }

  grouping sdwan-action-audit {
    description
      "Audit RPC input parameters";
    leaf uuid {
      type string;
      description
        "UUID is used to uniquely identify the audit action invoked
         and it is replayed back in the response notifications to correlate
         them back to the original operation.";
    }
    leaf route-type {
      type ios-xe-sdwan-rpc:sdwan-action-route-type-to-dump;
      description
        "OMP route types to dump";
    }
    leaf file-format {
      type ios-xe-sdwan-rpc:sdwan-action-file-format-to-dump;
      description
        "Audit file format to dump";
    }
    leaf file-to-delete {
      type string;
      description
        "Audit file to delete";
    }
  }

  rpc sdwan-action-audit {
    description
      "Audit action RPC";
    input {
      uses ios-xe-sdwan-rpc:sdwan-action-audit;
    }
  }
}
