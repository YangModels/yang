module Cisco-IOS-XE-process-cpu-oper {
  yang-version 1.1;
  namespace "http://cisco.com/ns/yang/Cisco-IOS-XE-process-cpu-oper";
  prefix process-cpu-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     monitoring CPU usage of processes in a Network Element.
     Copyright (c) 2016-2017, 2019, 2022, 2026 by Cisco Systems, Inc.
     All rights reserved.";

  revision 2026-08-01 {
    description
      "Improved CPU usage container and node descriptions for clarity and consistency.";
    reference
      "1.3.1";
    cisco-semver:module-version "1.3.1";
  }
  revision 2022-11-01 {
    description
      "Update yang-version to 1.1";
    reference
      "1.3.0";
    cisco-semver:module-version "1.3.0";
  }
  revision 2019-05-01 {
    description
      "Added semantic version";
    reference
      "1.2.0";
    cisco-semver:module-version "1.2.0";
  }
  revision 2018-10-29 {
    description
      "Cleaned up spelling errors in descriptions.";
    reference
      "1.1.0";
    cisco-semver:module-version "1.1.0";
  }
  revision 2017-02-07 {
    description
      "Initial revision";
    reference
      "1.0.0";
    cisco-semver:module-version "1.0.0";
  }

  grouping process-cpu-key {
    description
      "Unique process identifier";
    leaf pid {
      type uint32;
      description
        "Process ID.";
    }
    leaf name {
      type string;
      description
        "The name of the process.";
    }
  }

  grouping process-pid-cpu-usage {
    description
      "CPU usage statistics for a given IOS task.";
    leaf tty {
      type uint16;
      description
        "TTY associated with the IOS task.";
    }
    leaf total-run-time {
      type uint64;
      units "milli-seconds";
      description
        "Total run time of this IOS task (milliseconds).";
    }
    leaf invocation-count {
      type uint32;
      description
        "Total number of task invocations.";
    }
    leaf avg-run-time {
      type uint64;
      units "micro-seconds";
      description
        "Average run time of this IOS task (microseconds).";
    }
    leaf five-seconds {
      type decimal64 {
        fraction-digits 2;
      }
      units "percent";
      description
        "CPU busy percentage over the last 5 seconds.";
    }
    leaf one-minute {
      type decimal64 {
        fraction-digits 2;
      }
      units "percent";
      description
        "CPU busy percentage over the last 1 minute.";
    }
    leaf five-minutes {
      type decimal64 {
        fraction-digits 2;
      }
      units "percent";
      description
        "CPU busy percentage over the last 5 minutes.";
    }
  }

  grouping cpu-utilization {
    description
      "Container for total CPU utilization statistics.";
    leaf five-seconds {
      type uint8;
      units "percent";
      description
        "CPU busy percentage over the last 5 seconds.";
    }
    leaf five-seconds-intr {
      type uint8;
      units "percent";
      description
        "Interrupt CPU busy percentage over the last 5 seconds.";
    }
    leaf one-minute {
      type uint8;
      units "percent";
      description
        "CPU busy percentage over the last 1 minute.";
    }
    leaf five-minutes {
      type uint8;
      units "percent";
      description
        "CPU busy percentage over the last 5 minutes.";
    }
    container cpu-usage-processes {
      description
        "Container for system-wide per-IOS-task CPU usage statistics.";
      list cpu-usage-process {
        key "pid name";
        description
          "List of IOS tasks on the device.";
        uses process-cpu-ios-xe-oper:process-cpu-key;
        uses process-cpu-ios-xe-oper:process-pid-cpu-usage;
      }
    }
  }

  container cpu-usage {
    config false;
    description
      "Container for overall IOS task CPU utilization and per-IOS-task CPU usage statistics.";
    container cpu-utilization {
      description
        "Container for the IOS task utilization statistics.
         The task statistics are the share of the IOS process scheduling time that each IOS task uses.";
      uses process-cpu-ios-xe-oper:cpu-utilization;
    }
  }
}
