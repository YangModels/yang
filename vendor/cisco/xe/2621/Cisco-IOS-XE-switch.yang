module Cisco-IOS-XE-switch {
  yang-version 1.1;
  namespace "http://cisco.com/ns/yang/Cisco-IOS-XE-switch";
  prefix ios-sw;

  import cisco-semver {
    prefix cisco-semver;
  }
  import ietf-yang-types {
    prefix yang;
  }
  import ietf-inet-types {
    prefix inet;
  }
  import Cisco-IOS-XE-device-tracking {
    prefix ios-dt;
  }
  import Cisco-IOS-XE-native {
    prefix ios;
  }
  import Cisco-IOS-XE-igmp {
    prefix ios-igmp;
  }
  import Cisco-IOS-XE-types {
    prefix ios-types;
  }
  import Cisco-IOS-XE-features {
    prefix ios-features;
  }
  import Cisco-IOS-XE-arp {
    prefix ios-arp;
  }
  import Cisco-IOS-XE-flow {
    prefix ios-flow;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Switch Yang model.
     Copyright (c) 2016-2025 by Cisco Systems, Inc.
     All rights reserved.";

  revision 2026-08-01 {
    description
      "- Update device classifier cli to suite mac regex for or operation
       - Update condition as check in device classifier
       - Added model support for voice vlan
       - Obsoleted config-network-policy-grouping
       - Added the model support for voice-signaling vlan
       - Adding new cli for auto macsec
       - Moved the must from container mac-move to the redundancy-protocol leaf
       - Update range for system mtu";
    cisco-semver:module-version "11.0.0";
  }
  revision 2026-02-01 {
    description
      "- Adding new clis for device classifier
       - Obsolete enable-break container
       - Obsolete tftp-path, flash-path and tftp in switch container
       - Adding switchport access for HSR-ring interface and PRP-channel
       - Modify device classifier attach cli
       - Obsolete switchport trunk allowed vlan and switchport trunk allowed vlan none
       - Add support for device-tracking on 200 GigabitEthernet and 400 GigabitEthernet interfaces
       - Added support for switchport on 400 GigabitEthernet interfaces
       - Update string pattern for mac regex in device classifier
       - Added support for switchport on 200 GigabitEthernet interfaces
       - Update leaf interface to list interface under mrouter
       - Adding mac-move permit redundancy-protocol to port-security";
    cisco-semver:module-version "10.0.0";
  }
  revision 2025-07-01 {
    description
      "- Added tailf:alt-name to deprecated vlan and moved tailf:cli-drop-node-name to annotation file
       - Obsolete igmp snooping container
       - Added FiftyGigabitEthernet interface support
       - Updated IGMP snooping descriptions by removing 'Catalyst' reference
       - Obsolete interface switchport
       - Fixed sampler and datalink flow monitor attachment dependencies";
    cisco-semver:module-version "9.0.0";
  }
  revision 2024-07-01 {
    description
      "- Deprecated old device-classifier implementation
       - Obsolete old device-classifier deprecated implementation
       - Obsolete switchport trunk native VLAN tag
       - Added maximum-address-config container under port-security and deprecated maxcount container
       - Obsolete port-security-mac-address container and switchport-port-security container
       - Obsolete the node flash
       - Added datalink flow monitor support to SVI interface
       - Added 'tailf:cli-remove-before-change' to device classifier device-type list node
       - Fixed datalink flow monitor model
       - Obsolete access-group and tag nodes of service-template
       - Container level replace fix with pre-config for device-classifier";
    cisco-semver:module-version "8.0.0";
  }
  revision 2024-03-01 {
    description
      "- Deprecated enable-break container, added new container to have only enable-break per switch command
       - Added report leaf in switchport port-security violation
       - Added a dependency between trunk-allowed-vlan vs trunk-allowed-vlan-add commands";
    cisco-semver:module-version "7.1.0";
  }
  revision 2023-11-01 {
    description
      "- Added tailf create before and delete after annotations in max-addresses
       - Added tailf create after and delete before annotation in port-security-conf and modified the delete before tailf annotation in max-addresses
       - Deprecated switchport trunk allowed vlan container and added switchport-trunk-allowed-vlan-v2
       - Added range option for switchport trunk allowed vlan";
    cisco-semver:module-version "7.0.0";
  }
  revision 2023-07-01 {
    description
      "- macsec feature rearrange
       - Obsolete the XPath's of TwentyFiveGigabitEthernet interface";
    cisco-semver:module-version "6.0.0";
  }
  revision 2022-11-01 {
    description
      "- Update yang-version to 1.1
       - Added support for allowlist
       - Deprecated and added ip-igmp-snooping-vlan grouping
       - Removed must condition and fixed ordering for device-classifier configuration commands";
    cisco-semver:module-version "5.1.0";
  }
  revision 2022-07-01 {
    description
      "- Added support for boot command for multiple filename
       - Deprecated and added device-classifier configuration commands";
    cisco-semver:module-version "5.0.0";
  }
  revision 2022-03-01 {
    description
      "- Deprecated mac-address container
       - Added support for vlan voice and multiple hw-address
       - Added support for device-classifier configuration commands
       - Added description for hw-address in deprecated mac-address container
       - Updated description for vlan in deprecated mac-address container
       - Added dependency between switchport mode and switchport no negotiate";
    cisco-semver:module-version "4.2.0";
  }
  revision 2021-11-01 {
    description
      "- switch stack-speed support
       - Defender Mini support";
    cisco-semver:module-version "4.1.0";
  }
  revision 2021-07-01 {
    description
      "- Deprecated interface switchport
       - Add support of backward compatibility in switchport mode-choice and vlan-choice";
    cisco-semver:module-version "4.0.1";
  }
  revision 2021-03-01 {
    description
      "- Change range for absolute-timer of service-template";
    cisco-semver:module-version "4.0.0";
  }
  revision 2020-11-01 {
    description
      "- Used macsec-common feature";
    cisco-semver:module-version "3.0.0";
  }
  revision 2020-07-01 {
    description
      "- Added OpenFlow IPv6 support
       - Prepend switchport-config to switchport";
    cisco-semver:module-version "2.2.0";
  }
  revision 2020-03-01 {
    description
      "- Added vlan-config to replace vlan in interface switchport trunk
       - Added tag-config to replace tag in service-template
       - Add a new leaf for local-trustpoint for every openflow controller
         connection";
    cisco-semver:module-version "2.1.0";
  }
  revision 2019-11-01 {
    description
      "
       - Added switchport app-interface option
       - New tunnel config
       - Add add/except/remove options for switchport trunk allowed vlan";
    cisco-semver:module-version "2.0.0";
  }
  revision 2019-07-01 {
    description
      "- Establish semantic version baseline
       - Added support for device-tracking feature on Port-channel
       - Added support for access-group under service-template
       - Support l2protocol-tunnel on switchport
       - Added support for service-template sub clis - description,
         interface-template, tunnel type capwap name, vnid
       - Added support for redirect sub clis under service-template
       - Added support for service-template sub clis : dns-acl,
         service-policy qos input, service-policy qos output,tag ";
    cisco-semver:module-version "1.0.0";
  }
  revision 2019-01-22 {
    description
      "Added leaf for App-hosting Gigabit Ethernet interface";
  }
  revision 2018-12-15 {
    description
      "Added description and length range for service-template name";
  }
  revision 2018-12-06 {
    description
      "Added support for absolute-timer <value> under service-template";
  }
  revision 2018-12-05 {
    description
      "Removed switchport mode check for port-security";
  }
  revision 2018-11-07 {
    description
      "Cleanup spelling errors in description statements";
  }
  revision 2018-08-20 {
    description
      "Removed switch virtual";
  }
  revision 2018-07-24 {
    description
      "Removed switchport trunk allowed vlan leaves add/remove/except";
  }
  revision 2018-01-10 {
    description
      "Added command change switchport vepa enabled";
  }
  revision 2018-01-09 {
    description
      "Added annotations to openflow controller model to require entering all controller config parameters on delete";
  }
  revision 2017-11-27 {
    description
      "Added Change 25GE name";
  }
  revision 2017-11-14 {
    description
      "Added 100GE Interface";
  }
  revision 2017-11-08 {
    description
      "Added virtual-ethernet-bridge option";
  }
  revision 2017-09-21 {
    description
      "Added macsec without option";
  }
  revision 2017-09-20 {
    description
      "Added macsec option";
  }
  revision 2017-08-09 {
    description
      "This revision has changes for new 2gig interface addition";
  }
  revision 2017-08-09 {
    description
      "This revision has changes for new 5gig and 25gig interfaces addition";
  }
  revision 2017-07-01 {
    description
      "Updated access-group for mac acl mapping";
  }
  revision 2017-05-10 {
    description
      "added openflow config";
  }
  revision 2017-03-31 {
    description
      "Move interface LLDP configurations from switch to common";
  }
  revision 2017-02-07 {
    description
      "Initial revision";
  }

  grouping config-openflow-grouping {
    container feature {
      description
        "feature enable config";
      leaf openflow {
        description
          "feature OpenFlow Agent enable config";
        type empty;
      }
    }
    container openflow {
      description
        "OpenFlow configuration";
      list switch {
        description
          "OpenFlow Agent logical switch config";
        key "number";
        leaf number {
          type uint32;
        }
        leaf pipeline {
          description
            "OpenFlow Agent pipeline id config";
          type uint32;
        }
        container controller {
          description
            "set OpenFlow controller connection info";
          list ipv4 {
            description
              "OpenFlow controller IPv4 protocol";
            key "address";
            leaf address {
              description
                "IPv4 Address of the OpenFlow controller";
              type inet:ipv4-address;
            }
            list port {
              description
                "OpenFlow controller TCP port (default is 6653)";
              key "number";
              leaf number {
                type uint16;
              }
              list vrf {
                description
                  "OpenFlow controller vrf";
                key "name";
                leaf name {
                  type string;
                }
                leaf security {
                  description
                    "OpenFlow controller connection security";
                  type enumeration {
                    enum none;
                    enum tls;
                  }
                }
                leaf local-trustpoint {
                  description
                    "Local Trustpoint ID is used for TLS connections. When
                     installed, certificates are associated with an ID. This ID
                     specifies the certificate to use in a TLS connection.";
                  when "../security = 'tls'";
                  type string;
                }
              }
            }
          }
          list ipv6 {
            description
              "OpenFlow controller IPv6 protocol";
            key "address";
            leaf address {
              description
                "IPv6 Address of the OpenFlow controller";
              type inet:ipv6-address;
            }
            list port {
              description
                "OpenFlow controller TCP port (default is 6653)";
              key "number";
              leaf number {
                type uint16;
              }
              list vrf {
                description
                  "OpenFlow controller vrf";
                key "name";
                leaf name {
                  type string;
                }
                leaf security {
                  description
                    "OpenFlow controller connection security";
                  type enumeration {
                    enum none;
                    enum tls;
                  }
                }
                leaf local-trustpoint {
                  description
                    "Local Trustpoint ID is used for TLS connections. When
                     installed, certificates are associated with an ID. This ID
                     specifies the certificate to use in a TLS connection.";
                  when "../security = 'tls'";
                  type string;
                }
              }
            }
          }
        }
        container of-port {
          description
            "OpenFlow port/interface";
          list interface {
            description
              "OpenFlow Agent interface";
            key "name";
            leaf name {
              type string;
            }
          }
        }
        leaf datapath-id {
          description
            "Set OpenFlow logical switch datapath-id";
          type string;
        }
        leaf protocol-version {
          description
            "Set OpenFlow protocol version";
          type enumeration {
            enum 1.0;
            enum 1.3;
            enum negotiate;
          }
        }
        leaf backoff {
          description
            "OpenFlow Agent backoff in seconds";
          type uint16 {
            range "1..65535";
          }
        }
        leaf max-backoff {
          description
            "OpenFlow Agent max backoff in seconds";
          type uint16 {
            range "1..65535";
          }
        }
        leaf probe-interval {
          description
            "OpenFlow Agent probe interval in seconds";
          type uint16 {
            range "5..65535";
          }
        }
        container rate-limit {
          description
            "OpenFlow rate limit to controller";
          leaf packet_in {
            description
              "packet in rate (default is 0, indefinite)";
            type uint16 {
              range "1..65535";
            }
          }
          leaf burst {
            description
              "Maximum number of packets to controller (default is 0, indefinite)";
            type uint16 {
              range "1..65535";
            }
          }
        }
        leaf shutdown {
          description
            "shutdown OpenFlow Agent logical switch";
          type empty;
        }
        container statistics {
          description
            "Statistics configuration";
          leaf collection-interval {
            description
              "OpenFlow flow statistics collection interval in seconds";
            type uint8 {
              range "0..16";
            }
          }
        }
        leaf dataplane-default {
          description
            "set OpenFlow Agent dataplane config";
          type enumeration {
            enum secure;
            enum standalone;
          }
        }
        leaf default-miss {
          description
            "Specifies behavior if a packet does not match any controller installed flow";
          type enumeration {
            enum continue-drop;
            enum drop;
          }
        }
        container logging {
          description
            "Enable logging";
          leaf flow-modify {
            description
              "Enable logging for flow-modify";
            type empty;
          }
        }
        container tls {
          description
            "OpenFlow switch tls";
          container trustpoint {
            description
              "tls trust point";
            leaf local {
              description
                "tls local trust point";
              type string;
            }
            leaf remote {
              description
                "tls remote trust point";
              type string;
            }
          }
        }
      }
    }
  }

  grouping config-system-grouping {
    container debug {
      description
        "Debug Shell";
      container shell {
        description
          "Debug Shell";
        container switch {
          description
            "Set config on switches in stack";
          leaf switch-number {
            description
              "Switch number";
            type uint8 {
              range "1..9";
            }
          }
          leaf all {
            description
              "Set config for all switches in stack";
            type empty;
          }
        }
      }
    }
    container disable {
      description
        "Disable password recovery";
      container password {
        description
          "Disable password recovery";
        container recovery {
          description
            "Disable password recovery";
          container switch {
            description
              "Set config on switches in stack";
            leaf number {
              description
                "Switch number";
              type uint8 {
                range "1..9";
              }
            }
            leaf all {
              description
                "Set config for all switches in stack";
              type empty;
            }
          }
        }
      }
    }
    container environment {
      description
        "Set the system environment settings";
      container fan-fail-action {
        description
          "Set the FRU/PS fan fail action. ";
        leaf shut {
          description
            "Shutdown the system when multiple fan fails";
          type empty;
        }
      }
      container temperature {
        description
          "Set the system temperature settings";
        container threshold {
          description
            "Set the system temperature thresholds";
          container yellow {
            description
              "Set the yellow thresholds. ";
            leaf delta-value {
              description
                "Delta value from Red threshold in Degree Celsius";
              type uint8 {
                range "5..25";
              }
            }
            leaf detail {
              description
                "print yellow temperature threshold";
              type empty;
            }
          }
        }
      }
    }
    container fnf {
      description
        "Flexible Netflow";
      container bytes-count {
        description
          "Bytes Count";
        leaf layer2 {
          description
            "Show L2 bytes in byte count collect field";
          type empty;
        }
      }
    }
    container ignore {
      description
        "Ignore Startup Config";
      container startupconfig {
        description
          "Ignore Startup Config";
        container switch {
          description
            "Set config on switches in stack";
          leaf number {
            description
              "Switch number";
            type uint8 {
              range "1..9";
            }
          }
          leaf all {
            description
              "Set config for all switches in stack";
            type empty;
          }
        }
      }
    }
    container mode-button {
      description
        "Enable Mode button for reset";
      leaf reset {
        description
          "Enable reset";
        type empty;
      }
    }
    container mtu {
      description
        "Set the system Maximum Transmission Unit (MTU)";
      leaf size {
        type uint16 {
          range "1500..9216";
        }
      }
      leaf jumbo {
        description
          "Set Jumbo MTU value for GigabitEthernet or TenGigabitEthernet interfaces";
        type uint16 {
          range "1500..9000";
        }
      }
      leaf routing {
        description
          "Set the Routing MTU for the system";
        type uint16 {
          range "1500";
        }
      }
    }
  }

  grouping config-interface-switchport-grouping {
    container access {
      description
        "Set access mode characteristics of the interface";
      container vlan {
        description
          "Set VLAN when interface is in access mode";
        leaf vlan {
          type union {
            type uint16 {
              range "1..4094";
            }
            type enumeration {
              enum dynamic;
            }
          }
        }
      }
    }
    container block {
      description
        "Disable forwarding of unknown uni/multi cast addresses";
      leaf multicast {
        description
          "Block unknown multicast addresses";
        type empty;
      }
      leaf unicast {
        description
          "Block unknown unicast addresses";
        type empty;
      }
    }
    container mode {
      description
        "Set trunking mode of the interface";
      choice mode-choice {
        container access {
          presence "true";
          description
            "Set trunking mode to ACCESS unconditionally";
        }
        container dot1q-tunnel {
          presence "true";
          description
            "set trunking mode to TUNNEL unconditionally";
        }
        leaf dynamic {
          description
            "Set trunking mode to dynamically negotiate access or trunk mode";
          type enumeration {
            enum auto;
            enum desirable;
          }
        }
        container private-vlan {
          description
            "Set private-vlan mode";
          container trunk {
            description
              "Set the mode to private-vlan trunk";
            presence "true";
            leaf trunk-config {
              type enumeration {
                enum promiscuous;
                enum secondary;
              }
              default "secondary";
            }
          }
          leaf host {
            description
              "Set the mode to private-vlan host";
            type empty;
          }
          leaf promiscuous {
            description
              "Set the mode to private-vlan promiscuous";
            type empty;
          }
        }
        container trunk {
          presence "true";
          description
            "Set trunking mode to TRUNK unconditionally";
        }
      }
    }
    leaf nonegotiate {
      description
        "Device will not engage in negotiation protocol on this interface";
      type empty;
    }
    leaf port-security-conf {
      description
        "port-security";
      type empty;
    }
    container port-security-config {
      container port-security {
        description
          "Security related command";
        container aging {
          description
            "Port-security aging commands";
          leaf static {
            description
              "Enable aging for configured secure addresses";
            type empty;
          }
          leaf time {
            description
              "Port-security aging time";
            type uint16 {
              range "1..1440";
            }
          }
          leaf type {
            description
              "Port-security aging type";
            type enumeration {
              enum absolute;
              enum inactivity;
            }
          }
        }
        container allowlist-on {
          description
            "Allowlist mac address";
          leaf allowlist {
            description
              "Enable allowlist feature";
            must 'not(../../mac-address-sticky-on/mac-address/sticky) and not(../../../../port-security-conf) and not(../../aging/time) and not(../../aging/type) and not(../../aging/static) and not(../../maximum-address-config/maximum/maximum) and not(../../mac-address-config/mac-address/hw-address-trunk) and not(../../violation/protect) and not(../../mac-address-config/mac-address/hw-address-voice) and not(../../violation/restrict) and not(../../mac-address-config/mac-address/hw-address-access) and not(../../violation/shutdown/vlan)' {
              error-message "Allowlist feature and other port-security configurations aging, violation, maximum vlan port-security, port-security mac-address, port-security mac-address sticky are mutually exclusive and should not be configured together";
            }
            type empty;
          }
        }
        container allowlist-config {
          container allowlist {
            container mac-address {
              list mac-address-conf {
                description
                  "Configure MAC address for allowlist";
                must 'not(../../../../mac-address-config/mac-address/hw-address-trunk) and not(../../../../mac-address-config/mac-address/hw-address-voice) and not(../../../../mac-address-config/mac-address/hw-address-access)' {
                  error-message "Delete all the port-security mac-address configurations before configuring allowlist mac-address, and vice versa";
                }
                key "hw-address";
                leaf hw-address {
                  description
                    "H.H.H 48 bit mac address";
                  type ios-types:cisco-mac-address-type;
                }
              }
            }
          }
        }
        container mac-address-sticky-on {
          container mac-address {
            description
              "Secure mac address";
            leaf sticky {
              description
                "Configure dynamic secure addresses as sticky";
              type empty;
            }
          }
        }
        container mac-address-config {
          container mac-address {
            description
              "Secure mac address";
            list hw-address-voice {
              must '(../../../../../mode/access) and (../../../../../voice/vlan/vlan)' {
                error-message "Delete all the configurations present in mode access before switching to mode trunk or check if VLAN voice is configured before configuring any hw-address with voice configuration";
              }
              key "hw-address vlan voice";
              leaf hw-address {
                description
                  "H.H.H 48 bit mac address";
                type ios-types:cisco-mac-address-type;
              }
              leaf vlan {
                type enumeration {
                  enum vlan;
                }
              }
              leaf voice {
                description
                  "voice vlan";
                type enumeration {
                  enum voice;
                }
              }
              leaf sticky {
                description
                  "Configure dynamic secure addresses as sticky";
                must '../../../../mac-address-sticky-on/mac-address/sticky' {
                  error-message "Delete sticky configurations first before deleting global sticky or Check if global sticky is enabled or not.";
                }
                type enumeration {
                  enum sticky;
                }
              }
            }
            list hw-address-access {
              when 'not(../../../../../mode/trunk)';
              key "hw-address";
              leaf hw-address {
                description
                  "H.H.H 48 bit mac address";
                type ios-types:cisco-mac-address-type;
              }
              leaf sticky {
                description
                  "Configure dynamic secure addresses as sticky";
                must '../../../../mac-address-sticky-on/mac-address/sticky' {
                  error-message "Delete sticky configurations first before deleting global sticky or Check if global sticky is enabled or not.";
                }
                type enumeration {
                  enum sticky;
                }
              }
            }
            list hw-address-trunk {
              must '../../../../../mode/trunk' {
                error-message "Delete all present trunk mode configurations before switching the mode or make sure the dependent trunk mode CLI is configured.";
              }
              key "hw-address vlan";
              leaf hw-address {
                description
                  "H.H.H 48 bit mac address";
                type ios-types:cisco-mac-address-type;
              }
              leaf vlan {
                description
                  "set VLAN ID of the VLAN on which this address can be learned";
                type uint16 {
                  range "1..4094";
                }
              }
              leaf sticky {
                description
                  "Configure dynamic secure addresses as sticky";
                must '../../../../mac-address-sticky-on/mac-address/sticky' {
                  error-message "Delete sticky configurations first before deleting global sticky or Check if global sticky is enabled or not.";
                }
                type enumeration {
                  enum sticky;
                }
              }
            }
          }
        }
        container mac-address {
          status obsolete;
          description
            "Secure mac address (OBSOLETE)";
          leaf sticky {
            status obsolete;
            description
              "Configure dynamic secure addresses as sticky (OBSOLETE)";
            type empty;
          }
          leaf hw-address {
            status obsolete;
            description
              "In trunk mode hw-address and VLAN must be configured together. hw-address can be configured alone only in access mode (OBSOLETE)";
            type yang:mac-address;
          }
          leaf vlan {
            status obsolete;
            description
              "Set VLAN ID of the VLAN on which this address can be learned. VLAN must be configured along with hw-address (OBSOLETE)";
            type uint16 {
              range "1..4094";
            }
          }
        }
        container maximum-address-config {
          description
            "Maximum number of MAC addresses";
          container maximum {
            description
              "Maximum number of MAC addresses";
            leaf maximum {
              description
                "Maximum number of MAC addresses for interface";
              type uint16 {
                range "1..4096";
              }
            }
          }
          container maximum-vlan {
            description
              "Maximum number of MAC addresses for access, voice, or trunk VLAN";
            when '../../../../mode/access or ../../../../mode/trunk';
            leaf maximum {
              description
                "Maximum number of MAC addresses";
              must '../vlan';
              type uint16 {
                range "1..4096";
              }
            }
            leaf vlan {
              description
                "Access, voice, or trunk VLAN";
              must '../maximum';
              type enumeration {
                enum vlan;
              }
            }
          }
          container maximum-vlan-access {
            description
              "Maximum number of MAC addresses for access VLAN";
            when '../../../../mode/access';
            leaf maximum {
              description
                "Maximum number of MAC addresses";
              must '../vlan';
              type uint16 {
                range "1..4096";
              }
            }
            leaf vlan {
              description
                "Access VLAN";
              must '../maximum';
              type enumeration {
                enum access;
              }
            }
          }
          container maximum-vlan-voice {
            description
              "Maximum number of MAC addresses for voice VLAN";
            when '../../../../mode/access and ../../../../voice/vlan/vlan';
            leaf maximum {
              description
                "Maximum number of MAC addresses";
              must '../vlan';
              type uint16 {
                range "1..4096";
              }
            }
            leaf vlan {
              description
                "Voice VLAN";
              must '../maximum';
              type enumeration {
                enum voice;
              }
            }
          }
          list maximum-vlan-trunk {
            description
              "Maximum number of MAC addresses for trunk VLAN";
            when '../../../../mode/trunk';
            key "maximum";
            leaf maximum {
              description
                "Maximum number of MAC addresses";
              must '../vlan';
              type uint16 {
                range "1..4096";
              }
            }
            leaf-list vlan {
              description
                "Trunk VLAN";
              must '../maximum';
              type uint16 {
                range "1..4094";
              }
            }
          }
        }
        list maxcount {
          status deprecated;
          description
            "Max secure addresses";
          key "max-addresses";
          leaf max-addresses {
            status deprecated;
            type uint16 {
              range "1..4097";
            }
          }
          leaf vlan {
            description
              "Max secure addresses per vlan (OBSOLETE)";
            status obsolete;
            type string;
          }
        }
        container violation {
          description
            "Security violation mode";
          choice violation-choice {
            leaf protect {
              description
                "Security violation protect mode";
              type empty;
            }
            leaf report {
              description
                "Security violation report mode";
              type empty;
            }
            leaf restrict {
              description
                "Security violation restrict mode";
              type empty;
            }
            container shutdown {
              description
                "Security violation shutdown mode";
              leaf vlan {
                description
                  "Security violation shutdown vlan mode";
                type empty;
              }
            }
          }
        }
        container mac-move {
          description
            "Set required action when a MAC address move is detected";
          if-feature "ios-features:switching-platform";
          container permit {
            description
              "Permit MAC address move";
            leaf redundancy-protocol {
              description
                "Permit MAC move for redundancy protocol (HSRP/VRRP) MAC addresses";
              must 'not(../../../mac-address-sticky-on/mac-address/sticky)' {
                error-message "Cannot enable mac-move permit redundancy-protocol and sticky on the same interface";
              }
              type empty;
            }
          }
        }
      }
    }
    container trunk {
      description
        "Set trunking characteristics of the interface";
      container allowed {
        description
          "Set allowed VLAN characteristics when interface is in trunking mode";
        uses switchport-trunk-allowed-vlan-v2;
        container vlan {
          description
            "Set allowed VLANs when interface is in trunking mode";
          status obsolete;
          choice vlan-choice {
            status obsolete;
            leaf vlans {
              status obsolete;
              type union {
                type uint16 {
                  range "1..4094";
                }
                type string;
              }
            }
            leaf none {
              description
                "no VLANs";
              status obsolete;
              type empty;
            }
            leaf add {
              description
                "VLAN IDs of the allowed VLANs when this port is in trunking mode";
              status obsolete;
              type union {
                type uint16 {
                  range "1..4094";
                }
                type string;
              }
            }
            leaf except {
              description
                "all VLANs except the following";
              status obsolete;
              type union {
                type uint16 {
                  range "1..4094";
                }
                type string;
              }
            }
            leaf remove {
              description
                "VLAN IDs of disallowed VLANs when this port is in trunking mode";
              status obsolete;
              type union {
                type uint16 {
                  range "1..4094";
                }
                type string;
              }
            }
          }
        }
      }
      leaf encapsulation {
        description
          "Set encapsulation format on trunk port";
        type enumeration {
          enum dot1q;
          enum isl;
          enum negotiate;
        }
      }
      container native {
        description
          "Set trunking native characteristics when interface is in trunking mode";
        container vlan {
          description
            "Set native VLAN when interface is in trunking mode and native VLAN id";
          leaf tag {
            type boolean;
            default "true";
          }
          leaf vlan-id {
            type uint16 {
              range "1..4094";
            }
          }
        }
      }
      container pruning {
        description
          "Set pruning VLAN characteristics when interface is in trunking mode";
        container vlan {
          description
            "Set VLANs enabled for pruning when interface is in trunking mode";
          choice vlan-choice {
            leaf-list vlans {
              type union {
                type uint16;
                type string;
              }
            }
            leaf add {
              description
                "VLAN IDs of the allowed VLANs when this port is in trunking mode";
              type union {
                type uint16;
                type string;
              }
            }
            leaf-list except {
              description
                "all VLANs except the following";
              type union {
                type uint16;
                type string;
              }
            }
            leaf none {
              description
                "no VLANs";
              type empty;
            }
            leaf remove {
              description
                "VLAN IDs of disallowed VLANS when this port is in trunking mode";
              type union {
                type uint16;
                type string;
              }
            }
          }
        }
      }
    }
    container voice {
      description
        "Voice appliance attributes";
      container vlan {
        description
          "Vlan for voice traffic";
        leaf vlan {
          type union {
            type enumeration {
              enum dot1p;
              enum none;
              enum untagged;
            }
            type uint16 {
              range "1..4094";
            }
            type string;
          }
        }
        leaf name {
          description
            "Vlan name";
          type string;
        }
      }
      container detect {
        description
          "detection enhancement keyword";
        container cisco-phone {
          description
            "Cisco IP phone";
          presence "true";
          leaf full-duplex {
            description
              "full duplex keyword";
            type empty;
          }
        }
      }
    }
    container priority {
      description
        "Set appliance 802.1p priority";
      container extend {
        description
          "Set appliance 802.1p priority";
        choice trust-choice {
          leaf trust {
            description
              "Trust 802.1p priorities of devices on appliance";
            type empty;
          }
          leaf cos {
            description
              "Override 802.1p priority of devices on appliance";
            type uint8 {
              range "0..7";
            }
          }
        }
      }
    }
    container autostate {
      description
        "Include or exclude this port from vlan link up calculation";
      leaf exclude {
        description
          "Exclude this port from vlan link up calculation";
        type empty;
      }
    }
    leaf protected {
      description
        "Configure an interface to be a protected port";
      type empty;
    }
    leaf host {
      description
        "Set port host";
      type empty;
    }
    container private-vlan {
      description
        "Set the private VLAN configuration";
      container association {
        description
          "Set the private VLAN association";
        container host {
          description
            "Set the private VLAN host association";
          leaf primary-range {
            description
              "Primary normal range VLAN ID of the private VLAN port association";
            type uint16 {
              range "2..1001 | 1006..4094";
            }
          }
          leaf secondary-range {
            description
              "Secondary normal range VLAN ID of the private VLAN host port association";
            type uint16 {
              range "2..1001 | 1006..4094";
            }
          }
        }
        container mapping {
          description
            "Set the private VLAN promiscuous mapping";
          leaf primary-range {
            description
              "Primary normal range VLAN ID of the private VLAN promiscuous port mapping";
            type uint16 {
              range "2..1001 | 1006..4094";
            }
          }
          leaf secondary-range {
            description
              "Secondary VLAN IDs of the private VLAN promiscuous port mapping";
            type string;
          }
          leaf add {
            description
              "Secondary VLAN IDs of the private VLAN promiscuous port mapping";
            type string;
          }
          leaf remove {
            description
              "Secondary VLAN IDs of the private VLAN promiscuous port mapping";
            type string;
          }
        }
      }
      container host-association {
        description
          "Set the private VLAN host association";
        leaf primary-range {
          description
            "Primary normal range VLAN ID of the private VLAN port association";
          type uint16 {
            range "2..1001 | 1006..4094";
          }
        }
        leaf secondary-range {
          description
            "Secondary normal range VLAN ID of the private VLAN host port association";
          type uint16 {
            range "2..1001 | 1006..4094";
          }
        }
      }
      container mapping {
        description
          "Set the private VLAN promiscuous mapping";
        leaf trunk {
          description
            "Set the private VLAN promiscuous trunk mapping";
          type empty;
        }
        leaf primary-range {
          description
            "Primary normal range VLAN ID of the private VLAN promiscuous port mapping";
          type uint16 {
            range "2..1001 | 1006..4094";
          }
        }
        leaf secondary-range {
          description
            "Secondary VLAN IDs of the private VLAN promiscuous port mapping";
          type string;
        }
      }
      container trunk {
        description
          "Set the private vlan trunking configuration";
        container allowed {
          description
            "Set allowed VLAN characteristics when interface is in trunking mode";
          container vlan {
            description
              "Set allowed VLANs when interface is in trunking mode";
            leaf vlans {
              type union {
                type uint16;
                type string;
              }
            }
          }
        }
        container native {
          description
            "Set the private vlan trunking native configuration";
          container vlan {
            description
              "Set native VLAN configuration";
            leaf vlans {
              description
                "VLAN ID of the native VLAN when this port is in trunking mode";
              type uint16 {
                range "1..4094";
              }
            }
            leaf tag {
              description
                "Set native VLAN tagging state on Private VLAN trunk";
              type empty;
            }
          }
        }
      }
    }
    container vepa {
      description
        "Reflective relay configuration";
      leaf enabled {
        description
          "Enable reflective relay";
        type empty;
      }
    }
    leaf app-interface {
      description
        "Enable port for application hosting";
      type empty;
    }
  }

  grouping config-interface-switchport-grouping-obsoleted-v2 {
    container access {
      status obsolete;
      description
        "Set access mode characteristics of the interface (OBSOLETE)";
      container vlan {
        status obsolete;
        description
          "Set VLAN when interface is in access mode (OBSOLETE)";
        leaf vlan {
          status obsolete;
          type union {
            type uint16 {
              range "1..4094";
            }
            type enumeration {
              enum dynamic;
            }
          }
        }
        leaf name {
          description
            "Vlan name, obsolete (OBSOLETE)";
          status obsolete;
          type string;
        }
      }
    }
    container block {
      status obsolete;
      description
        "Disable forwarding of unknown uni/multi cast addresses (OBSOLETE)";
      leaf multicast {
        status obsolete;
        description
          "Block unknown multicast addresses (OBSOLETE)";
        type empty;
      }
      leaf unicast {
        status obsolete;
        description
          "Block unknown unicast addresses (OBSOLETE)";
        type empty;
      }
    }
    container mode {
      status obsolete;
      description
        "Set trunking mode of the interface (OBSOLETE)";
      choice mode-choice {
        status obsolete;
        container access {
          status obsolete;
          presence "true";
          description
            "Set trunking mode to ACCESS unconditionally (OBSOLETE)";
        }
        container dot1q-tunnel {
          status obsolete;
          presence "true";
          description
            "set trunking mode to TUNNEL unconditionally (OBSOLETE)";
        }
        leaf dynamic {
          status obsolete;
          description
            "Set trunking mode to dynamically negotiate access or trunk mode (OBSOLETE)";
          type enumeration {
            enum auto;
            enum desirable;
          }
        }
        container private-vlan {
          status obsolete;
          description
            "Set private-vlan mode";
          container trunk {
            status obsolete;
            description
              "Set the mode to private-vlan trunk (OBSOLETE)";
            presence "true";
            leaf trunk-config {
              status obsolete;
              type enumeration {
                enum promiscuous;
                enum secondary;
              }
              default "secondary";
            }
          }
          leaf host {
            status obsolete;
            description
              "Set the mode to private-vlan host (OBSOLETE)";
            type empty;
          }
          leaf promiscuous {
            status obsolete;
            description
              "Set the mode to private-vlan promiscuous (OBSOLETE)";
            type empty;
          }
        }
        container trunk {
          status obsolete;
          presence "true";
          description
            "Set trunking mode to TRUNK unconditionally (OBSOLETE)";
        }
      }
    }
    leaf nonegotiate {
      status obsolete;
      description
        "Device will not engage in negotiation protocol on this interface (OBSOLETE)";
      type empty;
    }
    leaf port-security-cfg {
      status obsolete;
      description
        "port-security";
      type empty;
    }
    container port-security-conf {
      status obsolete;
      container port-security {
        status obsolete;
        description
          "Security related command (OBSOLETE)";
        container aging {
          status obsolete;
          description
            "Port-security aging commands (OBSOLETE)";
          leaf static {
            status obsolete;
            description
              "Enable aging for configured secure addresses (OBSOLETE)";
            type empty;
          }
          leaf time {
            status obsolete;
            description
              "Port-security aging time (OBSOLETE)";
            type uint16 {
              range "1..1440";
            }
          }
          leaf type {
            status obsolete;
            description
              "Port-security aging type (OBSOLETE)";
            type enumeration {
              enum absolute;
              enum inactivity;
            }
          }
        }
        container mac-address {
          status obsolete;
          description
            "Secure mac address (OBSOLETE)";
          leaf sticky {
            status obsolete;
            description
              "Configure dynamic secure addresses as sticky (OBSOLETE)";
            type empty;
          }
          leaf hw-address {
            status obsolete;
            type yang:mac-address;
          }
          leaf vlan {
            status obsolete;
            description
              "set VLAN ID of the VLAN on which this address can be learned (OBSOLETE)";
            type uint16 {
              range "1..4094";
            }
          }
        }
        list maxcount {
          status obsolete;
          description
            "Max secure addresses (OBSOLETE)";
          key "max-addresses";
          leaf max-addresses {
            status obsolete;
            type uint16 {
              range "1..4097";
            }
          }
          leaf vlan {
            status obsolete;
            description
              "Max secure addresses per vlan (OBSOLETE)";
            type string;
          }
        }
        container maximum {
          status obsolete;
          description
            "Max secure addresses (OBSOLETE)";
          leaf max-addresses {
            status obsolete;
            type uint16 {
              range "1..4097";
            }
          }
          leaf vlan {
            status obsolete;
            description
              "Max secure addresses per vlan (OBSOLETE)";
            type string;
          }
        }
        container violation {
          status obsolete;
          description
            "Security violation mode (OBSOLETE)";
          choice violation-choice {
            status obsolete;
            leaf protect {
              status obsolete;
              description
                "Security violation protect mode (OBSOLETE)";
              type empty;
            }
            leaf restrict {
              status obsolete;
              description
                "Security violation restrict mode (OBSOLETE)";
              type empty;
            }
            container shutdown {
              status obsolete;
              description
                "Security violation shutdown mode (OBSOLETE)";
              leaf vlan {
                status obsolete;
                description
                  "Security violation shutdown vlan mode (OBSOLETE)";
                type empty;
              }
            }
          }
        }
      }
    }
    container port-security {
      status obsolete;
      description
        "Security related command (OBSOLETE)";
      presence "true";
      container aging {
        status obsolete;
        description
          "Port-security aging commands (OBSOLETE)";
        leaf static {
          status obsolete;
          description
            "Enable aging for configured secure addresses (OBSOLETE)";
          type empty;
        }
        leaf time {
          status obsolete;
          description
            "Port-security aging time (OBSOLETE)";
          type uint16 {
            range "1..1440";
          }
        }
        leaf type {
          status obsolete;
          description
            "Port-security aging type (OBSOLETE)";
          type enumeration {
            enum absolute;
            enum inactivity;
          }
        }
      }
      container mac-address {
        status obsolete;
        description
          "Secure mac address (OBSOLETE)";
        leaf sticky {
          status obsolete;
          description
            "Configure dynamic secure addresses as sticky (OBSOLETE)";
          type empty;
        }
        leaf hw-address {
          status obsolete;
          description
            "In trunk mode hw-address and VLAN must be configured together. hw-address can be configured alone only in access mode (OBSOLETE)";
          type yang:mac-address;
        }
        leaf vlan {
          status obsolete;
          description
            "Set VLAN ID of the VLAN on which this address can be learned. VLAN must be configured along with hw-address (OBSOLETE)";
          type uint16 {
            range "1..4094";
          }
        }
      }
      container maximum {
        status obsolete;
        description
          "Max secure addresses (OBSOLETE)";
        leaf max-addresses {
          status obsolete;
          type uint16 {
            range "1..4097";
          }
        }
        leaf vlan {
          status obsolete;
          description
            "Max secure addresses per vlan (OBSOLETE)";
          type string;
        }
      }
      leaf violation {
        status obsolete;
        type enumeration {
          enum protect;
          enum restrict;
          enum shutdown;
        }
      }
    }
    container trunk {
      status obsolete;
      description
        "Set trunking characteristics of the interface (OBSOLETE)";
      container allowed {
        status obsolete;
        description
          "Set allowed VLAN characteristics when interface is in trunking mode (OBSOLETE)";
        container vlan {
          status obsolete;
          description
            "Set allowed VLANs when interface is in trunking mode (OBSOLETE)";
          choice vlan-choice {
            status obsolete;
            leaf vlans {
              status obsolete;
              type union {
                type uint16;
                type string;
              }
            }
            leaf all {
              status obsolete;
              description
                "all VLANs";
              type empty;
            }
            leaf none {
              status obsolete;
              description
                "no VLANs";
              type empty;
            }
            leaf add {
              status obsolete;
              description
                "VLAN IDs of the allowed VLANs when this port is in trunking mode (OBSOLETE)";
              type union {
                type uint16 {
                  range "1..4094";
                }
                type string;
              }
            }
            leaf except {
              status obsolete;
              description
                "all VLANs except the following (OBSOLETE)";
              type union {
                type uint16 {
                  range "1..4094";
                }
                type string;
              }
            }
            leaf remove {
              status obsolete;
              description
                "VLAN IDs of disallowed VLANs when this port is in trunking mode (OBSOLETE)";
              type union {
                type uint16 {
                  range "1..4094";
                }
                type string;
              }
            }
          }
        }
      }
      leaf encapsulation {
        status obsolete;
        description
          "Set encapsulation format on trunk port (OBSOLETE)";
        type enumeration {
          enum dot1q;
          enum isl;
          enum negotiate;
        }
      }
      container native {
        status obsolete;
        description
          "Set trunking native characteristics when interface is in trunking mode (OBSOLETE)";
        container vlan-config {
          status obsolete;
          description
            "Set native VLAN when interface is in trunking mode and native VLAN id (OBSOLETE)";
          leaf tag {
            status obsolete;
            type boolean;
          }
          leaf vlan-id {
            status obsolete;
            type uint16 {
              range "1..4094";
            }
          }
        }
        leaf vlan {
          status obsolete;
          description
            "Set native VLAN when interface is in trunking mode (OBSOLETE)";
          type union {
            type enumeration {
              enum tag;
            }
            type uint16 {
              range "1..4094";
            }
          }
        }
      }
      container pruning {
        status obsolete;
        description
          "Set pruning VLAN characteristics when interface is in trunking mode (OBSOLETE)";
        container vlan {
          status obsolete;
          description
            "Set VLANs enabled for pruning when interface is in trunking mode (OBSOLETE)";
          choice vlan-choice {
            status obsolete;
            leaf-list vlans {
              status obsolete;
              type union {
                type uint16;
                type string;
              }
            }
            leaf add {
              status obsolete;
              description
                "VLAN IDs of the allowed VLANs when this port is in trunking mode (OBSOLETE)";
              type union {
                type uint16;
                type string;
              }
            }
            leaf-list except {
              status obsolete;
              description
                "all VLANs except the following (OBSOLETE)";
              type union {
                type uint16;
                type string;
              }
            }
            leaf none {
              status obsolete;
              description
                "no VLANs";
              type empty;
            }
            leaf remove {
              status obsolete;
              description
                "VLAN IDs of disallowed VLANS when this port is in trunking mode (OBSOLETE)";
              type union {
                type uint16;
                type string;
              }
            }
          }
        }
      }
    }
    container voice {
      status obsolete;
      description
        "Voice appliance attributes (OBSOLETE)";
      container vlan {
        status obsolete;
        description
          "Vlan for voice traffic (OBSOLETE)";
        leaf vlan {
          status obsolete;
          type union {
            type enumeration {
              enum dot1p;
              enum none;
              enum untagged;
            }
            type uint16 {
              range "1..4094";
            }
            type string;
          }
        }
        leaf name {
          status obsolete;
          description
            "Vlan name";
          type string;
        }
      }
      container detect {
        status obsolete;
        description
          "detection enhancement keyword (OBSOLETE)";
        container cisco-phone {
          status obsolete;
          description
            "Cisco IP phone";
          presence "true";
          leaf full-duplex {
            status obsolete;
            description
              "full duplex keyword";
            type empty;
          }
        }
      }
    }
    container priority {
      status obsolete;
      description
        "Set appliance 802.1p priority (OBSOLETE)";
      container extend {
        status obsolete;
        description
          "Set appliance 802.1p priority (OBSOLETE)";
        choice trust-choice {
          status obsolete;
          leaf trust {
            status obsolete;
            description
              "Trust 802.1p priorities of devices on appliance (OBSOLETE)";
            type empty;
          }
          leaf cos {
            status obsolete;
            description
              "Override 802.1p priority of devices on appliance (OBSOLETE)";
            type uint8 {
              range "0..7";
            }
          }
        }
      }
    }
    container autostate {
      status obsolete;
      description
        "Include or exclude this port from vlan link up calculation (OBSOLETE)";
      leaf exclude {
        status obsolete;
        description
          "Exclude this port from vlan link up calculation (OBSOLETE)";
        type empty;
      }
    }
    leaf protected {
      status obsolete;
      description
        "Configure an interface to be a protected port (OBSOLETE)";
      type empty;
    }
    leaf host {
      status obsolete;
      description
        "Set port host (OBSOLETE)";
      type empty;
    }
    container private-vlan {
      status obsolete;
      description
        "Set the private VLAN configuration (OBSOLETE)";
      container association {
        status obsolete;
        description
          "Set the private VLAN association (OBSOLETE)";
        container host {
          status obsolete;
          description
            "Set the private VLAN host association (OBSOLETE)";
          leaf primary-range {
            status obsolete;
            description
              "Primary normal range VLAN ID of the private VLAN port association (OBSOLETE)";
            type uint16 {
              range "2..1001 | 1006..4094";
            }
          }
          leaf secondary-range {
            status obsolete;
            description
              "Secondary normal range VLAN ID of the private VLAN host port association (OBSOLETE)";
            type uint16 {
              range "2..1001 | 1006..4094";
            }
          }
        }
        container mapping {
          status obsolete;
          description
            "Set the private VLAN promiscuous mapping (OBSOLETE)";
          leaf primary-range {
            status obsolete;
            description
              "Primary normal range VLAN ID of the private VLAN promiscuous port mapping (OBSOLETE)";
            type uint16 {
              range "2..1001 | 1006..4094";
            }
          }
          leaf secondary-range {
            status obsolete;
            description
              "Secondary VLAN IDs of the private VLAN promiscuous port mapping (OBSOLETE)";
            type string;
          }
          leaf add {
            status obsolete;
            description
              "Secondary VLAN IDs of the private VLAN promiscuous port mapping (OBSOLETE)";
            type string;
          }
          leaf remove {
            status obsolete;
            description
              "Secondary VLAN IDs of the private VLAN promiscuous port mapping (OBSOLETE)";
            type string;
          }
        }
      }
      container host-association {
        status obsolete;
        description
          "Set the private VLAN host association (OBSOLETE)";
        leaf primary-range {
          status obsolete;
          description
            "Primary normal range VLAN ID of the private VLAN port association (OBSOLETE)";
          type uint16 {
            range "2..1001 | 1006..4094";
          }
        }
        leaf secondary-range {
          status obsolete;
          description
            "Secondary normal range VLAN ID of the private VLAN host port association (OBSOLETE)";
          type uint16 {
            range "2..1001 | 1006..4094";
          }
        }
      }
      container mapping {
        status obsolete;
        description
          "Set the private VLAN promiscuous mapping (OBSOLETE)";
        leaf trunk {
          status obsolete;
          description
            "Set the private VLAN promiscuous trunk mapping (OBSOLETE)";
          type empty;
        }
        leaf primary-range {
          status obsolete;
          description
            "Primary normal range VLAN ID of the private VLAN promiscuous port mapping (OBSOLETE)";
          type uint16 {
            range "2..1001 | 1006..4094";
          }
        }
        leaf secondary-range {
          status obsolete;
          description
            "Secondary VLAN IDs of the private VLAN promiscuous port mapping (OBSOLETE)";
          type string;
        }
        leaf add {
          status obsolete;
          description
            "Secondary VLAN IDs of the private VLAN promiscuous port mapping (OBSOLETE)";
          type string;
        }
        leaf remove {
          status obsolete;
          description
            "Secondary VLAN IDs of the private VLAN promiscuous port mapping (OBSOLETE)";
          type string;
        }
      }
      container trunk {
        status obsolete;
        description
          "Set the private vlan trunking configuration (OBSOLETE)";
        container allowed {
          status obsolete;
          description
            "Set allowed VLAN characteristics when interface is in trunking mode (OBSOLETE)";
          container vlan {
            status obsolete;
            description
              "Set allowed VLANs when interface is in trunking mode (OBSOLETE)";
            leaf vlans {
              status obsolete;
              type union {
                type uint16;
                type string;
              }
            }
          }
        }
        container native {
          status obsolete;
          description
            "Set the private vlan trunking native configuration (OBSOLETE)";
          container vlan {
            status obsolete;
            description
              "Set native VLAN configuration (OBSOLETE)";
            leaf vlans {
              status obsolete;
              description
                "VLAN ID of the native VLAN when this port is in trunking mode (OBSOLETE)";
              type uint16 {
                range "1..4094";
              }
            }
            leaf tag {
              status obsolete;
              description
                "Set native VLAN tagging state on Private VLAN trunk (OBSOLETE)";
              type empty;
            }
          }
        }
      }
    }
    container vepa {
      status obsolete;
      description
        "Reflective relay configuration (OBSOLETE)";
      leaf enabled {
        status obsolete;
        description
          "Enable reflective relay";
        type empty;
      }
    }
    leaf app-interface {
      status obsolete;
      description
        "Enable port for application hosting (OBSOLETE)";
      type empty;
    }
  }

  grouping config-interface-switchport-grouping-obsolete {
    container access {
      status obsolete;
      description
        "Set access mode characteristics of the interface";
      container vlan {
        status obsolete;
        description
          "Set VLAN when interface is in access mode";
        leaf vlan {
          status obsolete;
          type union {
            type uint16 {
              range "1..4094";
            }
            type enumeration {
              enum dynamic;
            }
          }
        }
        leaf name {
          description
            "Vlan name, obsolete";
          status obsolete;
          type string;
        }
      }
    }
    container block {
      status obsolete;
      description
        "Disable forwarding of unknown uni/multi cast addresses";
      leaf multicast {
        status obsolete;
        description
          "Block unknown multicast addresses";
        type empty;
      }
      leaf unicast {
        status obsolete;
        description
          "Block unknown unicast addresses";
        type empty;
      }
    }
    container mode {
      status obsolete;
      description
        "Set trunking mode of the interface";
      choice mode-choice {
        status obsolete;
        container access {
          status obsolete;
          presence "true";
          description
            "Set trunking mode to ACCESS unconditionally";
        }
        container dot1q-tunnel {
          status obsolete;
          presence "true";
          description
            "set trunking mode to TUNNEL unconditionally";
        }
        leaf dynamic {
          status obsolete;
          description
            "Set trunking mode to dynamically negotiate access or trunk mode";
          type enumeration {
            enum auto;
            enum desirable;
          }
        }
        container private-vlan {
          status obsolete;
          description
            "Set private-vlan mode";
          container trunk {
            status obsolete;
            description
              "Set the mode to private-vlan trunk";
            presence "true";
            leaf trunk-config {
              status obsolete;
              type enumeration {
                enum promiscuous;
                enum secondary;
              }
              default "secondary";
            }
          }
          leaf host {
            status obsolete;
            description
              "Set the mode to private-vlan host";
            type empty;
          }
          leaf promiscuous {
            status obsolete;
            description
              "Set the mode to private-vlan promiscuous";
            type empty;
          }
        }
        container trunk {
          status obsolete;
          presence "true";
          description
            "Set trunking mode to TRUNK unconditionally";
        }
      }
    }
    leaf nonegotiate {
      status obsolete;
      description
        "Device will not engage in negotiation protocol on this interface";
      type empty;
    }
    leaf port-security-cfg {
      status obsolete;
      description
        "port-security";
      type empty;
    }
    container port-security-conf {
      status obsolete;
      container port-security {
        status obsolete;
        description
          "Security related command";
        container aging {
          status obsolete;
          description
            "Port-security aging commands";
          leaf static {
            status obsolete;
            description
              "Enable aging for configured secure addresses";
            type empty;
          }
          leaf time {
            status obsolete;
            description
              "Port-security aging time";
            type uint16 {
              range "1..1440";
            }
          }
          leaf type {
            status obsolete;
            description
              "Port-security aging type";
            type enumeration {
              enum absolute;
              enum inactivity;
            }
          }
        }
        container mac-address {
          status obsolete;
          description
            "Secure mac address";
          leaf sticky {
            status obsolete;
            description
              "Configure dynamic secure addresses as sticky";
            type empty;
          }
          leaf hw-address {
            status obsolete;
            type yang:mac-address;
          }
          leaf vlan {
            status obsolete;
            description
              "set VLAN ID of the VLAN on which this address can be learned";
            type uint16 {
              range "1..4094";
            }
          }
        }
        list maxcount {
          status obsolete;
          description
            "Max secure addresses";
          key "max-addresses";
          leaf max-addresses {
            status obsolete;
            type uint16 {
              range "1..4097";
            }
          }
          leaf vlan {
            status obsolete;
            description
              "Max secure addresses per vlan";
            type string;
          }
        }
        container maximum {
          status obsolete;
          description
            "Max secure addresses";
          leaf max-addresses {
            status obsolete;
            type uint16 {
              range "1..4097";
            }
          }
          leaf vlan {
            status obsolete;
            description
              "Max secure addresses per vlan";
            type string;
          }
        }
        container violation {
          status obsolete;
          description
            "Security violation mode";
          choice violation-choice {
            status obsolete;
            leaf protect {
              status obsolete;
              description
                "Security violation protect mode";
              type empty;
            }
            leaf restrict {
              status obsolete;
              description
                "Security violation restrict mode";
              type empty;
            }
            container shutdown {
              status obsolete;
              description
                "Security violation shutdown mode";
              leaf vlan {
                status obsolete;
                description
                  "Security violation shutdown vlan mode";
                type empty;
              }
            }
          }
        }
      }
    }
    container port-security {
      status obsolete;
      description
        "Security related command";
      presence "true";
      container aging {
        status obsolete;
        description
          "Port-security aging commands";
        leaf static {
          status obsolete;
          description
            "Enable aging for configured secure addresses";
          type empty;
        }
        leaf time {
          status obsolete;
          description
            "Port-security aging time";
          type uint16 {
            range "1..1440";
          }
        }
        leaf type {
          status obsolete;
          description
            "Port-security aging type";
          type enumeration {
            enum absolute;
            enum inactivity;
          }
        }
      }
      container mac-address {
        status obsolete;
        description
          "Secure mac address";
        leaf sticky {
          status obsolete;
          description
            "Configure dynamic secure addresses as sticky";
          type empty;
        }
        leaf hw-address {
          status obsolete;
          description
            "In trunk mode hw-address and VLAN must be configured together. hw-address can be configured alone only in access mode";
          type yang:mac-address;
        }
        leaf vlan {
          status obsolete;
          description
            "Set VLAN ID of the VLAN on which this address can be learned. VLAN must be configured along with hw-address";
          type uint16 {
            range "1..4094";
          }
        }
      }
      container maximum {
        status obsolete;
        description
          "Max secure addresses";
        leaf max-addresses {
          status obsolete;
          type uint16 {
            range "1..4097";
          }
        }
        leaf vlan {
          status obsolete;
          description
            "Max secure addresses per vlan";
          type string;
        }
      }
      leaf violation {
        status obsolete;
        type enumeration {
          enum protect;
          enum restrict;
          enum shutdown;
        }
      }
    }
    container trunk {
      status obsolete;
      description
        "Set trunking characteristics of the interface";
      container allowed {
        status obsolete;
        description
          "Set allowed VLAN characteristics when interface is in trunking mode";
        container vlan {
          status obsolete;
          description
            "Set allowed VLANs when interface is in trunking mode";
          choice vlan-choice {
            status obsolete;
            leaf vlans {
              status obsolete;
              type union {
                type uint16;
                type string;
              }
            }
            leaf all {
              status obsolete;
              description
                "all VLANs";
              type empty;
            }
            leaf none {
              status obsolete;
              description
                "no VLANs";
              type empty;
            }
            leaf add {
              status obsolete;
              description
                "VLAN IDs of the allowed VLANs when this port is in trunking mode";
              type union {
                type uint16 {
                  range "1..4094";
                }
                type string;
              }
            }
            leaf except {
              status obsolete;
              description
                "all VLANs except the following";
              type union {
                type uint16 {
                  range "1..4094";
                }
                type string;
              }
            }
            leaf remove {
              status obsolete;
              description
                "VLAN IDs of disallowed VLANs when this port is in trunking mode";
              type union {
                type uint16 {
                  range "1..4094";
                }
                type string;
              }
            }
          }
        }
      }
      leaf encapsulation {
        status obsolete;
        description
          "Set encapsulation format on trunk port";
        type enumeration {
          enum dot1q;
          enum isl;
          enum negotiate;
        }
      }
      container native {
        status obsolete;
        description
          "Set trunking native characteristics when interface is in trunking mode";
        container vlan-config {
          status obsolete;
          description
            "Set native VLAN when interface is in trunking mode and native VLAN id";
          leaf tag {
            status obsolete;
            type boolean;
          }
          leaf vlan-id {
            status obsolete;
            type uint16 {
              range "1..4094";
            }
          }
        }
        leaf vlan {
          status obsolete;
          description
            "Set native VLAN when interface is in trunking mode";
          type union {
            type enumeration {
              enum tag;
            }
            type uint16 {
              range "1..4094";
            }
          }
        }
      }
      container pruning {
        status obsolete;
        description
          "Set pruning VLAN characteristics when interface is in trunking mode";
        container vlan {
          status obsolete;
          description
            "Set VLANs enabled for pruning when interface is in trunking mode";
          choice vlan-choice {
            status obsolete;
            leaf-list vlans {
              status obsolete;
              type union {
                type uint16;
                type string;
              }
            }
            leaf add {
              status obsolete;
              description
                "VLAN IDs of the allowed VLANs when this port is in trunking mode";
              type union {
                type uint16;
                type string;
              }
            }
            leaf-list except {
              status obsolete;
              description
                "all VLANs except the following";
              type union {
                type uint16;
                type string;
              }
            }
            leaf none {
              status obsolete;
              description
                "no VLANs";
              type empty;
            }
            leaf remove {
              status obsolete;
              description
                "VLAN IDs of disallowed VLANS when this port is in trunking mode";
              type union {
                type uint16;
                type string;
              }
            }
          }
        }
      }
    }
    container voice {
      status obsolete;
      description
        "Voice appliance attributes";
      container vlan {
        status obsolete;
        description
          "Vlan for voice traffic";
        leaf vlan {
          status obsolete;
          type union {
            type enumeration {
              enum dot1p;
              enum none;
              enum untagged;
            }
            type uint16 {
              range "1..4094";
            }
            type string;
          }
        }
        leaf name {
          status obsolete;
          description
            "Vlan name";
          type string;
        }
      }
      container detect {
        status obsolete;
        description
          "detection enhancement keyword";
        container cisco-phone {
          status obsolete;
          description
            "Cisco IP phone";
          presence "true";
          leaf full-duplex {
            status obsolete;
            description
              "full duplex keyword";
            type empty;
          }
        }
      }
    }
    container priority {
      status obsolete;
      description
        "Set appliance 802.1p priority";
      container extend {
        status obsolete;
        description
          "Set appliance 802.1p priority";
        choice trust-choice {
          status obsolete;
          leaf trust {
            status obsolete;
            description
              "Trust 802.1p priorities of devices on appliance";
            type empty;
          }
          leaf cos {
            status obsolete;
            description
              "Override 802.1p priority of devices on appliance";
            type uint8 {
              range "0..7";
            }
          }
        }
      }
    }
    container autostate {
      status obsolete;
      description
        "Include or exclude this port from vlan link up calculation";
      leaf exclude {
        status obsolete;
        description
          "Exclude this port from vlan link up calculation";
        type empty;
      }
    }
    leaf protected {
      status obsolete;
      description
        "Configure an interface to be a protected port";
      type empty;
    }
    leaf host {
      status obsolete;
      description
        "Set port host";
      type empty;
    }
    container private-vlan {
      status obsolete;
      description
        "Set the private VLAN configuration";
      container association {
        status obsolete;
        description
          "Set the private VLAN association";
        container host {
          status obsolete;
          description
            "Set the private VLAN host association";
          leaf primary-range {
            status obsolete;
            description
              "Primary normal range VLAN ID of the private VLAN port association";
            type uint16 {
              range "2..1001 | 1006..4094";
            }
          }
          leaf secondary-range {
            status obsolete;
            description
              "Secondary normal range VLAN ID of the private VLAN host port association";
            type uint16 {
              range "2..1001 | 1006..4094";
            }
          }
        }
        container mapping {
          status obsolete;
          description
            "Set the private VLAN promiscuous mapping";
          leaf primary-range {
            status obsolete;
            description
              "Primary normal range VLAN ID of the private VLAN promiscuous port mapping";
            type uint16 {
              range "2..1001 | 1006..4094";
            }
          }
          leaf secondary-range {
            status obsolete;
            description
              "Secondary VLAN IDs of the private VLAN promiscuous port mapping";
            type string;
          }
          leaf add {
            status obsolete;
            description
              "Secondary VLAN IDs of the private VLAN promiscuous port mapping";
            type string;
          }
          leaf remove {
            status obsolete;
            description
              "Secondary VLAN IDs of the private VLAN promiscuous port mapping";
            type string;
          }
        }
      }
      container host-association {
        status obsolete;
        description
          "Set the private VLAN host association";
        leaf primary-range {
          status obsolete;
          description
            "Primary normal range VLAN ID of the private VLAN port association";
          type uint16 {
            range "2..1001 | 1006..4094";
          }
        }
        leaf secondary-range {
          status obsolete;
          description
            "Secondary normal range VLAN ID of the private VLAN host port association";
          type uint16 {
            range "2..1001 | 1006..4094";
          }
        }
      }
      container mapping {
        status obsolete;
        description
          "Set the private VLAN promiscuous mapping";
        leaf trunk {
          status obsolete;
          description
            "Set the private VLAN promiscuous trunk mapping";
          type empty;
        }
        leaf primary-range {
          status obsolete;
          description
            "Primary normal range VLAN ID of the private VLAN promiscuous port mapping";
          type uint16 {
            range "2..1001 | 1006..4094";
          }
        }
        leaf secondary-range {
          status obsolete;
          description
            "Secondary VLAN IDs of the private VLAN promiscuous port mapping";
          type string;
        }
        leaf add {
          status obsolete;
          description
            "Secondary VLAN IDs of the private VLAN promiscuous port mapping";
          type string;
        }
        leaf remove {
          status obsolete;
          description
            "Secondary VLAN IDs of the private VLAN promiscuous port mapping";
          type string;
        }
      }
      container trunk {
        status obsolete;
        description
          "Set the private vlan trunking configuration";
        container allowed {
          status obsolete;
          description
            "Set allowed VLAN characteristics when interface is in trunking mode";
          container vlan {
            status obsolete;
            description
              "Set allowed VLANs when interface is in trunking mode";
            leaf vlans {
              status obsolete;
              type union {
                type uint16;
                type string;
              }
            }
          }
        }
        container native {
          status obsolete;
          description
            "Set the private vlan trunking native configuration";
          container vlan {
            status obsolete;
            description
              "Set native VLAN configuration";
            leaf vlans {
              status obsolete;
              description
                "VLAN ID of the native VLAN when this port is in trunking mode";
              type uint16 {
                range "1..4094";
              }
            }
            leaf tag {
              status obsolete;
              description
                "Set native VLAN tagging state on Private VLAN trunk";
              type empty;
            }
          }
        }
      }
    }
    container vepa {
      status obsolete;
      description
        "Reflective relay configuration";
      leaf enabled {
        status obsolete;
        description
          "Enable reflective relay";
        type empty;
      }
    }
    leaf app-interface {
      status obsolete;
      description
        "Enable port for application hosting";
      type empty;
    }
  }

  grouping config-interface-switch-grouping {
    container auto {
      description
        "Configure Automation";
      container qos {
        description
          "Configure AutoQoS";
        container classify {
          description
            "Configure classification for untrusted devices";
          presence "true";
          leaf police {
            description
              "Configure QoS policing for untrusted devices";
            type empty;
          }
        }
        container trust {
          description
            "Trust the DSCP/CoS marking";
          presence "true";
          leaf cos {
            description
              "Trust the CoS marking";
            type empty;
          }
          leaf dscp {
            description
              "Trust the DSCP marking";
            type empty;
          }
        }
        container video {
          description
            "Configure AutoQoS for video devices";
          leaf cts {
            description
              "Trust the QoS marking of the Cisco Telepresence System";
            type empty;
          }
          leaf ip-camera {
            description
              "Trust the QoS marking of the Ip Video Surveillance camera";
            type empty;
          }
          leaf media-player {
            description
              "Trust the Qos marking of the Cisco Media Player";
            type empty;
          }
        }
        container voip {
          description
            "Configure AutoQoS for VoIP";
          presence "true";
          leaf cisco-phone {
            description
              "Trust the QoS marking of Cisco IP Phone";
            type empty;
          }
          leaf cisco-softphone {
            description
              "Trust the QoS marking of Cisco IP SoftPhone";
            type empty;
          }
          leaf trust {
            description
              "Trust the DSCP/CoS marking";
            type empty;
          }
        }
      }
      container detection {
        description
          "Configure automatic detection features for interface protocols";
        if-feature "ios-features:switching-platform";
        leaf macsec {
          description
            "Enable automatic detection and configuration of MACsec capable peers
             on the interface. When enabled, the interface automatically detects
             MACsec-capable neighbors and initiates security negotiation.";
          type boolean;
          default "true";
        }
      }
    }
    container datalink {
      description
        "Interface Datalink commands";
      container flow {
        description
          "Interface Flow configuration subcommands";
        list monitor-new {
          description
            "Apply a Flow Monitor";
          key "name direction";
          leaf name {
            description
              "User defined";
            type leafref {
              path "/ios:native/ios:flow/ios-flow:monitor/ios-flow:name";
            }
          }
          leaf direction {
            type enumeration {
              enum input;
              enum output;
            }
          }
          leaf sampler {
            type string;
          }
          leaf subtraffic {
            type enumeration {
              enum unicast;
              enum multicast;
            }
          }
        }
        container monitor {
          status obsolete;
          description
            "Apply a Flow Monitor";
          presence "true";
          leaf User-defined-flow {
            status obsolete;
            description
              "User defined";
            type string;
          }
          leaf input-output {
            status obsolete;
            description
              "Apply Flow Monitor on input/output traffic";
            type enumeration {
              enum input;
              enum output;
            }
          }
        }
      }
    }
    container energywise {
      description
        "EnergyWise interface configurations";
      presence "true";
      leaf activitycheck {
        description
          "Apply an activity check before turning off power
             to this PoE port";
        type empty;
      }
      list level {
        description
          "Set the EnergyWise level of this interface
           or attached entity";
        key "range";
        leaf range {
          type uint8 {
            range "0..10";
          }
        }
        container recurrence {
          description
            "Specify that this level setting should
             recur at the specified time";
          list importance {
            description
              "Specify the importance at which the event
               should be sent when it recurs";
            key "range";
            leaf range {
              type uint16 {
                range "1..100";
              }
            }
            container at {
              description
                "Specify the time(s) this level setting should occur";
              leaf minute {
                description
                  "cron format of minute(s)";
                type union {
                  type uint16 {
                    range "0..59";
                  }
                  type string {
                    pattern '[*].*';
                  }
                }
              }
              leaf hour {
                description
                  "cron format of hour(s)";
                type union {
                  type uint16 {
                    range "0..23";
                  }
                  type string {
                    pattern '[*].*';
                  }
                }
              }
              leaf day {
                description
                  "cron format of day(s) of month";
                type union {
                  type uint16 {
                    range "1..31";
                  }
                  type string {
                    pattern '[*].*';
                  }
                }
              }
              leaf month {
                description
                  "cron format of month(s)";
                type union {
                  type uint16 {
                    range "1..12";
                  }
                  type string {
                    pattern '[*].*';
                  }
                }
              }
              leaf weekday {
                description
                  "cron format of weekday(s)";
                type union {
                  type uint16 {
                    range "0..7";
                  }
                  type string {
                    pattern '[*].*';
                  }
                }
              }
            }
          }
        }
      }
    }
    container location {
      description
        "Interface location information";
      container civic-location-id {
        description
          "Civic location information";
        leaf location-identifier {
          description
            "civic location identifier string";
          type string;
        }
        container host {
          description
            "Globally defined host location identifier";
          presence "true";
          leaf port-location {
            description
              "Port specific attributes";
            type string;
          }
        }
        container none {
          description
            "No globally defined location identifier";
          presence "true";
          leaf port-location {
            description
              "Port specific attributes";
            type string;
          }
        }
      }
    }
    container mac {
      description
        "MAC interface commands";
      list access-group {
        description
          "MAC access-group configuration commands";
        key "direction";
        leaf direction {
          type enumeration {
            enum in;
            enum out;
          }
        }
        leaf acl-name {
          type string;
        }
      }
    }
    container macro {
      description
        "Command macro";
      leaf description {
        description
          "Macro description for this interface";
        type string;
      }
      container auto {
        description
          "Smartport interface macro configurations";
        leaf processing {
          description
            "Enable smartport macro auto execution on this interface";
          type boolean;
        }
        container port {
          description
            "Provide interface specific configuration for macro processing";
          leaf sticky {
            type empty;
          }
        }
        container control {
          description
            "Control macro auto execution";
          container device {
            description
              "Enable macro auto execution for devices";
            leaf phone {
              type empty;
            }
          }
        }
      }
    }
    container dual-active {
      leaf fast-hello {
        type empty;
      }
    }
    container load-balancing {
      description
        "Etherchannel Load-Balancing";
      leaf flow {
        description
          "Based on the traffic flows identified by the packet headers";
        type empty;
      }
      leaf vlan {
        description
          "Based on the VLAN to member links manual configuration";
        type empty;
      }
    }
    list vlan-range {
      key "id";
      leaf id {
        type union {
          type uint16 {
            range "1..4096";
          }
          type string;
        }
      }
      container service-policy {
        description
          "Configure QoS Service Policy";
        leaf input {
          description
            "Assign policy-map to the input of an interface";
          type string;
        }
        leaf output {
          description
            "Assign policy-map to the output of an interface";
          type string;
        }
      }
    }
    container switch {
      container virtual {
        leaf link {
          type uint8;
        }
      }
    }
    container srr-queue {
      container bandwidth {
        container shape {
          leaf weight1 {
            type uint16;
          }
          leaf weight2 {
            type uint16;
          }
          leaf weight3 {
            type uint16;
          }
          leaf weight4 {
            type uint16;
          }
        }
        container share {
          leaf weight1 {
            type uint8 {
              range "1..255";
            }
          }
          leaf weight2 {
            type uint8 {
              range "1..255";
            }
          }
          leaf weight3 {
            type uint8 {
              range "1..255";
            }
          }
          leaf weight4 {
            type uint8 {
              range "1..255";
            }
          }
        }
      }
    }
    leaf macsec {
      status obsolete;
      description
        "Enable macsec on the interface";
      if-feature "ios-features:macsec-switch";
      type empty;
    }
    container macsec-option {
      status obsolete;
      description
        "Enable macsec on the interface";
      if-feature "ios-features:macsec-switch";
      container macsec {
        container replay-protection {
          status obsolete;
          description
            "Set replay-protection";
          leaf window-size {
            status obsolete;
            description
              "Set replay window-size";
            type uint32;
          }
        }
        leaf network-link {
          description
            "Enable macsec on switch connected interface";
          type empty;
        }
        leaf strict {
          description
            "Enable strict validation of macsec";
          type empty;
        }
      }
    }
    uses interface-l2protocol-tunnel-grouping;
  }

  grouping config-interface-switch-grouping-obsolete {
    container auto {
      status obsolete;
      description
        "Configure Automation";
      container qos {
        status obsolete;
        description
          "Configure AutoQoS";
        container classify {
          status obsolete;
          description
            "Configure classification for untrusted devices";
          presence "true";
          leaf police {
            status obsolete;
            description
              "Configure QoS policing for untrusted devices";
            type empty;
          }
        }
        container trust {
          status obsolete;
          description
            "Trust the DSCP/CoS marking";
          presence "true";
          leaf cos {
            status obsolete;
            description
              "Trust the CoS marking";
            type empty;
          }
          leaf dscp {
            status obsolete;
            description
              "Trust the DSCP marking";
            type empty;
          }
        }
        container video {
          status obsolete;
          description
            "Configure AutoQoS for video devices";
          leaf cts {
            status obsolete;
            description
              "Trust the QoS marking of the Cisco Telepresence System";
            type empty;
          }
          leaf ip-camera {
            status obsolete;
            description
              "Trust the QoS marking of the Ip Video Surveillance camera";
            type empty;
          }
          leaf media-player {
            status obsolete;
            description
              "Trust the Qos marking of the Cisco Media Player";
            type empty;
          }
        }
        container voip {
          status obsolete;
          description
            "Configure AutoQoS for VoIP";
          presence "true";
          leaf cisco-phone {
            status obsolete;
            description
              "Trust the QoS marking of Cisco IP Phone";
            type empty;
          }
          leaf cisco-softphone {
            status obsolete;
            description
              "Trust the QoS marking of Cisco IP SoftPhone";
            type empty;
          }
          leaf trust {
            status obsolete;
            description
              "Trust the DSCP/CoS marking";
            type empty;
          }
        }
      }
    }
    container datalink {
      status obsolete;
      description
        "Interface Datalink commands";
      container flow {
        status obsolete;
        description
          "Interface Flow configuration subcommands";
        container monitor {
          status obsolete;
          description
            "Apply a Flow Monitor";
          presence "true";
          leaf User-defined-flow {
            status obsolete;
            description
              "User defined";
            type string;
          }
          leaf input-output {
            status obsolete;
            description
              "Apply Flow Monitor on input/output traffic";
            type enumeration {
              enum input;
              enum output;
            }
          }
        }
      }
    }
    container energywise {
      status obsolete;
      description
        "EnergyWise interface configurations";
      presence "true";
      leaf activitycheck {
        status obsolete;
        description
          "Apply an activity check before turning off power
                 to this PoE port";
        type empty;
      }
      list level {
        status obsolete;
        description
          "Set the EnergyWise level of this interface
           or attached entity";
        key "range";
        leaf range {
          status obsolete;
          type uint8 {
            range "0..10";
          }
        }
        container recurrence {
          status obsolete;
          description
            "Specify that this level setting should
             recur at the specified time";
          list importance {
            status obsolete;
            description
              "Specify the importance at which the event
               should be sent when it recurs";
            key "range";
            leaf range {
              status obsolete;
              type uint16 {
                range "1..100";
              }
            }
            container at {
              status obsolete;
              description
                "Specify the time(s) this level setting should occur";
              leaf minute {
                status obsolete;
                description
                  "cron format of minute(s)";
                type union {
                  type uint16 {
                    range "0..59";
                  }
                  type string {
                    pattern '[*].*';
                  }
                }
              }
              leaf hour {
                status obsolete;
                description
                  "cron format of hour(s)";
                type union {
                  type uint16 {
                    range "0..23";
                  }
                  type string {
                    pattern '[*].*';
                  }
                }
              }
              leaf day {
                status obsolete;
                description
                  "cron format of day(s) of month";
                type union {
                  type uint16 {
                    range "1..31";
                  }
                  type string {
                    pattern '[*].*';
                  }
                }
              }
              leaf month {
                status obsolete;
                description
                  "cron format of month(s)";
                type union {
                  type uint16 {
                    range "1..12";
                  }
                  type string {
                    pattern '[*].*';
                  }
                }
              }
              leaf weekday {
                status obsolete;
                description
                  "cron format of weekday(s)";
                type union {
                  type uint16 {
                    range "0..7";
                  }
                  type string {
                    pattern '[*].*';
                  }
                }
              }
            }
          }
        }
      }
    }
    container location {
      status obsolete;
      description
        "Interface location information";
      container civic-location-id {
        status obsolete;
        description
          "Civic location information";
        leaf location-identifier {
          status obsolete;
          description
            "civic location identifier string";
          type string;
        }
        container host {
          status obsolete;
          description
            "Globally defined host location identifier";
          presence "true";
          leaf port-location {
            status obsolete;
            description
              "Port specific attributes";
            type string;
          }
        }
        container none {
          status obsolete;
          description
            "No globally defined location identifier";
          presence "true";
          leaf port-location {
            status obsolete;
            description
              "Port specific attributes";
            type string;
          }
        }
      }
    }
    container mac {
      status obsolete;
      description
        "MAC interface commands";
      list access-group {
        status obsolete;
        description
          "MAC access-group configuration commands";
        key "direction";
        leaf direction {
          status obsolete;
          type enumeration {
            enum in;
            enum out;
          }
        }
        leaf acl-name {
          status obsolete;
          type string;
        }
      }
    }
    container macro {
      status obsolete;
      description
        "Command macro";
      leaf description {
        status obsolete;
        description
          "Macro description for this interface";
        type string;
      }
      container auto {
        status obsolete;
        description
          "Smartport interface macro configurations";
        leaf processing {
          status obsolete;
          description
            "Enable smartport macro auto execution on this interface";
          type boolean;
        }
        container port {
          status obsolete;
          description
            "Provide interface specific configuration for macro processing";
          leaf sticky {
            status obsolete;
            type empty;
          }
        }
        container control {
          status obsolete;
          description
            "Control macro auto execution";
          container device {
            status obsolete;
            description
              "Enable macro auto execution for devices";
            leaf phone {
              status obsolete;
              type empty;
            }
          }
        }
      }
    }
    container dual-active {
      status obsolete;
      leaf fast-hello {
        status obsolete;
        type empty;
      }
    }
    container load-balancing {
      status obsolete;
      description
        "Etherchannel Load-Balancing";
      leaf flow {
        status obsolete;
        description
          "Based on the traffic flows identified by the packet headers";
        type empty;
      }
      leaf vlan {
        status obsolete;
        description
          "Based on the VLAN to member links manual configuration";
        type empty;
      }
    }
    list vlan-range {
      status obsolete;
      key "id";
      leaf id {
        status obsolete;
        type union {
          type uint16 {
            range "1..4096";
          }
          type string;
        }
      }
      container service-policy {
        status obsolete;
        description
          "Configure QoS Service Policy";
        leaf input {
          status obsolete;
          description
            "Assign policy-map to the input of an interface";
          type string;
        }
        leaf output {
          status obsolete;
          description
            "Assign policy-map to the output of an interface";
          type string;
        }
      }
    }
    container switch {
      status obsolete;
      container virtual {
        status obsolete;
        leaf link {
          status obsolete;
          type uint8;
        }
      }
    }
    container srr-queue {
      status obsolete;
      container bandwidth {
        status obsolete;
        container shape {
          status obsolete;
          leaf weight1 {
            status obsolete;
            type uint16;
          }
          leaf weight2 {
            status obsolete;
            type uint16;
          }
          leaf weight3 {
            status obsolete;
            type uint16;
          }
          leaf weight4 {
            status obsolete;
            type uint16;
          }
        }
        container share {
          status obsolete;
          leaf weight1 {
            status obsolete;
            type uint8 {
              range "1..255";
            }
          }
          leaf weight2 {
            status obsolete;
            type uint8 {
              range "1..255";
            }
          }
          leaf weight3 {
            status obsolete;
            type uint8 {
              range "1..255";
            }
          }
          leaf weight4 {
            status obsolete;
            type uint8 {
              range "1..255";
            }
          }
        }
      }
    }
    leaf macsec {
      status obsolete;
      description
        "Enable macsec on the interface";
      if-feature "ios-features:macsec-switch";
      type empty;
    }
    container macsec-option {
      status obsolete;
      description
        "Enable macsec on the interface";
      if-feature "ios-features:macsec-switch";
      container macsec {
        status obsolete;
        container replay-protection {
          status obsolete;
          description
            "Set replay-protection";
          leaf window-size {
            status obsolete;
            description
              "Set replay window-size";
            type uint32;
          }
        }
        leaf network-link {
          status obsolete;
          description
            "Enable macsec on switch connected interface";
          type empty;
        }
      }
    }
    uses interface-l2protocol-tunnel-grouping-obsolete;
  }

  grouping config-macro-auto-grouping {
    list execute {
      description
        "Map event trigger to macro";
      key "trigger-event";
      leaf trigger-event {
        type string;
      }
      container builtin {
        description
          "Display builtin shell functions";
        leaf smart-port-configuration {
          type enumeration {
            enum CISCO_AP_AUTO_SMARTPORT;
            enum CISCO_DMP_AUTO_SMARTPORT;
            enum CISCO_DMP_AUTO_SMARTPORT_V1;
            enum CISCO_IP_CAMERA_AUTO_SMARTPORT;
            enum CISCO_LAST_RESORT_SMARTPORT;
            enum CISCO_LIGHT_AUTO_SMARTPORT;
            enum CISCO_LWAP_AUTO_SMARTPORT;
            enum CISCO_PHONE_AUTO_SMARTPORT;
            enum CISCO_PHONE_AUTO_SMARTPORT_V1;
            enum CISCO_ROUTER_AUTO_SMARTPORT;
            enum CISCO_SWITCH_AUTO_SMARTPORT;
            enum MS_IP_CAMERA_AUTO_SMARTPORT;
            enum MS_VIDEO_CONF_AUTO_SMARTPORT;
          }
        }
        leaf parameters {
          type string;
        }
      }
    }
    container device {
      description
        " auto execution configuration";
      leaf media-player {
        description
          "digital media player for auto config";
        type string;
      }
      leaf ip-camera {
        description
          "video surveillance camera for auto config";
        type string;
      }
    }
    container global {
      description
        "Macro auto execution configuration";
      leaf processing {
        description
          "Enable auto smartports, all ports enabled by default";
        type empty;
      }
    }
  }

  grouping boot-filename-grouping {
    container boot-container {
      description
        "Set system image filename for switches in the stack";
      list boot-filename {
        ordered-by user;
        key "filename";
        leaf filename {
          description
            "System image file";
          type string {
            pattern '(bootflash|flash|ftp|http|sftp|tftp):.+';
          }
        }
      }
    }
  }

  grouping config-boot-system-grouping {
    container switch {
      description
        "Set system image for switches in the stack";
      list switch-number {
        key "range";
        leaf range {
          description
            "Switch number";
          type uint8 {
            range "1..16";
          }
        }
        uses boot-filename-grouping;
        leaf flash-1-path {
          status obsolete;
          description
            "Example edison.bin";
          type string;
        }
        leaf flash-path {
          status obsolete;
          description
            "Example edison.bin";
          type string;
        }
        leaf tftp-path {
          status obsolete;
          description
            "Example 192.x.x.x/<path>";
          type string;
        }
      }
      container all {
        description
          "Set system image for all switches in the stack";
        uses boot-filename-grouping;
        leaf flash-1 {
          status obsolete;
          description
            "Example edison.bin";
          type string;
        }
        leaf flash {
          status obsolete;
          description
            "Example edison.bin";
          type string;
        }
        leaf tftp {
          status obsolete;
          description
            "Example 192.x.x.x/<image-path>";
          type string;
        }
      }
    }
  }

  grouping config-boot-switch-options-grouping {
    container enable-break-per-switch {
      description
        "Enable break per switch";
      list enable-break {
        description
          "Set enable break for switches in the stack";
        key "switch";
        leaf switch {
          type uint8 {
            range "1..16";
          }
        }
      }
    }
    container enable-break {
      status obsolete;
      description
        "Enable break";
      presence "true";
      leaf switch {
        status obsolete;
        description
          "Set enable break for switches in the stack";
        type uint8 {
          range "1..9";
        }
      }
    }
    container manual {
      description
        "Manual boot";
      presence "true";
      leaf switch {
        description
          "Set manual boot for switches in the stack:Switch number(s)";
        type uint8 {
          range "1..9";
        }
      }
    }
  }

  grouping config-module-grouping {
    container provision {
      description
        "Configure module provision status";
      list switch {
        key "number";
        leaf number {
          type uint8;
        }
        container chassis {
          leaf chassis-type {
            type uint32;
          }
          leaf base-mac {
            type string;
          }
        }
        list slot {
          key "number";
          leaf number {
            type uint8;
          }
          leaf slot-type {
            type uint32;
          }
          leaf base-mac {
            type string;
          }
        }
      }
    }
  }

  grouping config-sdm-grouping {
    container prefer {
      description
        "Config TCAM and ASIC RAM size. Warning: need to reset switch for configuration to take effect";
      presence "true";
      choice sdm-prefer-choice {
        leaf default {
          type empty;
        }
        leaf qos {
          type empty;
        }
      }
    }
  }

  grouping config-setup-grouping {
    leaf express {
      description
        "Configure whether express setup mode is enabled";
      type boolean;
    }
  }

  grouping config-stack-mac-grouping {
    container stack-mac {
      description
        "Global stack mac-address feature configurations";
      container persistent {
        description
          "persistent stack mac-address";
        leaf timer {
          description
            "use stack mac-address timer after master failure( 0 means still using the current MAC)";
          type uint8 {
            range "0..60";
          }
        }
      }
    }
  }

  grouping config-switch-grouping {
    container switch-global-config {
      description
        "Set speed on next reboot";
      container switch {
        leaf stack-speed {
          type enumeration {
            enum high;
            enum low;
          }
        }
      }
    }
    list switch {
      description
        "Config commands for the switches in the stack";
      key "number";
      leaf number {
        type uint8 {
          range "1..16";
        }
      }
      leaf provision {
        description
          "Configure Switch provision / offline config";
        type enumeration {
          enum ws-c2960x-24pd-l;
          enum ws-c3650-48ps;
          enum ws-c3650-24ps;
          enum ws-c3850-48p;
          enum ws-c3850-24p;
          enum ws-c3850-48t;
          enum ws-c3850-24t;
          enum ws-c3850-48f;
          enum ws-c3850-48u;
          enum ws-c3850-24u;
          enum ws-c3850-12x48u;
          enum ws-c3850-24xu;
          enum ws-c3850-24ux;
          enum ws-c3850-12s;
          enum ws-c3850-24s;
          enum ws-c3850-12xs;
          enum ws-c3850-24xs;
          enum ws-c3850-48xs;
          enum ws-c3650-12x48fd;
          enum ws-c3650-12x48uq;
          enum ws-c3650-12x48ur;
          enum ws-c3650-12x48uz;
          enum ws-c3650-24pd;
          enum ws-c3650-24pdm;
          enum ws-c3650-24td;
          enum ws-c3650-24ts;
          enum ws-c3650-48fqm;
          enum ws-c3650-48pd;
          enum ws-c3650-48pq;
          enum ws-c3650-48td;
          enum ws-c3650-48tq;
          enum ws-c3650-48ts;
          enum ws-c3650-8x24pd;
          enum ws-c3650-8x24uq;
          enum ws-c3750x-24p;
          enum ws-c3750x-12s;
          enum ws-c3850-12x48au;
          enum c9300-24p;
          enum c9300-24t;
          enum c9300-24u;
          enum c9300-48p;
          enum c9300-48t;
          enum c9300-48u;
          enum c9300-24s;
          enum c9300-24ux;
          enum c9300-48mt;
          enum c9300-48s;
          enum c9300-48un;
          enum c9300-48uxm;
          enum c9300l-24p-4g;
          enum c9300l-24p-4x;
          enum c9300l-24t-4g;
          enum c9300l-24t-4x;
          enum c9300l-24uxg-2q;
          enum c9300l-24uxg-4x;
          enum c9300l-48p-4g;
          enum c9300l-48p-4x;
          enum c9300l-48t-4g;
          enum c9300l-48t-4x;
          enum c9300l-48uxg-2q;
          enum c9300l-48uxg-4x;
          enum c9500-12q;
          enum c9500-16x;
          enum c9500-24q;
          enum c9500-40x;
          enum c9200l-24p-4g;
          enum c9200l-24p-4x;
          enum c9200l-24pxg-2y;
          enum c9200l-24pxg-4x;
          enum c9200l-24t-4g;
          enum c9200l-24t-4x;
          enum c9200l-48p-4g;
          enum c9200l-48p-4x;
          enum c9200l-48pl-4g;
          enum c9200l-48pl-4x;
          enum c9200l-48pxg-2y;
          enum c9200l-48pxg-4x;
          enum c9200l-48t-4g;
          enum c9200l-48t-4x;
          enum c9200-24p;
          enum c9200-24pxg;
          enum c9200-24t;
          enum c9200-48p;
          enum c9200-48pl;
          enum c9200-48pxg;
          enum c9200-48t;
          enum C9200-24PB;
          enum C9200-48PB;
          enum c9300lm-24u-4y;
          enum c9300lm-48t-4y;
          enum c9300lm-48u-4y;
          enum c9300lm-48ux-4y;
          enum c9500-32c;
          enum c9500-32qc;
          enum c9500-48y4c;
          enum c9500-24y4c;
        }
      }
    }
  }

  grouping config-switch-virtual-grouping {
    status obsolete;
    list switch-virtual {
      status obsolete;
      key "domain";
      leaf domain {
        status obsolete;
        type uint32;
      }
      leaf virtual {
        status obsolete;
        type empty;
      }
      container switch {
        description
          "Configure switch command";
        status obsolete;
        leaf switch-number {
          description
            "Virtual switch number";
          status obsolete;
          type uint32 {
            range "1..2";
          }
        }
        leaf priority {
          status obsolete;
          description
            "Virtual switch priority value";
          type uint32;
        }
        leaf mode {
          status obsolete;
          type enumeration {
            enum virtual;
          }
        }
      }
      container mac-address {
        status obsolete;
        leaf use-virtual {
          status obsolete;
          type empty;
        }
      }
      container dual-active {
        status obsolete;
        description
          "Virtual switch dual-active config";
        container recovery {
          status obsolete;
          description
            "Recovery IP address";
          leaf switch {
            status obsolete;
            description
              "Switch ID for recovery IP address";
            type uint8 {
              range "1..2";
            }
          }
          container ip {
            status obsolete;
            description
              "Recovery IP address";
            leaf address {
              status obsolete;
              description
                "Recovery IP address";
              type inet:ipv4-address;
            }
            leaf mask {
              status obsolete;
              description
                "IP address mask";
              type inet:ipv4-address;
            }
          }
        }
        container detection {
          status obsolete;
          description
            "Dual-active detection enable";
          container pagp {
            status obsolete;
            description
              "Dual-active detection using PAgP";
            presence "true";
            container trust {
              status obsolete;
              description
                "Trusted channels for PAgP dual-active detection";
              leaf channel-group {
                status obsolete;
                description
                  "Etherchannel/port bundle to be used for pagp dual-active detection";
                type uint8 {
                  range "1..254";
                }
              }
            }
          }
        }
      }
    }
  }

  grouping config-network-policy-grouping {
    status obsolete;
    container network-policy {
      status obsolete;
      description
        "Network Policy";
      leaf profile {
        status obsolete;
        description
          "Network Policy Profile";
        type uint32 {
          range "1..4294967295";
        }
      }
    }
  }

  grouping config-network-policy-grouping-v2 {
    container network-policy-v2 {
      description
        "Configure Network Policy profiles";
      list profile-v2 {
        description
          "Configure a Network Policy profile";
        key "profile-id";
        leaf profile-id {
          description
            "Network Policy profile number";
          type uint32 {
            range "1..4294967295";
          }
        }
        container voice {
          description
            "Voice appliance attributes";
          container vlan {
            description
              "Vlan for voice traffic";
            choice vlan-type {
              description
                "Select the type of VLAN configuration for voice traffic";
              case vlan-id-case {
                container vlan-id-parameters {
                  description
                    "VLAN ID and associated QoS parameters";
                  leaf vlan-id {
                    description
                      "Vlan for voice traffic";
                    type uint16 {
                      range "1..4094";
                    }
                  }
                  choice qos-marking {
                    description
                      "Choose either CoS or DSCP for QoS marking";
                    leaf cos {
                      description
                        "L2 Priority(CoS) for voice devices";
                      type uint8 {
                        range "0..7";
                      }
                      when '../vlan-id';
                    }
                    leaf dscp {
                      description
                        "DSCP used for LLDP-MED Network Policy TLV";
                      type uint8 {
                        range "0..63";
                      }
                      when '../vlan-id';
                    }
                  }
                }
              }
              case dot1p-case {
                container dot1p {
                  description
                    "Priority tagged on Port VLAN ID";
                  presence "Priority tagged on Port VLAN ID";
                  leaf cos {
                    description
                      "L2 Priority(CoS) for voice devices";
                    type uint8 {
                      range "0..7";
                    }
                  }
                  leaf dscp {
                    description
                      "DSCP used for LLDP-MED Network Policy TLV";
                    type uint8 {
                      range "0..63";
                    }
                  }
                }
              }
              case untagged-case {
                leaf untagged {
                  description
                    "Untagged on Port VLAN ID";
                  type empty;
                }
              }
            }
          }
        }
        container voice-signaling {
          description
            "Voice signaling appliance attributes";
          container vlan {
            description
              "Vlan for voice-signaling traffic";
            choice vlan-type {
              description
                "Select the type of VLAN configuration for voice-signaling traffic";
              case vlan-id-case {
                container vlan-id-parameters {
                  description
                    "VLAN ID and associated QoS parameters";
                  leaf vlan-id {
                    description
                      "Vlan for voice-signaling traffic";
                    type uint16 {
                      range "1..4094";
                    }
                  }
                  choice qos-marking {
                    description
                      "Choose either CoS or DSCP for QoS marking";
                    leaf cos {
                      description
                        "L2 Priority(CoS) for voice-signaling devices";
                      type uint8 {
                        range "0..7";
                      }
                      when '../vlan-id';
                    }
                    leaf dscp {
                      description
                        "DSCP used for LLDP-MED Network Policy TLV";
                      type uint8 {
                        range "0..63";
                      }
                      when '../vlan-id';
                    }
                  }
                }
              }
              case dot1p-case {
                container dot1p {
                  description
                    "Priority tagged on Port VLAN ID";
                  presence "Priority tagged on Port VLAN ID";
                  leaf cos {
                    description
                      "L2 Priority(CoS) for voice-signaling devices";
                    type uint8 {
                      range "0..7";
                    }
                  }
                  leaf dscp {
                    description
                      "DSCP used for LLDP-MED Network Policy TLV";
                    type uint8 {
                      range "0..63";
                    }
                  }
                }
              }
              case untagged-case {
                leaf untagged {
                  description
                    "Untagged on Port VLAN ID";
                  type empty;
                }
              }
            }
          }
        }
      }
    }
  }

  grouping config-device-grouping {
    container device {
      description
        "device classifier configuration";
      container classifier-enable {
        description
          "device classifier enable configuration";
        leaf classifier {
          description
            "Enable/Disable classification of attached devices";
          type empty;
        }
      }
      container classifier-with-condition {
        description
          "device classifier condition and device type configuration";
        container classifier {
          description
            "device classifier condition device type configuration";
          list condition {
            description
              "Define device classifier condition";
            key "name";
            leaf name {
              description
                "Condition name";
              type string;
            }
            leaf op {
              description
                "Define condition operator";
              type enumeration {
                enum AND;
                enum OR;
              }
            }
            uses cdp-condition-grouping-v2;
            uses lldp-condition-grouping-v2;
            uses dhcp-condition-grouping-v2;
            uses mac-regex-condition-grouping-v2;
            uses condition-list-grouping;
          }
          list device-type {
            description
              "Define device type";
            key "name";
            leaf name {
              description
                "Device type name";
              type string;
            }
            uses condition-name-grouping-v2;
          }
        }
      }
      container config-classifier-condition-devtype {
        status obsolete;
        list condition {
          status obsolete;
          description
            "Define device classifier condition";
          must 'not (../../classifier)' {
            error-message "Device classifier is enabled.Please disable it and execute the command again.";
          }
          key "name";
          leaf name {
            status obsolete;
            description
              "Condition name";
            type string;
          }
          leaf op {
            status obsolete;
            description
              "Define condition operator";
            type enumeration {
              enum AND;
              enum OR;
            }
          }
          uses cdp-condition-grouping-deprecate;
          uses lldp-condition-grouping-deprecate;
          uses dhcp-condition-grouping-deprecate;
        }
        list device-type {
          status obsolete;
          description
            "Define device type";
          key "name";
          leaf name {
            status obsolete;
            description
              "Device type name";
            must 'not (../../../../device/classifier)' {
              error-message "Device classifier is enabled.Please disable it and execute the command again.";
            }
            type string;
          }
          uses condition-name-grouping-deprecate;
        }
      }
      leaf classifier {
        status obsolete;
        description
          "Enable/Disable classification of attached devices";
        type empty;
      }
    }
  }

  grouping cdp-condition-grouping-v2 {
    container CDP {
      description
        "CDP related rules";
      uses grouping-tlv-type-v2;
    }
  }

  grouping dhcp-condition-grouping-v2 {
    container DHCP {
      description
        "DHCP related rules";
      uses grouping-tlv-type-v2;
    }
  }

  grouping lldp-condition-grouping-v2 {
    container LLDP {
      description
        "LLDP related rules";
      uses grouping-tlv-type-v2;
    }
  }

  grouping mac-regex-condition-grouping-v2 {
    container MAC {
      description
        "MAC related rules";
      leaf-list Regex {
        type string {
          pattern '(((([0-9a-fA-F]{4}\.){2}[0-9a-fA-F]{4}|([0-9a-fA-F]{4}\.)*([0-9a-fA-F]{0,4})\*((\.([0-9a-fA-F]{4}\.)*|([0-9a-fA-F]{0,4}\.([0-9a-fA-F]{4}\.)*)?[0-9a-fA-F]{1,4}|[0-9a-fA-F]{1,4}((\.[0-9a-fA-F]{4})*\.))\*)*([0-9a-fA-F]{0,4})(\.[0-9a-fA-F]{4})*)\|)*(([0-9a-fA-F]{4}\.){2}[0-9a-fA-F]{4}|([0-9a-fA-F]{4}\.)*([0-9a-fA-F]{0,4})\*((\.([0-9a-fA-F]{4}\.)*|([0-9a-fA-F]{0,4}\.([0-9a-fA-F]{4}\.)*)?[0-9a-fA-F]{1,4}|[0-9a-fA-F]{1,4}((\.[0-9a-fA-F]{4})*\.))\*)*([0-9a-fA-F]{0,4})(\.[0-9a-fA-F]{4})*))' {
            error-message "Invalid format string";
          }
          length "1..240" {
            error-message "Invalid string length";
          }
        }
      }
    }
  }

  grouping condition-list-grouping {
    leaf-list condition {
      description
        "Condition name";
      must '../../condition[name = current()]' {
        error-message "Create after Condition Creation or Delete before Condition Deletion";
      }
      type string;
    }
  }

  grouping grouping-tlv-type-v2 {
    list tlv-type {
      description
        "Give TLV type";
      key "tlv-type-number";
      leaf tlv-type-number {
        description
          "TLV type value";
        type uint32 {
          range "1..255";
        }
      }
      container value {
        description
          "Give value type";
        leaf-list Integer {
          description
            "Match Integer";
          type uint32 {
            range "1..2147483647";
          }
        }
        leaf-list String {
          description
            "Match string";
          type string;
        }
        leaf-list Regex {
          description
            "Match regular expression";
          type string;
        }
        leaf-list Hexstr {
          description
            "Match Hexadecimal string";
          type string {
            length "1..256";
            pattern '[0-9a-fA-F]*' {
              error-message "Incorrect format";
            }
          }
        }
      }
    }
  }

  grouping condition-name-grouping-v2 {
    list condition-list {
      description
        "Give condition name";
      must 'count(../condition-list) <= 1' {
        error-message "Already condition is attached. Max one condition is allowed.";
      }
      key "name";
      leaf name {
        description
          "Condition name";
        type string;
        must '../../../condition[name = current()]' {
          error-message "Create after Condition Creation or Delete before Condition Deletion";
        }
      }
      leaf priority {
        description
          "Give priority value";
        type uint32 {
          range "10..100";
        }
      }
    }
    leaf condition {
      status deprecated;
      description
        "Give condition name";
      must '../../condition[name = current()]' {
        error-message "Create after Condition Creation or Delete before Condition Deletion";
      }
      type string;
    }
  }

  grouping cdp-condition-grouping-deprecate {
    container CDP {
      status obsolete;
      description
        "CDP related rules";
      uses grouping-tlv-type-deprecate;
    }
  }

  grouping dhcp-condition-grouping-deprecate {
    container DHCP {
      status obsolete;
      description
        "DHCP related rules";
      uses grouping-tlv-type-deprecate;
    }
  }

  grouping lldp-condition-grouping-deprecate {
    container LLDP {
      status obsolete;
      description
        "LLDP related rules";
      uses grouping-tlv-type-deprecate;
    }
  }

  grouping grouping-tlv-type-deprecate {
    list tlv-type {
      status obsolete;
      description
        "Give TLV type";
      key "tlv-type-number";
      leaf tlv-type-number {
        status obsolete;
        description
          "TLV type value";
        type uint32 {
          range "1..255";
        }
      }
      container value {
        status obsolete;
        description
          "Give value type";
        leaf-list Integer {
          status obsolete;
          description
            "Match Integer";
          type uint32 {
            range "1..2147483647";
          }
        }
        leaf-list String {
          status obsolete;
          description
            "Match string";
          type string;
        }
        leaf-list Regex {
          status obsolete;
          description
            "Match regular expression";
          type string;
        }
      }
    }
  }

  grouping condition-name-grouping-deprecate {
    leaf condition {
      status obsolete;
      description
        "Give condition name";
      must '../../condition[name = current()]' {
        error-message "Given condition doesn't exist. Create the condition first";
      }
      type string;
    }
  }

  grouping l2pt-parameter-grouping {
    leaf pps_num {
      description
        "Packets/sec rate beyond which interface is put to err-disable";
      type uint16 {
        range "1..4096";
      }
    }
  }

  grouping l2pt-parameter-grouping-obsolete {
    leaf pps_num {
      status obsolete;
      description
        "Packets/sec rate beyond which interface is put to err-disable";
      type uint16 {
        range "1..4096";
      }
    }
  }

  grouping l2pt-choice-grouping {
    container cdp {
      description
        "Cisco Discovery Protocol";
      uses l2pt-parameter-grouping;
    }
    container stp {
      description
        "Spanning Tree Protocol";
      uses l2pt-parameter-grouping;
    }
    container vtp {
      description
        "Vlan Trunking Protocol";
      uses l2pt-parameter-grouping;
    }
    container lldp {
      description
        "Link Layer Discovery Protocol";
      uses l2pt-parameter-grouping;
    }
    container point-to-point {
      description
        "point-to-point L2 Protocol";
      container lacp {
        description
          "Link Aggregation Control Protocol";
        uses l2pt-parameter-grouping;
      }
      container pagp {
        description
          "Port Aggregation Protocol";
        uses l2pt-parameter-grouping;
      }
      container udld {
        description
          "Unidirectional Link Detection";
        uses l2pt-parameter-grouping;
      }
    }
  }

  grouping l2pt-choice-grouping-obsolete {
    container cdp {
      status obsolete;
      description
        "Cisco Discovery Protocol";
      uses l2pt-parameter-grouping-obsolete;
    }
    container stp {
      status obsolete;
      description
        "Spanning Tree Protocol";
      uses l2pt-parameter-grouping-obsolete;
    }
    container vtp {
      status obsolete;
      description
        "Vlan Trunking Protocol";
      uses l2pt-parameter-grouping-obsolete;
    }
    container lldp {
      status obsolete;
      description
        "Link Layer Discovery Protocol";
      uses l2pt-parameter-grouping-obsolete;
    }
    container point-to-point {
      status obsolete;
      description
        "point-to-point L2 Protocol";
      container lacp {
        status obsolete;
        description
          "Link Aggregation Control Protocol";
        uses l2pt-parameter-grouping-obsolete;
      }
      container pagp {
        status obsolete;
        description
          "Port Aggregation Protocol";
        uses l2pt-parameter-grouping-obsolete;
      }
      container udld {
        status obsolete;
        description
          "Unidirectional Link Detection";
        uses l2pt-parameter-grouping-obsolete;
      }
    }
  }

  grouping interface-l2protocol-tunnel-grouping {
    container l2protocol-tunnel {
      description
        "Tunnel Layer2 protocols";
      container drop-threshold {
        description
          "Set drop threshold for protocol packets";
        uses l2pt-choice-grouping;
      }
      container shutdown-threshold {
        description
          "Set shutdown threshold for protocol packets";
        uses l2pt-choice-grouping;
      }
      leaf cdp {
        description
          "Cisco Discovery Protocol";
        type empty;
      }
      leaf stp {
        description
          "Spanning Tree Protocol";
        type empty;
      }
      leaf vtp {
        description
          "Vlan Trunking Protocol";
        type empty;
      }
      leaf lldp {
        description
          "Link Layer Discovery Protocol";
        type empty;
      }
      container point-to-point {
        description
          "point-to-point L2 Protocol";
        leaf lacp {
          description
            "Link Aggregation Control Protocol";
          type empty;
        }
        leaf pagp {
          description
            "Port Aggregation Protocol";
          type empty;
        }
        leaf udld {
          description
            "Unidirectional Link Detection";
          type empty;
        }
      }
    }
  }

  grouping interface-l2protocol-tunnel-grouping-obsolete {
    container l2protocol-tunnel {
      status obsolete;
      description
        "Tunnel Layer2 protocols";
      container drop-threshold {
        status obsolete;
        description
          "Set drop threshold for protocol packets";
        uses l2pt-choice-grouping-obsolete;
      }
      container shutdown-threshold {
        status obsolete;
        description
          "Set shutdown threshold for protocol packets";
        uses l2pt-choice-grouping-obsolete;
      }
      leaf cdp {
        status obsolete;
        description
          "Cisco Discovery Protocol";
        type empty;
      }
      leaf stp {
        status obsolete;
        description
          "Spanning Tree Protocol";
        type empty;
      }
      leaf vtp {
        status obsolete;
        description
          "Vlan Trunking Protocol";
        type empty;
      }
      leaf lldp {
        status obsolete;
        description
          "Link Layer Discovery Protocol";
        type empty;
      }
      container point-to-point {
        status obsolete;
        description
          "point-to-point L2 Protocol";
        leaf lacp {
          status obsolete;
          description
            "Link Aggregation Control Protocol";
          type empty;
        }
        leaf pagp {
          status obsolete;
          description
            "Port Aggregation Protocol";
          type empty;
        }
        leaf udld {
          status obsolete;
          description
            "Unidirectional Link Detection";
          type empty;
        }
      }
    }
  }

  grouping config-l2protocol-tunnel-grouping {
    container l2protocol-tunnel {
      description
        "Tunnel Layer2 protocols";
      leaf cos {
        description
          "Class of Service";
        type uint8 {
          range "0..7";
        }
      }
      container global {
        description
          "Global settings";
        leaf drop-threshold {
          description
            "Global L2PT packets drop threshold";
          type uint16 {
            range "100..20000";
          }
        }
      }
    }
  }

  grouping config-rep-grouping {
    container rep {
      description
        "Resilient Ethernet Protocol characteristics";
      container admin {
        description
          "administrative configuration";
        list vlan {
          description
            "VLAN";
          key "name";
          leaf name {
            type uint16 {
              range "2..4094";
            }
          }
        }
      }
    }
  }

  grouping config-hw-switch-grouping {
    container hw-switch {
      description
        "Hw-switch";
      container switch {
        description
          "Switch in the system";
        list switch-number {
          key "switch-number";
          leaf switch-number {
            description
              "Switch number in the Stack (Refer to show switch CLI)";
            type uint8 {
              range "1..9";
            }
          }
          container logging {
            description
              "Logging onboard";
            container onboard {
              description
                "Logging onboard";
              presence "true";
              leaf counter {
                description
                  "Configure logging onboard counter";
                type empty;
              }
              leaf environment {
                description
                  "Configure logging onboard environment";
                type empty;
              }
              leaf message {
                description
                  "Configure logging onboard message";
                type empty;
              }
              leaf poe {
                description
                  "Configure logging onboard poe";
                type empty;
              }
              leaf temperature {
                description
                  "Configure logging onboard temperature";
                type empty;
              }
              leaf voltage {
                description
                  "Configure logging onboard voltage";
                type empty;
              }
            }
          }
        }
      }
    }
  }

  grouping config-energywise-grouping {
    container energywise {
      description
        "EnergyWise Global Configuration Commands";
      list domain {
        description
          "Set the EnergyWise domain this entity should join";
        key "word";
        leaf word {
          type string;
        }
        container security {
          description
            "Set security parameters for this EnergyWise domain";
          container shared-secret {
            description
              "Set the shared secret for this EnergyWise domain";
            list zero {
              description
                "Specifies an UNENCRYPTED shared secret for the domain will follow";
              key "word";
              leaf word {
                type string;
              }
              container protocol {
                description
                  "Specify a communication protocol to use to communicate with the EnergyWise domain";
                container udp {
                  description
                    "UDP protocol";
                  leaf port {
                    description
                      "Specify a port number to use to communicate with the EnergyWise domain";
                    type uint16 {
                      range "1..65000";
                    }
                  }
                  leaf ip {
                    description
                      "Specify an ipaddress to use to communicate with the EnergyWise domain";
                    type inet:ipv4-address;
                  }
                }
              }
            }
          }
        }
      }
    }
  }

  grouping config-service-template-grouping {
    list service-template {
      description
        "Configure a service-template/identity policy";
      key "word";
      leaf word {
        description
          "Specify a template name (maximum 48 characters)";
        type string {
          length "1..48";
        }
      }
      list access-group-config {
        description
          "Access list to be applied";
        key "name";
        leaf name {
          description
            "Specify the access list name";
          type string;
        }
      }
      leaf access-group {
        status obsolete;
        description
          "Access list to be applied. OBSOLETE, Use access-group-config
           instead";
        type string;
      }
      container inactivity-timer {
        description
          "Inactivity timeout value in seconds";
        leaf value {
          description
            "Enter a value between 1 and 65535";
          type uint16 {
            range "1..65535";
          }
        }
        leaf probe {
          description
            "ARP probe";
          type empty;
        }
      }
      leaf vlan {
        description
          "Vlan to be applied";
        type uint16 {
          range "1..4094";
        }
      }
      container linksec {
        description
          "Configure link security parameters";
        leaf policy {
          description
            "Set the link security policy";
          type enumeration {
            enum must-not-secure;
            enum must-secure;
            enum should-secure;
          }
        }
      }
      leaf mdns-service-policy {
        description
          "mdns policy to be applied";
        type string {
          length "1..164";
        }
      }
      container voice {
        description
          "Voice feature";
        leaf vlan {
          description
            "Critical voice vlan";
          type empty;
        }
      }
      leaf sgt {
        description
          "SGT tag";
        type uint16 {
          range "2..65519";
        }
      }
      leaf absolute-timer {
        description
          "Enter a value between 1 and 1073741823";
        type uint32 {
          range "1..1073741823";
        }
      }
      leaf description {
        description
          "Enter a description";
        type string;
      }
      list interface-template {
        description
          "Interface template to be applied";
        key "name";
        leaf name {
          description
            "Enter name of interface template";
          type string;
        }
      }
      container tunnel {
        description
          "tunnel for wired client access";
        container type {
          description
            "tunnel type";
          container capwap {
            description
              "capwap tunnel type";
            leaf name {
              description
                "tunnel profile name";
              type string;
            }
          }
        }
      }
      leaf vnid {
        description
          "Vnid to be applied";
        type string;
      }
      container redirect {
        description
          "Redirect clients to a particular location";
        container append {
          description
            "Append URL query in redirect URL";
          leaf client-mac {
            description
              "Append client Mac Address in redirect URL";
            type string;
          }
          leaf switch-mac {
            description
              "Append switch Mac Address in redirect URL";
            type string;
          }
        }
        container url {
          description
            "URL where clients should be redirected";
          leaf url_name {
            description
              "Specify a valid URL";
            type string;
          }
          container match {
            description
              "Traffic matching this access list will be redirected";
            leaf acl_name {
              description
                "Specify the access list name";
              type string;
            }
            leaf action {
              type enumeration {
                enum one-time-redirect;
                enum redirect-on-no-match;
              }
            }
          }
        }
      }
      container dns-acl {
        description
          "DNS ACL";
        leaf preauth {
          description
            "pre-authentication";
          type string;
        }
      }
      container service-policy {
        description
          "Configure service policy";
        container qos {
          description
            "Configure Qos policies for client";
          leaf input {
            description
              "Configure input Qos policy";
            type string;
          }
          leaf output {
            description
              "Configure output Qos policy";
            type string;
          }
        }
      }
      list tag-config {
        description
          "tag name";
        key "name";
        leaf name {
          description
            "Specify the Tag name";
          type string;
        }
      }
      leaf tag {
        status obsolete;
        description
          "tag name. OBSOLETE use tag-config instead";
        type string;
      }
    }
  }

  grouping arp-access-list-mac {
    container mac {
      description
        "Sender MAC address";
      list sender-mac-address {
        description
          "Sender MAC address";
        key "mac-address";
        leaf mac-address {
          type string;
        }
        leaf mac-address-mask {
          description
            "Sender MAC address mask";
          type string;
        }
        leaf log {
          description
            "Log on match";
          type empty;
        }
      }
      container any {
        description
          "Any MAC address";
        presence "true";
        leaf log {
          description
            "Log on match";
          type empty;
        }
      }
      container host {
        description
          "Single Sender host";
        list sender-mac-address {
          description
            "Sender MAC address";
          key "mac-address";
          leaf mac-address {
            type string;
          }
          leaf log {
            description
              "Log on match";
            type empty;
          }
        }
      }
    }
  }

  grouping arp-access-list-ip-grouping {
    container ip {
      description
        "Sender IP address";
      list sender-ip-address {
        description
          "Sender IP address";
        key "ip-address";
        leaf ip-address {
          type string;
        }
        leaf ip-address-mask {
          description
            "Sender IP wildcard mask";
          type string;
        }
        uses arp-access-list-mac;
      }
      container any {
        description
          "Any Sender IP address";
        uses arp-access-list-mac;
      }
      container host {
        description
          "Single Sender host";
        list ip-address {
          description
            "Sender IP address";
          key "ip-address";
          leaf ip-address {
            type string;
          }
          uses arp-access-list-mac;
        }
      }
    }
  }

  grouping arp-access-list-request-response-grouping {
    uses arp-access-list-ip-grouping;
    container request {
      description
        "ARP Request";
      uses arp-access-list-ip-grouping;
    }
    container response {
      description
        "ARP Response";
      uses arp-access-list-ip-grouping;
    }
  }

  grouping arp-access-list-config-grouping {
    container permit {
      description
        "Specify packets to forward";
      uses arp-access-list-request-response-grouping;
    }
    container deny {
      description
        "Specify packets to reject";
      uses arp-access-list-request-response-grouping;
    }
  }

  grouping config-arp-access-list-grouping {
    list access-list {
      description
        "Named access-list";
      key "name";
      leaf name {
        type string;
      }
      uses arp-access-list-config-grouping;
      container default {
        description
          "Set a command to its defaults";
        uses arp-access-list-config-grouping;
      }
      container no {
        description
          "Negate a command or set its defaults";
        uses arp-access-list-config-grouping;
      }
    }
  }

  grouping config-ip-igmp-snooping-vlan-grouping {
    container vlan {
      description
        "IGMP Snooping enable for VLAN";
      list range {
        key "range";
        leaf range {
          description
            "Vlan number";
          type uint16 {
            range "1..1001 | 1006..4094";
          }
        }
        leaf immediate-leave {
          description
            "Enable IGMPv2 immediate leave processing";
          type empty;
        }
        leaf last-member-query-count {
          description
            "Interval (milliseconds)";
          type uint8 {
            range "1..7";
          }
        }
        leaf last-member-query-interval {
          description
            "Interval (milliseconds)";
          type uint16 {
            range "100..32767";
          }
        }
        container mrouter {
          description
            "Configure an L2 port as a multicast router port";
          leaf-list interfaces {
            description
              "next-hop interface to mrouter";
            type string;
          }
          leaf interface {
            description
              "GigabitEthernet IEEE 802.3z";
            status deprecated;
            type string;
          }
          container learn {
            description
              "Set the multicast router learning method";
            leaf cgmp {
              description
                "Learn the multicast router snooping CGMP packets";
              type empty;
            }
            leaf pim-dvmrp {
              description
                "Learn the multicast router snooping PIM-DVMRP packets";
              type empty;
            }
          }
        }
        container querier {
          description
            "Enable IGMP querier for this Vlan";
          presence "true";
          leaf address {
            description
              "IGMP querier source IP address";
            type inet:ipv4-address;
          }
          leaf max-response-time {
            description
              "IGMP querier maximum response time (sec)";
            type uint8 {
              range "1..25";
            }
          }
          leaf query-interval {
            description
              "IGMP querier query interval (sec)";
            type uint16 {
              range "1..18000";
            }
          }
          container tcn {
            description
              "IGMP querier TCN related parameters";
            container query {
              description
                "IGMP querier TCN query related parameters";
              leaf count {
                description
                  "IGMP querier TCN query count";
                type uint8 {
                  range "1..10";
                }
              }
              leaf interval {
                description
                  "IGMP querier TCN query interval (sec)";
                type uint8 {
                  range "1..255";
                }
              }
            }
          }
          container timer {
            description
              "IGMP other querier timer";
            leaf expiry {
              description
                "IGMP querier other querier time out (sec)";
              type uint16 {
                range "60..300";
              }
            }
          }
          leaf version {
            description
              "IGMP version";
            type uint8 {
              range "1..2";
            }
          }
        }
        leaf robustness-variable {
          description
            "Robustness variable";
          type uint8 {
            range "1..3";
          }
        }
        container static {
          description
            "Configure an L2 port as a member of a group";
          list ipv4 {
            key "ipv4";
            leaf ipv4 {
              description
                "IP address of the group";
              type inet:ipv4-address;
            }
            leaf interface {
              description
                "GigabitEthernet IEEE 802.3z";
              type string;
            }
          }
        }
      }
    }
  }

  grouping config-ip-igmp-snooping-vlan-grouping-deprecated {
    container vlan {
      status obsolete;
      description
        "IGMP Snooping enable for Catalyst VLAN (OBSOLETE)";
      list range {
        status obsolete;
        key "range";
        leaf range {
          status obsolete;
          description
            "Vlan number (OBSOLETE)";
          type uint16 {
            range "1..1001 | 1006..4094";
          }
        }
        leaf immediate-leave {
          status obsolete;
          description
            "Enable IGMPv2 immediate leave processing (OBSOLETE)";
          type empty;
        }
        leaf last-member-query-count {
          status obsolete;
          description
            "Interval (milliseconds) (OBSOLETE)";
          type uint8 {
            range "1..7";
          }
        }
        leaf last-member-query-interval {
          status obsolete;
          description
            "Interval (milliseconds) (OBSOLETE)";
          type uint16 {
            range "100..32767";
          }
        }
        container mrouter {
          status obsolete;
          description
            "Configure an L2 port as a multicast router port (OBSOLETE)";
          leaf interface {
            status obsolete;
            description
              "GigabitEthernet IEEE 802.3z (OBSOLETE)";
            type string;
          }
          container learn {
            status obsolete;
            description
              "Set the multicast router learning method (OBSOLETE)";
            leaf cgmp {
              status obsolete;
              description
                "Learn the multicast router snooping CGMP packets (OBSOLETE)";
              type empty;
            }
            leaf pim-dvmrp {
              status obsolete;
              description
                "Learn the multicast router snooping PIM-DVMRP packets (OBSOLETE)";
              type empty;
            }
          }
        }
        container querier {
          status obsolete;
          description
            "Enable IGMP querier for this Vlan (OBSOLETE)";
          presence "true";
          leaf address {
            status obsolete;
            description
              "IGMP querier source IP address (OBSOLETE)";
            type inet:ipv4-address;
          }
          leaf max-response-time {
            status obsolete;
            description
              "IGMP querier maximum response time (sec) (OBSOLETE)";
            type uint8 {
              range "1..25";
            }
          }
          leaf query-interval {
            status obsolete;
            description
              "IGMP querier query interval (sec) (OBSOLETE)";
            type uint16 {
              range "1..18000";
            }
          }
          container tcn {
            status obsolete;
            description
              "IGMP querier TCN related parameters (OBSOLETE)";
            container query {
              status obsolete;
              description
                "IGMP querier TCN query related parameters (OBSOLETE)";
              leaf count {
                status obsolete;
                description
                  "IGMP querier TCN query count (OBSOLETE)";
                type uint8 {
                  range "1..10";
                }
              }
              leaf interval {
                status obsolete;
                description
                  "IGMP querier TCN query interval (sec) (OBSOLETE)";
                type uint8 {
                  range "1..255";
                }
              }
            }
          }
          container timer {
            status obsolete;
            description
              "IGMP other querier timer (OBSOLETE)";
            leaf expiry {
              status obsolete;
              description
                "IGMP querier other querier time out (sec) (OBSOLETE)";
              type uint16 {
                range "60..300";
              }
            }
          }
          leaf version {
            status obsolete;
            description
              "IGMP version (OBSOLETE)";
            type uint8 {
              range "1..2";
            }
          }
        }
        leaf robustness-variable {
          status obsolete;
          description
            "Robustness variable (OBSOLETE)";
          type uint8 {
            range "1..3";
          }
        }
        container static {
          status obsolete;
          description
            "Configure an L2 port as a member of a group (OBSOLETE)";
          list ipv4 {
            status obsolete;
            key "ipv4";
            leaf ipv4 {
              status obsolete;
              description
                "IP address of the group (OBSOLETE)";
              type inet:ipv4-address;
            }
            leaf interface {
              status obsolete;
              description
                "GigabitEthernet IEEE 802.3z (OBSOLETE)";
              type string;
            }
          }
        }
      }
    }
  }

  grouping switchport-trunk-allowed-vlan-v2 {
    container vlan-v2 {
      description
        "Set allowed VLANs when interface is in trunking mode";
      container vlan-choices {
        choice vlan-choice {
          default "all-case";
          case vlans-case {
            leaf vlans {
              type string {
                length "1..224" {
                  error-message "Character length exceeds 224";
                }
                pattern '([0-9]+[,-]?)*';
              }
            }
          }
          case none-case {
            leaf none {
              description
                "no VLANs";
              type empty;
            }
          }
          case all-case {
            leaf all {
              description
                "all VLANs";
              type boolean;
              default "true";
            }
          }
        }
      }
      container add-vlans {
        list add {
          key "vlans";
          leaf vlans {
            type string {
              length "1..219" {
                error-message "Character length exceeds 219";
              }
              pattern '([0-9]+[,-]?)*';
            }
          }
        }
      }
      leaf except {
        description
          "all VLANs except the following";
        type string {
          length "1..216" {
            error-message "Character length exceeds 216";
          }
          pattern '([0-9]+[,-]?)*';
        }
      }
      leaf remove {
        description
          "VLAN IDs of disallowed VLANs when this port is in trunking mode";
        type string {
          length "1..216" {
            error-message "Character length exceeds 216";
          }
          pattern '([0-9]+[,-]?)*';
        }
      }
    }
  }

  augment "/ios:native" {
    uses config-network-policy-grouping {
      status obsolete;
    }
    uses config-network-policy-grouping-v2;
  }

  augment "/ios:native/ios:system" {
    uses config-system-grouping;
  }

  augment "/ios:native/ios:interface/ios:FastEthernet/ios:switchport-config/ios:switchport" {
    uses config-interface-switchport-grouping;
  }

  augment "/ios:native/ios:interface/ios:GigabitEthernet/ios:switchport-config/ios:switchport" {
    uses config-interface-switchport-grouping;
  }

  augment "/ios:native/ios:interface/ios:TwoGigabitEthernet/ios:switchport-config/ios:switchport" {
    uses config-interface-switchport-grouping;
  }

  augment "/ios:native/ios:interface/ios:FiveGigabitEthernet/ios:switchport-config/ios:switchport" {
    uses config-interface-switchport-grouping;
  }

  augment "/ios:native/ios:interface/ios:AppGigabitEthernet/ios:switchport-config/ios:switchport" {
    uses config-interface-switchport-grouping;
  }

  augment "/ios:native/ios:interface/ios:TenGigabitEthernet/ios:switchport-config/ios:switchport" {
    uses config-interface-switchport-grouping;
  }

  augment "/ios:native/ios:interface/ios:TwentyFiveGigE/ios:switchport-config/ios:switchport" {
    uses config-interface-switchport-grouping;
  }

  augment "/ios:native/ios:interface/ios:FortyGigabitEthernet/ios:switchport-config/ios:switchport" {
    uses config-interface-switchport-grouping;
  }

  augment "/ios:native/ios:interface/ios:FiftyGigabitEthernet/ios:switchport-config/ios:switchport" {
    uses config-interface-switchport-grouping;
  }

  augment "/ios:native/ios:interface/ios:HundredGigE/ios:switchport-config/ios:switchport" {
    uses config-interface-switchport-grouping;
  }

  augment "/ios:native/ios:interface/ios:TwoHundredGigE/ios:switchport-config/ios:switchport" {
    uses config-interface-switchport-grouping;
  }

  augment "/ios:native/ios:interface/ios:FourHundredGigE/ios:switchport-config/ios:switchport" {
    uses config-interface-switchport-grouping;
  }

  augment "/ios:native/ios:interface/ios:Port-channel/ios:switchport-config/ios:switchport" {
    uses config-interface-switchport-grouping;
  }

  augment "/ios:native/ios:interface/ios:HSR-ring/ios:switchport-config/ios:switchport" {
    uses config-interface-switchport-grouping;
  }

  augment "/ios:native/ios:interface/ios:PRP-channel/ios:switchport-config/ios:switchport" {
    uses config-interface-switchport-grouping;
  }

  augment "/ios:native/ios:interface/ios:Port-channel-subinterface/ios:Port-channel/ios:switchport-config/ios:switchport" {
    uses config-interface-switchport-grouping;
  }

  augment "/ios:native/ios:interface/ios:ucse/ios:switchport-config/ios:switchport" {
    uses config-interface-switchport-grouping;
  }

  augment "/ios:native/ios:interface/ios:Ethernet-Internal/ios:switchport-config/ios:switchport" {
    uses config-interface-switchport-grouping;
  }

  augment "/ios:native/ios:interface/ios:Wlan-GigabitEthernet/ios:switchport-config/ios:switchport" {
    uses config-interface-switchport-grouping;
  }

  augment "/ios:native/ios:interface/ios:FastEthernet/ios:switchport" {
    status obsolete;
    uses config-interface-switchport-grouping-obsoleted-v2;
    uses ios-dt:config-interface-switchport-device-tracking-grouping;
  }

  augment "/ios:native/ios:interface/ios:GigabitEthernet/ios:switchport" {
    status obsolete;
    uses config-interface-switchport-grouping-obsoleted-v2;
    uses ios-dt:config-interface-switchport-device-tracking-grouping;
  }

  augment "/ios:native/ios:interface/ios:TwoGigabitEthernet/ios:switchport" {
    status obsolete;
    uses config-interface-switchport-grouping-obsoleted-v2;
    uses ios-dt:config-interface-switchport-device-tracking-grouping;
  }

  augment "/ios:native/ios:interface/ios:FiveGigabitEthernet/ios:switchport" {
    status obsolete;
    uses config-interface-switchport-grouping-obsoleted-v2;
    uses ios-dt:config-interface-switchport-device-tracking-grouping;
  }

  augment "/ios:native/ios:interface/ios:AppGigabitEthernet/ios:switchport" {
    status obsolete;
    uses config-interface-switchport-grouping-obsoleted-v2;
    uses ios-dt:config-interface-switchport-device-tracking-grouping;
  }

  augment "/ios:native/ios:interface/ios:TenGigabitEthernet/ios:switchport" {
    status obsolete;
    uses config-interface-switchport-grouping-obsoleted-v2;
    uses ios-dt:config-interface-switchport-device-tracking-grouping;
  }

  augment "/ios:native/ios:interface/ios:TwentyFiveGigabitEthernet/ios:switchport" {
    uses config-interface-switchport-grouping-obsolete;
  }

  augment "/ios:native/ios:interface/ios:TwentyFiveGigE/ios:switchport" {
    status obsolete;
    uses config-interface-switchport-grouping-obsoleted-v2;
  }

  augment "/ios:native/ios:interface/ios:FortyGigabitEthernet/ios:switchport" {
    status obsolete;
    uses config-interface-switchport-grouping-obsoleted-v2;
  }

  augment "/ios:native/ios:interface/ios:FiftyGigabitEthernet/ios:switchport" {
    status obsolete;
    uses config-interface-switchport-grouping-obsoleted-v2;
  }

  augment "/ios:native/ios:interface/ios:HundredGigE/ios:switchport" {
    status obsolete;
    uses config-interface-switchport-grouping-obsoleted-v2;
  }

  augment "/ios:native/ios:interface/ios:Port-channel/ios:switchport" {
    status obsolete;
    uses config-interface-switchport-grouping-obsoleted-v2;
    uses ios-dt:config-interface-switchport-device-tracking-grouping;
  }

  augment "/ios:native/ios:interface/ios:Port-channel-subinterface/ios:Port-channel/ios:switchport" {
    status obsolete;
    uses config-interface-switchport-grouping-obsoleted-v2;
  }

  augment "/ios:native/ios:interface/ios:FastEthernet" {
    uses config-interface-switch-grouping;
    uses ios-dt:config-interface-device-tracking-grouping;
  }

  augment "/ios:native/ios:interface/ios:GigabitEthernet" {
    uses config-interface-switch-grouping;
    uses ios-dt:config-interface-device-tracking-grouping;
  }

  augment "/ios:native/ios:interface/ios:TwoGigabitEthernet" {
    uses config-interface-switch-grouping;
    uses ios-dt:config-interface-device-tracking-grouping;
  }

  augment "/ios:native/ios:interface/ios:FiveGigabitEthernet" {
    uses config-interface-switch-grouping;
    uses ios-dt:config-interface-device-tracking-grouping;
  }

  augment "/ios:native/ios:interface/ios:AppGigabitEthernet" {
    uses config-interface-switch-grouping;
    uses ios-dt:config-interface-device-tracking-grouping;
  }

  augment "/ios:native/ios:interface/ios:TenGigabitEthernet" {
    uses config-interface-switch-grouping;
    uses ios-dt:config-interface-device-tracking-grouping;
  }

  augment "/ios:native/ios:interface/ios:TwentyFiveGigabitEthernet" {
    uses config-interface-switch-grouping-obsolete;
  }

  augment "/ios:native/ios:interface/ios:TwentyFiveGigE" {
    uses config-interface-switch-grouping;
    uses ios-dt:config-interface-device-tracking-grouping;
  }

  augment "/ios:native/ios:interface/ios:FortyGigabitEthernet" {
    uses config-interface-switch-grouping;
    uses ios-dt:config-interface-device-tracking-grouping;
  }

  augment "/ios:native/ios:interface/ios:FiftyGigabitEthernet" {
    uses config-interface-switch-grouping;
    uses ios-dt:config-interface-device-tracking-grouping;
  }

  augment "/ios:native/ios:interface/ios:HundredGigE" {
    uses config-interface-switch-grouping;
    uses ios-dt:config-interface-device-tracking-grouping;
  }

  augment "/ios:native/ios:interface/ios:TwoHundredGigE" {
    uses config-interface-switch-grouping;
    uses ios-dt:config-interface-device-tracking-grouping;
  }

  augment "/ios:native/ios:interface/ios:FourHundredGigE" {
    uses config-interface-switch-grouping;
    uses ios-dt:config-interface-device-tracking-grouping;
  }

  augment "/ios:native/ios:interface/ios:Port-channel" {
    uses config-interface-switch-grouping;
    uses ios-dt:config-interface-device-tracking-grouping;
  }

  augment "/ios:native/ios:interface/ios:Port-channel-subinterface/ios:Port-channel" {
    uses config-interface-switch-grouping;
  }

  augment "/ios:native/ios:interface/ios:Vlan" {
    uses config-interface-switch-grouping;
  }

  augment "/ios:native/ios:interface/ios:ucse/ios:switchport" {
    status obsolete;
    uses config-interface-switchport-grouping-obsoleted-v2;
  }

  augment "/ios:native/ios:interface/ios:Ethernet-Internal/ios:switchport" {
    status obsolete;
    uses config-interface-switchport-grouping-obsoleted-v2;
  }

  augment "/ios:native/ios:interface/ios:Wlan-GigabitEthernet/ios:switchport" {
    status obsolete;
    uses config-interface-switchport-grouping-obsoleted-v2;
  }

  augment "/ios:native/ios:macro/ios:auto" {
    uses config-macro-auto-grouping;
  }

  augment "/ios:native/ios:boot/ios:system" {
    uses config-boot-system-grouping;
  }

  augment "/ios:native/ios:boot" {
    uses config-boot-switch-options-grouping;
  }

  augment "/ios:native/ios:module" {
    uses config-module-grouping {
      if-feature "ios-features:module";
    }
  }

  augment "/ios:native/ios:sdm" {
    uses config-sdm-grouping;
  }

  augment "/ios:native/ios:setup" {
    uses config-setup-grouping {
      if-feature "ios-features:setup";
    }
  }

  augment "/ios:native" {
    uses config-energywise-grouping;
  }

  augment "/ios:native" {
    uses config-service-template-grouping;
  }

  augment "/ios:native/ios-arp:arp" {
    uses config-arp-access-list-grouping;
  }

  augment "/ios:native/ios:ip/ios-igmp:igmp/ios-igmp:snooping-entry/ios-igmp:snooping" {
    uses config-ip-igmp-snooping-vlan-grouping;
  }

  augment "/ios:native/ios:ip/ios-igmp:igmp/ios-igmp:snooping" {
    status obsolete;
    uses config-ip-igmp-snooping-vlan-grouping-deprecated;
  }

  augment "/ios:native" {
    uses config-switch-grouping;
    uses config-switch-virtual-grouping {
      status obsolete;
      if-feature "ios-features:switch-virtual";
    }
    uses config-device-grouping;
    uses config-stack-mac-grouping;
    uses config-l2protocol-tunnel-grouping;
    uses config-rep-grouping;
    uses config-hw-switch-grouping;
    uses config-openflow-grouping;
  }
}
