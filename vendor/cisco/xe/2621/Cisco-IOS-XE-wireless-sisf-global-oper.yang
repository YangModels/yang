module Cisco-IOS-XE-wireless-sisf-global-oper {
  yang-version 1.1;
  namespace "http://cisco.com/ns/yang/Cisco-IOS-XE-wireless-sisf-global-oper";
  prefix wireless-sisf-global-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains SISF global operational data aggregated across wireless processes.
     Copyright (c) 2022, 2026 by Cisco Systems, Inc.
     All rights reserved.";

  revision 2026-08-01 {
    description
      "Clarified DHCPv4 statistics leaf descriptions for DECLINE, RELEASE, and INFORM counters.";
    reference
      "1.1.1";
    cisco-semver:module-version "1.1.1";
  }
  revision 2022-11-01 {
    description
      "Update yang-version to 1.1";
    reference
      "1.1.0";
    cisco-semver:module-version "1.1.0";
  }
  revision 2022-07-01 {
    description
      "Initial revision";
    reference
      "1.0.0";
    cisco-semver:module-version "1.0.0";
  }

  grouping sisf-dhcpv4-stats {
    description
      "DHCPv4 statistics for a DHCP server";
    leaf ip-addr {
      type inet:ipv4-address;
      description
        "DHCP server IPv4 address";
    }
    leaf discover-count {
      type uint64;
      description
        "Number of DHCP DISCOVER messages processed";
    }
    leaf bootp-forward-count {
      type uint64;
      description
        "Number of BOOTP requests forwarded to the DHCP server";
    }
    leaf bootp-reply-count {
      type uint64;
      description
        "Number of BOOTP replies received from the DHCP server";
    }
    leaf offer-count {
      type uint64;
      description
        "Number of DHCP OFFER messages processed";
    }
    leaf request-count {
      type uint64;
      description
        "Number of DHCP REQUEST messages processed";
    }
    leaf ack-count {
      type uint64;
      description
        "Number of DHCP ACK messages processed";
    }
    leaf nak-count {
      type uint64;
      description
        "Number of DHCP NAK messages processed";
    }
    leaf decline-count {
      type uint64;
      description
        "Number of DHCP DECLINE messages processed (clients declining offered IP addresses)";
    }
    leaf release-count {
      type uint64;
      description
        "Number of DHCP RELEASE messages processed (clients releasing assigned IP addresses)";
    }
    leaf inform-count {
      type uint64;
      description
        "Number of DHCP INFORM messages processed (clients requesting additional parameters without requesting a new IP address)";
    }
    leaf tx-drop-count {
      type uint64;
      description
        "Number of DHCP packets that failed to transmit to the DHCP server";
    }
    leaf last-rx-time {
      type yang:date-and-time;
      description
        "Time of the most recent packet received from the DHCP server";
    }
    leaf last-tx-time {
      type yang:date-and-time;
      description
        "Time of the most recent packet transmitted to the DHCP server";
    }
    leaf min-disc-offer-latency {
      type uint64;
      units "milliseconds";
      description
        "Minimum DHCP discover-offer latency";
    }
    leaf max-disc-offer-latency {
      type uint64;
      units "milliseconds";
      description
        "Maximum DHCP discover-offer latency";
    }
    leaf min-req-ack-latency {
      type uint64;
      units "milliseconds";
      description
        "Minimum DHCP request-ack latency";
    }
    leaf max-req-ack-latency {
      type uint64;
      units "milliseconds";
      description
        "Maximum DHCP request-ack latency";
    }
    leaf min-disc-ack-latency {
      type uint64;
      units "milliseconds";
      description
        "Minimum DHCP discover-ack latency";
    }
    leaf max-disc-ack-latency {
      type uint64;
      units "milliseconds";
      description
        "Maximum DHCP discover-ack latency";
    }
    leaf avg-disc-offer-latency {
      type uint64;
      units "milliseconds";
      description
        "Average DHCP discover-offer latency";
    }
    leaf avg-req-ack-latency {
      type uint64;
      units "milliseconds";
      description
        "Average DHCP request-ack latency";
    }
    leaf avg-disc-ack-latency {
      type uint64;
      units "milliseconds";
      description
        "Average DHCP discover-ack latency";
    }
    leaf total-disc-offer-latency {
      type uint64;
      units "milliseconds";
      description
        "Cumulative DHCP discover-offer latency";
    }
    leaf total-req-ack-latency {
      type uint64;
      units "milliseconds";
      description
        "Cumulative DHCP request-ack latency";
    }
    leaf total-disc-ack-latency {
      type uint64;
      units "milliseconds";
      description
        "Cumulative DHCP discover-ack latency";
    }
    leaf total-disc-offer-count {
      type uint64;
      description
        "Cumulative DHCP discover-offer count";
    }
    leaf total-req-ack-count {
      type uint64;
      description
        "Cumulative DHCP request-ack count";
    }
    leaf total-disc-ack-count {
      type uint64;
      description
        "Cumulative DHCP discover-ack count";
    }
    leaf total-req-nak-latency {
      type uint64;
      units "milliseconds";
      description
        "Cumulative DHCP request-nak latency";
    }
    leaf total-req-nak-count {
      type uint64;
      description
        "Cumulative DHCP request-nak count";
    }
  }

  container sisf-global-oper-data {
    config false;
    description
      "Root container for SISF global operational data aggregated across wireless processes";
    list sisf-dhcpv4-statistics {
      key "ip-addr";
      description
        "Snapshot of statistics of DHCPv4";
      uses wireless-sisf-global-oper:sisf-dhcpv4-stats;
    }
  }
}
