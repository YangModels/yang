module Cisco-IOS-XE-bfd {
  yang-version 1.1;
  namespace "http://cisco.com/ns/yang/Cisco-IOS-XE-bfd";
  prefix ios-bfd;

  import cisco-semver {
    prefix cisco-semver;
  }
  import Cisco-IOS-XE-types {
    prefix ios-types;
  }
  import ietf-inet-types {
    prefix inet;
  }
  import Cisco-IOS-XE-native {
    prefix ios;
  }
  import Cisco-IOS-XE-features {
    prefix ios-features;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Bidirectional Forwarding Detection (BFD) Yang Model.
     Copyright (c) 2016-2019, 2022-2023 by Cisco Systems, Inc.
     All rights reserved.";

  revision 2026-08-01 {
    description
      "- Added TwoHundredGigE and FourHundredGigE interface support";
    cisco-semver:module-version "4.2.0";
  }
  revision 2025-07-01 {
    description
      "- Added FiftyGigabitEthernet interface support";
    cisco-semver:module-version "4.1.0";
  }
  revision 2024-11-01 {
    description
      "- Obsolete BFD Template grouping interval-singlehop and interval-multihop container deprecated nodes";
    cisco-semver:module-version "4.0.0";
  }
  revision 2024-07-01 {
    description
      "- Added BFD interface configuration support for LISP interface
       - Added annotations for obsolete BFD Interface grouping interval
       - container for Vmanage/NSO mapping of device side bfd template interval config";
    cisco-semver:module-version "3.0.1";
  }
  revision 2024-03-01 {
    description
      "- Updated BFD Template deprecated model tailf annotations
       - obsolete BFD Template Single-Hop and Multi-Hop grouping interval container deprecated nodes
       - obsolete BFD Interface grouping interval container deprecated nodes
       - Added BFD interface configuration support for Loopback interface";
    cisco-semver:module-version "3.0.0";
  }
  revision 2022-11-01 {
    description
      "- Update yang-version to 1.1
       - Added support to Serial interface and Serial subinterface";
    cisco-semver:module-version "2.4.0";
  }
  revision 2022-07-01 {
    description
      "- Added new interval container and deprecated the previous one
       - Deprecated interval-multihop and replaced it with interval-multihop-v2
       - Removed mandatory constraints from min-tx in interval-singlehop-v2 to avoid Yang Sync NSO Compilation failure.
       - Added must statement to min-rx and min-tx.
       - Added changes to display default multiplier in interval-singlehop-v2.";
    cisco-semver:module-version "2.3.0";
  }
  revision 2021-11-01 {
    description
      "- Added enable and local address leaf support for openconfig";
    cisco-semver:module-version "2.2.0";
  }
  revision 2020-07-01 {
    description
      "- Added down-monitoring and threshold leaf";
    cisco-semver:module-version "2.1.0";
  }
  revision 2019-11-01 {
    description
      "- Added status deprecated for choice both-or-tx-rx";
    cisco-semver:module-version "2.0.0";
  }
  revision 2019-07-01 {
    description
      "- Establish semantic version baseline
       - Added leafs for port-channel subinterface
       - Interval containers with presence
       - Change in bfd dampen suppress-time
       - Modelled map command to accept multiple entries
       - Add interface BD-VIF bfd";
    cisco-semver:module-version "1.0.0";
  }
  revision 2019-01-22 {
    description
      "Added leaf for App-hosting Gigabit Ethernet interface";
  }
  revision 2018-10-10 {
    description
      "Added dependency for interface bfd echo";
  }
  revision 2017-11-27 {
    description
      "Added Change 25GE name";
  }
  revision 2017-11-14 {
    description
      "Added 40 and 100GE augmentations";
  }
  revision 2017-09-14 {
    description
      "Modify yang model for new 2gig interface addition";
  }
  revision 2017-08-23 {
    description
      "Modify yang model for interval * command under bfd-template";
  }
  revision 2017-08-16 {
    description
      "This revision has changes for new 5gig and 25gig interfaces addition";
  }
  revision 2017-07-20 {
    description
      "Add interface BDI bfd";
  }
  revision 2017-04-28 {
    description
      "inet:ipv6-prefix changed to ios-types:ipv6-prefix";
  }
  revision 2017-02-07 {
    description
      "Initial revision";
  }

  grouping config-interface-bfd-grouping {
    leaf template {
      description
        "BFD template";
      type string;
    }
    leaf enable {
      description
        "Enable BFD under the interface";
      type boolean;
      default "true";
    }
    leaf local-address {
      type ios-types:ip-address-both;
      description
        "The Source IP address to be used for BFD sessions over this
         interface.";
    }
    container interval-interface {
      description
        "Transmit interval between BFD packets";
      presence "true";
      leaf msecs {
        mandatory true;
        type uint16 {
          range "50..9999";
        }
      }
      leaf min_rx {
        description
          "Minimum receive interval capability";
        mandatory true;
        type uint16 {
          range "50..9999";
        }
      }
      leaf multiplier {
        description
          "Multiplier value used to compute holddown";
        mandatory true;
        type uint8 {
          range "3..50";
        }
      }
    }
    container interval {
      status obsolete;
      description
        "Transmit interval between BFD packets";
      leaf msecs {
        status obsolete;
        type uint16 {
          range "50..9999";
        }
      }
      leaf min_rx {
        status obsolete;
        description
          "Minimum receive interval capability";
        type uint16 {
          range "50..9999";
        }
      }
      leaf multiplier {
        status obsolete;
        description
          "Multiplier value used to compute holddown";
        type uint8 {
          range "3..50";
        }
      }
    }
    leaf echo {
      description
        "Use echo adjunct as bfd detection mechanism";
      when '../interval-interface/multiplier';
      type boolean;
      default "true";
    }
  }

  grouping config-bfd-grouping {
    leaf fast-timers-on-slow-interface {
      description
        "Allow fast timers on slow interfaces";
      type empty;
    }
    leaf l2cos {
      description
        "Value of L2 COS for BFD Pkts over VLAN interfaces";
      type uint8 {
        range "0..6";
      }
    }
    container l3cos {
      description
        "L3 COS value to be used for BFD packets";
      leaf ipv6 {
        description
          "IPV6 L3 COS value";
        type uint8 {
          range "0..7";
        }
      }
    }
    grouping dest-ip {
      leaf dest-ip {
        description
          "Destination IP prefix/len";
        type ios-types:ipv4-address-slash-prefix-len;
      }
    }

    grouping dest-ipv6 {
      leaf dest-ipv6 {
        description
          "Destination IPv6 prefix/len";
        type ios-types:ipv6-prefix;
      }
    }

    grouping src-ip {
      leaf src-ip {
        description
          "Source IP prefix/len";
        type ios-types:ipv4-address-slash-prefix-len;
      }
    }

    grouping src-ipv6 {
      leaf src-ipv6 {
        description
          "Source IPv6 prefix/len";
        type ios-types:ipv6-prefix;
      }
    }

    grouping dst-vrf {
      leaf dst-vrf {
        description
          "Destination VRF instance name";
        type string;
      }
    }

    grouping src-vrf {
      leaf src-vrf {
        description
          "source VRF instance name";
        type string;
      }
    }

    grouping bfd-temp {
      leaf template-name {
        mandatory true;
        description
          "BFD template name";
        type string;
      }
    }

    container map {
      description
        "configure BFD map entry for multi-hop sessions";
      container ipv4-list-with-both-vrf {
        description
          "IPv4 Address Family with vrf";
        list ipv4 {
          description
            "IPv4 Address Family with vrf";
          key "dst-vrf dest-ip src-vrf src-ip";
          uses dst-vrf;
          uses dest-ip;
          uses src-vrf;
          uses src-ip;
          uses bfd-temp;
        }
      }
      container ipv4-list-without-vrf {
        description
          "IPv4 Address Family with out vrf";
        list ipv4 {
          description
            "IPv4 Address Family with vrf";
          key "dest-ip src-ip";
          uses dest-ip;
          uses src-ip;
          uses bfd-temp;
        }
      }
      container ipv4-list-with-src-vrf {
        description
          "IPv4 Address Family with source vrf";
        list ipv4 {
          description
            "IPv4 Address Family with vrf";
          key "dest-ip src-vrf src-ip";
          uses dest-ip;
          uses src-vrf;
          uses src-ip;
          uses bfd-temp;
        }
      }
      container ipv4-list-with-dst-vrf {
        description
          "IPv4 Address Family with destination vrf";
        list ipv4 {
          description
            "IPv4 Address Family with vrf";
          key "dst-vrf dest-ip src-ip";
          uses dst-vrf;
          uses dest-ip;
          uses src-ip;
          uses bfd-temp;
        }
      }
      container ipv6-list-with-both-vrf {
        description
          "IPv6 Address Family with vrf";
        list ipv6 {
          description
            "IPv6 Address Family with vrf";
          key "dst-vrf dest-ipv6 src-vrf src-ipv6";
          uses dst-vrf;
          uses dest-ipv6;
          uses src-vrf;
          uses src-ipv6;
          uses bfd-temp;
        }
      }
      container ipv6-list-without-vrf {
        description
          "IPv6 Address Family with out vrf";
        list ipv6 {
          description
            "IPv6 Address Family with vrf";
          key "dest-ipv6 src-ipv6";
          uses dest-ipv6;
          uses src-ipv6;
          uses bfd-temp;
        }
      }
      container ipv6-list-with-src-vrf {
        description
          "IPv6 Address Family with source vrf";
        list ipv6 {
          description
            "IPv6 Address Family with vrf";
          key "dest-ipv6 src-vrf src-ipv6";
          uses dest-ipv6;
          uses src-vrf;
          uses src-ipv6;
          uses bfd-temp;
        }
      }
      container ipv6-list-with-dst-vrf {
        description
          "IPv6 Address Family with destination vrf";
        list ipv6 {
          description
            "IPv6 Address Family with vrf";
          key "dst-vrf dest-ipv6 src-ipv6";
          uses dst-vrf;
          uses dest-ipv6;
          uses src-ipv6;
          uses bfd-temp;
        }
      }
      container ipv4 {
        status obsolete;
        description
          "IPv4 Address Family";
        container no-vrf {
          status obsolete;
          leaf dest-ip {
            status obsolete;
            type inet:ipv4-prefix;
          }
          leaf src-ip {
            status obsolete;
            type inet:ipv4-prefix;
          }
          leaf template-name {
            status obsolete;
            type string;
          }
        }
        container vrf {
          status obsolete;
          description
            "Destination VRF name";
          list dst-vrf {
            status obsolete;
            key "dst-vrf";
            leaf dst-vrf {
              status obsolete;
              description
                "Destination VRF instance name";
              type string;
            }
            leaf A_PERIOD_B_PERIOD_C_PERIOD_D_SLASH_nn {
              status obsolete;
              description
                "Destination IP prefix/len";
              type empty;
            }
          }
        }
      }
      container ipv6 {
        status obsolete;
        description
          "IPv6 Address Family";
        list dp-ipv6_prefix {
          status obsolete;
          key "dp-ipv6_prefix";
          leaf dp-ipv6_prefix {
            status obsolete;
            description
              "Destination IPv6 prefix/len";
            type ios-types:ipv6-prefix;
          }
          leaf bfd-nm {
            status obsolete;
            description
              "bfd template name";
            type string;
          }
          list src-ipv6_prefix0 {
            status obsolete;
            key "src-ipv6_prefix0";
            leaf src-ipv6_prefix0 {
              status obsolete;
              description
                "Source IPv6 prefix/len";
              type ios-types:ipv6-prefix;
            }
            leaf bfd-name {
              status obsolete;
              description
                "bfd template name";
              type string;
            }
          }
          container vrf {
            status obsolete;
            description
              "Source VRF name";
            list src-vrf {
              status obsolete;
              key "src-vrf";
              leaf src-vrf {
                status obsolete;
                description
                  "Source VRF instance name";
                type string;
              }
              leaf src-ipv6_prefix {
                status obsolete;
                description
                  "Source IPv6 prefix/len";
                type ios-types:ipv6-prefix;
              }
            }
          }
        }
        container vrf {
          status obsolete;
          description
            "Destination VRF name";
          list dst-vrf {
            status obsolete;
            key "dst-vrf";
            leaf dst-vrf {
              status obsolete;
              description
                "Destination VRF instance name";
              type string;
            }
            leaf dst-ipv6_prefix {
              status obsolete;
              description
                "Destination IPv6 prefix/len";
              type ios-types:ipv6-prefix;
            }
          }
        }
      }
    }
    leaf slow-timers {
      description
        "Value in ms to use for slow timers";
      type uint16 {
        range "1000..30000";
      }
    }
    container snmp {
      description
        "Provides snmp related information that are specific to BFD";
      container traps {
        description
          "Provides traps related information";
        leaf more {
          description
            "Provides additional variable bindings along with the traps";
          type empty;
        }
      }
    }
  }

  typedef range-type {
    type union {
      type uint32 {
        range "4..9999";
      }
      type uint32 {
        range "3300..9999000";
      }
    }
  }

  typedef lrange-type {
    type uint32 {
      range "4..9999";
    }
  }

  typedef mrange-type {
    type uint32 {
      range "3300..9999000";
    }
  }

  grouping config-bfd-template-authentication-grouping {
    container authentication {
      description
        "Authentication type";
      choice auth-type {
        case md5 {
          container md5 {
            leaf keychain {
              description
                "keychain name";
              type string;
            }
          }
        }
        case meticulous-md5 {
          container meticulous-md5 {
            description
              "Meticulous Keyed md5";
            leaf keychain {
              description
                "keychain name";
              type string;
            }
          }
        }
        case meticulous-sha-1 {
          container meticulous-sha-1 {
            description
              "Meticulous Keyed sha-1";
            leaf keychain {
              description
                "keychain name";
              type string;
            }
          }
        }
        case sha-1 {
          container sha-1 {
            description
              "Keyed sha-1";
            leaf keychain {
              description
                "keychain name";
              type string;
            }
          }
        }
      }
    }
  }

  grouping config-bfd-template-dampening-grouping {
    container dampening {
      description
        "Enable session dampening";
      presence "true";
      leaf half-time {
        description
          "Half-life time for the penalty";
        type uint8 {
          range "1..30";
        }
      }
      leaf unsuppress-time {
        description
          "Value to unsuppress a session";
        type uint16 {
          range "1..18000";
        }
      }
      leaf suppress-time {
        description
          "Value to start suppressing a session";
        type uint16 {
          range "1..18000";
        }
      }
      leaf max-suppressing-time {
        description
          "Maximum duration to suppress a session";
        type uint16 {
          range "1..420";
        }
      }
      leaf threshold {
        if-feature "ios-features:bfd-dm";
        description
          "Stability threshold to enter dampening in down dampened state(seconds)";
        type uint16 {
          range "60..3600";
        }
      }
      leaf down-monitoring {
        if-feature "ios-features:bfd-dm";
        description
          "down monitoring";
        type empty;
      }
    }
  }

  grouping config-bfd-template-echo-grouping {
    leaf echo {
      description
        "Use echo adjunct as bfd detection mechanism";
      type empty;
    }
  }

  grouping config-bfd-template-grouping {
    list single-hop {
      description
        "Single-hop template";
      key "name";
      leaf name {
        type string;
      }
      container interval-singlehop-v2 {
        description
          "Transmit interval between BFD packets";
        choice units {
          case unit-ms {
            container ms-unit {
              leaf microseconds {
                description
                  "Specify BFD timers in microseconds";
                mandatory true;
                type empty;
              }
              choice interval-types {
                case both {
                  leaf both {
                    description
                      "Minimum transmit and receive interval capability";
                    type mrange-type;
                  }
                }
                case tx-rx {
                  leaf min-tx {
                    description
                      "Minimum transmit interval capability";
                    must '../min-rx';
                    type mrange-type;
                  }
                  leaf min-rx {
                    description
                      "Minimum receive interval capability";
                    must '../min-tx';
                    type mrange-type;
                  }
                }
              }
              leaf multiplier {
                description
                  "Multiplier value used to compute holddown";
                default "3";
                type uint8 {
                  range "3..50";
                }
              }
            }
          }
          case unit-mill {
            container mill-unit {
              choice interval-types {
                case both {
                  leaf both {
                    description
                      "Minimum transmit and receive interval capability";
                    type lrange-type;
                  }
                }
                case tx-rx {
                  leaf min-tx {
                    description
                      "Minimum transmit interval capability";
                    must '../min-rx';
                    type lrange-type;
                  }
                  leaf min-rx {
                    description
                      "Minimum receive interval capability";
                    must '../min-tx';
                    type lrange-type;
                  }
                }
              }
              leaf multiplier {
                description
                  "Multiplier value used to compute holddown";
                default "3";
                type uint8 {
                  range "3..50";
                }
              }
            }
          }
        }
      }
      container interval-singlehop {
        status obsolete;
        description
          "Obsolete: use interval-singlehop-v2 instead";
        presence "true";
        leaf microseconds {
          status obsolete;
          description
            "Specify BFD timers in microseconds";
          type empty;
        }
        leaf min-tx {
          status obsolete;
          description
            "Minimum transmit interval capability";
          mandatory true;
          type range-type;
        }
        leaf min-rx {
          status obsolete;
          description
            "Minimum receive interval capability";
          mandatory true;
          type range-type;
        }
        leaf multiplier {
          status obsolete;
          description
            "Multiplier value used to compute holddown";
          default "3";
          type uint8 {
            range "3..50";
          }
        }
      }
      container interval {
        status obsolete;
        description
          "Obsolete: use interval-singlehop-v2 instead";
        leaf microseconds {
          status obsolete;
          description
            "Specify BFD timers in microseconds";
          type empty;
        }
        choice both-or-tx-rx {
          status obsolete;
          case both {
            status obsolete;
            leaf both {
              status obsolete;
              description
                "Minimum transmit and receive interval capability";
              type range-type;
            }
          }
          case tx-rx {
            status obsolete;
            leaf min-tx {
              status obsolete;
              description
                "Minimum transmit interval capability";
              type range-type;
            }
            leaf min-rx {
              status obsolete;
              description
                "Minimum receive interval capability";
              type range-type;
            }
          }
        }
        leaf multiplier {
          status obsolete;
          description
            "Multiplier value used to compute holddown";
          type uint8 {
            range "3..50";
          }
        }
      }
      uses config-bfd-template-authentication-grouping;
      uses config-bfd-template-dampening-grouping;
      uses config-bfd-template-echo-grouping;
    }
    list multi-hop {
      description
        "Multi-hop template";
      key "name";
      leaf name {
        type string;
      }
      container interval-multihop-v2 {
        description
          "Transmit interval between BFD packets";
        choice units {
          case unit-ms {
            container ms-unit {
              leaf microseconds {
                description
                  "Specify BFD timers in microseconds";
                mandatory true;
                type empty;
              }
              choice interval-types {
                case both {
                  leaf both {
                    description
                      "Minimum transmit and receive interval capability";
                    type mrange-type;
                  }
                }
                case tx-rx {
                  leaf min-tx {
                    description
                      "Minimum transmit interval capability";
                    must '../min-rx';
                    type mrange-type;
                  }
                  leaf min-rx {
                    description
                      "Minimum receive interval capability";
                    must '../min-tx';
                    type mrange-type;
                  }
                }
              }
              leaf multiplier {
                description
                  "Multiplier value used to compute holddown";
                default "3";
                type uint8 {
                  range "3..50";
                }
              }
            }
          }
          case unit-mill {
            container mill-unit {
              choice interval-types {
                case both {
                  leaf both {
                    description
                      "Minimum transmit and receive interval capability";
                    type lrange-type;
                  }
                }
                case tx-rx {
                  leaf min-tx {
                    description
                      "Minimum transmit interval capability";
                    must '../min-rx';
                    type lrange-type;
                  }
                  leaf min-rx {
                    description
                      "Minimum receive interval capability";
                    type lrange-type;
                    must '../min-tx';
                  }
                }
              }
              leaf multiplier {
                description
                  "Multiplier value used to compute holddown";
                default "3";
                type uint8 {
                  range "3..50";
                }
              }
            }
          }
        }
      }
      container interval-multihop {
        status obsolete;
        description
          "Obsolete: use interval-multihop-v2 instead";
        presence "true";
        leaf microseconds {
          status obsolete;
          description
            "Specify BFD timers in microseconds";
          type empty;
        }
        leaf min-tx {
          status obsolete;
          description
            "Minimum transmit interval capability";
          mandatory true;
          type range-type;
        }
        leaf min-rx {
          status obsolete;
          description
            "Minimum receive interval capability";
          mandatory true;
          type range-type;
        }
        leaf multiplier {
          status obsolete;
          description
            "Multiplier value used to compute holddown";
          default "3";
          type uint8 {
            range "3..50";
          }
        }
      }
      container interval {
        status obsolete;
        description
          "Obsolete: use interval-multihop-v2 instead";
        leaf microseconds {
          status obsolete;
          description
            "Specify BFD timers in microseconds";
          type empty;
        }
        choice both-or-tx-rx {
          status obsolete;
          case both {
            status obsolete;
            leaf both {
              status obsolete;
              description
                "Minimum transmit and receive interval capability";
              type range-type;
            }
          }
          case tx-rx {
            status obsolete;
            leaf min-tx {
              status obsolete;
              description
                "Minimum transmit interval capability";
              type range-type;
            }
            leaf min-rx {
              status obsolete;
              description
                "Minimum receive interval capability";
              type range-type;
            }
          }
        }
        leaf multiplier {
          status obsolete;
          description
            "Multiplier value used to compute holddown";
          type uint8 {
            range "3..50";
          }
        }
      }
      uses config-bfd-template-authentication-grouping;
      uses config-bfd-template-dampening-grouping;
      uses config-bfd-template-echo-grouping;
    }
  }

  augment "/ios:native/ios:bfd" {
    uses config-bfd-grouping;
  }

  augment "/ios:native/ios:bfd-template" {
    uses config-bfd-template-grouping;
  }

  augment "/ios:native/ios:interface/ios:FastEthernet/ios:bfd" {
    uses config-interface-bfd-grouping;
  }

  augment "/ios:native/ios:interface/ios:GigabitEthernet/ios:bfd" {
    uses config-interface-bfd-grouping;
  }

  augment "/ios:native/ios:interface/ios:TenGigabitEthernet/ios:bfd" {
    uses config-interface-bfd-grouping;
  }

  augment "/ios:native/ios:interface/ios:TwoGigabitEthernet/ios:bfd" {
    uses config-interface-bfd-grouping;
  }

  augment "/ios:native/ios:interface/ios:FiveGigabitEthernet/ios:bfd" {
    uses config-interface-bfd-grouping;
  }

  augment "/ios:native/ios:interface/ios:AppGigabitEthernet/ios:bfd" {
    uses config-interface-bfd-grouping;
  }

  augment "/ios:native/ios:interface/ios:TwentyFiveGigE/ios:bfd" {
    uses config-interface-bfd-grouping;
  }

  augment "/ios:native/ios:interface/ios:FortyGigabitEthernet/ios:bfd" {
    uses config-interface-bfd-grouping;
  }

  augment "/ios:native/ios:interface/ios:FiftyGigabitEthernet/ios:bfd" {
    uses config-interface-bfd-grouping;
  }

  augment "/ios:native/ios:interface/ios:HundredGigE/ios:bfd" {
    uses config-interface-bfd-grouping;
  }

  augment "/ios:native/ios:interface/ios:TwoHundredGigE/ios:bfd" {
    uses config-interface-bfd-grouping;
  }

  augment "/ios:native/ios:interface/ios:FourHundredGigE/ios:bfd" {
    uses config-interface-bfd-grouping;
  }

  augment "/ios:native/ios:interface/ios:Vlan/ios:bfd" {
    uses config-interface-bfd-grouping;
  }

  augment "/ios:native/ios:interface/ios:Tunnel/ios:bfd" {
    uses config-interface-bfd-grouping;
  }

  augment "/ios:native/ios:interface/ios:Port-channel/ios:bfd" {
    uses config-interface-bfd-grouping;
  }

  augment "/ios:native/ios:interface/ios:Port-channel-subinterface/ios:Port-channel/ios:bfd" {
    uses config-interface-bfd-grouping;
  }

  augment "/ios:native/ios:interface/ios:VirtualPortGroup/ios:bfd" {
    uses config-interface-bfd-grouping;
  }

  augment "/ios:native/ios:interface/ios:BDI/ios:bfd" {
    uses config-interface-bfd-grouping;
  }

  augment "/ios:native/ios:interface/ios:BD-VIF/ios:bfd" {
    uses config-interface-bfd-grouping;
  }

  augment "/ios:native/ios:interface/ios:Serial/ios:bfd" {
    uses config-interface-bfd-grouping;
  }

  augment "/ios:native/ios:interface/ios:Serial-subinterface/ios:Serial/ios:bfd" {
    uses config-interface-bfd-grouping;
  }

  augment "/ios:native/ios:interface/ios:Loopback/ios:bfd" {
    uses config-interface-bfd-grouping;
  }

  augment "/ios:native/ios:interface/ios:LISP/ios:bfd" {
    uses config-interface-bfd-grouping;
  }
}
