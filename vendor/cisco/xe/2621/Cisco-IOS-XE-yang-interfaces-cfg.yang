module Cisco-IOS-XE-yang-interfaces-cfg {
  yang-version 1.1;
  namespace "http://cisco.com/ns/yang/Cisco-IOS-XE-yang-interfaces-cfg";
  prefix yang-interfaces-cfg;

  import Cisco-IOS-XE-dmi-common-types {
    prefix dmi-common-types;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Configuration for YANG model-based interfaces.
     Copyright (c) 2018-2026 by Cisco Systems, Inc.
     All rights reserved.";

  revision 2026-08-01 {
    description
      "- Refined existing leaf descriptions for clarity and consistency
       - Added aes128-gcm@openssh.com to Device Management Interface SSH cipher algorithms
       - Disabled diffie-hellman-group14-sha1 key exchange algorithm in FIPS mode";
    reference
      "3.0.0";
    cisco-semver:module-version "3.0.0";
  }
  revision 2025-07-01 {
    description
      "- Deprecate NETCONF SSH trustpoint nodes
       - Added support for high scale paths configuration";
    reference
      "2.1.0";
    cisco-semver:module-version "2.1.0";
  }
  revision 2025-03-01 {
    description
      "- Add length and pattern constraints on strings.";
    reference
      "2.0.0";
    cisco-semver:module-version "2.0.0";
  }
  revision 2024-11-01 {
    description
      "- Added configuration of a trustpoint to be used for NETCONF SSH transport";
    reference
      "1.7.0";
    cisco-semver:module-version "1.7.0";
  }
  revision 2024-07-01 {
    description
      "- Added features config including atomic config for YANG Interfaces
       - Added config knob to control handling of deprecated Yang model elements
       - Added accounting configuration for YANG interfaces";
    reference
      "1.6.0";
    cisco-semver:module-version "1.6.0";
  }
  revision 2023-03-01 {
    description
      "- Added NETCONF SSH server configuration for YANG Interfaces.";
    reference
      "1.5.0";
    cisco-semver:module-version "1.5.0";
  }
  revision 2022-11-01 {
    description
      "Update yang-version to 1.1";
    reference
      "1.4.0";
    cisco-semver:module-version "1.4.0";
  }
  revision 2022-03-01 {
    description
      "- Added AAA configuration for YANG Interfaces.";
    reference
      "1.3.0";
    cisco-semver:module-version "1.3.0";
  }
  revision 2021-07-01 {
    description
      "- Added netconf SSH local VRF configuration
       - Allow usage of special characters in netconf ACL name";
    reference
      "1.2.0";
    cisco-semver:module-version "1.2.0";
  }
  revision 2019-05-21 {
    description
      "- Add semantic version
       - Add SNMP to NETCONF/YANG configuration";
    reference
      "1.1.0";
    cisco-semver:module-version "1.1.0";
  }
  revision 2018-11-01 {
    description
      "Initial revision";
    reference
      "1.0.0";
    cisco-semver:module-version "1.0.0";
  }

  typedef enm-hs-path-type {
    type enumeration {
      enum hs-path-xpath-inv {
        value 0;
        description
          "Deprecated. Set the XPath value instead";
      }
      enum hs-path-tdl-uri-inv {
        value 1;
        description
          "Deprecated. Set the TDL-URI value instead";
      }
    }
    description
      "Deprecated. Set the XPath or TDL-URI instead";
  }

  typedef enm-hs-path-type-v2 {
    type enumeration {
      enum hs-path-invalid {
        value 0;
        description
          "Default filter type, only for internal use";
      }
      enum hs-path-xpath {
        value 1;
        description
          "XPath filter type to specify a high-scale model path";
      }
      enum hs-path-tdl-uri {
        value 2;
        description
          "TDL-URI filter type to specify a high-scale model path";
      }
    }
    description
      "Type of the high-scale path";
  }

  grouping dmi-ssh-hostkey-algorithms {
    description
      "Host key public key algorithms.";
    leaf rsa-sha2-256 {
      type boolean;
      default "true";
      description
        "Enables or disables RSA-SHA2-256 public key based authentication for the NETCONF SSH server.";
    }
    leaf rsa-sha2-512 {
      type boolean;
      default "true";
      description
        "Enables or disables RSA-SHA2-512 public key based authentication for the NETCONF SSH server.";
    }
    leaf ssh-rsa {
      type boolean;
      default "true";
      description
        "Enables or disables RSA-SHA1 public key based authentication for the NETCONF SSH server.";
    }
  }

  grouping dmi-ssh-cipher-algorithms {
    description
      "Encryption algorithms.";
    leaf aes128-ctr {
      type boolean;
      default "true";
      description
        "Enables or disables the use of AES with 128-bit key in CTR mode as a cipher algorithm for the NETCONF SSH server.";
    }
    leaf aes192-ctr {
      type boolean;
      default "true";
      description
        "Enables or disables the use of AES with 192-bit key in CTR mode as a cipher algorithm for the NETCONF SSH server.";
    }
    leaf aes256-ctr {
      type boolean;
      default "true";
      description
        "Enables or disables the use of AES with 256-bit key in CTR mode as a cipher algorithm for the NETCONF SSH server.";
    }
    leaf aes128-cbc {
      type boolean;
      default "true";
      description
        "Enables or disables the use of AES with 128-bit key in CBC mode as a cipher algorithm for the NETCONF SSH server.";
    }
    leaf aes256-cbc {
      type boolean;
      default "true";
      description
        "Enables or disables the use of AES with 256-bit key in CBC mode as a cipher algorithm for the NETCONF SSH server.";
    }
    leaf aes128-gcm {
      type boolean;
      default "true";
      description
        "Enables or disables the use of AES with 128-bit key in GCM mode defined by OpenSSH as a cipher algorithm for the NETCONF SSH server.";
    }
  }

  grouping dmi-ssh-mac-algorithms {
    description
      "Message authentication code algorithms.";
    leaf hmac-sha2-256 {
      type boolean;
      default "true";
      description
        "Enables or disables the use of the HMAC-SHA2-256 message authentication code algorithm for the NETCONF SSH server.";
    }
    leaf hmac-sha2-512 {
      type boolean;
      default "true";
      description
        "Enables or disables the use of the HMAC-SHA2-512 message authentication code algorithm for the NETCONF SSH server.";
    }
    leaf hmac-sha1 {
      type boolean;
      default "true";
      description
        "Enables or disables the use of the HMAC-SHA1 message authentication code algorithm for the NETCONF SSH server.";
    }
  }

  grouping dmi-ssh-kex-algorithms {
    description
      "Key exchange algorithms.";
    leaf dh-group14-sha1 {
      type boolean;
      default "true";
      description
        "Enables or disables DH-GROUP-14-SHA1 key exchange algorithm for the NETCONF SSH server.";
    }
    leaf dh-group14-sha256 {
      type boolean;
      default "true";
      description
        "Enables or disables DH-GROUP-14-SHA256 key exchange algorithm for the NETCONF SSH server.";
    }
    leaf ecdh-sha2-nistp256 {
      type boolean;
      default "true";
      description
        "Enables or disables Elliptic Curve DH-SHA2-P256 key exchange algorithm for the NETCONF SSH server.";
    }
    leaf ecdh-sha2-nistp384 {
      type boolean;
      default "true";
      description
        "Enables or disables Elliptic Curve DH-SHA2-P384 key exchange algorithm for the NETCONF SSH server.";
    }
    leaf ecdh-sha2-nistp521 {
      type boolean;
      default "true";
      description
        "Enables or disables Elliptic Curve DH-SHA2-P521 key exchange algorithm for the NETCONF SSH server.";
    }
    leaf dh-group16-sha512 {
      type boolean;
      default "true";
      description
        "Enables or disables DH-GROUP-16-SHA512 key exchange algorithm for the NETCONF SSH server.";
    }
  }

  grouping dmi-ssh-server {
    description
      "SSH server algorithm.";
    container kex-alg {
      description
        "Key exchange algorithms for NETCONF SSH server.";
      uses yang-interfaces-cfg:dmi-ssh-kex-algorithms;
    }
    container macs {
      description
        "Message authentication code algorithms for NETCONF SSH server.";
      uses yang-interfaces-cfg:dmi-ssh-mac-algorithms;
    }
    container ciphers {
      description
        "Encryption algorithms for NETCONF SSH server.";
      uses yang-interfaces-cfg:dmi-ssh-cipher-algorithms;
    }
    container hostkey-alg {
      description
        "Host key algorithms for NETCONF SSH server.";
      uses yang-interfaces-cfg:dmi-ssh-hostkey-algorithms;
    }
    leaf tp-name {
      type string {
        length "0..128" {
          error-message "Trustpoint name must be between 0 and 128 characters";
          error-app-tag "must-violation";
        }
        pattern '[!-~]([ -~]*[!-~])?|' {
          error-message "Trustpoint name must use ASCII 32-126 characters and must not contain leading or trailing spaces";
          error-app-tag "pattern-violation";
        }
      }
      default "";
      status deprecated;
      description
        "Specifies the trustpoint used for NETCONF SSH server host key. Deprecated.";
    }
  }

  grouping dmi-authentication {
    description
      "AAA authentication method list for YANG Interfaces.";
    leaf login-method-list {
      type string {
        length "1..128" {
          error-message "AAA authentication method list must be between 1 and 128 characters";
          error-app-tag "must-violation";
        }
        pattern '[!-~]([ -~]*[!-~])?' {
          error-message "AAA authentication method list must use ASCII 32-126 characters and must not contain leading or trailing spaces";
          error-app-tag "pattern-violation";
        }
      }
      default "default";
      description
        "Specifies the name of the AAA authentication method list to be used for YANG interface authentication.";
    }
  }

  grouping dmi-authorization {
    description
      "AAA authorization method list for YANG Interfaces.";
    leaf exec-method-list {
      type string {
        length "1..128" {
          error-message "AAA authorization method list must be between 1 and 128 characters";
          error-app-tag "must-violation";
        }
        pattern '[!-~]([ -~]*[!-~])?' {
          error-message "AAA authorization method list must use ASCII 32-126 characters and must not contain leading or trailing spaces";
          error-app-tag "pattern-violation";
        }
      }
      default "default";
      description
        "Specifies the name of the AAA authorization method list to be used for YANG interface authorization.";
    }
  }

  grouping dmi-accounting {
    description
      "AAA accounting for YANG interfaces";
    leaf enabled {
      type boolean;
      default "true";
      description
        "Flag indicating whether AAA accounting for model interfaces is enabled";
    }
  }

  grouping dmi-aaa {
    description
      "AAA service for YANG Interfaces.";
    container authn {
      description
        "AAA authentication service for YANG Interfaces.";
      uses yang-interfaces-cfg:dmi-authentication;
    }
    container authz {
      description
        "AAA authorization service for YANG Interfaces.";
      uses yang-interfaces-cfg:dmi-authorization;
    }
    container acct {
      description
        "AAA accounting service for YANG Interfaces.";
      uses yang-interfaces-cfg:dmi-accounting;
    }
  }

  grouping dmi-yang-feature {
    description
      "Configuration details for YANG related features";
    leaf atomic-config {
      type boolean;
      default "false";
      description
        "Enables or disables non-service interrupting configuration validation";
    }
  }

  grouping dmi-acl-nbi-type {
    description
      "Configure an access-list for the selected service";
    leaf ipv4-acl-name {
      type string {
        length "1..32";
      }
      description
        "Validate access using an IPv4 access-list";
    }
    leaf ipv6-acl-name {
      type string {
        length "1..32";
      }
      description
        "Validate access using an IPv6 access-list";
    }
  }

  grouping dmi-acl {
    description
      "Service ACLs for YANG Interfaces";
    container netconf-yang-ssh {
      description
        "Configuration for access control to the NETCONF-YANG SSH management service using ACLs.";
      uses yang-interfaces-cfg:dmi-acl-nbi-type;
    }
    container restconf {
      description
        "Configuration for access control to the RESTCONF management service using ACLs.";
      uses yang-interfaces-cfg:dmi-acl-nbi-type;
    }
  }

  grouping dmi-snmp-trap {
    description
      "SNMP trap to NETCONF translation";
    leaf trap-oid {
      type string {
        length "3..200" {
          error-message "SNMP trap OID must be between 3 and 200 characters";
          error-app-tag "must-violation";
        }
        pattern '(([0-1](\.[1-3]?[0-9]))|(2\.(0|([1-9]\d*))))(\.(0|([1-9]\d*)))*';
        pattern '\d*(\.\d*){1,127}';
      }
      description
        "The OID for this trap";
    }
    leaf description {
      type string {
        length "0..128" {
          error-message "SNMP trap description must be between 0 and 128 characters";
          error-app-tag "must-violation";
        }
        pattern '[!-~]([ -~]*[!-~])?|' {
          error-message "SNMP trap description must use ASCII 32-126 characters and must not contain leading or trailing spaces";
          error-app-tag "pattern-violation";
        }
      }
      default "";
      description
        "A description for this trap";
    }
    leaf forward {
      type boolean;
      default "true";
      description
        "Enables or disables forwarding for this trap";
    }
  }

  grouping dmi-general {
    description
      "Configuration applicable to all YANG model-based interfaces";
    leaf snmp-global-forwarding {
      type boolean;
      default "true";
      description
        "Enables or disables forwarding for all SNMP traps";
    }
    list snmp-trap {
      key "trap-oid";
      description
        "List of SNMP traps considered for automatic translation to NETCONF
         notifications";
      uses yang-interfaces-cfg:dmi-snmp-trap;
    }
    leaf snmp-community {
      type string {
        length "1..128" {
          error-message "SNMP community string must be between 1 and 128 characters";
          error-app-tag "must-violation";
        }
        pattern '[!-~]([ -~]*[!-~])?' {
          error-message "SNMP community string must use ASCII 32-126 characters and must not contain leading or trailing spaces";
          error-app-tag "pattern-violation";
        }
      }
      default "private";
      description
        "The community string for communication with the SNMP agent";
    }
    leaf disable-deprecated {
      type boolean;
      description
        "Flag controlling behavior of deprecated model elements.
         When the flag is turned off deprecated model elements are not functional";
    }
  }

  grouping dmi-ssh-local-vrf {
    description
      "Configuration details of NETCONF access on local host in a specific VRF";
    leaf vrf-name {
      type dmi-common-types:enm-local-vrf-name;
      description
        "The name of the given VRF";
    }
    leaf vrf-enable {
      type boolean;
      default "false";
      description
        "Determines whether NETCONF access for local host in a given VRF
         is enabled";
    }
    leaf vrf-port {
      type uint32 {
        range "1 .. 65535";
      }
      default "830";
      description
        "Determines the port number to be open in a given VRF on local host
         for NETCONF access";
    }
  }

  grouping xpath-hs-path {
    description
      "XPath type high-scale path configuration";
    leaf xpath {
      type string {
        length "1..230";
        pattern '[!-~]([ -~]*[!-~])?';
      }
      description
        "XPath value defining the high-scale model data to enable";
    }
  }

  grouping tdl-uri-hs-path {
    description
      "TDL URI type high-scale path configuration";
    leaf tdl-uri {
      type string {
        length "1..230";
        pattern '[!-~]([ -~]*[!-~])?';
      }
      description
        "TDL-URI value defining the high-scale model data to enable";
    }
  }

  grouping dmi-hs-path {
    description
      "High-scale paths configuration for YANG Interfaces";
    leaf index {
      type uint32;
      description
        "Index of the high-scale path";
    }
    leaf type {
      type yang-interfaces-cfg:enm-hs-path-type;
      description
        "Use of this is deprecated";
    }
    leaf hs-path {
      type string {
        length "1..230";
        pattern '[!-~]([ -~]*[!-~])?';
      }
      description
        "Use of this is deprecated. Use hs-xpath or hs-tdl-uri instead";
    }
    choice path-type-choice {
      description
        "Type of the high-scale path chosen";
      case hs-path-xpath {
        description
          "Indicates that xpath type high-scale path is specified";
        container hs-xpath {
          description
            "XPath defining the high-scale model data to enable";
          uses yang-interfaces-cfg:xpath-hs-path;
        }
      }
      case hs-path-tdl-uri {
        description
          "Indicates that TDL-URI type high-scale path is specified";
        container hs-tdl-uri {
          description
            "TDL-URI defining the high-scale model data to enable";
          uses yang-interfaces-cfg:tdl-uri-hs-path;
        }
      }
    }
  }

  container yang-interfaces-cfg-data {
    description
      "Configuration for YANG model-based interfaces";
    container hs-paths {
      description
        "List of high scale model paths";
      list hs-path {
        key "index";
        description
          "Configuration of high-scale model paths";
        uses yang-interfaces-cfg:dmi-hs-path;
      }
    }
    container acl {
      description
        "Optionally configure an access-list to validate access
         to the device";
      uses yang-interfaces-cfg:dmi-acl;
    }
    container aaa {
      presence "aaa";
      description
        "Configuration of AAA service for YANG Interfaces.";
      uses yang-interfaces-cfg:dmi-aaa;
    }
    container ssh-server {
      must "not((../ssh-server/kex-alg/dh-group14-sha256 = 'false') and (../ssh-server/kex-alg/ecdh-sha2-nistp256 = 'false') and (../ssh-server/kex-alg/ecdh-sha2-nistp384 = 'false') and (../ssh-server/kex-alg/ecdh-sha2-nistp521 = 'false') and (../ssh-server/kex-alg/dh-group16-sha512 = 'false'))" {
        error-message "At least one FIPS-compliant key exchange algorithm must be enabled";
        error-app-tag "must-violation";
      }
      must "not((../ssh-server/macs/hmac-sha2-256 = 'false') and (../ssh-server/macs/hmac-sha2-512 = 'false') and (../ssh-server/macs/hmac-sha1 = 'false'))" {
        error-message "At least one MAC algorithm must be enabled";
        error-app-tag "must-violation";
      }
      must "not((../ssh-server/ciphers/aes128-ctr = 'false') and (../ssh-server/ciphers/aes192-ctr = 'false') and (../ssh-server/ciphers/aes256-ctr = 'false') and (../ssh-server/ciphers/aes128-cbc = 'false') and (../ssh-server/ciphers/aes256-cbc = 'false') and (../ssh-server/ciphers/aes128-gcm = 'false'))" {
        error-message "At least one cipher algorithm must be enabled";
        error-app-tag "must-violation";
      }
      must "not((../ssh-server/hostkey-alg/rsa-sha2-256 = 'false') and (../ssh-server/hostkey-alg/rsa-sha2-512 = 'false'))" {
        error-message "Either rsa-sha2-256 or rsa-sha2-512 host key algorithm must be enabled";
        error-app-tag "must-violation";
      }
      presence "ssh-server";
      description
        "Configuration of NETCONF SSH server.";
      uses yang-interfaces-cfg:dmi-ssh-server;
    }
    container general {
      description
        "Configuration applicable to all YANG model-based interfaces";
      uses yang-interfaces-cfg:dmi-general;
    }
    list local-vrf {
      key "vrf-name";
      description
        "Configuration of NETCONF access on local host in a specific VRF";
      uses yang-interfaces-cfg:dmi-ssh-local-vrf;
    }
    container dmi-yang-feature {
      presence "dmi-yang-feature";
      description
        "Configuration details for YANG related features";
      uses yang-interfaces-cfg:dmi-yang-feature;
    }
  }
}
