module Cisco-IOS-XE-rip {
  yang-version 1.1;
  namespace "http://cisco.com/ns/yang/Cisco-IOS-XE-rip";
  prefix ios-rip;

  import cisco-semver {
    prefix cisco-semver;
  }
  import ietf-inet-types {
    prefix inet;
  }
  import Cisco-IOS-XE-types {
    prefix ios-types;
  }
  import Cisco-IOS-XE-native {
    prefix ios;
  }
  import Cisco-IOS-XE-bgp {
    prefix ios-bgp;
  }
  import Cisco-IOS-XE-eigrp {
    prefix ios-eigrp;
  }
  import Cisco-IOS-XE-isis {
    prefix ios-isis;
  }
  import Cisco-IOS-XE-ospf {
    prefix ios-ospf;
  }
  import Cisco-IOS-XE-ospfv3 {
    prefix ios-ospfv3;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Routing Information Protocol (RIP) Yang model.
     Copyright (c) 2016-2017, 2021 by Cisco Systems, Inc.
     All rights reserved.";

  revision 2026-08-01 {
    description
      "- Added TwoHundredGigE and FourHundredGigE interface support";
    cisco-semver:module-version "6.1.0";
  }
  revision 2026-02-01 {
    description
      "- Obsolete nodes: bgp-redistribute";
    cisco-semver:module-version "6.0.0";
  }
  revision 2025-07-01 {
    description
      "- Added FiftyGigabitEthernet interface support";
    cisco-semver:module-version "5.1.0";
  }
  revision 2025-03-01 {
    description
      "Obsolete nodes deprecated on 17.11 and before";
    cisco-semver:module-version "5.0.0";
  }
  revision 2024-03-01 {
    description
      "- Obsolete nodes: prefix-gateway, distance-list, auto-summary";
    cisco-semver:module-version "4.0.0";
  }
  revision 2023-11-01 {
    description
      "Removed must constraint from redistribute ospf process id.
       Update BGP redistribute list deprecating the leafref";
    cisco-semver:module-version "3.2.0";
  }
  revision 2022-11-01 {
    description
      "- Update yang-version to 1.1";
    cisco-semver:module-version "3.1.0";
  }
  revision 2021-11-01 {
    description
      "Added id leaf under distribute-list under af vrf and af unicast.
       Added grouping for distribute list under ospf.
       Enabled RIPng commands for Vlan interfaces.
       Fixed an issue with redistribute isis.
       Added omp-route-tag leaf.
       Fixed redistribute ospf model.
       Added omp-route-tag leaf for RIPng.
       Added support of metric-offset and summary-address for ripng interfaces.
       Updated summary-address from leaf to leaf-list.
       Updated default values for auto-summary-fix leaf.
       Obsolete disable passive-interface in RIPv2 model.
       Changed passive-interface model to block configuration switch between passive-interface default and passive-interface <interface>.
       Corrected the redistribute isis behaviour during deletion.
       isis default level-2 is made to appear by default.
       Restricting redistribute isis creation until router isis is created.
       Added traffic-share model under address-family vrf.
       Added string pattern support for offset-list ID under address-family vrf.
       Update redistribute bgp list.
       Obsolete the isis-area list under the deprecated isis container.
       Deprecating internal container under redistribute ospf";
    cisco-semver:module-version "3.0.0";
  }
  revision 2021-07-01 {
    description
      "Added on-passive leaf under address-family-vrf-grouping.
       Obsolete interface-routing-id, isis-tag, vrf nodes under distribute list.
       Fixed the issue of no auto-summary not getting saved in CDB.
       Added redistribute omp.
       Added redistribute ospfv3.
       Support to configure both gateway and prefix under distribute-list together.
       Fixed issue in deletion of redistribute configuration.";
    cisco-semver:module-version "2.0.0";
  }
  revision 2021-03-01 {
    description
      "Added default value for maximum path node";
    cisco-semver:module-version "1.1.0";
  }
  revision 2019-07-01 {
    description
      "Establish semantic version baseline";
    cisco-semver:module-version "1.0.0";
  }
  revision 2019-01-22 {
    description
      "Added leaf for App-hosting Gigabit Ethernet interface";
  }
  revision 2018-09-20 {
    description
      "Changed to leafref for interface ip rip id from type string";
  }
  revision 2018-06-28 {
    description
      "Added must constraints for deleting vrf";
  }
  revision 2017-11-27 {
    description
      "Added Change 25GE name";
  }
  revision 2017-11-14 {
    description
      "This revision has changes for new 40 and 100GE interface addition";
  }
  revision 2017-09-15 {
    description
      "This revision has changes for new 2gig interface addition";
  }
  revision 2017-08-16 {
    description
      "This revision has changes for new 5gig and 25gig interfaces addition";
  }
  revision 2017-04-12 {
    description
      "Send ipv6 rip vrf-mode enable before address-family in ipv6 router rip";
  }
  revision 2017-02-07 {
    description
      "Initial revision";
  }

  typedef default-access-list-id-type {
    type union {
      type uint32 {
        range "1 .. 199";
      }
      type uint32 {
        range "1300 .. 2699";
      }
    }
  }

  typedef access-list-id-type {
    type union {
      type default-access-list-id-type;
      type string {
        pattern '[a-zA-Z].*';
      }
    }
  }

  typedef default-offset-list-id-type {
    type union {
      type uint32 {
        range "0 .. 99";
      }
      type uint32 {
        range "1300 .. 1999";
      }
    }
  }

  typedef offset-list-id-type {
    type union {
      type default-offset-list-id-type;
      type string {
        pattern '[a-zA-Z].*';
      }
    }
  }

  typedef offset-list-in-out-type {
    type enumeration {
      enum in;
      enum out;
    }
  }

  grouping distribute-list-grouping {
    container distribute-list {
      description
        "Filter networks in routing updates";
      list accesslist {
        key "in-out";
        leaf in-out {
          type ios-types:access-list-in-out-type;
        }
      }
      list accesslist-ifname {
        key "in-out interface";
        leaf in-out {
          type ios-types:access-list-in-out-type;
        }
        leaf interface {
          type string;
        }
        leaf interface-routing-id {
          status obsolete;
          type uint8;
        }
        leaf isis-tag {
          status obsolete;
          type string;
        }
        leaf vrf {
          description
            "VPN Routing/Forwarding Instance";
          status obsolete;
          type string;
        }
      }
      list accesslist-prefix-gateway {
        key "in-out";
        leaf in-out {
          type ios-types:access-list-in-out-type;
        }
        leaf prefix {
          description
            "Filter prefixes in routing updates";
          type string;
        }
        leaf gateway {
          description
            "Filtering incoming updates based on gateway";
          type string;
        }
        leaf prefix-gateway {
          status obsolete;
          type enumeration {
            enum prefix;
            enum gateway;
            enum route-map;
          }
        }
        leaf name {
          status obsolete;
          type string;
        }
      }
      list accesslist-prefix-gateway-ifname {
        key "in-out interface";
        leaf in-out {
          type ios-types:access-list-in-out-type;
        }
        leaf interface {
          type string;
        }
        leaf prefix {
          description
            "Filter prefixes in routing updates";
          type string;
        }
        leaf gateway {
          description
            "Filtering incoming updates based on gateway";
          type string;
        }
        leaf prefix-gateway {
          status obsolete;
          type enumeration {
            enum prefix;
            enum gateway;
            enum route-map;
          }
        }
        leaf name {
          status obsolete;
          type string;
        }
        leaf interface-routing-id {
          status obsolete;
          type uint8;
        }
        leaf isis-tag {
          status obsolete;
          type string;
        }
        leaf vrf {
          description
            "VPN Routing/Forwarding Instance";
          status obsolete;
          type string;
        }
      }
    }
  }

  grouping router-rip-grouping {
    uses address-family-vrf-grouping;
    leaf flash-update-threshold {
      description
        "Specify flash update threshold in second";
      type uint8 {
        range "0 .. 30";
      }
    }
    leaf input-queue {
      description
        "Specify input queue depth";
      type uint16 {
        range "0 .. 1024";
      }
      default "150";
    }
    leaf output-delay {
      description
        "Interpacket delay for RIP updates";
      type uint8 {
        range "8 .. 50";
      }
    }
    container passive-interface {
      description
        "Suppress routing updates on an interface";
      leaf default-all-interfaces {
        description
          "Suppress routing updates on all interfaces";
        must 'not (../interfaces)' {
          error-message "Remove existing passive-interface configuration.";
        }
        type empty;
      }
      leaf-list interfaces {
        description
          "Suppress routing updates on a particular interface";
        must 'not (../default-all-interfaces)' {
          error-message "Remove existing passive-interface configuration.";
        }
        type string;
      }
      choice passive-interface-choice {
        status obsolete;
        leaf default {
          status obsolete;
          description
            "Suppress routing updates on all interfaces (OBSOLETE)";
          type empty;
        }
        leaf-list interface {
          status obsolete;
          type string;
        }
      }
    }
    container disable {
      status obsolete;
      when '../passive-interface/default';
      list passive-interface {
        status obsolete;
        key "interface";
        leaf interface {
          status obsolete;
          type string;
        }
      }
    }
  }

  grouping default-redistribute-grouping {
    container connected {
      presence "Connected";
      description
        "Connected";
      uses rip-metric-route-map-grouping;
    }
    list bgp-redistribute-v2 {
      description
        "Border Gateway Protocol (BGP)";
      key "as-number";
      leaf as-number {
        type ios-types:bgp-as-number-type;
      }
      uses rip-metric-route-map-grouping;
    }
    list bgp-redistribute {
      description
        "OBSOLETE - please use bgp-redistribute-v2";
      status obsolete;
      key "as-number";
      leaf as-number {
        status obsolete;
        type leafref {
          path "/ios:native/ios:router/ios-bgp:bgp/ios-bgp:id";
        }
      }
      uses rip-metric-route-map-grouping-deprecated;
    }
    list bgp {
      description
        "OBSOLETE - please use bgp-redistribute";
      status obsolete;
      key "as-number";
      leaf as-number {
        status obsolete;
        type ios-types:bgp-as-number-type;
      }
      container rip-metric-route-map {
        status obsolete;
        container metric {
          status obsolete;
          description
            "Metric for redistributed routes";
          choice metric-transparent-choice {
            status obsolete;
            leaf metric-value {
              status obsolete;
              description
                "Metric for redistributed routes";
              type uint32 {
                range "0 .. 16";
              }
            }
            leaf transparent {
              description
                "Transparently redistribute metric";
              status obsolete;
              type empty;
            }
          }
        }
        leaf route-map {
          description
            "Route map reference";
          status obsolete;
          type string;
        }
      }
    }
    list eigrp {
      description
        "Enhanced Interior Gateway Routing Protocol (EIGRP)";
      key "as-number";
      leaf as-number {
        type uint16 {
          range "1 .. 65535";
        }
      }
      uses rip-metric-route-map-grouping;
    }
    container isis-no-area {
      description
        "ISO IS-IS";
      presence "true";
      must '/ios:native/ios:router/ios-isis:isis' {
        error-message "Create 'redistribute isis' after 'router isis' and delete is before the deletion of 'router isis'.";
      }
      uses redist-isis-grouping;
    }
    container isis-area-tag {
      description
        "ISO IS-IS area-tag";
      list isis {
        description
          "ISO IS-IS";
        key "area-tag";
        leaf area-tag {
          description
            "ISO IS-IS area-tag";
          must '/ios:native/ios:router/ios-isis:isis-container/ios-isis:isis[ios-isis:area-tag=current()]' {
            error-message "Create 'redistribute isis <area>' after 'router isis <area>' and delete is before the deletion of 'router isis <area>'.";
          }
          type string;
        }
        uses redist-isis-grouping;
      }
    }
    container isis {
      status obsolete;
      presence "ISO IS-IS";
      description
        "ISO IS-IS (OBSOLETE)";
      list isis-area {
        status obsolete;
        key "name";
        leaf name {
          status obsolete;
          type string;
        }
        container rip-isis-redist {
          status obsolete;
          leaf isis-level-routes {
            status obsolete;
            type enumeration {
              enum level-1;
              enum level-2;
              enum level-1-2;
            }
            default "level-2";
          }
          container rip-metric-route-map {
            status obsolete;
            container metric {
              status obsolete;
              description
                "Metric for redistributed routes";
              choice metric-transparent-choice {
                status obsolete;
                leaf metric-value {
                  status obsolete;
                  description
                    "Metric for redistributed routes";
                  type uint32 {
                    range "0 .. 16";
                  }
                }
                leaf transparent {
                  status obsolete;
                  description
                    "Transparently redistribute metric";
                  type empty;
                }
              }
            }
            leaf route-map {
              status obsolete;
              description
                "Route map reference";
              type string;
            }
          }
        }
      }
      container rip-isis-redist {
        status obsolete;
        leaf isis-level-routes {
          status obsolete;
          type enumeration {
            enum level-1;
            enum level-2;
            enum level-1-2;
          }
          default "level-2";
        }
        container rip-metric-route-map {
          status obsolete;
          container metric {
            status obsolete;
            description
              "Metric for redistributed routes (OBSOLETE)";
            choice metric-transparent-choice {
              leaf metric-value {
                status obsolete;
                description
                  "Metric for redistributed routes (OBSOLETE)";
                type uint32 {
                  range "0 .. 16";
                }
              }
              leaf transparent {
                status obsolete;
                description
                  "Transparently redistribute metric (OBSOLETE)";
                type empty;
              }
            }
          }
          leaf route-map {
            status obsolete;
            description
              "Route map reference (OBSOLETE)";
            type string;
          }
        }
      }
    }
    container iso-igrp {
      presence "IGRP for OSI networks";
      description
        "IGRP for OSI networks";
      list isoigrp-list {
        description
          "Border Gateway Protocol (BGP)";
        key "iso-area-tag";
        leaf iso-area-tag {
          type string;
        }
        uses rip-iso-igrp-metric-route-map-grouping;
      }
      uses rip-iso-igrp-metric-route-map-grouping;
    }
    container mobile {
      presence "Mobile routes";
      description
        "Mobile routes";
      uses rip-metric-route-map-grouping;
    }
    container odr {
      presence "On Demand stub Routes";
      description
        "On Demand stub Routes";
      uses rip-metric-route-map-grouping;
    }
    container omp {
      presence "true";
      description
        "Overlay Management Protocol";
      uses rip-metric-route-map-grouping;
    }
    list ospf {
      description
        "Open Shortest Path First (OSPF)";
      key "process-id";
      leaf process-id {
        type uint16 {
          range "1 .. 65535";
        }
      }
      list vrf {
        description
          "VPN Routing/Forwarding Instance";
        key "name";
        leaf name {
          must '/ios:native/ios:vrf/ios:definition[ios:name=current()] or /ios:native/ios:ip/ios:vrf[ios:name=current()]' {
            error-message "VRF must be created 1st, deleted last";
          }
          type string;
        }
        container match {
          description
            "Redistribution of OSPF routes";
          leaf internal-leaf {
            description
              "Redistribute OSPF internal routes";
            type empty;
          }
          container internal {
            status obsolete;
            presence "Redistribute OSPF internal routes";
            description
              "Redistribute OSPF internal routes (OBSOLETE)";
            uses rip-metric-route-map-grouping-obsolete;
          }
          leaf external1 {
            description
              "Redistribute OSPF external routes";
            type ios-types:redist-ospf-external-type;
          }
          leaf external2 {
            description
              "Redistribute OSPF external routes";
            type ios-types:redist-ospf-external-type;
          }
          leaf nssa-external1 {
            description
              "Redistribute OSPF NSSA external routes";
            type ios-types:redist-ospf-external-type;
          }
          leaf nssa-external2 {
            description
              "Redistribute OSPF NSSA external routes";
            type ios-types:redist-ospf-external-type;
          }
          uses rip-metric-route-map-grouping;
        }
        container metric {
          description
            "Metric for redistributed routes";
          choice metric-transparent-choice {
            leaf metric-value {
              description
                "Metric for redistributed routes";
              type uint32 {
                range "0 .. 16";
              }
            }
            leaf transparent {
              description
                "Transparently redistribute metric";
              type empty;
            }
          }
        }
        leaf route-map {
          description
            "Route map reference";
          type string;
        }
      }
      container match {
        description
          "Redistribution of OSPF routes";
        leaf internal-leaf {
          description
            "Redistribute OSPF internal routes";
          type empty;
        }
        container internal {
          status obsolete;
          presence "Redistribute OSPF internal routes";
          description
            "Redistribute OSPF internal routes (OBSOLETE)";
          uses rip-metric-route-map-grouping-obsolete;
        }
        leaf external1 {
          description
            "Redistribute OSPF external routes";
          type ios-types:redist-ospf-external-type;
        }
        leaf external2 {
          description
            "Redistribute OSPF external routes";
          type ios-types:redist-ospf-external-type;
        }
        leaf nssa-external1 {
          description
            "Redistribute OSPF NSSA external routes";
          type ios-types:redist-ospf-external-type;
        }
        leaf nssa-external2 {
          description
            "Redistribute OSPF NSSA external routes";
          type ios-types:redist-ospf-external-type;
        }
        uses rip-metric-route-map-grouping;
        container external {
          status obsolete;
          description
            "Redistribute OSPF external routes";
          presence "Redistribute OSPF external routes";
          leaf external-routes {
            status obsolete;
            type ios-types:redist-ospf-external-type;
          }
          container rip-metric-route-map {
            status obsolete;
            container metric {
              status obsolete;
              description
                "Metric for redistributed routes";
              choice metric-transparent-choice {
                status obsolete;
                leaf metric-value {
                  status obsolete;
                  description
                    "Metric for redistributed routes";
                  type uint32 {
                    range "0 .. 16";
                  }
                }
                leaf transparent {
                  status obsolete;
                  description
                    "Transparently redistribute metric";
                  type empty;
                }
              }
            }
            leaf route-map {
              status obsolete;
              description
                "Route map reference";
              type string;
            }
          }
        }
        container nssa-external {
          status obsolete;
          description
            "Redistribute OSPF NSSA external routes";
          presence "Redistribute OSPF NSSA external routes";
          leaf nssa-external-routes {
            status obsolete;
            type ios-types:redist-ospf-external-type;
          }
          container rip-metric-route-map {
            status obsolete;
            container metric {
              status obsolete;
              description
                "Metric for redistributed routes";
              choice metric-transparent-choice {
                status obsolete;
                leaf metric-value {
                  status obsolete;
                  description
                    "Metric for redistributed routes";
                  type uint32 {
                    range "0 .. 16";
                  }
                }
                leaf transparent {
                  status obsolete;
                  description
                    "Transparently redistribute metric";
                  type empty;
                }
              }
            }
            leaf route-map {
              status obsolete;
              description
                "Route map reference";
              type string;
            }
          }
        }
      }
      container metric {
        description
          "Metric for redistributed routes";
        choice metric-transparent-choice {
          leaf metric-value {
            description
              "Metric for redistributed routes";
            type uint32 {
              range "0 .. 16";
            }
          }
          leaf transparent {
            description
              "Transparently redistribute metric";
            type empty;
          }
        }
      }
      leaf route-map {
        description
          "Route map reference";
        type string;
      }
      container rip-metric-route-map {
        status obsolete;
        container metric {
          status obsolete;
          description
            "Metric for redistributed routes (OBSOLETE)";
          choice metric-transparent-choice {
            status obsolete;
            leaf metric-value {
              status obsolete;
              description
                "Metric for redistributed routes (OBSOLETE)";
              type uint32 {
                range "0 .. 16";
              }
            }
            leaf transparent {
              status obsolete;
              description
                "Transparently redistribute metric (OBSOLETE)";
              type empty;
            }
          }
        }
        leaf route-map {
          status obsolete;
          description
            "Route map reference (OBSOLETE)";
          type string;
        }
      }
    }
    list ospfv3 {
      description
        "OSPFv3";
      key "proc-id";
      leaf proc-id {
        description
          "Process ID";
        type uint16 {
          range "1 .. 65535";
        }
      }
      container match {
        description
          "Redistribution of OSPF routes";
        leaf internal {
          description
            "Redistribute OSPF internal routes";
          type empty;
        }
        leaf external1 {
          description
            "Redistribute OSPF external routes";
          type ios-types:redist-ospf-external-type;
        }
        leaf external2 {
          description
            "Redistribute OSPF external routes";
          type ios-types:redist-ospf-external-type;
        }
        leaf nssa-external1 {
          description
            "Redistribute OSPF NSSA external routes";
          type ios-types:redist-ospf-external-type;
        }
        leaf nssa-external2 {
          description
            "Redistribute OSPF NSSA external routes";
          type ios-types:redist-ospf-external-type;
        }
        container metric {
          description
            "Metric for redistributed routes";
          choice metric-transparent-choice {
            leaf metric-value {
              description
                "Metric for redistributed routes";
              type uint32 {
                range "0 .. 16";
              }
            }
            leaf transparent {
              description
                "Transparently redistribute metric";
              type empty;
            }
          }
        }
        leaf route-map {
          description
            "Route map reference";
          type string;
        }
      }
      container metric {
        description
          "Metric for redistributed routes";
        choice metric-transparent-choice {
          leaf metric-value {
            description
              "Metric for redistributed routes";
            type uint32 {
              range "0 .. 16";
            }
          }
          leaf transparent {
            description
              "Transparently redistribute metric";
            type empty;
          }
        }
      }
      leaf route-map {
        description
          "Route map reference";
        type string;
      }
    }
    container static {
      presence "Static routes";
      description
        "Static routes";
      uses rip-metric-route-map-grouping;
    }
    container rip {
      presence "Routing Information Protocol (RIP)";
      description
        "Routing Information Protocol (RIP)";
      uses rip-metric-route-map-grouping;
    }
  }

  grouping ipv6-router-rip-redistribute-grouping {
    leaf include-connected {
      description
        "Include connected";
      type empty;
    }
    uses ios-bgp:metric-route-map-grouping;
  }

  grouping distance-grouping {
    container distance {
      description
        "Define an administrative distance";
      leaf distance-leaf {
        type uint8 {
          range "1..255";
        }
      }
      list distance-list-config {
        key "ip mask";
        leaf number {
          mandatory true;
          type uint8 {
            range "1 .. 255";
          }
        }
        leaf ip {
          type inet:ipv4-address;
        }
        leaf mask {
          type inet:ipv4-address;
        }
      }
      list distance-list {
        status obsolete;
        key "number ip mask";
        leaf number {
          status obsolete;
          type uint8 {
            range "1 .. 255";
          }
        }
        leaf ip {
          status obsolete;
          type inet:ipv4-address;
        }
        leaf mask {
          status obsolete;
          type inet:ipv4-address;
        }
      }
    }
  }

  grouping offset-list-grouping {
    list offset-list {
      description
        "Add or subtract offset from RIP metrics";
      key "in-out";
      leaf in-out {
        description
          "Perform offset on incoming/outgoing updates";
        type offset-list-in-out-type;
      }
      leaf offset {
        description
          "Offset";
        mandatory true;
        type uint8 {
          range "0 .. 16";
        }
      }
    }
    container offset-list-interface {
      description
        "Add or subtract offset from RIP metrics per interface";
      list offset-list {
        description
          "Add or subtract offset from RIP metrics";
        key "in-out interface";
        leaf id {
          description
            "Access list of networks to apply offset";
          mandatory true;
          type offset-list-id-type;
        }
        leaf in-out {
          description
            "Perform offset on incoming/outgoing updates";
          type offset-list-in-out-type;
        }
        leaf offset {
          description
            "Offset";
          type uint8 {
            range "0..16";
          }
          mandatory true;
        }
        leaf interface {
          description
            "Interface name";
          type string;
        }
      }
    }
  }

  grouping default-router-rip-grouping {
    leaf auto-summary-fix {
      description
        "Enable automatic network number summarization";
      type boolean;
    }
    leaf auto-summary {
      status obsolete;
      description
        "Enable automatic network number summarization";
      type empty;
    }
    leaf maximum-paths {
      description
        "Forward packets over multiple paths";
      type uint8 {
        range "1 .. 32";
      }
      default "4";
    }
    list neighbor {
      description
        "Specify a neighbor router";
      key "ip";
      leaf ip {
        description
          "Neighbor IP address";
        type inet:ipv4-address;
      }
      leaf bfd {
        description
          "Enable BFD for the neighbor";
        type empty;
      }
    }
    list network {
      description
        "Enable routing on an IP network";
      key "ip";
      leaf ip {
        type inet:ipv4-address;
      }
    }
    leaf validate-update-source {
      description
        "Perform sanity checks against source address of routing updates";
      type boolean;
      default "true";
    }
  }

  grouping address-family-vrf-grouping {
    uses default-router-rip-grouping;
    container default-information {
      description
        "Control distribution of default information";
      container originate {
        presence "Distribute a default route";
        description
          "Distribute a default route";
        leaf route-map {
          description
            "Route-map reference";
          type string;
        }
      }
    }
    leaf default-metric {
      description
        "Set metric of redistributed routes";
      type uint32 {
        range "1..4294967295";
      }
    }
    uses distance-grouping;
    uses distribute-list-grouping;
    uses offset-list-grouping;
    leaf omp-route-tag {
      description
        "Enable automatic RIPv2 route tag for OMP routes";
      type boolean;
      default "true";
    }
    container redistribute {
      description
        "Redistribute information from another routing protocol";
      uses rip-metric-route-map-grouping;
      uses default-redistribute-grouping;
    }
    container timers {
      description
        "Adjust routing timers";
      container basic {
        description
          "Basic routing protocol update timers";
        leaf updates {
          description
            "Interval between updates for RIP";
          type uint32 {
            range "1 .. 2147483";
          }
          default "30";
        }
        leaf invalid {
          description
            "Invalid";
          type uint32 {
            range "1 .. 2147483";
          }
          default "180";
        }
        leaf holddown {
          description
            "Holddown";
          type uint32 {
            range "0 .. 2147483";
          }
          default "180";
        }
        leaf flush {
          description
            "Flush";
          type uint32 {
            range "1 .. 2147483";
          }
          default "240";
        }
        leaf sleep {
          description
            "Sleep time, in milliseconds";
          type uint32 {
            range "1 .. 2147483647";
          }
        }
      }
    }
    container traffic-share {
      description
        "How to compute traffic share over alternate paths";
      container min {
        description
          "All traffic shared among min metric paths";
        leaf across-interfaces {
          description
            "Use different interfaces for equal-cost paths";
          type empty;
        }
      }
    }
    leaf version {
      description
        "Set routing protocol version";
      type uint8 {
        range "1 .. 2";
      }
    }
  }

  grouping redist-isis-grouping {
    container rip-isis-redist {
      leaf isis-level-routes {
        type enumeration {
          enum level-1;
          enum level-2;
          enum level-1-2;
        }
        default "level-2";
      }
      uses rip-metric-route-map-grouping;
    }
  }

  grouping rip-metric-route-map-grouping {
    container rip-metric-route-map {
      container metric {
        description
          "Metric for redistributed routes";
        choice metric-transparent-choice {
          leaf metric-value {
            description
              "Metric for redistributed routes";
            type uint32 {
              range "0 .. 16";
            }
          }
          leaf transparent {
            description
              "Transparently redistribute metric";
            type empty;
          }
        }
      }
      leaf route-map {
        description
          "Route map reference";
        type string;
      }
    }
  }

  grouping rip-iso-igrp-metric-route-map-grouping {
    container rip-metric-route-map {
      leaf route-map {
        description
          "Route map reference";
        type string;
      }
      container metric {
        description
          "Metric for redistributed routes";
        choice metric-transparent-choice {
          leaf metric-value {
            description
              "Metric for redistributed routes";
            type uint32 {
              range "0 .. 16";
            }
          }
          leaf transparent {
            description
              "Transparently redistribute metric";
            type empty;
          }
        }
      }
    }
  }

  grouping ipv6-router-rip-grouping {
    leaf distance {
      description
        "Administrative distance";
      type uint8 {
        range "1..254";
      }
    }
    uses ios-eigrp:config-eigrp-distribute-list-classic-ipv6-grouping;
    leaf maximum-paths {
      description
        "Forward packets over multiple paths";
      type uint32 {
        range "1..32";
      }
    }
    leaf omp-route-tag {
      description
        "Enable automatic IPv6 RIP route tag for OMP routes";
      type boolean;
      default "true";
    }
    leaf poison-reverse {
      description
        "Poison reverse updates";
      type empty;
    }
    container redistribute {
      description
        "Redistribute IPv6 prefixes from another routing protocol";
      container application {
        description
          "Application Protocol";
        uses ipv6-router-rip-redistribute-grouping;
      }
      container lisp {
        description
          "Locator ID Separation Protocol (LISP)";
        uses ipv6-router-rip-redistribute-grouping;
      }
      container nd {
        description
          "Neighbor Discovery";
        uses ipv6-router-rip-redistribute-grouping;
      }
      uses default-redistribute-grouping;
    }
    leaf split-horizon {
      description
        "Split horizon updates";
      type empty;
    }
    container timers {
      description
        "Adjust routing timers";
      leaf update {
        description
          "Update period";
        type uint16 {
          range "5..65535";
        }
      }
      leaf timeout {
        description
          "Route timeout period";
        type uint16 {
          range "1..65535";
        }
      }
      leaf holddown {
        description
          "Route holddown period";
        type uint16 {
          range "0..65535";
        }
      }
      leaf garbage-collection {
        description
          "Route garbage collection period";
        type uint16 {
          range "1..65535";
        }
      }
    }
  }

  grouping config-ipv6-router-rip-grouping {
    list rip {
      description
        "IPv6 Routing Information Protocol (RIPv6)";
      key "id";
      leaf id {
        type string;
      }
      container address-family {
        description
          "Enter Address Family command mode";
        container ipv6 {
          description
            "Address family";
          list vrf {
            description
              "Specify parameters for a VPN Routing/Forwarding instance";
            key "name";
            leaf name {
              must '/ios:native/ios:vrf/ios:definition[ios:name=current()] or /ios:native/ios:ip/ios:vrf[ios:name=current()]' {
                error-message "VRF must be created 1st, deleted last";
              }
              type string;
            }
            uses ipv6-router-rip-grouping;
          }
        }
      }
      uses ipv6-router-rip-grouping;
    }
  }

  grouping config-router-rip-grouping {
    container rip {
      presence "true";
      description
        "Routing Information Protocol (RIP)";
      uses router-rip-grouping {
        refine "auto-summary-fix" {
          default "true";
        }
        refine "redistribute/ospf/process-id";
        refine "redistribute/ospfv3/proc-id" {
          must '/ios:native/ios:router/ios-ospfv3:ospfv3[ios-ospfv3:id=current()]/ios-ospfv3:address-family/ios-ospfv3:ipv4/ios-ospfv3:unicast' {
            error-message "Create 'redistribute ospfv3' after 'router ospfv3 address-family' and delete it before the deletion of 'router ospfv3 address-family'.";
          }
        }
      }
      container address-family {
        description
          "Enter Address Family command mode";
        container ipv4 {
          description
            "Address family";
          container unicast {
            status obsolete;
            uses router-rip-grouping-obsolete {
              refine "auto-summary-fix" {
                default "true";
              }
            }
          }
          list vrf {
            description
              "Specify parameters for a VPN Routing/Forwarding instance";
            key "name";
            leaf name {
              must '/ios:native/ios:vrf/ios:definition[ios:name=current()] or /ios:native/ios:ip/ios:vrf[ios:name=current()]' {
                error-message "VRF must be created 1st, deleted last";
              }
              type string;
            }
            uses address-family-vrf-grouping {
              refine "auto-summary-fix" {
                default "false";
              }
              refine "redistribute/ospf/process-id" {
                must '/ios:native/ios:router/ios-ospf:router-ospf/ios-ospf:ospf/ios-ospf:process-id-vrf[ios-ospf:id=current()]' {
                  error-message "Create 'redistribute ospf' after 'router ospf vrf' and delete is before the deletion of 'router ospf vrf'.";
                }
              }
              refine "redistribute/ospfv3/proc-id" {
                must '(/ios:native/ios:router/ios-ospfv3:ospfv3[ios-ospfv3:id=current()]) and (../../../ios-rip:name=/ios:native/ios:router/ios-ospfv3:ospfv3[ios-ospfv3:id=current()]/ios-ospfv3:address-family/ios-ospfv3:ipv4/ios-ospfv3:vrf/ios-ospfv3:vrf)' {
                  error-message "Create 'redistribute ospfv3' after 'router ospfv3 address-family vrf' and delete it before the deletion of 'router ospfv3 address-family vrf'.";
                }
              }
            }
          }
        }
      }
      container default {
        status obsolete;
        description
          "Set a command to its defaults";
        container address-family {
          status obsolete;
          description
            "Enter Address Family command mode";
          container ipv4 {
            status obsolete;
            presence "true";
            description
              "Address family";
            leaf unicast {
              status obsolete;
              description
                "Address Family Modifier";
              type empty;
            }
            list vrf {
              status obsolete;
              description
                "Specify parameters for a VPN Routing/Forwarding instance";
              key "name";
              leaf name {
                status obsolete;
                must '/ios:native/ios:vrf/ios:definition[ios:name=current()] or /ios:native/ios:ip/ios:vrf[ios:name=current()]';
                type string;
              }
            }
          }
        }
        uses default-router-rip-grouping-obsolete;
        container default-information {
          status obsolete;
          description
            "Control distribution of default information";
          leaf originate {
            status obsolete;
            description
              "Distribute a default route";
            type empty;
          }
        }
        leaf default-metric {
          status obsolete;
          description
            "Set metric of redistributed routes";
          type empty;
        }
        uses distance-grouping-obsolete;
        uses distribute-list-grouping-obsolete;
        leaf flash-update-threshold {
          status obsolete;
          description
            "Specify flash update threshold in second";
          type empty;
        }
        leaf input-queue {
          status obsolete;
          description
            "Specify input queue depth";
          type empty;
        }
        uses offset-list-grouping-obsolete;
        leaf output-delay {
          status obsolete;
          description
            "Interpacket delay for RIP updates";
          type empty;
        }
        container passive-interface {
          status obsolete;
          description
            "Suppress routing updates on an interface";
          choice passive-interface-choice {
            status obsolete;
            leaf default {
              status obsolete;
              description
                "Suppress routing updates on all interfaces";
              type empty;
            }
            leaf-list interface {
              status obsolete;
              type string;
            }
          }
        }
        container disable {
          status obsolete;
          when '../passive-interface/default';
          list passive-interface {
            status obsolete;
            key "interface";
            leaf interface {
              status obsolete;
              type string;
            }
          }
        }
        container redistribute {
          status obsolete;
          description
            "Redistribute information from another routing protocol";
          uses default-redistribute-grouping-obsolete;
        }
        container timers {
          status obsolete;
          description
            "Adjust routing timers";
          leaf basic {
            status obsolete;
            description
              "Basic routing protocol update timers";
            type empty;
          }
        }
        container traffic-share {
          status obsolete;
          description
            "How to compute traffic share over alternate paths";
          container min {
            status obsolete;
            description
              "All traffic shared among min metric paths";
            leaf across-interfaces {
              status obsolete;
              description
                "Use different interfaces for equal-cost paths";
              type empty;
            }
          }
        }
        leaf version {
          status obsolete;
          description
            "Set routing protocol version";
          type empty;
        }
      }
    }
  }

  grouping config-interface-ip-rip-grouping {
    list rip {
      description
        "Configure RIP routing protocol";
      key "id";
      leaf id {
        type leafref {
          path "/ios:native/ios:ipv6/ios:router/ios-rip:rip/ios-rip:id";
        }
      }
      leaf enable {
        description
          "Enable/disable RIP routing";
        type empty;
      }
      container default-information {
        description
          "Configure handling of default route";
        leaf route {
          type enumeration {
            enum only;
            enum originate;
          }
        }
        leaf metric {
          description
            "Default route metric";
          type uint8 {
            range "1..15";
          }
        }
      }
      leaf metric-offset {
        description
          "Adjust default metric increment";
        type uint8 {
          range "1..16";
        }
      }
      leaf-list summary-address {
        description
          "Configure address summarization";
        type ios-types:ipv6-prefix;
      }
    }
  }

  grouping config-ipv6-rip-grouping {
    container rip {
      description
        "Configure ipv6 RIP settings";
      leaf vrf-mode {
        description
          "Enable RIPng VRF support";
        type enumeration {
          enum enable;
        }
      }
    }
  }

  grouping default-router-rip-grouping-obsolete {
    leaf auto-summary-fix {
      status obsolete;
      description
        "Enable automatic network number summarization";
      type boolean;
    }
    leaf auto-summary {
      status obsolete;
      description
        "Enable automatic network number summarization";
      type empty;
    }
    leaf maximum-paths {
      status obsolete;
      description
        "Forward packets over multiple paths";
      type uint8 {
        range "1 .. 32";
      }
      default "4";
    }
    list neighbor {
      status obsolete;
      description
        "Specify a neighbor router";
      key "ip";
      leaf ip {
        status obsolete;
        description
          "Neighbor IP address";
        type inet:ipv4-address;
      }
      leaf bfd {
        status obsolete;
        description
          "Enable BFD for the neighbor";
        type empty;
      }
    }
    list network {
      status obsolete;
      description
        "Enable routing on an IP network";
      key "ip";
      leaf ip {
        status obsolete;
        type inet:ipv4-address;
      }
    }
    leaf validate-update-source {
      status obsolete;
      description
        "Perform sanity checks against source address of routing updates";
      type boolean;
      default "true";
    }
  }

  grouping distance-grouping-obsolete {
    container distance {
      status obsolete;
      description
        "Define an administrative distance";
      leaf distance-leaf {
        status obsolete;
        type uint8 {
          range "1..255";
        }
      }
      list distance-list-config {
        status obsolete;
        key "ip mask";
        leaf number {
          status obsolete;
          mandatory true;
          type uint8 {
            range "1 .. 255";
          }
        }
        leaf ip {
          status obsolete;
          type inet:ipv4-address;
        }
        leaf mask {
          status obsolete;
          type inet:ipv4-address;
        }
      }
      list distance-list {
        status obsolete;
        key "number ip mask";
        leaf number {
          status obsolete;
          type uint8 {
            range "1 .. 255";
          }
        }
        leaf ip {
          status obsolete;
          type inet:ipv4-address;
        }
        leaf mask {
          status obsolete;
          type inet:ipv4-address;
        }
      }
    }
  }

  grouping offset-list-grouping-obsolete {
    list offset-list {
      status obsolete;
      description
        "Add or subtract offset from RIP metrics";
      key "in-out";
      leaf in-out {
        status obsolete;
        description
          "Perform offset on incoming/outgoing updates";
        type offset-list-in-out-type;
      }
      leaf offset {
        status obsolete;
        description
          "Offset";
        mandatory true;
        type uint8 {
          range "0 .. 16";
        }
      }
    }
    container offset-list-interface {
      status obsolete;
      description
        "Add or subtract offset from RIP metrics per interface";
      list offset-list {
        status obsolete;
        description
          "Add or subtract offset from RIP metrics";
        key "in-out interface";
        leaf id {
          status obsolete;
          description
            "Access list of networks to apply offset";
          mandatory true;
          type offset-list-id-type;
        }
        leaf in-out {
          status obsolete;
          description
            "Perform offset on incoming/outgoing updates";
          type offset-list-in-out-type;
        }
        leaf offset {
          status obsolete;
          description
            "Offset";
          type uint8 {
            range "0..16";
          }
          mandatory true;
        }
        leaf interface {
          status obsolete;
          description
            "Interface name";
          type string;
        }
      }
    }
  }

  grouping distribute-list-grouping-obsolete {
    container distribute-list {
      status obsolete;
      description
        "Filter networks in routing updates";
      list accesslist {
        status obsolete;
        key "in-out";
        leaf in-out {
          status obsolete;
          type ios-types:access-list-in-out-type;
        }
      }
      list accesslist-ifname {
        status obsolete;
        key "in-out interface";
        leaf in-out {
          status obsolete;
          type ios-types:access-list-in-out-type;
        }
        leaf interface {
          status obsolete;
          type string;
        }
        leaf interface-routing-id {
          status obsolete;
          type uint8;
        }
        leaf isis-tag {
          status obsolete;
          type string;
        }
        leaf vrf {
          description
            "VPN Routing/Forwarding Instance";
          status obsolete;
          type string;
        }
      }
      list accesslist-prefix-gateway {
        status obsolete;
        key "in-out";
        leaf in-out {
          status obsolete;
          type ios-types:access-list-in-out-type;
        }
        leaf prefix {
          status obsolete;
          description
            "Filter prefixes in routing updates";
          type string;
        }
        leaf gateway {
          status obsolete;
          description
            "Filtering incoming updates based on gateway";
          type string;
        }
        leaf prefix-gateway {
          status obsolete;
          type enumeration {
            enum prefix;
            enum gateway;
            enum route-map;
          }
        }
        leaf name {
          status obsolete;
          type string;
        }
      }
      list accesslist-prefix-gateway-ifname {
        status obsolete;
        key "in-out interface";
        leaf in-out {
          status obsolete;
          type ios-types:access-list-in-out-type;
        }
        leaf interface {
          status obsolete;
          type string;
        }
        leaf prefix {
          status obsolete;
          description
            "Filter prefixes in routing updates";
          type string;
        }
        leaf gateway {
          status obsolete;
          description
            "Filtering incoming updates based on gateway";
          type string;
        }
        leaf prefix-gateway {
          status obsolete;
          type enumeration {
            enum prefix;
            enum gateway;
            enum route-map;
          }
        }
        leaf name {
          status obsolete;
          type string;
        }
        leaf interface-routing-id {
          status obsolete;
          type uint8;
        }
        leaf isis-tag {
          status obsolete;
          type string;
        }
        leaf vrf {
          description
            "VPN Routing/Forwarding Instance";
          status obsolete;
          type string;
        }
      }
    }
  }

  grouping default-redistribute-grouping-obsolete {
    container connected {
      status obsolete;
      presence "Connected";
      description
        "Connected";
      uses rip-metric-route-map-grouping-obsolete;
    }
    list bgp {
      status obsolete;
      description
        "Border Gateway Protocol (BGP)";
      key "as-number";
      leaf as-number {
        status obsolete;
        type ios-types:bgp-as-number-type;
      }
      uses rip-metric-route-map-grouping-obsolete;
    }
    list eigrp {
      status obsolete;
      description
        "Enhanced Interior Gateway Routing Protocol (EIGRP)";
      key "as-number";
      leaf as-number {
        status obsolete;
        type uint16 {
          range "1 .. 65535";
        }
      }
      uses rip-metric-route-map-grouping-obsolete;
    }
    container isis-no-area {
      status obsolete;
      description
        "ISO IS-IS";
      presence "true";
      container rip-isis-redist {
        status obsolete;
        leaf isis-level-routes {
          status obsolete;
          type enumeration {
            enum level-1;
            enum level-2;
            enum level-1-2;
          }
          default "level-2";
        }
        uses rip-metric-route-map-grouping-obsolete;
      }
    }
    container isis-area-tag {
      status obsolete;
      description
        "ISO IS-IS area-tag";
      list isis {
        status obsolete;
        description
          "ISO IS-IS";
        key "area-tag";
        leaf area-tag {
          status obsolete;
          description
            "ISO IS-IS area-tag";
          type string;
        }
        container rip-isis-redist {
          status obsolete;
          leaf isis-level-routes {
            status obsolete;
            type enumeration {
              enum level-1;
              enum level-2;
              enum level-1-2;
            }
            default "level-2";
          }
          uses rip-metric-route-map-grouping-obsolete;
        }
      }
    }
    container isis {
      status obsolete;
      presence "ISO IS-IS";
      description
        "ISO IS-IS";
      list isis-area {
        status obsolete;
        key "name";
        leaf name {
          status obsolete;
          type string;
        }
        container rip-isis-redist {
          status obsolete;
          leaf isis-level-routes {
            status obsolete;
            type enumeration {
              enum level-1;
              enum level-2;
              enum level-1-2;
            }
            default "level-2";
          }
          uses rip-metric-route-map-grouping-obsolete;
        }
      }
      container rip-isis-redist {
        status obsolete;
        leaf isis-level-routes {
          status obsolete;
          type enumeration {
            enum level-1;
            enum level-2;
            enum level-1-2;
          }
          default "level-2";
        }
        uses rip-metric-route-map-grouping-obsolete;
      }
    }
    container iso-igrp {
      status obsolete;
      presence "IGRP for OSI networks";
      description
        "IGRP for OSI networks";
      list isoigrp-list {
        status obsolete;
        description
          "Border Gateway Protocol (BGP)";
        key "iso-area-tag";
        leaf iso-area-tag {
          status obsolete;
          type string;
        }
        uses rip-iso-igrp-metric-route-map-grouping-obsolete;
      }
      uses rip-iso-igrp-metric-route-map-grouping-obsolete;
    }
    container mobile {
      status obsolete;
      presence "Mobile routes";
      description
        "Mobile routes";
      uses rip-metric-route-map-grouping-obsolete;
    }
    container odr {
      status obsolete;
      presence "On Demand stub Routes";
      description
        "On Demand stub Routes";
      uses rip-metric-route-map-grouping-obsolete;
    }
    container omp {
      status obsolete;
      presence "true";
      description
        "Overlay Management Protocol";
      uses rip-metric-route-map-grouping-obsolete;
    }
    list ospf {
      status obsolete;
      description
        "Open Shortest Path First (OSPF)";
      key "process-id";
      leaf process-id {
        status obsolete;
        type uint16 {
          range "1 .. 65535";
        }
      }
      list vrf {
        status obsolete;
        description
          "VPN Routing/Forwarding Instance";
        key "name";
        leaf name {
          status obsolete;
          must '/ios:native/ios:vrf/ios:definition[ios:name=current()] or /ios:native/ios:ip/ios:vrf[ios:name=current()]' {
            error-message "VRF must be created 1st, deleted last";
          }
          type string;
        }
        container match {
          status obsolete;
          description
            "Redistribution of OSPF routes";
          container internal {
            status obsolete;
            presence "Redistribute OSPF internal routes";
            description
              "Redistribute OSPF internal routes";
            uses rip-metric-route-map-grouping-obsolete;
          }
          leaf external1 {
            status obsolete;
            description
              "Redistribute OSPF external routes";
            type ios-types:redist-ospf-external-type;
          }
          leaf external2 {
            status obsolete;
            description
              "Redistribute OSPF external routes";
            type ios-types:redist-ospf-external-type;
          }
          leaf nssa-external1 {
            status obsolete;
            description
              "Redistribute OSPF NSSA external routes";
            type ios-types:redist-ospf-external-type;
          }
          leaf nssa-external2 {
            status obsolete;
            description
              "Redistribute OSPF NSSA external routes";
            type ios-types:redist-ospf-external-type;
          }
          uses rip-metric-route-map-grouping-obsolete;
        }
        container metric {
          status obsolete;
          description
            "Metric for redistributed routes";
          choice metric-transparent-choice {
            leaf metric-value {
              status obsolete;
              description
                "Metric for redistributed routes";
              type uint32 {
                range "0 .. 16";
              }
            }
            leaf transparent {
              status obsolete;
              description
                "Transparently redistribute metric";
              type empty;
            }
          }
        }
        leaf route-map {
          status obsolete;
          description
            "Route map reference";
          type string;
        }
      }
      container match {
        status obsolete;
        description
          "Redistribution of OSPF routes";
        container internal {
          status obsolete;
          presence "Redistribute OSPF internal routes";
          description
            "Redistribute OSPF internal routes";
          uses rip-metric-route-map-grouping-obsolete;
        }
        leaf external1 {
          status obsolete;
          description
            "Redistribute OSPF external routes";
          type ios-types:redist-ospf-external-type;
        }
        leaf external2 {
          status obsolete;
          description
            "Redistribute OSPF external routes";
          type ios-types:redist-ospf-external-type;
        }
        leaf nssa-external1 {
          status obsolete;
          description
            "Redistribute OSPF NSSA external routes";
          type ios-types:redist-ospf-external-type;
        }
        leaf nssa-external2 {
          status obsolete;
          description
            "Redistribute OSPF NSSA external routes";
          type ios-types:redist-ospf-external-type;
        }
        uses rip-metric-route-map-grouping-obsolete;
        container external {
          status obsolete;
          description
            "Redistribute OSPF external routes";
          presence "Redistribute OSPF external routes";
          leaf external-routes {
            status obsolete;
            type ios-types:redist-ospf-external-type;
          }
          container rip-metric-route-map {
            status obsolete;
            container metric {
              status obsolete;
              description
                "Metric for redistributed routes";
              choice metric-transparent-choice {
                status obsolete;
                leaf metric-value {
                  status obsolete;
                  description
                    "Metric for redistributed routes";
                  type uint32 {
                    range "0 .. 16";
                  }
                }
                leaf transparent {
                  status obsolete;
                  description
                    "Transparently redistribute metric";
                  type empty;
                }
              }
            }
            leaf route-map {
              status obsolete;
              description
                "Route map reference";
              type string;
            }
          }
        }
        container nssa-external {
          status obsolete;
          description
            "Redistribute OSPF NSSA external routes";
          presence "Redistribute OSPF NSSA external routes";
          leaf nssa-external-routes {
            status obsolete;
            type ios-types:redist-ospf-external-type;
          }
          container rip-metric-route-map {
            status obsolete;
            container metric {
              status obsolete;
              description
                "Metric for redistributed routes";
              choice metric-transparent-choice {
                status obsolete;
                leaf metric-value {
                  status obsolete;
                  description
                    "Metric for redistributed routes";
                  type uint32 {
                    range "0 .. 16";
                  }
                }
                leaf transparent {
                  status obsolete;
                  description
                    "Transparently redistribute metric";
                  type empty;
                }
              }
            }
            leaf route-map {
              status obsolete;
              description
                "Route map reference";
              type string;
            }
          }
        }
      }
      container metric {
        status obsolete;
        description
          "Metric for redistributed routes";
        choice metric-transparent-choice {
          leaf metric-value {
            status obsolete;
            description
              "Metric for redistributed routes";
            type uint32 {
              range "0 .. 16";
            }
          }
          leaf transparent {
            status obsolete;
            description
              "Transparently redistribute metric";
            type empty;
          }
        }
      }
      leaf route-map {
        status obsolete;
        description
          "Route map reference";
        type string;
      }
      container rip-metric-route-map {
        status obsolete;
        container metric {
          status obsolete;
          description
            "Metric for redistributed routes";
          choice metric-transparent-choice {
            status obsolete;
            leaf metric-value {
              status obsolete;
              description
                "Metric for redistributed routes";
              type uint32 {
                range "0 .. 16";
              }
            }
            leaf transparent {
              status obsolete;
              description
                "Transparently redistribute metric";
              type empty;
            }
          }
        }
        leaf route-map {
          status obsolete;
          description
            "Route map reference";
          type string;
        }
      }
    }
    list ospfv3 {
      status obsolete;
      description
        "OSPFv3";
      key "proc-id";
      leaf proc-id {
        status obsolete;
        description
          "Process ID";
        type uint16 {
          range "1 .. 65535";
        }
      }
      container match {
        status obsolete;
        description
          "Redistribution of OSPF routes";
        leaf internal {
          status obsolete;
          description
            "Redistribute OSPF internal routes";
          type empty;
        }
        leaf external1 {
          status obsolete;
          description
            "Redistribute OSPF external routes";
          type ios-types:redist-ospf-external-type;
        }
        leaf external2 {
          status obsolete;
          description
            "Redistribute OSPF external routes";
          type ios-types:redist-ospf-external-type;
        }
        leaf nssa-external1 {
          status obsolete;
          description
            "Redistribute OSPF NSSA external routes";
          type ios-types:redist-ospf-external-type;
        }
        leaf nssa-external2 {
          status obsolete;
          description
            "Redistribute OSPF NSSA external routes";
          type ios-types:redist-ospf-external-type;
        }
        container metric {
          status obsolete;
          description
            "Metric for redistributed routes";
          choice metric-transparent-choice {
            status obsolete;
            leaf metric-value {
              status obsolete;
              description
                "Metric for redistributed routes";
              type uint32 {
                range "0 .. 16";
              }
            }
            leaf transparent {
              status obsolete;
              description
                "Transparently redistribute metric";
              type empty;
            }
          }
        }
        leaf route-map {
          status obsolete;
          description
            "Route map reference";
          type string;
        }
      }
      container metric {
        status obsolete;
        description
          "Metric for redistributed routes";
        choice metric-transparent-choice {
          status obsolete;
          leaf metric-value {
            status obsolete;
            description
              "Metric for redistributed routes";
            type uint32 {
              range "0 .. 16";
            }
          }
          leaf transparent {
            status obsolete;
            description
              "Transparently redistribute metric";
            type empty;
          }
        }
      }
      leaf route-map {
        status obsolete;
        description
          "Route map reference";
        type string;
      }
    }
    container static {
      status obsolete;
      presence "Static routes";
      description
        "Static routes";
      uses rip-metric-route-map-grouping-obsolete;
    }
    container rip {
      status obsolete;
      presence "Routing Information Protocol (RIP)";
      description
        "Routing Information Protocol (RIP)";
      uses rip-metric-route-map-grouping-obsolete;
    }
  }

  grouping rip-metric-route-map-grouping-deprecated {
    container rip-metric-route-map {
      status obsolete;
      container metric {
        status obsolete;
        description
          "Metric for redistributed routes (OBSOLETE)";
        choice metric-transparent-choice {
          status obsolete;
          leaf metric-value {
            status obsolete;
            description
              "Metric for redistributed routes (OBSOLETE)";
            type uint32 {
              range "0 .. 16";
            }
          }
          leaf transparent {
            status obsolete;
            description
              "Transparently redistribute metric (OBSOLETE)";
            type empty;
          }
        }
      }
      leaf route-map {
        status obsolete;
        description
          "Route map reference (OBSOLETE)";
        type string;
      }
    }
  }

  grouping rip-metric-route-map-grouping-obsolete {
    container rip-metric-route-map {
      status obsolete;
      container metric {
        status obsolete;
        description
          "Metric for redistributed routes (OBSOLETE)";
        choice metric-transparent-choice {
          status obsolete;
          leaf metric-value {
            status obsolete;
            description
              "Metric for redistributed routes (OBSOLETE)";
            type uint32 {
              range "0 .. 16";
            }
          }
          leaf transparent {
            status obsolete;
            description
              "Transparently redistribute metric (OBSOLETE)";
            type empty;
          }
        }
      }
      leaf route-map {
        status obsolete;
        description
          "Route map reference (OBSOLETE)";
        type string;
      }
    }
  }

  grouping rip-iso-igrp-metric-route-map-grouping-obsolete {
    container rip-metric-route-map {
      status obsolete;
      leaf route-map {
        status obsolete;
        description
          "Route map reference";
        type string;
      }
      container metric {
        status obsolete;
        description
          "Metric for redistributed routes";
        choice metric-transparent-choice {
          status obsolete;
          leaf metric-value {
            status obsolete;
            description
              "Metric for redistributed routes";
            type uint32 {
              range "0 .. 16";
            }
          }
          leaf transparent {
            status obsolete;
            description
              "Transparently redistribute metric";
            type empty;
          }
        }
      }
    }
  }

  grouping address-family-vrf-grouping-obsolete {
    uses default-router-rip-grouping-obsolete;
    container default-information {
      status obsolete;
      description
        "Control distribution of default information";
      container originate {
        status obsolete;
        presence "Distribute a default route";
        description
          "Distribute a default route";
        leaf route-map {
          status obsolete;
          description
            "Route-map reference";
          type string;
        }
      }
    }
    leaf default-metric {
      status obsolete;
      description
        "Set metric of redistributed routes";
      type uint32 {
        range "1..4294967295";
      }
    }
    uses distance-grouping-obsolete;
    uses distribute-list-grouping-obsolete;
    uses offset-list-grouping-obsolete;
    leaf omp-route-tag {
      status obsolete;
      description
        "Enable automatic RIPv2 route tag for OMP routes";
      type boolean;
      default "true";
    }
    container redistribute {
      status obsolete;
      description
        "Redistribute information from another routing protocol";
      container rip-metric-route-map {
        status obsolete;
        container metric {
          status obsolete;
          description
            "Metric for redistributed routes";
          choice metric-transparent-choice {
            leaf metric-value {
              status obsolete;
              description
                "Metric for redistributed routes";
              type uint32 {
                range "0 .. 16";
              }
            }
            leaf transparent {
              status obsolete;
              description
                "Transparently redistribute metric";
              type empty;
            }
          }
        }
        leaf route-map {
          status obsolete;
          description
            "Route map reference";
          type string;
        }
      }
      uses default-redistribute-grouping-obsolete;
    }
    container timers {
      status obsolete;
      description
        "Adjust routing timers";
      container basic {
        status obsolete;
        description
          "Basic routing protocol update timers";
        leaf updates {
          status obsolete;
          description
            "Interval between updates for RIP";
          type uint32 {
            range "1 .. 2147483";
          }
          default "30";
        }
        leaf invalid {
          status obsolete;
          description
            "Invalid";
          type uint32 {
            range "1 .. 2147483";
          }
          default "180";
        }
        leaf holddown {
          status obsolete;
          description
            "Holddown";
          type uint32 {
            range "0 .. 2147483";
          }
          default "180";
        }
        leaf flush {
          status obsolete;
          description
            "Flush";
          type uint32 {
            range "1 .. 2147483";
          }
          default "240";
        }
        leaf sleep {
          status obsolete;
          description
            "Sleep time, in milliseconds";
          type uint32 {
            range "1 .. 2147483647";
          }
        }
      }
    }
    leaf version {
      status obsolete;
      description
        "Set routing protocol version";
      type uint8 {
        range "1 .. 2";
      }
    }
  }

  grouping router-rip-grouping-obsolete {
    uses address-family-vrf-grouping-obsolete;
    leaf flash-update-threshold {
      status obsolete;
      description
        "Specify flash update threshold in second";
      type uint8 {
        range "0 .. 30";
      }
    }
    leaf input-queue {
      status obsolete;
      description
        "Specify input queue depth";
      type uint16 {
        range "0 .. 1024";
      }
      default "150";
    }
    leaf output-delay {
      status obsolete;
      description
        "Interpacket delay for RIP updates";
      type uint8 {
        range "8 .. 50";
      }
    }
    container passive-interface {
      status obsolete;
      description
        "Suppress routing updates on an interface";
      choice passive-interface-choice {
        status obsolete;
        leaf default {
          status obsolete;
          description
            "Suppress routing updates on all interfaces";
          type empty;
        }
        leaf-list interface {
          status obsolete;
          type string;
        }
      }
    }
    container disable {
      status obsolete;
      when '../passive-interface/default';
      list passive-interface {
        status obsolete;
        key "interface";
        leaf interface {
          status obsolete;
          type string;
        }
      }
    }
    container traffic-share {
      status obsolete;
      description
        "How to compute traffic share over alternate paths";
      container min {
        status obsolete;
        description
          "All traffic shared among min metric paths";
        leaf across-interfaces {
          status obsolete;
          description
            "Use different interfaces for equal-cost paths";
          type empty;
        }
      }
    }
  }

  augment "/ios:native/ios:router" {
    uses config-router-rip-grouping;
  }

  augment "/ios:native/ios:ipv6" {
    uses config-ipv6-rip-grouping;
  }

  augment "/ios:native/ios:ipv6/ios:router" {
    uses config-ipv6-router-rip-grouping;
  }

  augment "/ios:native/ios:router/ios-rip:rip/default/distribute-list/accesslist" {
    leaf id {
      status obsolete;
      mandatory true;
      type default-access-list-id-type;
    }
  }

  augment "/ios:native/ios:router/ios-rip:rip/distribute-list/accesslist" {
    leaf id {
      mandatory true;
      type access-list-id-type;
    }
  }

  augment "/ios:native/ios:router/ios-rip:rip/default/distribute-list/accesslist-ifname" {
    leaf id {
      status obsolete;
      mandatory true;
      type default-access-list-id-type;
    }
  }

  augment "/ios:native/ios:router/ios-rip:rip/distribute-list/accesslist-ifname" {
    leaf id {
      mandatory true;
      type access-list-id-type;
    }
  }

  augment "/ios:native/ios:router/ios-rip:rip/ios-rip:address-family/ios-rip:ipv4/ios-rip:vrf/ios-rip:distribute-list/ios-rip:accesslist" {
    leaf id {
      mandatory true;
      type access-list-id-type;
    }
  }

  augment "/ios:native/ios:router/ios-rip:rip/ios-rip:address-family/ios-rip:ipv4/ios-rip:vrf/ios-rip:distribute-list/ios-rip:accesslist-ifname" {
    leaf id {
      mandatory true;
      type access-list-id-type;
    }
  }

  augment "/ios:native/ios:router/ios-rip:rip/ios-rip:address-family/ios-rip:ipv4/ios-rip:unicast/ios-rip:distribute-list/ios-rip:accesslist" {
    leaf id {
      status obsolete;
      mandatory true;
      type access-list-id-type;
    }
  }

  augment "/ios:native/ios:router/ios-rip:rip/ios-rip:address-family/ios-rip:ipv4/ios-rip:unicast/ios-rip:distribute-list/ios-rip:accesslist-ifname" {
    leaf id {
      status obsolete;
      mandatory true;
      type access-list-id-type;
    }
  }

  augment "/ios:native/ios:router/ios-rip:rip/default/distance/distance-list" {
    leaf access-list {
      status obsolete;
      type ios-types:default-access-list-standard-id-type;
    }
  }

  augment "/ios:native/ios:router/ios-rip:rip/distance/distance-list" {
    leaf access-list {
      status obsolete;
      type ios-types:access-list-standard-id-type;
    }
  }

  augment "/ios:native/ios:router/ios-rip:rip/distance/distance-list-config" {
    leaf access-list {
      type ios-types:access-list-standard-id-type;
    }
  }

  augment "/ios:native/ios:router/ios-rip:rip/ios-rip:address-family/ios-rip:ipv4/ios-rip:vrf/distance/distance-list-config" {
    leaf access-list {
      type ios-types:access-list-standard-id-type;
    }
  }

  augment "/ios:native/ios:router/ios-rip:rip/default/offset-list" {
    leaf id {
      status obsolete;
      mandatory true;
      type default-offset-list-id-type;
    }
  }

  augment "/ios:native/ios:router/ios-rip:rip/offset-list" {
    leaf id {
      description
        "Access list of networks to apply offset";
      mandatory true;
      type offset-list-id-type;
    }
  }

  augment "/ios:native/ios:router/ios-rip:rip/ios-rip:address-family/ios-rip:ipv4/ios-rip:vrf/ios-rip:offset-list" {
    leaf id {
      mandatory true;
      type offset-list-id-type;
    }
  }

  augment "/ios:native/ios:router/ios-rip:rip/ios-rip:address-family/ios-rip:ipv4/ios-rip:unicast/ios-rip:offset-list" {
    leaf id {
      status obsolete;
      description
        "Access list of networks to apply offset";
      mandatory true;
      type offset-list-id-type;
    }
  }

  augment "/ios:native/ios:router/ios-rip:rip/ios-rip:default-information/ios-rip:originate" {
    leaf on-passive {
      description
        "Send default only on Passive interface (RIP)";
      type empty;
    }
  }

  augment "/ios:native/ios:interface/ios:FastEthernet/ios:ipv6" {
    uses config-interface-ip-rip-grouping;
  }

  augment "/ios:native/ios:interface/ios:GigabitEthernet/ios:ipv6" {
    uses config-interface-ip-rip-grouping;
  }

  augment "/ios:native/ios:interface/ios:TenGigabitEthernet/ios:ipv6" {
    uses config-interface-ip-rip-grouping;
  }

  augment "/ios:native/ios:interface/ios:FiveGigabitEthernet/ios:ipv6" {
    uses config-interface-ip-rip-grouping;
  }

  augment "/ios:native/ios:interface/ios:AppGigabitEthernet/ios:ipv6" {
    uses config-interface-ip-rip-grouping;
  }

  augment "/ios:native/ios:interface/ios:TwentyFiveGigE/ios:ipv6" {
    uses config-interface-ip-rip-grouping;
  }

  augment "/ios:native/ios:interface/ios:FortyGigabitEthernet/ios:ipv6" {
    uses config-interface-ip-rip-grouping;
  }

  augment "/ios:native/ios:interface/ios:FiftyGigabitEthernet/ios:ipv6" {
    uses config-interface-ip-rip-grouping;
  }

  augment "/ios:native/ios:interface/ios:HundredGigE/ios:ipv6" {
    uses config-interface-ip-rip-grouping;
  }

  augment "/ios:native/ios:interface/ios:TwoHundredGigE/ios:ipv6" {
    uses config-interface-ip-rip-grouping;
  }

  augment "/ios:native/ios:interface/ios:FourHundredGigE/ios:ipv6" {
    uses config-interface-ip-rip-grouping;
  }

  augment "/ios:native/ios:interface/ios:TwoGigabitEthernet/ios:ipv6" {
    uses config-interface-ip-rip-grouping;
  }

  augment "/ios:native/ios:interface/ios:Port-channel/ios:ipv6" {
    uses config-interface-ip-rip-grouping;
  }

  augment "/ios:native/ios:interface/ios:Vlan/ios:ipv6" {
    uses config-interface-ip-rip-grouping;
  }

  augment "/ios:native/ios:interface/ios:Loopback/ios:ipv6" {
    uses config-interface-ip-rip-grouping;
  }

  augment "/ios:native/ios:interface/ios:Tunnel/ios:ipv6" {
    uses config-interface-ip-rip-grouping;
  }
}
