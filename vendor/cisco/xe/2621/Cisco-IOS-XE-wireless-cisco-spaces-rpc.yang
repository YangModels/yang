module Cisco-IOS-XE-wireless-cisco-spaces-rpc {
  yang-version 1.1;
  namespace "http://cisco.com/ns/yang/Cisco-IOS-XE-wireless-cisco-spaces-rpc";
  prefix wireless-cisco-spaces-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This model contains a collection of YANG definitions for wireless cisco spaces features.
     Copyright (c) 2025 by Cisco Systems, Inc.
     All rights reserved.";

  revision 2026-02-01 {
    description
      "Initial revision";
    reference
      "1.0.0";
    cisco-semver:module-version "1.0.0";
  }

  grouping ewlc-spaces-install-app {
    description
      "Parameter for installing an application from Spaces";
    leaf app-name {
      type string {
        length "1..255";
        pattern '[0-9a-zA-Z\-_]*';
      }
      mandatory true;
      description
        "Application name";
    }
  }

  rpc ewlc-spaces-install-app {
    description
      "Install an application from Spaces";
    input {
      uses wireless-cisco-spaces-rpc:ewlc-spaces-install-app;
    }
  }

  rpc iot-app-cfg-params-gen {
    description
      "Start generating configuration parameters for IoT Orchestrator";
  }

  rpc iot-app-cfg-params-set {
    description
      "Set generated configuration parameters and apply the NAT configuration for IoT Orchestrator";
  }
}
