module Cisco-IOS-XE-mlppp-oper {
  yang-version 1.1;
  namespace "http://cisco.com/ns/yang/Cisco-IOS-XE-mlppp-oper";
  prefix mlppp-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for mlppp operational data.
     Copyright (c) 2017-2019, 2026 by Cisco Systems, Inc.
     All rights reserved.";

  revision 2026-08-01 {
    description
      "Updated descriptions of several model elements to clarify their meaning and purpose";
    reference
      "1.3.1";
    cisco-semver:module-version "1.3.1";
  }
  revision 2022-11-01 {
    description
      "Update yang-version to 1.1";
    reference
      "1.3.0";
    cisco-semver:module-version "1.3.0";
  }
  revision 2019-05-01 {
    description
      "Added semantic version";
    reference
      "1.2.0";
    cisco-semver:module-version "1.2.0";
  }
  revision 2018-10-29 {
    description
      "Cleaned up spelling errors in descriptions.";
    reference
      "1.1.0";
    cisco-semver:module-version "1.1.0";
  }
  revision 2018-01-01 {
    description
      "Initial revision";
    reference
      "1.0.0";
    cisco-semver:module-version "1.0.0";
  }

  typedef mlppp-bundle-mode-type {
    type enumeration {
      enum mlppp-bundle-none {
        value 0;
        description
          "Default None";
      }
      enum mlppp-bundle-distributed {
        value 1;
        description
          "Distributed";
      }
      enum mlppp-bundle-interleaved {
        value 2;
        description
          "Interleaved";
      }
    }
    description
      "MLPPP bundle traffic is Distributed or Interleaved.";
  }

  typedef mlppp-member-type {
    type enumeration {
      enum mlppp-member-none {
        value 0;
        description
          "Default None";
      }
      enum mlppp-member-active {
        value 1;
        description
          "Active";
      }
      enum mlppp-member-inactive {
        value 2;
        description
          "Inactive";
      }
    }
    description
      "Authentication type for the PPP session";
  }

  grouping mlppp-link-interface-up-time {
    description
      "MLPPP bundle for the interface";
    leaf if-name {
      type string;
      description
        "Interface name";
    }
    leaf up-time {
      type yang:date-and-time;
      description
        "Timestamp of when the MLPPP member link interface came up.";
    }
    leaf member-type {
      type mlppp-ios-xe-oper:mlppp-member-type;
      description
        "Indicates whether the member link interface is active or inactive in the MLPPP bundle.";
    }
  }

  grouping mlppp-data {
    description
      "mlppp data";
    leaf if-name {
      type string;
      description
        "Interface name";
    }
    leaf bundle-name {
      type string;
      description
        "Bundle name";
    }
    leaf bundle-mode {
      type mlppp-ios-xe-oper:mlppp-bundle-mode-type;
      description
        "Indicates how a MLPPP bundle distributes traffic across its member links.";
    }
    leaf remote-username {
      type string;
      description
        "Remote user name ";
    }
    leaf local-username {
      type string;
      description
        "Local user name ";
    }
    leaf remote-endpoint-discriminator {
      type string;
      description
        "Remote end point discriminator";
    }
    leaf local-endpoint-discriminator {
      type string;
      description
        "Local end point discriminator";
    }
    leaf bundle-uptime {
      type yang:date-and-time;
      description
        "Bundle uptime duration";
    }
    leaf total-bandwidth {
      type uint32;
      description
        "Total bandwidth in bytes";
    }
    leaf load {
      type string;
      description
        "Specifies the current traffic load of the Multilink PPP bundle,
         expressed in fraction x/255 where x can be 1-255 (1/255 is idle, 255/255 is fully loaded).";
    }
    leaf receive-buffer-limit {
      type uint32;
      description
        "Receive buffer limit in bytes";
    }
    leaf frag-timeout {
      type uint32;
      description
        "Frag timeout in milliseconds";
    }
    leaf fragment-per-byte-in-reassembly-list {
      type string;
      description
        "Specifies the current count of fragments and their total byte size in the MLPPP reassembly queue, formatted as '<fragments>/<bytes>'.";
    }
    leaf lost-fragments {
      type uint32;
      description
        "Specifies the number of MLPPP fragments that were expected but never arrived at the receiving end.";
    }
    leaf reordered {
      type uint32;
      description
        "Specifies the number of MLPPP fragments that arrived out of sequence and had to be reordered before reassembly.";
    }
    leaf discarded-fragments-per-byte {
      type string;
      description
        "Specifies the cumulative count of MLPPP fragments and their total bytes that were discarded during reassembly, formatted as '<fragments>/<bytes>'.";
    }
    leaf lost-received {
      type uint32;
      description
        "Specifies the number of MLPPP packets (or fragments) that were detected as lost after later-sequenced data was received.";
    }
    leaf member-links {
      type uint32;
      description
        "Specifies the current number of member links in the MLPPP bundle.";
    }
    leaf member-link-max {
      type uint32;
      description
        "Specifies the maximum number of member links allowed for the MLPPP bundle.";
    }
    leaf member-link-min {
      type uint32;
      description
        "Specifies the minimum number of member links required for the MLPPP bundle.";
    }
    leaf member-type {
      type mlppp-ios-xe-oper:mlppp-member-type;
      description
        "Indicates whether the MLPPP bundle member is currently active or inactive.";
    }
    list interface-up-time {
      max-elements 10;
      description
        "List of MLPPP member interface up time";
      uses mlppp-ios-xe-oper:mlppp-link-interface-up-time;
    }
  }

  grouping mlppp-statistics {
    description
      "MLPPP statistics type definition";
    leaf mlppp-link-at-lcp-stage {
      type uint32;
      description
        "MLPPP link at lcp stage";
    }
    leaf mlppp-link-at-unauth-name-stage {
      type uint32;
      description
        "MLPPP links at unauthenticated name stage";
    }
    leaf mlppp-link-at-auth-name-stage {
      type uint32;
      description
        "MLPPP links at authenticated name stage";
    }
    leaf mlppp-link-at-post-lcp-noauth-stage {
      type uint32;
      description
        "MLPPP links at post-lcp no auth stage";
    }
    leaf mlppp-link-at-post-lcp-callback-stage {
      type uint32;
      description
        "MLPPP links at post-lcp callback stage";
    }
    leaf mlppp-link-at-forwarded-stage {
      type uint32;
      description
        "MLPPP links at forwarded stage";
    }
    leaf mlppp-link-at-local-termination-stage {
      type uint32;
      description
        "MLPPP links at local termination stage";
    }
    leaf non-mlppp-sessions {
      type uint32;
      description
        "Specifies the number of PPP sessions that are not using Multilink PPP.";
    }
    leaf mlppp-sessions {
      type uint32;
      description
        "Specifies the number of PPP sessions that are using Multilink PPP.";
    }
    leaf non-mlppp-links {
      type uint32;
      description
        "Specifies the number of physical PPP links that are not part of any Multilink PPP bundle.";
    }
    leaf mlppp-links {
      type uint32;
      description
        "Specifies the number of physical PPP links that are currently participating in Multilink PPP bundles.";
    }
    leaf mlppp-authorization-failed {
      type uint32;
      description
        "Specifies the number of MLPPP bundle join attempts that failed authorization.";
    }
    leaf removing-mlppp-bundle {
      type uint32;
      description
        "Removing mlppp bundle";
    }
    leaf mlppp-requires-authen-or-caller-id {
      type uint32;
      description
        "MLPPP requires authentication or caller ID";
    }
    leaf mlppp-drop-link {
      type uint32;
      description
        "The number of MLPPP (Multilink PPP) links that have been dropped due to errors or administrative actions.";
    }
    leaf mlppp-kill-link {
      type uint32;
      description
        "The number of MLPPP (Multilink PPP) links that have been forcefully terminated.";
    }
    leaf mlppp-add-link-failed {
      type uint32;
      description
        "MLPPP add link failed";
    }
    leaf mlppp-link-not-needed {
      type uint32;
      description
        "MLPPP link not needed";
    }
  }

  container mlppp-oper-data {
    config false;
    description
      "MLPPP operational data";
    container mlppp-statistics {
      presence "mlppp-statistics";
      description
        "MLPPP statistics";
      uses mlppp-ios-xe-oper:mlppp-statistics;
    }
    list mlppp-bundle {
      key "if-name";
      description
        "MLPPP data entry table";
      uses mlppp-ios-xe-oper:mlppp-data;
    }
  }
}
