module Cisco-IOS-XE-line-oper {
  yang-version 1.1;
  namespace "http://cisco.com/ns/yang/Cisco-IOS-XE-line-oper";
  prefix line-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for monitoring
     operational data of IOS terminal lines.
     Copyright (c) 2024, 2026 by Cisco Systems, Inc.
     All rights reserved.";

  revision 2026-08-01 {
    description
      "Updated the descriptions of several model elements to clarify their meaning and purpose.";
    reference
      "1.0.1";
    cisco-semver:module-version "1.0.1";
  }
  revision 2024-11-01 {
    description
      "Initial revision";
    reference
      "1.0.0";
    cisco-semver:module-version "1.0.0";
  }

  typedef e-line-type {
    type enumeration {
      enum line-type-bad {
        value 0;
        description
          "Unknown or invalid terminal line type.";
      }
      enum line-type-cty {
        value 1;
        description
          "Console terminal line.";
      }
      enum line-type-tty {
        value 2;
        description
          "Normal asynchronous TTY terminal line.";
      }
      enum line-type-vty {
        value 3;
        description
          "Virtual terminal line.";
      }
      enum line-type-str {
        value 4;
        description
          "String pointer terminal line.";
      }
      enum line-type-aux {
        value 5;
        description
          "AUX (auxiliary) terminal line.";
      }
    }
    description
      "Terminal line type.";
  }

  typedef e-line-state {
    type enumeration {
      enum line-state-in-use {
        value 0;
        description
          "Terminal line is already in use (busy).";
      }
      enum line-state-free {
        value 1;
        description
          "Terminal line is free.";
      }
    }
    description
      "Terminal line running state (e.g., in-use, free).";
  }

  grouping line-data-entry {
    description
      "Operational data entry for each terminal line.";
    leaf number {
      type uint32;
      description
        "Unique identifier number for the terminal line.";
    }
    leaf name {
      type string;
      description
        "Name assigned to the terminal line.";
    }
    leaf type {
      type line-ios-xe-oper:e-line-type;
      description
        "Type of the terminal line.";
    }
    leaf tx-speed {
      type uint32;
      units "bps";
      description
        "Transmit (TX) speed of the terminal line, in bits per second (bps).";
    }
    leaf rx-speed {
      type uint32;
      units "bps";
      description
        "Receive (RX) speed of the terminal line, in bits per second (bps).";
    }
    leaf state {
      type line-ios-xe-oper:e-line-state;
      description
        "Current terminal line running state (e.g., in use, free).";
    }
    leaf desc {
      type string;
      description
        "User-provided description for the terminal line.";
    }
  }

  container line-oper-data {
    config false;
    description
      "Top-level container for terminal line operational data.";
    list line-data {
      key "number";
      description
        "List of operational data entries for each terminal line.";
      uses line-ios-xe-oper:line-data-entry;
    }
  }
}
