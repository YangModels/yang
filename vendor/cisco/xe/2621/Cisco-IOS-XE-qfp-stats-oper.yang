module Cisco-IOS-XE-qfp-stats-oper {
  yang-version 1.1;
  namespace "http://cisco.com/ns/yang/Cisco-IOS-XE-qfp-stats-oper";
  prefix qfp-stats-ios-xe-oper;

  import Cisco-IOS-XE-common-types {
    prefix common-types-ios-xe;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for QFP statistics operational data.
     Copyright (c) 2019-2020, 2022, 2024-2026 by Cisco Systems, Inc.
     All rights reserved.";

  revision 2026-08-01 {
    description
      "- Update the counter descriptions.";
    reference
      "2.3.0";
    cisco-semver:module-version "2.3.0";
  }
  revision 2025-07-01 {
    description
      "- Added new drop cause for various features.
       - Add new drop cause queue in transition drops.";
    reference
      "2.2.0";
    cisco-semver:module-version "2.2.0";
  }
  revision 2022-11-01 {
    description
      "Update yang-version to 1.1";
    reference
      "2.1.0";
    cisco-semver:module-version "2.1.0";
  }
  revision 2020-07-01 {
    description
      "Use extended location";
    reference
      "2.0.0";
    cisco-semver:module-version "2.0.0";
  }
  revision 2020-03-01 {
    description
      "Initial revision";
    reference
      "1.0.0";
    cisco-semver:module-version "1.0.0";
  }

  grouping datapath-qfp-stats {
    description
      "Datapath QFP stats";
    leaf discontinuity-time {
      type yang:date-and-time;
      description
        "The time on the most recent occasion at which these
         counters have suffered a discontinuity. If no such discontinuities
         have occurred since the last re-initialization of the local
         management subsystem, then this is the set to unix time start.";
    }
    leaf uidb-not-cfgd-pkts {
      type uint64;
      description
        "Number of packets dropped by the datapath due to an unconfigured interface.";
    }
    leaf uidb-not-cfgd-octets {
      type uint64;
      units "octets";
      description
        "Total octets in packets dropped by the datapath due to an unconfigured interface.";
    }
    leaf bad-uidb-idx-pkts {
      type uint64;
      description
        "Number of packets dropped by the datapath due to invalid or unrecognized UIDB index.";
    }
    leaf bad-uidb-idx-octets {
      type uint64;
      units "octets";
      description
        "Total octets in packets dropped by the datapath due to invalid or unrecognized UIDB index.";
    }
    leaf bad-uidb-sub-idx-pkts {
      type uint64;
      description
        "Number of packets dropped by the datapath due to invalid or unrecognized UIDB sub-index.";
    }
    leaf bad-uidb-sub-idx-octets {
      type uint64;
      units "octets";
      description
        "Total octets in packets dropped by the datapath due to invalid or unrecognized UIDB sub-index.";
    }
    leaf unknown-encap-pkts {
      type uint64;
      description
        "Number of packets dropped by the datapath due to unknown encapsulation.";
    }
    leaf unknown-encap-octets {
      type uint64;
      units "octets";
      description
        "Total octets in packets dropped by the datapath due to unknown encapsulation.";
    }
    leaf inv-l2-hdr-pkts {
      type uint64;
      description
        "Number of packets dropped due to invalid input layer 2 headers in the datapath.";
    }
    leaf inv-l2-hdr-octets {
      type uint64;
      units "octets";
      description
        "Total octets in packets dropped due to invalid input layer 2 headers in the datapath.";
    }
    leaf bad-len-pkts {
      type uint64;
      description
        "Number of packets dropped due to invalid L2 packet length in the datapath.";
    }
    leaf bad-len-octets {
      type uint64;
      units "octets";
      description
        "Total octets in packets dropped due to invalid L2 packet length in the datapath.";
    }
    leaf tcp-badfrag-pkts {
      type uint64;
      description
        "Number of TCP packets dropped due to bad fragments.";
    }
    leaf tcp-badfrag-octets {
      type uint64;
      units "octets";
      description
        "Total octets in TCP packets dropped due to bad fragments.";
    }
    leaf ipv4-acl-pkts {
      type uint64;
      description
        "Number of packets dropped due to IPv4 access control list (ACL).";
    }
    leaf ipv4-acl-octets {
      type uint64;
      units "octets";
      description
        "Total octets in packets dropped due to IPv4 access control list (ACL).";
    }
    leaf ipv4-acl-lookup-miss-pkts {
      type uint64;
      description
        "Number of packets dropped due to IPv4 access control list (ACL) lookup miss.";
    }
    leaf ipv4-acl-lookup-miss-octets {
      type uint64;
      units "octets";
      description
        "Total octets in packets dropped due to IPv4 access control list (ACL) lookup miss.";
    }
    leaf bad-ip-checksum-pkts {
      type uint64;
      description
        "Number of packets dropped due to bad IP checksum.";
    }
    leaf bad-ip-checksum-octets {
      type uint64;
      units "octets";
      description
        "Total octets in packets dropped due to bad IP checksum.";
    }
    leaf ip-format-err-pkts {
      type uint64;
      description
        "Number of packets dropped due to IP format error.";
    }
    leaf ip-format-err-octets {
      type uint64;
      units "octets";
      description
        "Total octets in packets that were dropped due to IP format errors.";
    }
    leaf ip-bad-options-pkts {
      type uint64;
      description
        "Number of IP packets containing invalid or malformed options that were dropped by the QFP.";
    }
    leaf ip-bad-options-octets {
      type uint64;
      units "octets";
      description
        "Total octets in IP packets with invalid or malformed options dropped by the QFP.";
    }
    leaf ipv4-martian-pkts {
      type uint64;
      description
        "Number of IPv4 packets dropped due to invalid or reserved source or destination addresses (martian addresses).";
    }
    leaf ipv4-martian-octets {
      type uint64;
      units "octets";
      description
        "Total octets in IPv4 packets with invalid or reserved source or destination addresses (martian addresses) dropped by the QFP.";
    }
    leaf mpass-err-pkts {
      type uint64;
      description
        "Number of packets dropped by the datapath due to errors in multi-packet processing.";
    }
    leaf mpass-err-octets {
      type uint64;
      units "octets";
      description
        "Total octets in packets dropped by the datapath due to errors in multi-packet processing.";
    }
    leaf ipv4-pbr-pkts {
      type uint64;
      description
        "Number of packets dropped due to IPv4 policy based routing (PBR).";
    }
    leaf ipv4-pbr-octets {
      type uint64;
      units "octets";
      description
        "Total octets in packets dropped due to IPv4 policy based routing (PBR).";
    }
    leaf inv-hdr-err-pkts {
      type uint64;
      description
        "Number of packets dropped due to invalid input header errors in the datapath.";
    }
    leaf inv-hdr-err-octets {
      type uint64;
      units "octets";
      description
        "Total octets in packets dropped due to invalid input header errors in the datapath.";
    }
    leaf punt-err-pkts {
      type uint64;
      description
        "Number of packets dropped due to errors during the punt process in the QFP datapath.";
    }
    leaf punt-err-octets {
      type uint64;
      units "octets";
      description
        "Total octets in packets dropped due to errors during the punt process in the QFP datapath.";
    }
    leaf inject-err-pkts {
      type uint64;
      description
        "Number of packets dropped due to errors during the inject process in the datapath.";
    }
    leaf inject-err-octets {
      type uint64;
      units "octets";
      description
        "Total octets in packets dropped due to errors during the inject process in the datapath.";
    }
    leaf ipv4-no-route-pkts {
      type uint64;
      description
        "Number of IPv4 packets dropped because no matching route was found.";
    }
    leaf ipv4-no-route-octets {
      type uint64;
      units "octets";
      description
        "Total octets in IPv4 packets dropped because no matching route was found.";
    }
    leaf qos-policing-pkts {
      type uint64;
      description
        "Number of packets dropped due to Quality of Service (QoS) policing.";
    }
    leaf qos-policing-octets {
      type uint64;
      units "octets";
      description
        "Total octets in packets dropped due to Quality of Service (QoS) policing.";
    }
    leaf qos-actions-pkts {
      type uint64;
      description
        "Number of packets dropped due to Quality of Service (QoS) actions.";
    }
    leaf qos-actions-octets {
      type uint64;
      units "octets";
      description
        "Total octets dropped by Quality of Service (QoS) actions on the QFP datapath.";
    }
    leaf null-jib-hdr-tbl-pkts {
      type uint64;
      description
        "Number of packets dropped due to a null JIB header table entry in the QFP datapath.";
    }
    leaf null-jib-hdr-tbl-octets {
      type uint64;
      units "octets";
      description
        "Total octets in packets dropped due to a null JIB header table entry in the QFP datapath.";
    }
    leaf tail-drop-pkts {
      type uint64;
      description
        "Number of packets dropped due to tail drop, which occurs when a queue is full in the QFP datapath.";
    }
    leaf tail-drop-octets {
      type uint64;
      units "octets";
      description
        "Total octets dropped due to tail drop when a queue is full in the QFP datapath.";
    }
    leaf wred-pkts {
      type uint64;
      description
        "Number of packets dropped by Weighted Random Early Detection (WRED) in the QFP datapath.";
    }
    leaf wred-octets {
      type uint64;
      units "octets";
      description
        "Total octets dropped by Weighted Random Early Detection (WRED) in the QFP datapath.";
    }
    leaf invalid-queue-pkts {
      type uint64;
      description
        "Number of packets dropped due to an invalid queue identifier in the QFP datapath.";
    }
    leaf invalid-queue-octets {
      type uint64;
      units "octets";
      description
        "Total octets in packets dropped due to an invalid queue identifier in the QFP datapath.";
    }
    leaf invalid-wred-pkts {
      type uint64;
      description
        "Number of packets dropped due to an invalid Weighted Random Early Detection (WRED) configuration in the QFP datapath.";
    }
    leaf invalid-wred-octets {
      type uint64;
      units "octets";
      description
        "Total octets in packets dropped due to an invalid Weighted Random Early Detection (WRED) configuration in the QFP datapath.";
    }
    leaf mpls-pkts {
      type uint64;
      description
        "Number of MPLS packets dropped by the QFP datapath.";
    }
    leaf mpls-octets {
      type uint64;
      units "octets";
      description
        "Total octets in MPLS packets dropped by the QFP.";
    }
    leaf ipv6-truncatedpkts-pkts {
      type uint64;
      description
        "Number of IPv6 packets dropped by the QFP that were truncated and dropped (incomplete or shorter than expected).";
    }
    leaf ipv6-truncatedpkts-octets {
      type uint64;
      units "octets";
      description
        "Total octets in IPv6 packets dropped as truncated by the QFP.";
    }
    leaf ipv6-formaterr-pkts {
      type uint64;
      description
        "Number of packets dropped due to IPv6 format error.";
    }
    leaf ipv6-formaterr-octets {
      type uint64;
      units "octets";
      description
        "Total octets in packets dropped due to IPv6 format error.";
    }
    leaf ipv6-badsource-pkts {
      type uint64;
      description
        "Number of packets dropped due to IPv6 bad source address.";
    }
    leaf ipv6-badsource-octets {
      type uint64;
      units "octets";
      description
        "Total octets in packets dropped due to IPv6 bad source address.";
    }
    leaf ipv6-badhop-pkts {
      type uint64;
      description
        "Number of packets dropped due to IPv6 bad hop count.";
    }
    leaf ipv6-badhop-octets {
      type uint64;
      units "octets";
      description
        "Total octets in IPv6 packets dropped due to an invalid hop count.";
    }
    leaf ipv6-toobigpacket-pkts {
      type uint64;
      description
        "Number of IPv6 packets that were dropped due to exceeding the maximum transmission unit (MTU).";
    }
    leaf ipv6-toobigpacket-octets {
      type uint64;
      units "octets";
      description
        "Total octets in IPv6 packets that were dropped due to exceeding the maximum transmission unit (MTU).";
    }
    leaf ipv6-no-route-pkts {
      type uint64;
      description
        "Number of IPv6 packets dropped by the QFP datapath due to the absence of a matching route in the routing table.";
    }
    leaf ipv6-no-route-octets {
      type uint64;
      units "octets";
      description
        "Total octets in IPv6 packets dropped by the QFP datapath due to the absence of a matching route in the routing table.";
    }
    leaf ipv6-acl-lookup-miss-pkts {
      type uint64;
      description
        "Number of packets dropped due to IPv6 access control list (ACL) lookup miss.";
    }
    leaf ipv6-acl-lookup-miss-octets {
      type uint64;
      units "octets";
      description
        "Total octets in packets dropped due to IPv6 access control list (ACL) lookup miss.";
    }
    leaf ipv6-acl-pkts {
      type uint64;
      description
        "Number of IPv6 packets dropped by the access control list (ACL) in the QFP datapath.";
    }
    leaf ipv6-acl-octets {
      type uint64;
      units "octets";
      description
        "Total octets in IPv6 packets dropped by the access control list (ACL) in the QFP datapath.";
    }
    leaf ip-acl-err-pkts {
      type uint64;
      description
        "Number of packets dropped due to IP access control list (ACL) error.";
    }
    leaf ip-acl-err-octets {
      type uint64;
      units "octets";
      description
        "Total octets in packets dropped due to IP access control list (ACL) errors.";
    }
    leaf mac-acl-pkts {
      type uint64;
      description
        "Number of packets dropped by the MAC access control list (ACL) on the QFP datapath.";
    }
    leaf mac-acl-octets {
      type uint64;
      units "octets";
      description
        "Total octets in packets dropped by the MAC access control list (ACL) on the QFP datapath.";
    }
    leaf mac-acl-lookup-miss-pkts {
      type uint64;
      description
        "Number of packets dropped due to MAC access control list (ACL) lookup miss.";
    }
    leaf mac-acl-lookup-miss-octets {
      type uint64;
      units "octets";
      description
        "Total octets in packets dropped due to MAC access control list (ACL) lookup miss.";
    }
    leaf ipv4mc-no-route-pkts {
      type uint64;
      description
        "Number of packets dropped due to IPv4 multicast no route.";
    }
    leaf ipv4mc-no-route-octets {
      type uint64;
      units "octets";
      description
        "Total octets in packets dropped due to IPv4 multicast no route.";
    }
    leaf unknown-ext-header-pkts {
      type uint64;
      description
        "Number of packets dropped due to an unknown extension header.";
    }
    leaf unknown-ext-header-octets {
      type uint64;
      units "octets";
      description
        "Total octets in packets dropped due to an unknown extension header.";
    }
    leaf ipv4mc-rpf-failed-pkts {
      type uint64;
      description
        "Number of packets dropped because IPv4 multicast reverse path forwarding (RPF) checks failed.";
    }
    leaf ipv4mc-rpf-failed-octets {
      type uint64;
      units "octets";
      description
        "Total octets in IPv4 multicast packets that failed reverse path forwarding (RPF) checks on the QFP datapath.";
    }
    leaf ipv4mc-invalid-replica-record-pkts {
      type uint64;
      description
        "Number of IPv4 multicast packets dropped due to invalid replica records detected by the QFP datapath.";
    }
    leaf ipv4mc-invalid-replica-record-octets {
      type uint64;
      units "octets";
      description
        "Total octets in IPv4 multicast packets dropped due to invalid replica records detected by the QFP datapath.";
    }
    leaf ipv4mc-ttl-threshold-chk-failed-pkts {
      type uint64;
      description
        "Number of packets dropped because the IPv4 multicast time to live (TTL) threshold check failed.";
    }
    leaf ipv4mc-ttl-threshold-chk-failed-octets {
      type uint64;
      units "octets";
      description
        "Total octets in packets dropped due to IPv4 multicast time to live (TTL) threshold check failed.";
    }
    leaf ipv4mc-extra-replicae-pkts {
      type uint64;
      description
        "Number of IPv4 multicast packets dropped by the QFP datapath as extra (unwanted) replicas.";
    }
    leaf ipv4mc-extra-replicae-octets {
      type uint64;
      units "octets";
      description
        "Total octets in IPv4 multicast packets dropped by the QFP datapath as extra (unwanted) replicas.";
    }
    leaf ipv4-mtr-pkts {
      type uint64;
      description
        "Number of IPv4 packets dropped during Multi-Topology Routing (MTR) processing.";
    }
    leaf ipv4-mtr-octets {
      type uint64;
      units "octets";
      description
        "Total octets in IPv4 packets dropped during Multi-Topology Routing (MTR) processing.";
    }
    leaf internal-ctl-pkts {
      type uint64;
      description
        "Number of internal control packets dropped in the datapath.";
    }
    leaf internal-ctl-octets {
      type uint64;
      units "octets";
      description
        "Total octets in internal control packets dropped in the datapath.";
    }
    leaf bad-dist-fifo-pkts {
      type uint64;
      description
        "Number of packets dropped due to an invalid distribution FIFO in the datapath.";
    }
    leaf bad-dist-fifo-octets {
      type uint64;
      units "octets";
      description
        "Total octets in packets dropped due to an invalid distribution FIFO in the datapath.";
    }
    leaf frfab-wred-drop-pkts {
      type uint64;
      description
        "Number of packets dropped due to frame relay weighted random early detection (WRED) drop.";
    }
    leaf frfab-wred-drop-octets {
      type uint64;
      units "octets";
      description
        "Total octets in packets dropped due to frame relay weighted random early detection (WRED) drop.";
    }
    leaf firewall-nonsession-pkts {
      type uint64;
      description
        "Number of packets dropped by the firewall because they did not match any existing session in the QFP datapath.";
    }
    leaf firewall-nonsession-octets {
      type uint64;
      units "octets";
      description
        "Total octets in packets dropped by the firewall because they did not match any existing session in the QFP datapath.";
    }
    leaf firewall-invalid-zone-pkts {
      type uint64;
      description
        "Number of packets dropped by the firewall due to invalid or undefined security zones in the QFP datapath.";
    }
    leaf firewall-invalid-zone-octets {
      type uint64;
      units "octets";
      description
        "Total octets in packets dropped by the firewall due to invalid or undefined security zones in the QFP datapath.";
    }
    leaf firewall-backpressure-pkts {
      type uint64;
      description
        "Number of packets dropped due to backpressure conditions in the firewall processing path within the QFP datapath.";
    }
    leaf firewall-backpressure-octets {
      type uint64;
      units "octets";
      description
        "Total octets dropped due to firewall backpressure events on the QFP datapath.";
    }
    leaf firewall-l4-insp-pkts {
      type uint64;
      description
        "Number of packets dropped by the Layer 4 firewall inspection engine on the QFP datapath.";
    }
    leaf firewall-l4-insp-octets {
      type uint64;
      units "octets";
      description
        "Total octets dropped by the Layer 4 firewall inspection engine on the QFP datapath.";
    }
    leaf ip-frag-err-pkts {
      type uint64;
      description
        "Number of packets dropped due to IP fragments error.";
    }
    leaf ip-frag-err-octets {
      type uint64;
      units "octets";
      description
        "Total octets in packets dropped due to IP fragments error.";
    }
    leaf no-gpm-memory-err-pkts {
      type uint64;
      description
        "Number of packets dropped due to lack of global packet memory in the datapath.";
    }
    leaf no-gpm-memory-err-octets {
      type uint64;
      units "octets";
      description
        "Total octets dropped due to lack of global packet memory in the datapath.";
    }
    leaf for-us-pkts {
      type uint64;
      description
        "Number of packets destined for the local device that were dropped by the QFP.";
    }
    leaf for-us-octets {
      type uint64;
      units "octets";
      description
        "Total octets in packets destined for the local device that were dropped by the QFP.";
    }
    leaf ipsec-input-pkts {
      type uint64;
      description
        "Number of packets dropped due to IPSEC input.";
    }
    leaf ipsec-input-octets {
      type uint64;
      units "octets";
      description
        "Total octets in IPSEC input packets dropped by the QFP datapath.";
    }
    leaf ipsec-ike-indicate-pkts {
      type uint64;
      description
        "Number of packets dropped while being indicated to the IKE (Internet Key Exchange) process for IPSEC on the QFP datapath.";
    }
    leaf ipsec-ike-indicate-octets {
      type uint64;
      units "octets";
      description
        "Total octets in packets dropped while being indicated to the IKE (Internet Key Exchange) process for IPSEC on the QFP datapath.";
    }
    leaf ipsec-invalid-sa-pkts {
      type uint64;
      description
        "Number of packets dropped due to IPSEC invalid security association (SA).";
    }
    leaf ipsec-invalid-sa-octets {
      type uint64;
      units "octets";
      description
        "Total octets in packets dropped due to IPSEC invalid security association (SA).";
    }
    leaf ipsec-tail-drop-pkts {
      type uint64;
      description
        "Number of packets dropped due to IPSEC tail drop.";
    }
    leaf ipsec-tail-drop-octets {
      type uint64;
      units "octets";
      description
        "Total octets in packets dropped due to IPSEC tail drop.";
    }
    leaf layer2-no-route-pkts {
      type uint64;
      description
        "Number of Layer 2 packets dropped due to no route being found on the QFP datapath.";
    }
    leaf layer2-no-route-octets {
      type uint64;
      units "octets";
      description
        "Total octets in Layer 2 packets dropped due to no route being found on the QFP datapath.";
    }
    leaf icmp-pkts {
      type uint64;
      description
        "Number of ICMP packets dropped on the QFP datapath.";
    }
    leaf icmp-octets {
      type uint64;
      units "octets";
      description
        "Total octets in ICMP packets dropped by the QFP datapath.";
    }
    leaf ip-ttl-exceeded-pkts {
      type uint64;
      description
        "Number of packets dropped due to IP time to live (TTL) exceeded.";
    }
    leaf ip-ttl-exceeded-octets {
      type uint64;
      units "octets";
      description
        "Total octets in packets dropped due to IP time to live (TTL) exceeded.";
    }
    leaf tunnel-bad-gre-checksum-pkts {
      type uint64;
      description
        "Number of packets dropped due to tunnel bad generic route encapsulation (GRE) checksum.";
    }
    leaf tunnel-bad-gre-checksum-octets {
      type uint64;
      units "octets";
      description
        "Total octets in packets dropped due to tunnel bad generic route encapsulation (GRE) checksum.";
    }
    leaf tunnel-misconfiguration-pkts {
      type uint64;
      description
        "Number of packets dropped due to tunnel misconfiguration.";
    }
    leaf tunnel-misconfiguration-octets {
      type uint64;
      units "octets";
      description
        "Total octets in packets dropped due to tunnel misconfiguration.";
    }
    leaf gre-bad-options-pkts {
      type uint64;
      description
        "Number of packets dropped due to generic route encapsulation (GRE) bad options.";
    }
    leaf gre-bad-options-octets {
      type uint64;
      units "octets";
      description
        "Total octets in packets dropped due to generic route encapsulation (GRE) bad options.";
    }
    leaf frag-tail-drop-pkts {
      type uint64;
      description
        "Number of IP fragment packets dropped by the QFP datapath due to tail drop conditions (e.g., buffer overflow).";
    }
    leaf frag-tail-drop-octets {
      type uint64;
      units "octets";
      description
        "Total octets dropped due to tail drop of fragmented packets in the QFP datapath.";
    }
    leaf unconfigured-fia-pkts {
      type uint64;
      description
        "Number of packets dropped due to an unconfigured Feature Invocation Array (FIA) in the datapath.";
    }
    leaf unconfigured-fia-octets {
      type uint64;
      units "octets";
      description
        "Total octets in packets dropped due to an unconfigured Feature Invocation Array (FIA) in the datapath.";
    }
    leaf ipv4-fpm-pkts {
      type uint64;
      description
        "Number of packets dropped due to IPv4 flexible packet match.";
    }
    leaf ipv4-fpm-octets {
      type uint64;
      units "octets";
      description
        "Total octets in packets dropped due to IPv4 flexible packet match.";
    }
    leaf nat-in2out-pkts {
      type uint64;
      description
        "Number of packets dropped during inside-to-outside Network Address Translation (NAT) processing on the QFP datapath.";
    }
    leaf nat-in2out-octets {
      type uint64;
      units "octets";
      description
        "Total octets in packets dropped during inside-to-outside Network Address Translation (NAT) processing on the QFP datapath.";
    }
    leaf nat-out2in-pkts {
      type uint64;
      description
        "Number of packets dropped during outside-to-inside Network Address Translation (NAT) processing on the QFP datapath.";
    }
    leaf nat-out2in-octets {
      type uint64;
      units "octets";
      description
        "Total octets in packets dropped during outside-to-inside Network Address Translation (NAT) processing on the QFP datapath.";
    }
    leaf pa-walk-err-pkts {
      type uint64;
      description
        "Number of packets dropped due to packet abstraction walk error.";
    }
    leaf pa-walk-err-octets {
      type uint64;
      units "octets";
      description
        "Total octets in packets dropped due to packet abstraction walk errors on the QFP datapath.";
    }
    leaf ipv4-routing-err-pkts {
      type uint64;
      description
        "Number of IPv4 packets dropped due to routing errors on the QFP datapath.";
    }
    leaf ipv4-routing-err-octets {
      type uint64;
      units "octets";
      description
        "Total octets in IPv4 packets dropped due to routing errors on the QFP datapath.";
    }
    leaf ipv6-routing-err-pkts {
      type uint64;
      description
        "Number of IPv6 packets dropped due to routing errors on the QFP datapath.";
    }
    leaf ipv6-routing-err-octets {
      type uint64;
      units "octets";
      description
        "Total octets in IPv6 packets dropped due to routing errors on the QFP datapath.";
    }
    leaf mpass-invalid-fs-vector-pkts {
      type uint64;
      description
        "Number of packets dropped in the datapath due to invalid feature special vector detected during multi-pass processing.";
    }
    leaf mpass-invalid-fs-vector-octets {
      type uint64;
      units "octets";
      description
        "Total octets in packets dropped in the datapath due to invalid feature special vector detected during multi-pass processing.";
    }
    leaf reass-drop-pkts {
      type uint64;
      description
        "Number of packets dropped during IP reassembly in the QFP datapath, including generic reassembly failures as well as overlap and overwrite conditions.";
    }
    leaf reass-drop-octets {
      type uint64;
      units "octets";
      description
        "Total octets in packets dropped during IP reassembly in the QFP datapath, including generic reassembly failures as well as overlap and overwrite conditions.";
    }
    leaf reass-frag-too-big-pkts {
      type uint64;
      description
        "Number of packets dropped during reassembly because the resulting packet size exceeded the maximum allowed by the QFP datapath.";
    }
    leaf reass-frag-too-big-octets {
      type uint64;
      units "octets";
      description
        "Total octets in fragments that were too large to be reassembled by the QFP datapath.";
    }
    leaf reass-no-frag-info-pkts {
      type uint64;
      description
        "Number of packets dropped during reassembly because no fragment information was available in the QFP datapath.";
    }
    leaf reass-no-frag-info-octets {
      type uint64;
      units "octets";
      description
        "Total octets in packets dropped during reassembly because no fragment information was available in the QFP datapath.";
    }
    leaf reass-no-frag-info-low-pkts {
      type uint64;
      description
        "Number of packets dropped during reassembly due to insufficient fragment information in the QFP datapath.";
    }
    leaf reass-no-frag-info-low-octets {
      type uint64;
      units "octets";
      description
        "Total octets in packets dropped during reassembly due to insufficient fragment information in the QFP datapath.";
    }
    leaf reass-bad-len-pkts {
      type uint64;
      description
        "Number of packets dropped during reassembly due to invalid or inconsistent length in the QFP datapath.";
    }
    leaf reass-bad-len-octets {
      type uint64;
      units "octets";
      description
        "Total octets in packets dropped during reassembly due to invalid or inconsistent length in the QFP datapath.";
    }
    leaf reass-too-many-frags-pkts {
      type uint64;
      description
        "Number of packets dropped during reassembly due to exceeding the maximum allowed number of fragments in the QFP datapath.";
    }
    leaf reass-too-many-frags-octets {
      type uint64;
      units "octets";
      description
        "Total octets in packets dropped during reassembly due to exceeding the maximum allowed number of fragments in the QFP datapath.";
    }
    leaf reass-no-frags-left-pkts {
      type uint64;
      description
        "Number of packets for which no fragments remained to be reassembled in the QFP datapath.";
    }
    leaf reass-no-frags-left-octets {
      type uint64;
      units "octets";
      description
        "Total octets in packets where IP reassembly was attempted but no fragments were left to complete the reassembly.";
    }
    leaf reass-overlap-pkts {
      type uint64;
      description
        "Number of packets dropped during IP reassembly due to overlapping fragments.";
    }
    leaf reass-overlap-octets {
      type uint64;
      units "octets";
      description
        "Total octets in packets dropped during IP reassembly due to overlapping fragments.";
    }
    leaf reass-timeout-pkts {
      type uint64;
      description
        "Number of packets dropped due to reassembly timeout.";
    }
    leaf reass-timeout-octets {
      type uint64;
      units "octets";
      description
        "Total octets in packets dropped due to reassembly timeout.";
    }
    leaf no-mem-pkts {
      type uint64;
      description
        "Number of packets dropped by the datapath due to memory allocation failures during reassembly processing.";
    }
    leaf no-mem-octets {
      type uint64;
      units "octets";
      description
        "Total octets in packets dropped by the datapath due to memory allocation failures during reassembly processing.";
    }
    leaf vfr-err-pkts {
      type uint64;
      description
        "Number of packets dropped due to virtual forwarding and routing (VFR) error.";
    }
    leaf vfr-err-octets {
      type uint64;
      units "octets";
      description
        "Total octets in packets dropped due to virtual forwarding and routing (VFR) error.";
    }
    leaf vfr-tail-drop-pkts {
      type uint64;
      description
        "Number of packets dropped due to virtual forwarding and routing (VFR) tail drop.";
    }
    leaf vfr-tail-drop-octets {
      type uint64;
      units "octets";
      description
        "Total octets in packets dropped due to virtual forwarding and routing (VFR) tail drop.";
    }
    leaf iphc-pkts {
      type uint64;
      description
        "Number of packets dropped during IP header compression (IPHC) by the QFP datapath.";
    }
    leaf iphc-octets {
      type uint64;
      units "octets";
      description
        "Total octets dropped during IP header compression (IPHC) by the QFP datapath.";
    }
    leaf multilink-cfg-pkts {
      type uint64;
      description
        "Number of multilink configuration packets dropped by the QFP datapath.";
    }
    leaf multilink-cfg-octets {
      type uint64;
      units "octets";
      description
        "Total octets in multilink configuration packets dropped by the QFP datapath.";
    }
    leaf mlp-pkts {
      type uint64;
      description
        "Number of Multilink Protocol (MLP) packets dropped by the QFP datapath.";
    }
    leaf mlp-octets {
      type uint64;
      units "octets";
      description
        "Total octets in Multilink Protocol (MLP) packets dropped by the QFP datapath.";
    }
    leaf min-tu-pkts {
      type uint64;
      description
        "Number of packets at the minimum transfer unit (MTU) size dropped by the QFP datapath.";
    }
    leaf min-tu-octets {
      type uint64;
      units "octets";
      description
        "Total octets in packets at the minimum transfer unit (MTU) size dropped by the QFP datapath.";
    }
    leaf max-tu-pkts {
      type uint64;
      description
        "Number of packets at the maximum transfer unit (MTU) size dropped by the QFP datapath.";
    }
    leaf max-tu-octets {
      type uint64;
      units "octets";
      description
        "Total octets in packets at the maximum transfer unit (MTU) size dropped by the QFP datapath.";
    }
    leaf ipv4-unclassified-pkts {
      type uint64;
      description
        "Number of IPv4 packets dropped because they were not classified by any known protocol or policy.";
    }
    leaf ipv4-unclassified-octets {
      type uint64;
      units "octets";
      description
        "Total octets in IPv4 packets dropped because they were not classified by any known protocol or policy.";
    }
    leaf ipv6-unclassified-pkts {
      type uint64;
      description
        "Number of IPv6 packets dropped because they were not classified by any known protocol or policy.";
    }
    leaf ipv6-unclassified-octets {
      type uint64;
      units "octets";
      description
        "Total octets in IPv6 packets dropped because they were not classified by any known protocol or policy.";
    }
    leaf ipv4-no-adj-pkts {
      type uint64;
      description
        "Number of IPv4 packets dropped due to missing adjacency information.";
    }
    leaf ipv4-no-adj-octets {
      type uint64;
      units "octets";
      description
        "Total octets in IPv4 packets dropped due to missing adjacency information.";
    }
    leaf ipv4-null0-pkts {
      type uint64;
      description
        "Number of IPv4 packets dropped by being routed to the null0 interface.";
    }
    leaf ipv4-null0-octets {
      type uint64;
      units "octets";
      description
        "Total octets in IPv4 packets dropped by being routed to the null0 interface.";
    }
    leaf ipv6-null0-pkts {
      type uint64;
      description
        "Number of IPv6 packets dropped by being routed to the null0 interface.";
    }
    leaf ipv6-null0-octets {
      type uint64;
      units "octets";
      description
        "Total octets in IPv6 packets dropped by being routed to the null0 interface.";
    }
    leaf mpls-mismatch-linktype-pkts {
      type uint64;
      description
        "Number of packets dropped due to multiprotocol label switching (MPLS) mismatch linktype.";
    }
    leaf mpls-mismatch-linktype-octets {
      type uint64;
      units "octets";
      description
        "Total octets in packets dropped due to multiprotocol label switching (MPLS) mismatch linktype.";
    }
    leaf mpls-frag-req-pkts {
      type uint64;
      description
        "Number of packets dropped due to multiprotocol label switching (MPLS) fragments request.";
    }
    leaf mpls-frag-req-octets {
      type uint64;
      units "octets";
      description
        "Total octets in packets dropped due to multiprotocol label switching (MPLS) fragments request.";
    }
    leaf choice-oce-pkts {
      type uint64;
      description
        "Number of packets dropped by the QFP datapath using the 'choice' output chain element (OCE) action.";
    }
    leaf choice-oce-octets {
      type uint64;
      units "octets";
      description
        "Total octets dropped by the QFP datapath using the 'choice' output chain element (OCE) action.";
    }
    leaf unsupported-oce-pkts {
      type uint64;
      description
        "Number of packets dropped due to unsupported output chain element (OCE).";
    }
    leaf unsupported-oce-octets {
      type uint64;
      units "octets";
      description
        "Total octets in packets dropped due to unsupported output chain element (OCE).";
    }
    leaf attn-invalid-spid-pkts {
      type uint64;
      description
        "Number of packets dropped by the datapath due to an invalid Sync Point Identifier (SPID) in the Attention protocol.";
    }
    leaf attn-invalid-spid-octets {
      type uint64;
      units "octets";
      description
        "Total octets in packets dropped by the datapath due to an invalid sync point identifier (SPID) in the attention protocol.";
    }
    leaf inv-common-preamble-pkts {
      type uint64;
      description
        "Number of packets dropped due to an invalid common preamble in the datapath.";
    }
    leaf inv-common-preamble-octets {
      type uint64;
      units "octets";
      description
        "Total octets in packets dropped due to an invalid common preamble in the datapath.";
    }
    leaf ext-drop-path-pkts {
      type uint64;
      description
        "Number of packets dropped by the datapath on the extended processing path.";
    }
    leaf ext-drop-path-octets {
      type uint64;
      units "octets";
      description
        "Total octets in packets dropped by the datapath on the extended processing path.";
    }
    leaf frr-oce-no-backup-pkts {
      type uint64;
      description
        "Number of packets dropped due to fast reroute (FRR) output chain element (OCE) no backup.";
    }
    leaf frr-oce-no-backup-octets {
      type uint64;
      units "octets";
      description
        "Total octets in packets dropped due to fast reroute (FRR) output chain element (OCE) no backup.";
    }
    leaf frr-oce-invalid-state-pkts {
      type uint64;
      description
        "Number of packets dropped due to fast reroute (FRR) output chain element (OCE) invalid state.";
    }
    leaf frr-oce-invalid-state-octets {
      type uint64;
      units "octets";
      description
        "Total octets in packets dropped due to fast reroute (FRR) output chain element (OCE) invalid state.";
    }
    leaf bqs-oor-pkts {
      type uint64;
      description
        "Number of packets dropped due to buffering, queuing and scheduling out of resources.";
    }
    leaf bqs-oor-octets {
      type uint64;
      units "octets";
      description
        "Total octets dropped due to the QFP running out of buffering, queuing, or scheduling resources.";
    }
    leaf ess-bad-sess-uidb-pkts {
      type uint64;
      description
        "Number of packets dropped by Edge Switching Services (ESS) due to invalid or corrupted session interface information.";
    }
    leaf ess-bad-sess-uidb-octets {
      type uint64;
      units "octets";
      description
        "Total octets in packets dropped by Edge Switching Services (ESS) due to invalid or corrupted session interface information.";
    }
    leaf ess-pktsb-missed-pkts {
      type uint64;
      description
        "Number of packets dropped because Edge Switching Services (ESS) packet sub-block processing failed.";
    }
    leaf ess-pktsb-missed-octets {
      type uint64;
      units "octets";
      description
        "Total octets in packets dropped because Edge Switching Services (ESS) packet sub-block processing failed.";
    }
    leaf ess-unsup-pkt-type-pkts {
      type uint64;
      description
        "Number of packets dropped by Edge Switching Services (ESS) because the packet type is unsupported.";
    }
    leaf ess-unsup-pkt-type-octets {
      type uint64;
      units "octets";
      description
        "Total octets in packets dropped by Edge Switching Services (ESS) because the packet type is unsupported.";
    }
    leaf ess-no-encap-info-pkts {
      type uint64;
      description
        "Number of packets dropped by Edge Switching Services (ESS) because the required encapsulation information was missing.";
    }
    leaf ess-no-encap-info-octets {
      type uint64;
      units "octets";
      description
        "Total octets in packets dropped by Edge Switching Services (ESS) because the required encapsulation information was missing.";
    }
    leaf ess-inv-switch-mode-pkts {
      type uint64;
      description
        "Number of packets dropped by Edge Switching Services (ESS) because the switch mode is invalid.";
    }
    leaf ess-inv-switch-mode-octets {
      type uint64;
      units "octets";
      description
        "Total octets in packets dropped by Edge Switching Services (ESS) because the switch mode is invalid.";
    }
    leaf inv-ppp-cp-pkt-pkts {
      type uint64;
      description
        "Number of PPP control protocol packets dropped as invalid by the QFP datapath.";
    }
    leaf inv-ppp-cp-pkt-octets {
      type uint64;
      units "octets";
      description
        "Total octets in PPP control protocol packets dropped as invalid by the QFP datapath.";
    }
    leaf ppp-cxt-missed-pkts {
      type uint64;
      description
        "Number of PPP packets dropped because the required processing context was not found in the QFP datapath.";
    }
    leaf ppp-cxt-missed-octets {
      type uint64;
      units "octets";
      description
        "Total octets in PPP packets dropped because the required processing context was not found in the QFP datapath.";
    }
    leaf ess-unbound-session-pkts {
      type uint64;
      description
        "Number of packets dropped by Edge Switching Services (ESS) due to unbound sessions on the QFP datapath.";
    }
    leaf ess-unbound-session-octets {
      type uint64;
      units "octets";
      description
        "Total octets in packets dropped by Edge Switching Services (ESS) due to unbound sessions on the QFP datapath.";
    }
    leaf ess-pi-inv-subtype-pkts {
      type uint64;
      description
        "Number of packets dropped due to invalid subtypes in the platform-independent Edge Switching Services (ESS) on the QFP datapath.";
    }
    leaf ess-pi-inv-subtype-octets {
      type uint64;
      units "octets";
      description
        "Total octets in packets dropped due to invalid subtypes in the platform-independent Edge Switching Services (ESS) on the QFP datapath.";
    }
    leaf ess-pi-state-err-pkts {
      type uint64;
      description
        "Number of packets dropped due to state errors in the platform-independent Edge Switching Services (ESS) on the QFP datapath.";
    }
    leaf ess-pi-state-err-octets {
      type uint64;
      units "octets";
      description
        "Total octets in packets dropped due to state errors in the platform-independent Edge Switching Services (ESS) on the QFP datapath.";
    }
    leaf ess-inject-bad-hdr-pkts {
      type uint64;
      description
        "Number of packets dropped due to invalid or malformed headers injected by the Edge Switching Services (ESS) datapath.";
    }
    leaf ess-inject-bad-hdr-octets {
      type uint64;
      units "octets";
      description
        "Total octets in packets dropped due to invalid or malformed headers injected by the Edge Switching Services (ESS) datapath.";
    }
    leaf ess-l2-hdr-too-big-pkts {
      type uint64;
      description
        "Number of packets dropped by the Edge Switching Services (ESS) datapath due to layer 2 headers exceeding the maximum allowed size.";
    }
    leaf ess-l2-hdr-too-big-octets {
      type uint64;
      units "octets";
      description
        "Total octets in packets dropped by the Edge Switching Services (ESS) datapath due to layer 2 headers exceeding the maximum allowed size.";
    }
    leaf pppox-unconfigured-pkts {
      type uint64;
      description
        "Number of packets dropped due to PPP over any protocol (PPPoX) unconfigured.";
    }
    leaf pppox-unconfigured-octets {
      type uint64;
      units "octets";
      description
        "Total octets in packets dropped due to PPP over any protocol (PPPoX) unconfigured.";
    }
    leaf pppoe-pkt-inv-hdr-pkts {
      type uint64;
      description
        "Number of packets dropped due to PPP over Ethernet (PPPoE) packet invalid header.";
    }
    leaf pppoe-pkt-inv-hdr-octets {
      type uint64;
      units "octets";
      description
        "Total octets in packets dropped due to PPP over Ethernet (PPPoE) packet invalid header.";
    }
    leaf pppoe-pkt-bad-len-pkts {
      type uint64;
      description
        "Number of packets dropped due to PPP over Ethernet (PPPoE) packet bad length.";
    }
    leaf pppoe-pkt-bad-len-octets {
      type uint64;
      units "octets";
      description
        "Total octets in PPP over Ethernet (PPPoE) packets dropped due to invalid or incorrect length.";
    }
    leaf pppoe-no-session-pkts {
      type uint64;
      description
        "Number of PPP over Ethernet (PPPoE) packets dropped because no matching active PPPoE session was found.";
    }
    leaf pppoe-no-session-octets {
      type uint64;
      units "octets";
      description
        "Total octets in PPP over Ethernet (PPPoE) packets dropped because no matching active PPPoE session was found.";
    }
    leaf pppoe-inv-encap-info-pkts {
      type uint64;
      description
        "Number of PPP over Ethernet (PPPoE) packets dropped due to invalid encapsulation information.";
    }
    leaf pppoe-inv-encap-info-octets {
      type uint64;
      units "octets";
      description
        "Total octets in PPP over Ethernet (PPPoE) packets dropped due to invalid encapsulation information.";
    }
    leaf ess-cac-pkts {
      type uint64;
      description
        "Number of packets dropped due to edge switching services call admission control.";
    }
    leaf ess-cac-octets {
      type uint64;
      units "octets";
      description
        "Total octets in packets dropped due to edge switching services call admission control.";
    }
    leaf l2tp-unconfigured-pkts {
      type uint64;
      description
        "Number of Layer 2 Tunneling Protocol (L2TP) packets dropped because no corresponding L2TP configuration exists by the QFP.";
    }
    leaf l2tp-unconfigured-octets {
      type uint64;
      units "octets";
      description
        "Total octets in Layer 2 Tunneling Protocol (L2TP) packets dropped because no corresponding L2TP configuration exists by the QFP.";
    }
    leaf l2tp-pkt-inv-hdr-pkts {
      type uint64;
      description
        "Number of Layer 2 Tunneling Protocol (L2TP) packets dropped due to invalid headers.";
    }
    leaf l2tp-pkt-inv-hdr-octets {
      type uint64;
      units "octets";
      description
        "Total octets in Layer 2 Tunneling Protocol (L2TP) packets with invalid headers dropped by the QFP.";
    }
    leaf l2tp-pkt-bad-len-pkts {
      type uint64;
      description
        "Number of Layer 2 Tunneling Protocol (L2TP) packets with invalid or incorrect length fields dropped by the QFP.";
    }
    leaf l2tp-pkt-bad-len-octets {
      type uint64;
      units "octets";
      description
        "Total octets in Layer 2 Tunneling Protocol (L2TP) packets with invalid or incorrect length fields dropped by the QFP.";
    }
    leaf l2tp-no-session-pkts {
      type uint64;
      description
        "Number of Layer 2 Tunneling Protocol (L2TP) packets dropped by the QFP because they do not correspond to an existing session.";
    }
    leaf l2tp-no-session-octets {
      type uint64;
      units "octets";
      description
        "Total octets in Layer 2 Tunneling Protocol (L2TP) packets dropped by the QFP because they do not correspond to an existing session.";
    }
    leaf l2tp-pktsb-missed-pkts {
      type uint64;
      description
        "Number of Layer 2 Tunneling Protocol (L2TP) packets dropped because sub-block processing failed in the QFP datapath.";
    }
    leaf l2tp-pktsb-missed-octets {
      type uint64;
      units "octets";
      description
        "Total octets in Layer 2 Tunneling Protocol (L2TP) packets dropped because sub-block processing failed in the QFP datapath.";
    }
    leaf l2tp-security-check-pkts {
      type uint64;
      description
        "Number of Layer 2 Tunneling Protocol (L2TP) packets that failed security checks and were dropped by the QFP.";
    }
    leaf l2tp-security-check-octets {
      type uint64;
      units "octets";
      description
        "Total octets in Layer 2 Tunneling Protocol (L2TP) packets that failed security checks and were dropped by the QFP.";
    }
    leaf l2tp-bad-udp-chksum-pkts {
      type uint64;
      description
        "Number of packets dropped due to layer 2 tunnelling protocol (L2TP) bad UDP checksum.";
    }
    leaf l2tp-bad-udp-chksum-octets {
      type uint64;
      units "octets";
      description
        "Total octets in packets dropped due to layer 2 tunnelling protocol (L2TP) bad UDP checksum.";
    }
    leaf l2tp-ooo-rx-pkt-pkts {
      type uint64;
      description
        "Number of Layer 2 Tunneling Protocol (L2TP) packets dropped because they were received out of order and the L2TP sequencing policy was configured to drop out-of-order packets.";
    }
    leaf l2tp-ooo-rx-pkt-octets {
      type uint64;
      units "octets";
      description
        "Total octets in Layer 2 Tunneling Protocol (L2TP) packets dropped because they were received out of order and the L2TP sequencing policy was configured to drop out-of-order packets.";
    }
    leaf l2tp-exceed-tx-mtu-pkts {
      type uint64;
      description
        "Number of packets dropped due to layer 2 tunnelling protocol (L2TP) exceed transmit mtu.";
    }
    leaf l2tp-exceed-tx-mtu-octets {
      type uint64;
      units "octets";
      description
        "Total octets in packets dropped due to layer 2 tunnelling protocol (L2TP) exceed transmit mtu.";
    }
    leaf ipsec-output-pkts {
      type uint64;
      description
        "Number of packets dropped during IPSEC output sub-block processing.";
    }
    leaf ipsec-output-octets {
      type uint64;
      units "octets";
      description
        "Total octets in packets dropped during IPSEC output sub-block processing.";
    }
    leaf ipsec-ted-indicate-pkts {
      type uint64;
      description
        "Number of packets dropped because IPSEC tunnel endpoint discovery (TED) indication processing failed.";
    }
    leaf ipsec-ted-indicate-octets {
      type uint64;
      units "octets";
      description
        "Total octets in packets dropped because IPSEC tunnel endpoint discovery (TED) indication processing failed.";
    }
    leaf ipsec-deny-drop-pkts {
      type uint64;
      description
        "Number of packets dropped due to IPSEC deny policies.";
    }
    leaf ipsec-deny-drop-octets {
      type uint64;
      units "octets";
      description
        "Total octets in packets dropped due to IPSEC deny policies.";
    }
    leaf l2tp-cxt-missed-pkts {
      type uint64;
      description
        "Number of packets dropped because no matching Layer 2 Tunneling Protocol (L2TP) datapath context was found.";
    }
    leaf l2tp-cxt-missed-octets {
      type uint64;
      units "octets";
      description
        "Total octets in packets dropped because no matching Layer 2 Tunneling Protocol (L2TP) datapath context was found.";
    }
    leaf l2tp-tx-seq-missed-pkts {
      type uint64;
      description
        "Number of packets dropped because the required Layer 2 Tunneling Protocol (L2TP) transmit sequence block was missing.";
    }
    leaf l2tp-tx-seq-missed-octets {
      type uint64;
      units "octets";
      description
        "Total octets in packets dropped because the required Layer 2 Tunneling Protocol (L2TP) transmit sequence block was missing.";
    }
    leaf disabled-pkts {
      type uint64;
      description
        "Number of packets dropped due to a disabled interface in the datapath.";
    }
    leaf disabled-octets {
      type uint64;
      units "octets";
      description
        "Total octets in packets dropped due to a disabled interface in the datapath.";
    }
    leaf ipv6-no-adj-pkts {
      type uint64;
      description
        "Number of packets dropped due to IPv6 no adjacency.";
    }
    leaf ipv6-no-adj-octets {
      type uint64;
      units "octets";
      description
        "Total octets in packets dropped due to IPv6 no adjacency.";
    }
    leaf not-enabled-pkts {
      type uint64;
      description
        "Number of packets dropped by the datapath due to QFP not enabled.";
    }
    leaf not-enabled-octets {
      type uint64;
      units "octets";
      description
        "Total octets in packets dropped by the datapath due to QFP not enabled.";
    }
    leaf special-multicast-obj-pkts {
      type uint64;
      description
        "Number of packets dropped because they were classified as special multicast objects in the QFP datapath.";
    }
    leaf special-multicast-obj-octets {
      type uint64;
      units "octets";
      description
        "Total octets in packets dropped because they were classified as special multicast objects in the QFP datapath.";
    }
    leaf illegal-obj-pkts {
      type uint64;
      description
        "Number of packets dropped due to processing an OCE illegal object in the datapath.";
    }
    leaf illegal-obj-octets {
      type uint64;
      units "octets";
      description
        "Total octets in packets dropped due to processing an OCE illegal object in the datapath.";
    }
    leaf unresolved-pkts {
      type uint64;
      description
        "Number of packets dropped by the datapath because they could not be resolved to a valid forwarding path.";
    }
    leaf unresolved-octets {
      type uint64;
      units "octets";
      description
        "Total octets in packets dropped by the datapath because they could not be resolved to a valid forwarding path.";
    }
    leaf discard-pkts {
      type uint64;
      description
        "Number of packets dropped due to a discard adjacency in the datapath.";
    }
    leaf discard-octets {
      type uint64;
      units "octets";
      description
        "Total octets in packets dropped due to a discard adjacency in the datapath.";
    }
    leaf ipv6mc-no-route-pkts {
      type uint64;
      description
        "Number of IPv6 multicast packets dropped because no forwarding route was found.";
    }
    leaf ipv6mc-no-route-octets {
      type uint64;
      units "octets";
      description
        "Total octets in IPv6 multicast packets that were dropped because no forwarding route was found.";
    }
    leaf ipv6mc-rpf-failed-pkts {
      type uint64;
      description
        "Number of packets dropped because IPv6 multicast reverse path forwarding (RPF) checks failed.";
    }
    leaf ipv6mc-rpf-failed-octets {
      type uint64;
      units "octets";
      description
        "Total octets in packets dropped due to IPv6 multicast reverse path forwarding failed.";
    }
    leaf ipv6mc-invalid-replica-record-pkts {
      type uint64;
      description
        "Number of IPv6 multicast packets dropped due to invalid replica records during packet replication.";
    }
    leaf ipv6mc-invalid-replica-record-octets {
      type uint64;
      units "octets";
      description
        "Total octets in IPv6 multicast packets dropped due to invalid replica records during packet replication.";
    }
    leaf ipv6mc-ttl-threshold-chk-failed-pkts {
      type uint64;
      description
        "Number of packets dropped due to IPv6 multicast time to live (TTL) threshold check failed.";
    }
    leaf ipv6mc-ttl-threshold-chk-failed-octets {
      type uint64;
      units "octets";
      description
        "Total octets in packets dropped due to IPv6 multicast time to live (TTL) threshold check failed.";
    }
    leaf ipv6mc-extra-replica-pkts {
      type uint64;
      description
        "Number of IPv6 multicast packets dropped as extra (redundant or unnecessary) replications.";
    }
    leaf ipv6mc-extra-replica-octets {
      type uint64;
      units "octets";
      description
        "Total octets in IPv6 multicast packets dropped as extra (redundant or unnecessary) replications.";
    }
    leaf layer2-switching-pkts {
      type uint64;
      description
        "Number of packets dropped during Layer 2 switching by the QFP.";
    }
    leaf layer2-switching-octets {
      type uint64;
      units "octets";
      description
        "Total octets in packets dropped during Layer 2 switching by the QFP.";
    }
    leaf internal-intf-err-pkts {
      type uint64;
      description
        "Number of packets dropped due to internal interface errors in the datapath.";
    }
    leaf internal-intf-err-octets {
      type uint64;
      units "octets";
      description
        "Total octets in packets dropped due to internal interface errors in the datapath.";
    }
    leaf sbc-police-punt-pkts {
      type uint64;
      description
        "Number of packets dropped due to session border controller (SBC) police punt.";
    }
    leaf sbc-police-punt-octets {
      type uint64;
      units "octets";
      description
        "Total octets in packets dropped due to session border controller (SBC) police punt.";
    }
    leaf sbc-uidb-pkts {
      type uint64;
      description
        "Number of packets dropped by the Session Border Controller (SBC) on the UIDB (Universal Interface Descriptor Block) interface.";
    }
    leaf sbc-uidb-octets {
      type uint64;
      units "octets";
      description
        "Total octets in packets dropped by the Session Border Controller (SBC) on the UIDB (Universal Interface Descriptor Block) interface.";
    }
    leaf sbc-sess-pkts {
      type uint64;
      description
        "Number of packets associated with active sessions dropped by the Session Border Controller (SBC).";
    }
    leaf sbc-sess-octets {
      type uint64;
      units "octets";
      description
        "Total octets in packets associated with active sessions that were dropped by the Session Border Controller (SBC).";
    }
    leaf sbc-mmoh-invalid-replica-record-pkts {
      type uint64;
      description
        "Number of packets dropped due to session border controller (SBC) music on hold invalid replica record.";
    }
    leaf sbc-mmoh-invalid-replica-record-octets {
      type uint64;
      units "octets";
      description
        "Total octets in packets dropped due to session border controller (SBC) music on hold invalid replica record.";
    }
    leaf mpls-ipv6-frag-req-pkts {
      type uint64;
      description
        "Number of packets dropped due to multiprotocol label switching (MPLS) IPv6 fragments request.";
    }
    leaf mpls-ipv6-frag-req-octets {
      type uint64;
      units "octets";
      description
        "Total octets in packets dropped due to multiprotocol label switching (MPLS) IPv6 fragments request.";
    }
    leaf sw-mac-filter-pkts {
      type uint64;
      description
        "Number of packets dropped by the software-based MAC address filter.";
    }
    leaf sw-mac-filter-octets {
      type uint64;
      units "octets";
      description
        "Total octets dropped by the software-based MAC address filter.";
    }
    leaf tunnel-bad-pim-checksum-pkts {
      type uint64;
      description
        "Number of packets dropped due to tunnel bad protocol independent multicast (PIM) checksum.";
    }
    leaf tunnel-bad-pim-checksum-octets {
      type uint64;
      units "octets";
      description
        "Total octets in packets dropped due to tunnel bad protocol independent multicast (PIM) checksum.";
    }
    leaf tunnel-unsupported-config-pkts {
      type uint64;
      description
        "Number of tunnel packets dropped due to unsupported configuration parameters.";
    }
    leaf tunnel-unsupported-config-octets {
      type uint64;
      units "octets";
      description
        "Total octets in tunnel packets dropped due to unsupported configuration parameters.";
    }
    leaf firewall-no-forwarding-pkts {
      type uint64;
      description
        "Number of packets dropped by the firewall due to no forwarding action.";
    }
    leaf firewall-no-forwarding-octets {
      type uint64;
      units "octets";
      description
        "Total octets dropped by the firewall due to no forwarding action.";
    }
    leaf erspan-pkts {
      type uint64;
      description
        "Number of packets dropped due to extended reach SPAN (ERSPAN).";
    }
    leaf erspan-octets {
      type uint64;
      units "octets";
      description
        "Total octets in packets dropped due to extended reach SPAN (ERSPAN).";
    }
    leaf ipv4-urpf-null-path-list-pkts {
      type uint64;
      description
        "Number of packets dropped due to IPv4 unicast reverse path forwarding null path list.";
    }
    leaf ipv4-urpf-null-path-list-octets {
      type uint64;
      units "octets";
      description
        "Total octets in packets dropped due to IPv4 unicast reverse path forwarding null path list.";
    }
    leaf mpls-unclassified-pkts {
      type uint64;
      description
        "Number of packets dropped due to multiprotocol label switching (MPLS) unclassified.";
    }
    leaf mpls-unclassified-octets {
      type uint64;
      units "octets";
      description
        "Total octets in packets dropped due to multiprotocol label switching (MPLS) unclassified.";
    }
    leaf mpls-eos-invalid-pkts {
      type uint64;
      description
        "Number of packets dropped due to multiprotocol label switching (MPLS) end of stack invalid.";
    }
    leaf mpls-eos-invalid-octets {
      type uint64;
      units "octets";
      description
        "Total octets in packets dropped due to multiprotocol label switching (MPLS) end of stack invalid.";
    }
    leaf glean-adj-unsupport-linktype-pkts {
      type uint64;
      description
        "Number of packets dropped on glean adjacencies due to unsupported link types in the QFP datapath.";
    }
    leaf glean-adj-unsupport-linktype-octets {
      type uint64;
      units "octets";
      description
        "Total octets in packets dropped on glean adjacencies due to unsupported link types in the QFP datapath.";
    }
    leaf mpls-label-oce-ptr-null-pkts {
      type uint64;
      description
        "Number of packets dropped due to multiprotocol label switching (MPLS) label output chain element (OCE) pointer null.";
    }
    leaf mpls-label-oce-ptr-null-octets {
      type uint64;
      units "octets";
      description
        "Total octets in packets dropped due to multiprotocol label switching (MPLS) label output chain element (OCE) pointer null.";
    }
    leaf mpls-label-oce-invalid-label-pkts {
      type uint64;
      description
        "Number of packets dropped due to multiprotocol label switching (MPLS) label output chain element (OCE) invalid label.";
    }
    leaf mpls-label-oce-invalid-label-octets {
      type uint64;
      units "octets";
      description
        "Total octets in packets dropped due to multiprotocol label switching (MPLS) label output chain element (OCE) invalid label.";
    }
    leaf mpls-label-oce-unsupport-linktype-pkts {
      type uint64;
      description
        "Number of packets dropped due to multiprotocol label switching (MPLS) label output chain element (OCE) unsupported linktype.";
    }
    leaf mpls-label-oce-unsupport-linktype-octets {
      type uint64;
      units "octets";
      description
        "Total octets in packets dropped due to multiprotocol label switching (MPLS) label output chain element (OCE) unsupported linktype.";
    }
    leaf lookup-oce-should-drop-pkts {
      type uint64;
      description
        "Number of packets dropped by the lookup output chain element (OCE) on the QFP datapath.";
    }
    leaf lookup-oce-should-drop-octets {
      type uint64;
      units "octets";
      description
        "Total octets in packets dropped by the lookup output chain element (OCE) on the QFP datapath.";
    }
    leaf lookup-oce-unsupport-linktype-pkts {
      type uint64;
      description
        "Number of packets dropped due to lookup output chain element (OCE) unsupported linktype.";
    }
    leaf lookup-oce-unsupport-linktype-octets {
      type uint64;
      units "octets";
      description
        "Total octets in packets dropped by the lookup output chain element (OCE) due to unsupported link types on the QFP datapath.";
    }
    leaf unsupport-linktype-no-route-pkts {
      type uint64;
      description
        "Number of packets dropped because no route was found for packets with unsupported link types in the QFP datapath.";
    }
    leaf unsupport-linktype-no-route-octets {
      type uint64;
      units "octets";
      description
        "Total octets in packets dropped because no route was found for packets with unsupported link types in the QFP datapath.";
    }
    leaf unsupport-linktype-null0-pkts {
      type uint64;
      description
        "Number of packets with unsupported link types dropped to the null0 interface in the QFP datapath.";
    }
    leaf unsupport-linktype-null0-octets {
      type uint64;
      units "octets";
      description
        "Total octets in packets with unsupported link types dropped to the null0 interface in the QFP datapath.";
    }
    leaf sr-te-remote-error-pkts {
      type uint64;
      description
        "Number of packets dropped due to segment routing traffic engineering (TE) remote error.";
    }
    leaf sr-te-remote-error-octets {
      type uint64;
      units "octets";
      description
        "Total octets in packets dropped due to segment routing traffic engineering (TE) remote error.";
    }
    leaf ipv4-pop-pipe-php-ttl-expire-pkts {
      type uint64;
      description
        "Number of packets dropped due to IPv4 pop pipe penultimate hop pop time to live (TTL) expire.";
    }
    leaf ipv4-pop-pipe-php-ttl-expire-octets {
      type uint64;
      units "octets";
      description
        "Total octets in packets dropped due to IPv4 pop pipe penultimate hop pop time to live (TTL) expire.";
    }
    leaf ipv4-pop-unf-uhp-ttl-expire-pkts {
      type uint64;
      description
        "Number of packets dropped due to IPv4 pop uniform ultimate hop pop time to live (TTL) expire.";
    }
    leaf ipv4-pop-unf-uhp-ttl-expire-octets {
      type uint64;
      units "octets";
      description
        "Total octets in packets dropped due to IPv4 pop uniform ultimate hop pop time to live (TTL) expire.";
    }
    leaf ipv4-pop-unf-php-ttl-expire-pkts {
      type uint64;
      description
        "Number of packets dropped due to IPv4 pop uniform penultimate hop pop time to live (TTL) expire.";
    }
    leaf ipv4-pop-unf-php-ttl-expire-octets {
      type uint64;
      units "octets";
      description
        "Total octets in packets dropped due to IPv4 pop uniform penultimate hop pop time to live (TTL) expire.";
    }
    leaf mpls-pop-pipe-ttl-expire-pkts {
      type uint64;
      description
        "Number of packets dropped due to multiprotocol label switching (MPLS) pop pipe time to live (TTL) expire.";
    }
    leaf mpls-pop-pipe-ttl-expire-octets {
      type uint64;
      units "octets";
      description
        "Total octets in packets dropped due to multiprotocol label switching (MPLS) pop pipe time to live (TTL) expire.";
    }
    leaf mpls-pop-unf-uhp-ttl-expire-pkts {
      type uint64;
      description
        "Number of packets dropped due to multiprotocol label switching (MPLS) pop uniform ultimate hop pop time to live (TTL) expire.";
    }
    leaf mpls-pop-unf-uhp-ttl-expire-octets {
      type uint64;
      units "octets";
      description
        "Total octets in packets dropped due to multiprotocol label switching (MPLS) pop uniform ultimate hop pop time to live (TTL) expire.";
    }
    leaf mpls-pop-unf-php-ttl-expire-pkts {
      type uint64;
      description
        "Number of packets dropped due to multiprotocol label switching (MPLS) pop uniform penultimate hop pop time to live (TTL) expire.";
    }
    leaf mpls-pop-unf-php-ttl-expire-octets {
      type uint64;
      units "octets";
      description
        "Total octets in packets dropped due to multiprotocol label switching (MPLS) pop uniform penultimate hop pop time to live (TTL) expire.";
    }
    leaf label-pop-unsupport-linktype-pkts {
      type uint64;
      description
        "Number of packets dropped during label pop operation (such as MPLS label removal) due to unsupported link type.";
    }
    leaf label-pop-unsupport-linktype-octets {
      type uint64;
      units "octets";
      description
        "Total octets in packets where a label pop operation was attempted on an unsupported link type.";
    }
    leaf mpls-no-route-pkts {
      type uint64;
      description
        "Number of Multiprotocol Label Switching (MPLS) packets dropped because no matching route was found.";
    }
    leaf mpls-no-route-octets {
      type uint64;
      units "octets";
      description
        "Total octets in Multiprotocol Label Switching (MPLS) packets dropped because no matching route was found.";
    }
    leaf mpls-icmp-invalid-hdr-pkts {
      type uint64;
      description
        "Number of packets dropped due to multiprotocol label switching (MPLS) ICMP invalid header.";
    }
    leaf mpls-icmp-invalid-hdr-octets {
      type uint64;
      units "octets";
      description
        "Total octets in packets dropped due to multiprotocol label switching (MPLS) ICMP invalid header.";
    }
    leaf mpls-sanity-echo-req-pkts {
      type uint64;
      description
        "Number of packets dropped due to multiprotocol label switching (MPLS) sanity echo request.";
    }
    leaf mpls-sanity-echo-req-octets {
      type uint64;
      units "octets";
      description
        "Total octets in packets dropped due to multiprotocol label switching (MPLS) sanity echo request.";
    }
    leaf mpls-sanity-drop-pkts {
      type uint64;
      description
        "Number of packets dropped due to multiprotocol label switching (MPLS) sanity drop.";
    }
    leaf mpls-sanity-drop-octets {
      type uint64;
      units "octets";
      description
        "Total octets in packets dropped due to multiprotocol label switching (MPLS) sanity drop.";
    }
    leaf ess-unprov-session-pkts {
      type uint64;
      description
        "Number of packets dropped due to edge switching services unprovisioned session.";
    }
    leaf ess-unprov-session-octets {
      type uint64;
      units "octets";
      description
        "Total octets for unprovisioned sessions in Edge Switching Services (ESS) dropped by the QFP.";
    }
    leaf firewall-policy-pkts {
      type uint64;
      description
        "Number of packets dropped by configured firewall policies on the QFP datapath.";
    }
    leaf firewall-policy-octets {
      type uint64;
      units "octets";
      description
        "Total octets in packets dropped by configured firewall policies on the QFP datapath.";
    }
    leaf firewall-l4-pkts {
      type uint64;
      description
        "Number of Layer 4 (transport layer) packets dropped by the firewall policies on the QFP.";
    }
    leaf firewall-l4-octets {
      type uint64;
      units "octets";
      description
        "Total octets in Layer 4 (transport layer) packets dropped by the firewall policies on the QFP.";
    }
    leaf firewall-l7-pkts {
      type uint64;
      description
        "Number of Layer 7 (application layer) packets dropped by the firewall policies on the QFP.";
    }
    leaf firewall-l7-octets {
      type uint64;
      units "octets";
      description
        "Total octets in Layer 7 (application layer) packets dropped by the firewall policies on the QFP.";
    }
    leaf firewall-no-new-sessions-pkts {
      type uint64;
      description
        "Number of packets dropped by the firewall because the maximum number of allowed new sessions was exceeded on the QFP datapath.";
    }
    leaf firewall-no-new-sessions-octets {
      type uint64;
      units "octets";
      description
        "Total octets in packets dropped by the firewall because the maximum number of allowed new sessions was exceeded on the QFP.";
    }
    leaf firewall-not-initiator-pkts {
      type uint64;
      description
        "Number of packets dropped by the firewall because they were not sent by the session initiator, as tracked by the QFP datapath.";
    }
    leaf firewall-not-initiator-octets {
      type uint64;
      units "octets";
      description
        "Total octets dropped by the firewall for sessions where the device is not the initiator.";
    }
    leaf firewall-not-from-init-pkts {
      type uint64;
      description
        "Number of packets dropped by the firewall because they are not from the session initiator.";
    }
    leaf firewall-not-from-init-octets {
      type uint64;
      units "octets";
      description
        "Total octets dropped by the firewall because they are not from the session initiator.";
    }
    leaf gen-pkt-replication-pkts {
      type uint64;
      description
        "Number of packets dropped during packet replication in the datapath.";
    }
    leaf gen-pkt-replication-octets {
      type uint64;
      units "octets";
      description
        "Total octets in packets dropped during packet replication in the datapath.";
    }
    leaf esf-l4r-bad-config-pkts {
      type uint64;
      description
        "Number of packets dropped due to edge switching services feature (ESF) layer 4 redirect bad config.";
    }
    leaf esf-l4r-bad-config-octets {
      type uint64;
      units "octets";
      description
        "Total octets in packets dropped due to edge switching services feature (ESF) layer 4 redirect bad config.";
    }
    leaf esf-l4r-trans-unavail-pkts {
      type uint64;
      description
        "Number of packets dropped due to edge switching services feature (ESF) layer 4 redirect trans unavailable.";
    }
    leaf esf-l4r-trans-unavail-octets {
      type uint64;
      units "octets";
      description
        "Total octets in packets dropped due to edge switching services feature (ESF) layer 4 redirect trans unavailable.";
    }
    leaf esf-pbhk-bad-config-pkts {
      type uint64;
      description
        "Number of packets dropped due to edge switching services feature (ESF) port-bundle host key bad config.";
    }
    leaf esf-pbhk-bad-config-octets {
      type uint64;
      units "octets";
      description
        "Total octets for bad configuration detected for the port-bundle host key in the Edge Switching Services Feature (ESF).";
    }
    leaf esf-pbhk-unalloc-pkts {
      type uint64;
      description
        "Number of packets dropped because the port-bundle host key was not allocated in the Edge Switching Services Feature (ESF).";
    }
    leaf esf-pbhk-unalloc-octets {
      type uint64;
      units "octets";
      description
        "Total octets in packets dropped because the port-bundle host key was not allocated in the Edge Switching Services Feature (ESF).";
    }
    leaf esf-pbhk-port-unavail-pkts {
      type uint64;
      description
        "Number of packets dropped because the port associated with the port-bundle host key was unavailable in the Edge Switching Services Feature (ESF).";
    }
    leaf esf-pbhk-port-unavail-octets {
      type uint64;
      units "octets";
      description
        "Total octets in packets dropped because the port associated with the port-bundle host key was unavailable in the Edge Switching Services Feature (ESF).";
    }
    leaf esf-pbhk-port-notfound-pkts {
      type uint64;
      description
        "Number of packets dropped because the port associated with the port-bundle host key could not be found in the Edge Switching Services Feature (ESF).";
    }
    leaf esf-pbhk-port-notfound-octets {
      type uint64;
      units "octets";
      description
        "Total octets in packets dropped because the port associated with the port-bundle host key could not be found in the Edge Switching Services Feature (ESF).";
    }
    leaf esf-pbhk-port-removed-pkts {
      type uint64;
      description
        "Number of packets dropped because the port associated with the port-bundle host key was removed in the Edge Switching Services Feature (ESF).";
    }
    leaf esf-pbhk-port-removed-octets {
      type uint64;
      units "octets";
      description
        "Total octets in packets dropped because the port associated with the port-bundle host key was removed in the Edge Switching Services Feature (ESF).";
    }
    leaf mpls-no-adj-pkts {
      type uint64;
      description
        "Number of MPLS packets dropped due to missing adjacency information.";
    }
    leaf mpls-no-adj-octets {
      type uint64;
      units "octets";
      description
        "Total octets in MPLS packets dropped due to missing adjacency information.";
    }
    leaf ipv4-adj-drop-pkts {
      type uint64;
      description
        "Number of IPv4 packets dropped due to missing or invalid adjacency information during forwarding.";
    }
    leaf ipv4-adj-drop-octets {
      type uint64;
      units "octets";
      description
        "Total octets in IPv4 packets dropped due to missing or invalid adjacency information.";
    }
    leaf ipv6-adj-drop-pkts {
      type uint64;
      description
        "Number of IPv6 packets dropped due to missing or invalid adjacency information during forwarding.";
    }
    leaf ipv6-adj-drop-octets {
      type uint64;
      units "octets";
      description
        "Total octets in IPv6 packets dropped due to missing or invalid adjacency information.";
    }
    leaf mpls-adj-drop-pkts {
      type uint64;
      description
        "Number of MPLS packets dropped due to missing or invalid adjacency information during forwarding.";
    }
    leaf mpls-adj-drop-octets {
      type uint64;
      units "octets";
      description
        "Total octets in MPLS packets dropped due to missing or invalid adjacency information.";
    }
    leaf bad-adj-pkts {
      type uint64;
      description
        "Number of packets dropped due to invalid or corrupted adjacency information during forwarding.";
    }
    leaf bad-adj-octets {
      type uint64;
      units "octets";
      description
        "Total octets in packets dropped due to invalid or corrupted adjacency information.";
    }
    leaf punt-policer-drop-pkts {
      type uint64;
      description
        "Number of packets dropped by the punt policer due to exceeding the configured rate limit for punted traffic.";
    }
    leaf punt-policer-drop-octets {
      type uint64;
      units "octets";
      description
        "Total octets dropped by the punt policer in the QFP datapath.";
    }
    leaf punt-global-policer-drop-pkts {
      type uint64;
      description
        "Number of packets dropped by the punt global policer in the QFP datapath.";
    }
    leaf punt-global-policer-drop-octets {
      type uint64;
      units "octets";
      description
        "Total octets dropped by the punt global policer in the QFP datapath.";
    }
    leaf esf-tc-drop-pkts {
      type uint64;
      description
        "Number of packets dropped due to edge switching services feature (ESF) traffic classification drop.";
    }
    leaf esf-tc-drop-octets {
      type uint64;
      units "octets";
      description
        "Total octets in packets dropped due to edge switching services feature (ESF) traffic classification drop.";
    }
    leaf esf-drl-drop-pkts {
      type uint64;
      description
        "Number of packets dropped due to edge switching services feature (ESF) dynamic rate limit drop.";
    }
    leaf esf-drl-drop-octets {
      type uint64;
      units "octets";
      description
        "Total octets in packets dropped due to edge switching services feature (ESF) dynamic rate limit drop.";
    }
    leaf ess-ipsub-drop-pkts {
      type uint64;
      description
        "Number of packets dropped due to edge switching services IP subscriber drop.";
    }
    leaf ess-ipsub-drop-octets {
      type uint64;
      units "octets";
      description
        "Total octets in packets dropped due to edge switching services IP subscriber drop.";
    }
    leaf ess-ipsub-fsol-drop-pkts {
      type uint64;
      description
        "Number of packets dropped for IP subscriber sessions during the 'first sign of life' phase in Edge Switching Services (ESS).";
    }
    leaf ess-ipsub-fsol-drop-octets {
      type uint64;
      units "octets";
      description
        "Total octets dropped for IP subscriber sessions during the 'first sign of life' phase in Edge Switching Services (ESS).";
    }
    leaf ess-ipsub-classifier-drop-pkts {
      type uint64;
      description
        "Number of packets dropped by the IP subscriber classifier in Edge Switching Services (ESS) due to classification errors or policy enforcement.";
    }
    leaf ess-ipsub-classifier-drop-octets {
      type uint64;
      units "octets";
      description
        "Total octets dropped by the IP subscriber classifier in Edge Switching Services (ESS) due to classification errors or policy enforcement.";
    }
    leaf ess-ipsub-ka-drop-pkts {
      type uint64;
      description
        "Number of IP subscriber keepalive packets dropped in Edge Switching Services (ESS) because keepalive processing detected a session or protocol error.";
    }
    leaf ess-ipsub-ka-drop-octets {
      type uint64;
      units "octets";
      description
        "Total octets in IP subscriber keepalive packets dropped in Edge Switching Services (ESS) because keepalive processing detected a session or protocol error.";
    }
    leaf oam-loopback-pkts {
      type uint64;
      description
        "Number of packets dropped due to operations, administration and management (OAM) loopback.";
    }
    leaf oam-loopback-octets {
      type uint64;
      units "octets";
      description
        "Total octets in packets dropped due to operations, administration and management (OAM) loopback.";
    }
    leaf unconfigured-ipv4-fia-pkts {
      type uint64;
      description
        "Number of packets dropped due to unconfigured IPv4 feature invocation array (FIA).";
    }
    leaf unconfigured-ipv4-fia-octets {
      type uint64;
      units "octets";
      description
        "Total octets in packets dropped due to unconfigured IPv4 feature invocation array (FIA).";
    }
    leaf unconfigured-ipv6-fia-pkts {
      type uint64;
      description
        "Number of packets dropped due to unconfigured IPv6 feature invocation array (FIA).";
    }
    leaf unconfigured-ipv6-fia-octets {
      type uint64;
      units "octets";
      description
        "Total octets in IPv6 packets dropped due to an unconfigured Feature Invocation Array (FIA) on the QFP datapath.";
    }
    leaf unconfigured-mpls-fia-pkts {
      type uint64;
      description
        "Number of MPLS packets dropped due to an unconfigured Feature Invocation Array (FIA) on the QFP datapath.";
    }
    leaf unconfigured-mpls-fia-octets {
      type uint64;
      units "octets";
      description
        "Total octets in MPLS packets dropped due to an unconfigured Feature Invocation Array (FIA) on the QFP datapath.";
    }
    leaf smi-disabled-pkts {
      type uint64;
      description
        "Number of packets dropped due to simple management interface disabled.";
    }
    leaf smi-disabled-octets {
      type uint64;
      units "octets";
      description
        "Total octets in packets dropped due to simple management interface disabled.";
    }
    leaf oce-drop-adj-pkts {
      type uint64;
      description
        "Number of packets dropped due to output chain element (OCE) drop adjacency.";
    }
    leaf oce-drop-adj-octets {
      type uint64;
      units "octets";
      description
        "Total octets in packets dropped due to output chain element (OCE) drop adjacency.";
    }
    leaf internal-pkts {
      type uint64;
      description
        "Number of packets dropped as internal by the datapath.";
    }
    leaf internal-octets {
      type uint64;
      units "octets";
      description
        "Total octets in packets dropped as internal by the datapath.";
    }
    leaf inv-spa-hdr-pkts {
      type uint64;
      description
        "Number of packets dropped due to invalid shared port adaptor (SPA) header.";
    }
    leaf inv-spa-hdr-octets {
      type uint64;
      units "octets";
      description
        "Total octets in packets dropped due to invalid shared port adaptor (SPA) header.";
    }
    leaf ppe-exception-pkts {
      type uint64;
      description
        "Number of packets dropped due to exceptions in the Packet Processing Engine (PPE) within the QFP datapath.";
    }
    leaf ppe-exception-octets {
      type uint64;
      units "octets";
      description
        "Total octets in packets dropped due to exceptions in the Packet Processing Engine (PPE) within the QFP datapath.";
    }
    leaf internal-replication-pkts {
      type uint64;
      description
        "Number of packets dropped during internal replication by the datapath.";
    }
    leaf internal-replication-octets {
      type uint64;
      units "octets";
      description
        "Total octets in packets dropped during internal replication by the datapath.";
    }
    leaf internal-recycle-tail-pkts {
      type uint64;
      description
        "Number of packets tail dropped during internal recycling due to an oversubscribed queue in the datapath.";
    }
    leaf internal-recycle-tail-octets {
      type uint64;
      units "octets";
      description
        "Total octets in packets tail dropped during internal recycling due to an oversubscribed queue in the datapath.";
    }
    leaf internal-no-gpm-pkts {
      type uint64;
      description
        "Number of packets dropped due to lack of Global Packet Memory (GPM) in the datapath.";
    }
    leaf internal-no-gpm-octets {
      type uint64;
      units "octets";
      description
        "Total octets in packets dropped due to lack of Global Packet Memory (GPM) in the datapath.";
    }
    leaf internal-no-channel-mem-pkts {
      type uint64;
      description
        "Number of packets dropped due to lack of channel memory in the datapath.";
    }
    leaf internal-no-channel-mem-octets {
      type uint64;
      units "octets";
      description
        "Total octets in packets dropped due to lack of channel memory in the datapath.";
    }
    leaf ip-sia-hdr-err-pkts {
      type uint64;
      description
        "Number of packets dropped due to IP service insertion architecture (SIA) header error.";
    }
    leaf ip-sia-hdr-err-octets {
      type uint64;
      units "octets";
      description
        "Total octets in packets dropped due to IP service insertion architecture (SIA) header error.";
    }
    leaf ip-sia-hop-limit-exceeded-pkts {
      type uint64;
      description
        "Number of packets dropped due to IP service insertion architecture (SIA) hop limit exceeded.";
    }
    leaf ip-sia-hop-limit-exceeded-octets {
      type uint64;
      units "octets";
      description
        "Total octets in packets dropped due to IP service insertion architecture (SIA) hop limit exceeded.";
    }
    leaf ip-sia-processing-err-pkts {
      type uint64;
      description
        "Number of packets dropped due to IP service insertion architecture (SIA) processing error.";
    }
    leaf ip-sia-processing-err-octets {
      type uint64;
      units "octets";
      description
        "Total octets in packets dropped due to IP service insertion architecture (SIA) processing error.";
    }
    leaf sslvpn-svi-invalid-h-pkts {
      type uint64;
      description
        "Number of packets dropped due to SSL VPN switched virtual interface (SVI) invalid header.";
    }
    leaf sslvpn-svi-invalid-h-octets {
      type uint64;
      units "octets";
      description
        "Total octets in packets dropped due to SSL VPN switched virtual interface (SVI) invalid header.";
    }
    leaf esf-acct-exceed-drop-pkts {
      type uint64;
      description
        "Number of packets dropped due to edge switching services feature (ESF) accounting exceed drop.";
    }
    leaf esf-acct-exceed-drop-octets {
      type uint64;
      units "octets";
      description
        "Total octets in packets dropped due to edge switching services feature (ESF) accounting exceed drop.";
    }
    leaf tcp-pkts {
      type uint64;
      description
        "Number of TCP packets dropped by the QFP.";
    }
    leaf tcp-octets {
      type uint64;
      units "octets";
      description
        "Total octets in TCP packets dropped by the QFP.";
    }
    leaf invalid-encap-pkts {
      type uint64;
      description
        "Number of packets dropped due to invalid encapsulation in the datapath.";
    }
    leaf invalid-encap-octets {
      type uint64;
      units "octets";
      description
        "Total octets in packets dropped due to invalid encapsulation in the datapath.";
    }
    leaf dsp-pkts {
      type uint64;
      description
        "Number of packets dropped due to digital signal processing (DSP).";
    }
    leaf dsp-octets {
      type uint64;
      units "octets";
      description
        "Total octets in packets dropped due to digital signal processing (DSP).";
    }
    leaf mpls-csc-drop-pkts {
      type uint64;
      description
        "Number of packets dropped due to multiprotocol label switching (MPLS) carrier supporting carrier drop.";
    }
    leaf mpls-csc-drop-octets {
      type uint64;
      units "octets";
      description
        "Total octets in packets dropped due to multiprotocol label switching (MPLS) carrier supporting carrier drop.";
    }
    leaf cstp-cdtp-inv-frame-pkts {
      type uint64;
      description
        "Number of invalid frame packets dropped by Cisco SSL Tunneling Protocol (CSTP) and Cisco DTLS Tunneling Protocol (CDTP) by the QFP.";
    }
    leaf cstp-cdtp-inv-frame-octets {
      type uint64;
      units "octets";
      description
        "Total octets in invalid frames dropped by Cisco SSL Tunneling Protocol (CSTP) and Cisco DTLS Tunneling Protocol (CDTP) on the datapath.";
    }
    leaf cstp-cdtp-no-tunnel-pkts {
      type uint64;
      description
        "Number of packets for Cisco SSL Tunneling Protocol (CSTP) and Cisco DTLS Tunneling Protocol (CDTP) dropped because they were not associated with any tunnel on the datapath.";
    }
    leaf cstp-cdtp-no-tunnel-octets {
      type uint64;
      units "octets";
      description
        "Total octets in packets for Cisco SSL Tunneling Protocol (CSTP) and Cisco DTLS Tunneling Protocol (CDTP) dropped because they were not associated with any tunnel on the datapath.";
    }
    leaf cstp-cdtp-unsup-frame-pkts {
      type uint64;
      description
        "Number of packets with unsupported frame types dropped by Cisco SSL Tunneling Protocol (CSTP) and Cisco DTLS Tunneling Protocol (CDTP) on the datapath.";
    }
    leaf cstp-cdtp-unsup-frame-octets {
      type uint64;
      units "octets";
      description
        "Total octets in unsupported frame types dropped by Cisco SSL Tunneling Protocol (CSTP) and Cisco DTLS Tunneling Protocol (CDTP) on the datapath.";
    }
    leaf esf-l4r-trans-sess-limit-pkts {
      type uint64;
      description
        "Number of packets dropped due to edge switching services feature (ESF) layer 4 redirect trans session limit.";
    }
    leaf esf-l4r-trans-sess-limit-octets {
      type uint64;
      units "octets";
      description
        "Total octets in packets dropped due to edge switching services feature (ESF) layer 4 redirect trans session limit.";
    }
    leaf lisp-elig-oce-pkts {
      type uint64;
      description
        "Number of packets dropped due to LISP eligible output chain element (OCE).";
    }
    leaf lisp-elig-oce-octets {
      type uint64;
      units "octets";
      description
        "Total octets in packets dropped due to LISP eligible output chain element (OCE).";
    }
    leaf lisp-misconfiguration-pkts {
      type uint64;
      description
        "Number of packets dropped due to LISP misconfiguration.";
    }
    leaf lisp-misconfiguration-octets {
      type uint64;
      units "octets";
      description
        "Total octets dropped due to LISP (Locator/ID Separation Protocol) misconfiguration events on the QFP datapath.";
    }
    leaf lisp-disabled-pkts {
      type uint64;
      description
        "Number of packets dropped because LISP (Locator/ID Separation Protocol) is disabled on the QFP datapath.";
    }
    leaf lisp-disabled-octets {
      type uint64;
      units "octets";
      description
        "Total octets dropped because LISP (Locator/ID Separation Protocol) is disabled on the QFP datapath.";
    }
    leaf lisp-decap-failed-pkts {
      type uint64;
      description
        "Number of packets dropped due to LISP deencapsulation failed.";
    }
    leaf lisp-decap-failed-octets {
      type uint64;
      units "octets";
      description
        "Total octets in packets dropped due to LISP deencapsulation failed.";
    }
    leaf lisp-hash-lkup-failed-pkts {
      type uint64;
      description
        "Number of packets dropped due to LISP hash lookup failed.";
    }
    leaf lisp-hash-lkup-failed-octets {
      type uint64;
      units "octets";
      description
        "Total octets in packets dropped due to LISP hash lookup failed.";
    }
    leaf lisp-failed-to-punt-lsb-mismatch-pkts {
      type uint64;
      description
        "Number of packets that failed to be punted due to LISP (Locator/ID Separation Protocol) LSB (Least Significant Bit) mismatch on the QFP datapath.";
    }
    leaf lisp-failed-to-punt-lsb-mismatch-octets {
      type uint64;
      units "octets";
      description
        "Total octets in packets that failed to be punted due to LISP (Locator/ID Separation Protocol) LSB (Least Significant Bit) mismatch on the QFP datapath.";
    }
    leaf nat64-v6tov4-pkts {
      type uint64;
      description
        "Number of packets dropped because NAT64 translation from IPv6 to IPv4 could not be completed on the QFP datapath.";
    }
    leaf nat64-v6tov4-octets {
      type uint64;
      units "octets";
      description
        "Total octets in packets dropped because NAT64 translation from IPv6 to IPv4 could not be completed on the QFP datapath.";
    }
    leaf nat64-v4tov6-pkts {
      type uint64;
      description
        "Number of packets dropped during NAT64 translation from IPv4 to IPv6 on the QFP datapath.";
    }
    leaf nat64-v4tov6-octets {
      type uint64;
      units "octets";
      description
        "Total octets in packets dropped during NAT64 translation from IPv4 to IPv6 on the QFP datapath.";
    }
    leaf tunnel-sec-chk-fail-pkts {
      type uint64;
      description
        "Number of packets dropped due to tunnel security check failures on the QFP datapath.";
    }
    leaf tunnel-sec-chk-fail-octets {
      type uint64;
      units "octets";
      description
        "Total octets dropped by the QFP due to tunnel security check failures.";
    }
    leaf servicewire-hdr-err-pkts {
      type uint64;
      description
        "Number of packets dropped due to servicewire header errors on the QFP datapath.";
    }
    leaf servicewire-hdr-err-octets {
      type uint64;
      units "octets";
      description
        "Total octets in packets with Servicewire header errors dropped by the QFP.";
    }
    leaf servicewire-hop-limit-exceeded-pkts {
      type uint64;
      description
        "Number of packets dropped due to exceeding the Servicewire hop limit on the QFP datapath.";
    }
    leaf servicewire-hop-limit-exceeded-octets {
      type uint64;
      units "octets";
      description
        "Total octets in packets dropped by the QFP due to exceeding the Servicewire hop limit.";
    }
    leaf servicewire-processing-err-pkts {
      type uint64;
      description
        "Number of packets dropped due to servicewire processing errors on the QFP datapath.";
    }
    leaf servicewire-processing-err-octets {
      type uint64;
      units "octets";
      description
        "Total octets in packets dropped due to servicewire processing errors on the QFP datapath.";
    }
    leaf l2bd-pkts {
      type uint64;
      description
        "Number of packets dropped within the Layer 2 Bridge Domain (L2BD) by the QFP.";
    }
    leaf l2bd-octets {
      type uint64;
      units "octets";
      description
        "Total octets dropped within the Layer 2 Bridge Domain (L2BD) by the QFP.";
    }
    leaf tcp-bp-sslvpn-pkts {
      type uint64;
      description
        "Number of SSL VPN packets over TCP dropped due to back pressure conditions in the QFP.";
    }
    leaf tcp-bp-sslvpn-octets {
      type uint64;
      units "octets";
      description
        "Total octets in SSL VPN traffic over TCP dropped due to back pressure conditions in the QFP.";
    }
    leaf evc-efp-egress-filter-pkts {
      type uint64;
      description
        "Number of packets dropped due to ethernet virtual connection (EVC) ethernet flowpoint (EFP) egress filter.";
    }
    leaf evc-efp-egress-filter-octets {
      type uint64;
      units "octets";
      description
        "Total octets in packets dropped due to ethernet virtual connection (EVC) ethernet flowpoint (EFP) egress filter.";
    }
    leaf sslvpn-svi-if-err-pkts {
      type uint64;
      description
        "Number of packets dropped due to SSL VPN switched virtual interface (SVI) interface error.";
    }
    leaf sslvpn-svi-if-err-octets {
      type uint64;
      units "octets";
      description
        "Total octets in packets dropped due to SSL VPN switched virtual interface (SVI) interface error.";
    }
    leaf sslvpn-ctx-null-pkts {
      type uint64;
      description
        "Number of SSL VPN packets for which the context (CTX) was null or missing, causing the packet to be dropped by the QFP.";
    }
    leaf sslvpn-ctx-null-octets {
      type uint64;
      units "octets";
      description
        "Total octets in SSL VPN sessions where the context is null (uninitialized or missing).";
    }
    leaf sslvpn-ctx-not-alive-pkts {
      type uint64;
      description
        "Number of SSL VPN packets dropped because the context is not alive (inactive or terminated session).";
    }
    leaf sslvpn-ctx-not-alive-octets {
      type uint64;
      units "octets";
      description
        "Total octets in SSL VPN sessions where the context is not alive (inactive or terminated session).";
    }
    leaf sslvpn-invalid-pkt-pkts {
      type uint64;
      description
        "Number of packets dropped due to SSL VPN invalid.";
    }
    leaf sslvpn-invalid-pkt-octets {
      type uint64;
      units "octets";
      description
        "Total octets in packets dropped due to SSL VPN invalid packet.";
    }
    leaf sslvpn-socket-wr-err-pkts {
      type uint64;
      description
        "Number of packets dropped due to SSL VPN socket write error.";
    }
    leaf sslvpn-socket-wr-err-octets {
      type uint64;
      units "octets";
      description
        "Total octets in packets dropped due to SSL VPN socket write error.";
    }
    leaf sslvpn-pkt-rc-err-pkts {
      type uint64;
      description
        "Number of packets dropped due to SSL VPN packet return code error.";
    }
    leaf sslvpn-pkt-rc-err-octets {
      type uint64;
      units "octets";
      description
        "Total octets in packets dropped due to SSL VPN packet return code error.";
    }
    leaf sslvpn-null-rc-pkts {
      type uint64;
      description
        "Number of packets dropped due to SSL VPN null return code.";
    }
    leaf sslvpn-null-rc-octets {
      type uint64;
      units "octets";
      description
        "Total octets in SSL VPN packets that were dropped due to a null return code, indicating an error or unrecognized response in SSL VPN processing.";
    }
    leaf sslvpn-wrong-pkt-type-pkts {
      type uint64;
      description
        "Number of SSL VPN packets dropped due to an incorrect or unexpected packet type.";
    }
    leaf sslvpn-wrong-pkt-type-octets {
      type uint64;
      units "octets";
      description
        "Total octets in SSL VPN packets dropped due to an incorrect or unexpected packet type.";
    }
    leaf sslvpn-not-ssl-record-pkts {
      type uint64;
      description
        "Number of SSL VPN packets received that do not conform to the SSL record format.";
    }
    leaf sslvpn-not-ssl-record-octets {
      type uint64;
      units "octets";
      description
        "Total octets in SSL VPN packets that do not conform to the SSL record format.";
    }
    leaf firewall-syncookie-pkts {
      type uint64;
      description
        "Number of packets dropped by the firewall SYN cookie protection to mitigate SYN flood attacks.";
    }
    leaf firewall-syncookie-octets {
      type uint64;
      units "octets";
      description
        "Total octets in packets dropped by the firewall SYN cookie protection.";
    }
    leaf l2bd-mac-security-violation-pkts {
      type uint64;
      description
        "Number of packets dropped due to layer 2 Bridge Domain (L2BD) MAC security violation.";
    }
    leaf l2bd-mac-security-violation-octets {
      type uint64;
      units "octets";
      description
        "Total octets in packets dropped due to layer 2 Bridge Domain (L2BD) MAC security violation.";
    }
    leaf l2bd-src-filter-pkts {
      type uint64;
      description
        "Number of packets dropped due to layer 2 Bridge Domain (L2BD) source filter.";
    }
    leaf l2bd-src-filter-octets {
      type uint64;
      units "octets";
      description
        "Total octets dropped by the source filter in the Layer 2 Bridge Domain (L2BD) on the QFP datapath.";
    }
    leaf l2bd-policy-pkts {
      type uint64;
      description
        "Number of packets dropped by policy actions within the Layer 2 Bridge Domain (L2BD) on the QFP datapath.";
    }
    leaf l2bd-policy-octets {
      type uint64;
      units "octets";
      description
        "Total octets dropped by policy actions within the Layer 2 Bridge Domain (L2BD) on the QFP datapath.";
    }
    leaf l2bd-repl-start-pkts {
      type uint64;
      description
        "Number of packets dropped at the start of replication within the Layer 2 Bridge Domain (L2BD) on the QFP datapath.";
    }
    leaf l2bd-repl-start-octets {
      type uint64;
      units "octets";
      description
        "Total octets dropped at the start of replication within the Layer 2 Bridge Domain (L2BD) on the QFP datapath.";
    }
    leaf l2bd-repl-end-pkts {
      type uint64;
      description
        "Number of packets dropped at the end of replication within the Layer 2 Bridge Domain (L2BD) on the QFP datapath.";
    }
    leaf l2bd-repl-end-octets {
      type uint64;
      units "octets";
      description
        "Total octets dropped at the end of replication within the Layer 2 Bridge Domain (L2BD) on the QFP datapath.";
    }
    leaf l2bd-recycle-tail-pkts {
      type uint64;
      description
        "Number of packets dropped at the recycle tail stage within the Layer 2 Bridge Domain (L2BD) on the QFP datapath.";
    }
    leaf l2bd-recycle-tail-octets {
      type uint64;
      units "octets";
      description
        "Total octets dropped at the recycle tail stage within the Layer 2 Bridge Domain (L2BD) on the QFP datapath.";
    }
    leaf l2bd-static-mac-move-pkts {
      type uint64;
      description
        "Number of packets dropped due to static MAC address moves within the Layer 2 Bridge Domain (L2BD) on the QFP datapath.";
    }
    leaf l2bd-static-mac-move-octets {
      type uint64;
      units "octets";
      description
        "Total octets dropped due to static MAC address moves within the Layer 2 Bridge Domain (L2BD).";
    }
    leaf l2bd-bd-disabled-pkts {
      type uint64;
      description
        "Number of packets dropped because the Layer 2 Bridge Domain (L2BD) is administratively disabled.";
    }
    leaf l2bd-bd-disabled-octets {
      type uint64;
      units "octets";
      description
        "Total octets in packets dropped because the Layer 2 Bridge Domain (L2BD) is administratively disabled.";
    }
    leaf l2bd-inject-no-sb-pkts {
      type uint64;
      description
        "Number of packets injected into the Layer 2 Bridge Domain (L2BD) that do not have an associated sub-block.";
    }
    leaf l2bd-inject-no-sb-octets {
      type uint64;
      units "octets";
      description
        "Total octets in packets dropped in the Layer 2 Bridge Domain (L2BD) because they lacked an associated sub-block.";
    }
    leaf l2bd-inject-invalid-pkts {
      type uint64;
      description
        "Number of invalid packets injected into the Layer 2 Bridge Domain (L2BD).";
    }
    leaf l2bd-inject-invalid-octets {
      type uint64;
      units "octets";
      description
        "Total octets in invalid packets injected into the Layer 2 Bridge Domain (L2BD).";
    }
    leaf l2bd-stp-state-pkts {
      type uint64;
      description
        "Number of packets dropped due to layer 2 Bridge Domain (L2BD) spanning tree (STP) state.";
    }
    leaf l2bd-stp-state-octets {
      type uint64;
      units "octets";
      description
        "Total octets in packets dropped due to layer 2 Bridge Domain (L2BD) spanning tree (STP) state.";
    }
    leaf l2bd-storm-ctrl-pkts {
      type uint64;
      description
        "Number of packets in the Layer 2 Bridge Domain (L2BD) that have been dropped by storm control mechanisms, such as those dropped due to broadcast, multicast, or unknown unicast storms.";
    }
    leaf l2bd-storm-ctrl-octets {
      type uint64;
      units "octets";
      description
        "Total octets dropped by storm control mechanisms in the Layer 2 Bridge Domain (L2BD).";
    }
    leaf sslvpn-coprocessor-err-pkts {
      type uint64;
      description
        "Number of packets dropped due to SSL VPN coprocessor error.";
    }
    leaf sslvpn-coprocessor-err-octets {
      type uint64;
      units "octets";
      description
        "Total octets in packets dropped due to SSL VPN coprocessor error.";
    }
    leaf sslvpn-tail-drop-pkts {
      type uint64;
      description
        "Number of packets dropped due to SSL VPN tail drop.";
    }
    leaf sslvpn-tail-drop-octets {
      type uint64;
      units "octets";
      description
        "Total octets in packets dropped due to SSL VPN tail drop.";
    }
    leaf ecfm-pkts {
      type uint64;
      description
        "Number of packets dropped due to ethernet connection fault management (ECFM).";
    }
    leaf ecfm-octets {
      type uint64;
      units "octets";
      description
        "Total octets in packets dropped due to ethernet connection fault management (ECFM).";
    }
    leaf ipv4mc-oif-rpf-failed-pkts {
      type uint64;
      description
        "Number of packets dropped due to IPv4 multicast output interface reverse path forwarding failed.";
    }
    leaf ipv4mc-oif-rpf-failed-octets {
      type uint64;
      units "octets";
      description
        "Total octets in packets dropped due to IPv4 multicast output interface reverse path forwarding failed.";
    }
    leaf ipv6mc-oif-rpf-failed-pkts {
      type uint64;
      description
        "Number of packets dropped due to IPv6 multicast output interface reverse path forwarding failed.";
    }
    leaf ipv6mc-oif-rpf-failed-octets {
      type uint64;
      units "octets";
      description
        "Total octets in packets dropped due to IPv6 multicast output interface reverse path forwarding failed.";
    }
    leaf ipv6-pbr-pkts {
      type uint64;
      description
        "Number of IPv6 packets dropped by policy-based routing (PBR) on the QFP.";
    }
    leaf ipv6-pbr-octets {
      type uint64;
      units "octets";
      description
        "Total octets in IPv6 packets dropped by policy-based routing (PBR) on the QFP.";
    }
    leaf sslvpn-coprocessor-state-not-set-pkts {
      type uint64;
      description
        "Number of packets dropped due to SSL VPN coprocessor state not set.";
    }
    leaf sslvpn-coprocessor-state-not-set-octets {
      type uint64;
      units "octets";
      description
        "Total octets in packets dropped due to SSL VPN coprocessor state not set.";
    }
    leaf sslvpn-coprocessor-state-reply-not-set-pkts {
      type uint64;
      description
        "Number of packets dropped due to SSL VPN coprocessor state reply not set.";
    }
    leaf sslvpn-coprocessor-state-reply-not-set-octets {
      type uint64;
      units "octets";
      description
        "Total octets in packets dropped due to SSL VPN coprocessor state reply not set.";
    }
    leaf sslvpn-neg-ssl-rec-pad-len-pkts {
      type uint64;
      description
        "Number of packets dropped due to SSL VPN negotiated SSL record pad length.";
    }
    leaf sslvpn-neg-ssl-rec-pad-len-octets {
      type uint64;
      units "octets";
      description
        "Total octets in packets dropped due to SSL VPN negotiated SSL record pad length.";
    }
    leaf sslvpn-inv-ssl-rec-pkts {
      type uint64;
      description
        "Number of packets dropped due to SSL VPN invalid SSL record.";
    }
    leaf sslvpn-inv-ssl-rec-octets {
      type uint64;
      units "octets";
      description
        "Total octets in SSL VPN traffic that were identified as part of invalid SSL records dropped by the QFP datapath.";
    }
    leaf sslvpn-not-ssl-rec-rc-pkts {
      type uint64;
      description
        "Number of packets in SSL VPN traffic for which the QFP datapath returned a code indicating the data was not a valid SSL record.";
    }
    leaf sslvpn-not-ssl-rec-rc-octets {
      type uint64;
      units "octets";
      description
        "Total octets in SSL VPN traffic for which the QFP datapath returned a code indicating the data was not a valid SSL record.";
    }
    leaf sslvpn-ssl-rec-not-pkt-pkts {
      type uint64;
      description
        "Number of packets in SSL VPN traffic that were expected to be SSL records but were not recognized as valid SSL packets by the QFP datapath.";
    }
    leaf sslvpn-ssl-rec-not-pkt-octets {
      type uint64;
      units "octets";
      description
        "Total octets in SSL VPN traffic that were expected to be SSL records but were not recognized as valid SSL packets by the QFP datapath.";
    }
    leaf sslvpn-add-ssl-rec-hdr-err-pkts {
      type uint64;
      description
        "Number of SSL VPN packets dropped due to errors while adding an SSL record header on the QFP datapath.";
    }
    leaf sslvpn-add-ssl-rec-hdr-err-octets {
      type uint64;
      units "octets";
      description
        "Total octets in SSL VPN packets dropped due to errors while adding an SSL record header on the QFP datapath.";
    }
    leaf sslvpn-null-session-pkts {
      type uint64;
      description
        "Number of SSL VPN packets dropped due to a null (uninitialized or invalid) session on the QFP datapath.";
    }
    leaf sslvpn-null-session-octets {
      type uint64;
      units "octets";
      description
        "Total octets in SSL VPN packets dropped due to a null (uninitialized or invalid) session on the QFP datapath.";
    }
    leaf sslvpn-invalid-session-pkts {
      type uint64;
      description
        "Number of packets in SSL VPN traffic that were dropped due to an invalid session as determined by the QFP datapath.";
    }
    leaf sslvpn-invalid-session-octets {
      type uint64;
      units "octets";
      description
        "Total octets for invalid SSL VPN sessions dropped by the QFP datapath.";
    }
    leaf sslvpn-empty-pkt-pkts {
      type uint64;
      description
        "Number of SSL VPN packets with no payload (empty packets) dropped by the QFP datapath.";
    }
    leaf sslvpn-empty-pkt-octets {
      type uint64;
      units "octets";
      description
        "Total octets in SSL VPN packets with no payload (empty packets) dropped by the QFP datapath.";
    }
    leaf ipv4-reass-tail-drop-pkts {
      type uint64;
      description
        "Number of packets dropped due to IPv4 reassembly tail drop.";
    }
    leaf ipv4-reass-tail-drop-octets {
      type uint64;
      units "octets";
      description
        "Total octets in packets dropped due to IPv4 reassembly tail drop.";
    }
    leaf ipv6-reass-tail-drop-pkts {
      type uint64;
      description
        "Number of packets dropped due to IPv6 reassembly tail drop.";
    }
    leaf ipv6-reass-tail-drop-octets {
      type uint64;
      units "octets";
      description
        "Total octets in packets dropped due to IPv6 reassembly tail drop.";
    }
    leaf ipv4mc-nat-in2out-pkts {
      type uint64;
      description
        "Number of packets dropped due to IPv4 multicast NAT in to out.";
    }
    leaf ipv4mc-nat-in2out-octets {
      type uint64;
      units "octets";
      description
        "Total octets in packets dropped due to IPv4 multicast NAT in to out.";
    }
    leaf ipv4mc-nat-out2in-pkts {
      type uint64;
      description
        "Number of packets dropped due to IPv4 multicast NAT out to in.";
    }
    leaf ipv4mc-nat-out2in-octets {
      type uint64;
      units "octets";
      description
        "Total octets in IPv4 multicast packets dropped during out-to-in Network Address Translation (NAT) processing on the QFP datapath.";
    }
    leaf fia-error-pkts {
      type uint64;
      description
        "Number of packets dropped due to a feature invocation array (FIA) error in the datapath.";
    }
    leaf fia-error-octets {
      type uint64;
      units "octets";
      description
        "Total octets in packets dropped due to a feature invocation array (FIA) error in the datapath.";
    }
    leaf firewall-syncookie-max-dst-pkts {
      type uint64;
      description
        "Number of packets dropped because they exceeded the maximum destination threshold during firewall syncookie protection.";
    }
    leaf firewall-syncookie-max-dst-octets {
      type uint64;
      units "octets";
      description
        "Total octets dropped because they exceeded the maximum destination threshold during firewall syncookie protection.";
    }
    leaf ipv4-urpf-loose-failed-pkts {
      type uint64;
      description
        "Number of packets dropped due to IPv4 unicast reverse path forwarding loose failed.";
    }
    leaf ipv4-urpf-loose-failed-octets {
      type uint64;
      units "octets";
      description
        "Total octets in packets dropped due to IPv4 unicast reverse path forwarding loose failed.";
    }
    leaf ipv4-urpf-strict-failed-pkts {
      type uint64;
      description
        "Number of packets dropped due to IPv4 unicast reverse path forwarding strict failed.";
    }
    leaf ipv4-urpf-strict-failed-octets {
      type uint64;
      units "octets";
      description
        "Total octets in packets dropped due to IPv4 unicast reverse path forwarding strict failed.";
    }
    leaf ipv6-urpf-loose-failed-pkts {
      type uint64;
      description
        "Number of packets dropped due to IPv6 unicast reverse path forwarding loose failed.";
    }
    leaf ipv6-urpf-loose-failed-octets {
      type uint64;
      units "octets";
      description
        "Total octets in IPv6 unicast packets that failed reverse path forwarding (uRPF) checks in loose mode on the QFP datapath.";
    }
    leaf ipv6-urpf-strict-failed-pkts {
      type uint64;
      description
        "Number of IPv6 unicast packets that failed reverse path forwarding (uRPF) checks in strict mode on the QFP datapath.";
    }
    leaf ipv6-urpf-strict-failed-octets {
      type uint64;
      units "octets";
      description
        "Total octets in IPv6 unicast packets that failed reverse path forwarding (uRPF) checks in strict mode on the QFP datapath.";
    }
    leaf ipv6-urpf-null-path-list-pkts {
      type uint64;
      description
        "Number of IPv6 unicast packets dropped because reverse path forwarding (uRPF) checks returned a null path list on the QFP datapath.";
    }
    leaf ipv6-urpf-null-path-list-octets {
      type uint64;
      units "octets";
      description
        "Total octets in IPv6 unicast packets dropped because reverse path forwarding (uRPF) checks returned a null path list on the QFP datapath.";
    }
    leaf ipv6-urpf-no-fib-pkts {
      type uint64;
      description
        "Number of IPv6 unicast packets that failed reverse path forwarding (uRPF) checks due to missing FIB entries on the QFP datapath.";
    }
    leaf ipv6-urpf-no-fib-octets {
      type uint64;
      units "octets";
      description
        "Total octets in IPv6 unicast packets that failed reverse path forwarding (uRPF) checks due to missing FIB entries on the QFP datapath.";
    }
    leaf unknown-mcast-pkt-type-pkts {
      type uint64;
      description
        "Number of multicast packets with unknown or unsupported packet types dropped by the QFP datapath.";
    }
    leaf unknown-mcast-pkt-type-octets {
      type uint64;
      units "octets";
      description
        "Total octets in multicast packets with unknown or unsupported packet types dropped by the QFP datapath.";
    }
    leaf l2v4mc-invalid-replica-record-pkts {
      type uint64;
      description
        "Number of Layer 2 IPv4 multicast packets with invalid replica records dropped by the QFP datapath.";
    }
    leaf l2v4mc-invalid-replica-record-octets {
      type uint64;
      units "octets";
      description
        "Total octets in Layer 2 IPv4 multicast packets that were identified as invalid replica records by the QFP datapath.";
    }
    leaf l2v6mc-invalid-replica-record-pkts {
      type uint64;
      description
        "Number of Layer 2 IPv6 multicast packets that were classified as invalid replica records by the QFP datapath.";
    }
    leaf l2v6mc-invalid-replica-record-octets {
      type uint64;
      units "octets";
      description
        "Total octets in Layer 2 IPv6 multicast packets that were identified as invalid replica records by the QFP datapath.";
    }
    leaf l2mc-invalid-replica-record-pkts {
      type uint64;
      description
        "Number of Layer 2 multicast packets that were identified as invalid replica records by the QFP datapath.";
    }
    leaf l2mc-invalid-replica-record-octets {
      type uint64;
      units "octets";
      description
        "Total octets in Layer 2 multicast packets that were identified as invalid replica records by the QFP datapath.";
    }
    leaf lsm-invalid-replica-record-pkts {
      type uint64;
      description
        "Number of label switched multicast (LSM) packets that were identified as invalid replica records by the QFP datapath.";
    }
    leaf lsm-invalid-replica-record-octets {
      type uint64;
      units "octets";
      description
        "Total octets in label switched multicast (LSM) packets that were identified as invalid replica records by the QFP datapath.";
    }
    leaf cts-format-pkts {
      type uint64;
      description
        "Number of packets dropped due to Cisco TrustSec format.";
    }
    leaf cts-format-octets {
      type uint64;
      units "octets";
      description
        "Total octets in packets dropped due to Cisco TrustSec format.";
    }
    leaf cts-not-enable-pkts {
      type uint64;
      description
        "Number of packets dropped because Cisco TrustSec (CTS) is not enabled on the interface.";
    }
    leaf cts-not-enable-octets {
      type uint64;
      units "octets";
      description
        "Total octets dropped because Cisco TrustSec (CTS) is not enabled on the interface.";
    }
    leaf idle-packet-pkts {
      type uint64;
      description
        "Number of idle packets dropped by the datapath.";
    }
    leaf idle-packet-octets {
      type uint64;
      units "octets";
      description
        "Total octets in idle packets dropped by the datapath.";
    }
    leaf mfr-pkts {
      type uint64;
      description
        "Number of packets dropped due to multilink frame relay.";
    }
    leaf mfr-octets {
      type uint64;
      units "octets";
      description
        "Total octets in packets dropped due to multilink frame relay.";
    }
    leaf ar-tx-pkts {
      type uint64;
      description
        "Number of packets dropped due to asymmetric routing transmit.";
    }
    leaf ar-tx-octets {
      type uint64;
      units "octets";
      description
        "Total octets in packets dropped due to asymmetric routing transmit.";
    }
    leaf ar-rx-pkts {
      type uint64;
      description
        "Number of packets dropped due to asymmetric routing receive.";
    }
    leaf ar-rx-octets {
      type uint64;
      units "octets";
      description
        "Total octets in packets dropped due to asymmetric routing receive.";
    }
    leaf ar-standby-pkts {
      type uint64;
      description
        "Number of packets dropped due to asymmetric routing standby.";
    }
    leaf ar-standby-octets {
      type uint64;
      units "octets";
      description
        "Total octets dropped in standby mode for asymmetric routing flows on the QFP datapath.";
    }
    leaf ar-fnf-clnup-pkts {
      type uint64;
      description
        "Number of packets dropped during Flexible NetFlow cleanup in the context of asymmetric routing on the QFP datapath.";
    }
    leaf ar-fnf-clnup-octets {
      type uint64;
      units "octets";
      description
        "Total octets dropped during Flexible NetFlow cleanup for asymmetric routing flows on the QFP datapath.";
    }
    leaf mac-mcast-ip-nonmcast-pkts {
      type uint64;
      description
        "Number of packets with a MAC multicast address but not an IP multicast address dropped by the QFP datapath.";
    }
    leaf mac-mcast-ip-nonmcast-octets {
      type uint64;
      units "octets";
      description
        "Total octets in packets with a MAC multicast address but not an IP multicast address dropped by the QFP datapath.";
    }
    leaf bfd-pkts {
      type uint64;
      description
        "Number of packets dropped due to bidirectional fault detection (BFD).";
    }
    leaf bfd-octets {
      type uint64;
      units "octets";
      description
        "Total octets in packets dropped due to bidirectional fault detection (BFD).";
    }
    leaf bundle-oce-pkts {
      type uint64;
      description
        "Number of packets dropped due to bundle output chain element (OCE).";
    }
    leaf bundle-oce-octets {
      type uint64;
      units "octets";
      description
        "Total octets in packets dropped due to bundle output chain element (OCE).";
    }
    leaf bqs-oor-pri-pkts {
      type uint64;
      description
        "Number of priority packets dropped due to buffering, queuing, and scheduling (BQS) out-of-resources conditions in the QFP datapath.";
    }
    leaf bqs-oor-pri-octets {
      type uint64;
      units "octets";
      description
        "Total octets for priority traffic that were dropped due to buffering, queuing, and scheduling (BQS) running out of resources on the QFP datapath.";
    }
    leaf bqs-oor-pak-pri-pkts {
      type uint64;
      description
        "Number of priority packets dropped due to buffering, queuing, and scheduling (BQS) running out of resources for packet priority traffic on the QFP datapath.";
    }
    leaf bqs-oor-pak-pri-octets {
      type uint64;
      units "octets";
      description
        "Total octets for packet priority traffic dropped due to buffering, queuing, and scheduling (BQS) running out of resources on the QFP datapath.";
    }
    leaf bqs-oor-vital-pkts {
      type uint64;
      description
        "Number of vital packets dropped due to buffering, queuing, and scheduling (BQS) running out of resources on the QFP datapath.";
    }
    leaf bqs-oor-vital-octets {
      type uint64;
      units "octets";
      description
        "Total octets for vital traffic dropped due to buffering, queuing, and scheduling (BQS) running out of resources on the QFP datapath.";
    }
    leaf epc-pkts {
      type uint64;
      description
        "Number of packets dropped due to embedded packet capture.";
    }
    leaf epc-octets {
      type uint64;
      units "octets";
      description
        "Total octets in packets dropped due to embedded packet capture.";
    }
    leaf lisp-failed-to-punt-dynmaic-eid-config-pkts {
      type uint64;
      description
        "Number of LISP dynamic Endpoint Identifier (EID) configuration packets that failed to be punted from the QFP datapath.";
    }
    leaf lisp-failed-to-punt-dynmaic-eid-config-octets {
      type uint64;
      units "octets";
      description
        "Total octets in LISP dynamic Endpoint Identifier (EID) configuration packets that failed to be punted from the QFP datapath.";
    }
    leaf sv-match-fail-pkts {
      type uint64;
      description
        "Number of packets that failed Service Validation (SV) match checks on the QFP datapath.";
    }
    leaf sv-match-fail-octets {
      type uint64;
      units "octets";
      description
        "Total octets for which the Service Vector (SV) match failed during packet processing in the QFP datapath.";
    }
    leaf cblbf-null-repllist-pkts {
      type uint64;
      description
        "Number of packets dropped due to cable bundle flood null replication list.";
    }
    leaf cblbf-null-repllist-octets {
      type uint64;
      units "octets";
      description
        "Total octets in packets dropped due to cable bundle flood null replication list.";
    }
    leaf cblbf-repl-fail-pkts {
      type uint64;
      description
        "Number of packets dropped due to cable bundle flood replication fail.";
    }
    leaf cblbf-repl-fail-octets {
      type uint64;
      units "octets";
      description
        "Total octets in packets dropped due to cable bundle flood replication fail.";
    }
    leaf cblbf-repl-start-pkts {
      type uint64;
      description
        "Number of packets dropped due to cable bundle flood replication start.";
    }
    leaf cblbf-repl-start-octets {
      type uint64;
      units "octets";
      description
        "Total octets in packets dropped due to cable bundle flood replication start.";
    }
    leaf cblbf-repl-end-pkts {
      type uint64;
      description
        "Number of packets dropped due to cable bundle flood replication end.";
    }
    leaf cblbf-repl-end-octets {
      type uint64;
      units "octets";
      description
        "Total octets in packets dropped due to cable bundle flood replication end.";
    }
    leaf cblbf-recycle-tail-pkts {
      type uint64;
      description
        "Number of packets dropped due to cable bundle flood recycle tail.";
    }
    leaf cblbf-recycle-tail-octets {
      type uint64;
      units "octets";
      description
        "Total octets dropped at the tail end of the cable bundle flood recycle operation in the QFP datapath.";
    }
    leaf cblbf-fwdint-down-pkts {
      type uint64;
      description
        "Number of packets dropped during cable bundle flooding due to the forwarding interface being down in the QFP datapath.";
    }
    leaf cblbf-fwdint-down-octets {
      type uint64;
      units "octets";
      description
        "Total octets dropped during cable bundle flooding due to the forwarding interface being down in the QFP datapath.";
    }
    leaf cable-p2pl-oce-ptr-null-pkts {
      type uint64;
      description
        "Number of packets dropped due to cable P2PL output chain element (OCE) pointer null.";
    }
    leaf cable-p2pl-oce-ptr-null-octets {
      type uint64;
      units "octets";
      description
        "Total octets in packets dropped due to cable P2PL output chain element (OCE) pointer null.";
    }
    leaf cable-mc-invalid-replica-record-pkts {
      type uint64;
      description
        "Number of packets dropped due to cable multicast invalid replica record.";
    }
    leaf cable-mc-invalid-replica-record-octets {
      type uint64;
      units "octets";
      description
        "Total octets in packets dropped due to cable multicast invalid replica record.";
    }
    leaf no-def-jib-pkts {
      type uint64;
      description
        "Number of packets dropped because no default JIB entry was found in the QFP datapath.";
    }
    leaf no-def-jib-octets {
      type uint64;
      units "octets";
      description
        "Total octets in packets dropped because no default JIB entry was found in the QFP datapath.";
    }
    leaf no-inj-jib-pkts {
      type uint64;
      description
        "Number of packets dropped because no injected JIB entry was found in the QFP datapath.";
    }
    leaf no-inj-jib-octets {
      type uint64;
      units "octets";
      description
        "Total octets in packets dropped because no injected JIB entry was found in the QFP datapath.";
    }
    leaf onefw-pkts {
      type uint64;
      description
        "Number of packets dropped by the firewall feature in the QFP datapath.";
    }
    leaf onefw-octets {
      type uint64;
      units "octets";
      description
        "Total octets dropped by the firewall feature in the QFP datapath.";
    }
    leaf ccm-tx-pkts {
      type uint64;
      description
        "Number of packets dropped due to CCM transmit.";
    }
    leaf ccm-tx-octets {
      type uint64;
      units "octets";
      description
        "Total octets in packets dropped due to CCM transmit.";
    }
    leaf appnav-sn-pkt-invalid-pkts {
      type uint64;
      description
        "Number of invalid packets received from the APPNAV Service Node (SN) in the QFP datapath.";
    }
    leaf appnav-sn-pkt-invalid-octets {
      type uint64;
      units "octets";
      description
        "Total octets in invalid packets received from the APPNAV Service Node (SN) in the QFP datapath.";
    }
    leaf appnav-internal-err-pkts {
      type uint64;
      description
        "Number of packets dropped due to APPNAV internal error.";
    }
    leaf appnav-internal-err-octets {
      type uint64;
      units "octets";
      description
        "Total octets in packets dropped due to APPNAV internal error.";
    }
    leaf appnav-badroute-pkts {
      type uint64;
      description
        "Number of packets dropped due to APPNAV bad route.";
    }
    leaf appnav-badroute-octets {
      type uint64;
      units "octets";
      description
        "Total octets in packets dropped by APPNAV due to invalid or bad routing information.";
    }
    leaf appnav-notunnel-pkts {
      type uint64;
      description
        "Number of packets dropped by APPNAV because they did not match any configured tunnel.";
    }
    leaf appnav-notunnel-octets {
      type uint64;
      units "octets";
      description
        "Total octets in packets dropped by APPNAV because they did not match any configured tunnel.";
    }
    leaf appnav-nosvcctx-pkts {
      type uint64;
      description
        "Number of packets dropped by APPNAV because they did not have an associated service context.";
    }
    leaf appnav-nosvcctx-octets {
      type uint64;
      units "octets";
      description
        "Total octets in packets dropped by APPNAV because they did not have an associated service context.";
    }
    leaf appnav-inv-flow-state-pkts {
      type uint64;
      description
        "Number of packets dropped by APPNAV due to invalid or corrupted flow state information.";
    }
    leaf appnav-inv-flow-state-octets {
      type uint64;
      units "octets";
      description
        "Total octets in packets dropped by APPNAV due to invalid or corrupted flow state information.";
    }
    leaf appnav-unexpected-pkt-pkts {
      type uint64;
      description
        "Number of packets dropped by APPNAV because they did not match any expected flow or session.";
    }
    leaf appnav-unexpected-pkt-octets {
      type uint64;
      units "octets";
      description
        "Total octets in packets dropped by APPNAV because they did not match any expected flow or session.";
    }
    leaf rl2gp-non-tcb-pkts {
      type uint64;
      description
        "Number of packets dropped due to reverse layer 2 gateway protocol(R-L2GP) non topology change bridge protocol unit (TCB).";
    }
    leaf rl2gp-non-tcb-octets {
      type uint64;
      units "octets";
      description
        "Total octets dropped by the Reverse Layer 2 Gateway Protocol (R-L2GP) that are not associated with Topology Change Bridge (TCB) protocol units.";
    }
    leaf tunnel-pkt-sb-missed-pkts {
      type uint64;
      description
        "Number of packets dropped by the tunnel packet sub-block in the QFP datapath.";
    }
    leaf tunnel-pkt-sb-missed-octets {
      type uint64;
      units "octets";
      description
        "Total octets in packets dropped by the tunnel packet sub-block in the QFP datapath.";
    }
    leaf fhs-pkt-invalid-pkts {
      type uint64;
      description
        "Number of packets dropped due to first hop security packet invalid.";
    }
    leaf fhs-pkt-invalid-octets {
      type uint64;
      units "octets";
      description
        "Total octets in packets dropped due to first hop security packet invalid.";
    }
    leaf fhs-pkt-dropped-pkts {
      type uint64;
      description
        "Number of packets dropped due to first hop security packet dropped.";
    }
    leaf fhs-pkt-dropped-octets {
      type uint64;
      units "octets";
      description
        "Total octets in packets dropped due to first hop security packet dropped.";
    }
    leaf tunnel-sgre-virtual-mac-mismatch-pkts {
      type uint64;
      description
        "Number of packets dropped due to tunnel secure generic routing encapsulation (sGRE) virtual MAC mismatch.";
    }
    leaf tunnel-sgre-virtual-mac-mismatch-octets {
      type uint64;
      units "octets";
      description
        "Total octets in packets dropped due to tunnel secure generic routing encapsulation (sGRE) virtual MAC mismatch.";
    }
    leaf tunnel-sgre-unsupported-proto-pkts {
      type uint64;
      description
        "Number of packets dropped due to tunnel secure generic routing encapsulation (sGRE) unsupported protocol.";
    }
    leaf tunnel-sgre-unsupported-proto-octets {
      type uint64;
      units "octets";
      description
        "Total octets in packets dropped due to tunnel secure generic routing encapsulation (sGRE) unsupported protocol.";
    }
    leaf mpls-gal-check-non-gal-dropped-pkts {
      type uint64;
      description
        "Number of packets dropped during MPLS Generic Associated Channel Label (GAL) checks when the label is not a GAL.";
    }
    leaf mpls-gal-check-non-gal-dropped-octets {
      type uint64;
      units "octets";
      description
        "Total octets dropped during MPLS Generic Associated Channel Label (GAL) checks when the label is not a GAL.";
    }
    leaf mpls-gal-check-non-eos-dropped-pkts {
      type uint64;
      description
        "Number of packets dropped during MPLS GAL checks when the GAL is not at the end of the label stack.";
    }
    leaf mpls-gal-check-non-eos-dropped-octets {
      type uint64;
      units "octets";
      description
        "Total octets dropped during MPLS GAL checks when the GAL is not at the end of the label stack.";
    }
    leaf mpls-gal-check-invalid-pkts {
      type uint64;
      description
        "Number of packets dropped due to multiprotocol label switching (MPLS) generic associated channel label (GAL) check invalid.";
    }
    leaf mpls-gal-check-invalid-octets {
      type uint64;
      units "octets";
      description
        "Total octets in packets dropped due to multiprotocol label switching (MPLS) generic associated channel label (GAL) check invalid.";
    }
    leaf mpls-gal-exception-non-eos-dropped-pkts {
      type uint64;
      description
        "Number of packets dropped due to exceptions during MPLS GAL processing when the GAL is not at the end of the label stack.";
    }
    leaf mpls-gal-exception-non-eos-dropped-octets {
      type uint64;
      units "octets";
      description
        "Total octets dropped due to exceptions during MPLS GAL processing when the GAL is not at the end of the label stack.";
    }
    leaf mpls-gal-exception-non-gach-dropped-pkts {
      type uint64;
      description
        "Number of packets dropped due to exceptions during MPLS GAL processing when the associated channel is not a Generic Associated Channel (GACH).";
    }
    leaf mpls-gal-exception-non-gach-dropped-octets {
      type uint64;
      units "octets";
      description
        "Total octets in packets dropped due to multiprotocol label switching (MPLS) generic associated channel label (GAL) exception non generic associated channel (GACH) dropped.";
    }
    leaf conf-sw-sess-pkts {
      type uint64;
      description
        "Number of packets dropped by the configuration software session on the QFP datapath.";
    }
    leaf conf-sw-sess-octets {
      type uint64;
      units "octets";
      description
        "Total octets dropped by the configuration software session on the QFP datapath.";
    }
    leaf tunnel-decap-too-many-times-pkts {
      type uint64;
      description
        "Number of packets dropped due to tunnel deencapsulation too many times.";
    }
    leaf tunnel-decap-too-many-times-octets {
      type uint64;
      units "octets";
      description
        "Total octets in packets dropped due to tunnel deencapsulation too many times.";
    }
    leaf loadbalance-null0-pkts {
      type uint64;
      description
        "Number of packets dropped to the null0 interface as a result of load balancing on the QFP datapath.";
    }
    leaf loadbalance-null0-octets {
      type uint64;
      units "octets";
      description
        "Total octets dropped to the null0 interface as a result of load balancing on the QFP datapath.";
    }
    leaf gpm-tx-len-exceed-pkts {
      type uint64;
      description
        "Number of packets dropped due to global packet memory transmit length exceed in the datapath.";
    }
    leaf gpm-tx-len-exceed-octets {
      type uint64;
      units "octets";
      description
        "Total octets in packets dropped due to global packet memory transmit length exceed in the datapath.";
    }
    leaf esf-ffr-drop-pkts {
      type uint64;
      description
        "Number of packets dropped due to edge switching services feature (ESF) ffr drop.";
    }
    leaf esf-ffr-drop-octets {
      type uint64;
      units "octets";
      description
        "Total octets dropped by the Edge Switching Services Feature (ESF) due to Fast Failure Recovery (FFR) events on the QFP datapath.";
    }
    leaf ec-bundle-enq-pkts {
      type uint64;
      description
        "Number of packets dropped due to etherchannel bundle enqueue.";
    }
    leaf ec-bundle-enq-octets {
      type uint64;
      units "octets";
      description
        "Total octets in packets dropped due to etherchannel bundle enqueue.";
    }
    leaf ec-link-tx-pkts {
      type uint64;
      description
        "Number of packets dropped due to etherchannel link transmit.";
    }
    leaf ec-link-tx-octets {
      type uint64;
      units "octets";
      description
        "Total octets in packets dropped due to etherchannel link transmit.";
    }
    leaf pfrv3-probe-err-pkts {
      type uint64;
      description
        "Number of probe packets dropped due to errors detected by Performance Routing version 3 (pFRv3) on the QFP datapath.";
    }
    leaf pfrv3-probe-err-octets {
      type uint64;
      units "octets";
      description
        "Total octets in probe packets dropped due to errors detected by Performance Routing version 3 (pFRv3) on the QFP datapath.";
    }
    leaf ovl-bad-pkt-pkts {
      type uint64;
      description
        "Number of packets dropped because they were invalid or malformed in the overlay network on the QFP datapath.";
    }
    leaf ovl-bad-pkt-octets {
      type uint64;
      units "octets";
      description
        "Total octets in packets dropped because they were invalid or malformed in the overlay network on the QFP datapath.";
    }
    leaf ovl-l2-filter-pkts {
      type uint64;
      description
        "Number of packets dropped by Layer 2 filtering mechanisms in the overlay network on the QFP datapath.";
    }
    leaf ovl-l2-filter-octets {
      type uint64;
      units "octets";
      description
        "Total octets dropped by the overlay Layer 2 filter in the QFP datapath.";
    }
    leaf dpss-pkts {
      type uint64;
      description
        "Number of packets dropped due to dataplane service set (DPSS).";
    }
    leaf dpss-octets {
      type uint64;
      units "octets";
      description
        "Total octets in packets dropped due to dataplane service set (DPSS).";
    }
    leaf tunnel-invalid-protocol-pkts {
      type uint64;
      description
        "Number of packets dropped due to invalid protocol types detected in tunnel traffic by the QFP.";
    }
    leaf tunnel-invalid-protocol-octets {
      type uint64;
      units "octets";
      description
        "Total octets in packets dropped due to invalid protocol types in tunnel traffic by the QFP.";
    }
    leaf pfrv3-at-failure-pkts {
      type uint64;
      description
        "Number of packets dropped due to performance routing version 3 (pFRv3) at failure.";
    }
    leaf pfrv3-at-failure-octets {
      type uint64;
      units "octets";
      description
        "Total octets in packets dropped due to performance routing version 3 (pFRv3) at failure.";
    }
    leaf ipv4-mcast-acl-pkts {
      type uint64;
      description
        "Number of packets dropped due to IPv4 multicast access control list (ACL).";
    }
    leaf ipv4-mcast-acl-octets {
      type uint64;
      units "octets";
      description
        "Total octets in packets dropped due to IPv4 multicast access control list (ACL).";
    }
    leaf ipv6-mcast-acl-pkts {
      type uint64;
      description
        "Number of packets dropped due to IPv6 multicast access control list (ACL).";
    }
    leaf ipv6-mcast-acl-octets {
      type uint64;
      units "octets";
      description
        "Total octets dropped by the IPv6 multicast access control list (ACL) on the QFP datapath.";
    }
    leaf pprl-sbrl-drop-pkts {
      type uint64;
      description
        "Number of packets dropped due to PPRL (Per Port Rate Limiting) source-based rate limiting on the QFP datapath.";
    }
    leaf pprl-sbrl-drop-octets {
      type uint64;
      units "octets";
      description
        "Total octets dropped due to PPRL (Per Port Rate Limiting) source-based rate limiting on the QFP datapath.";
    }
    leaf cbl-req-arl-drop-pkts {
      type uint64;
      description
        "Number of ARP packets dropped in response to cable request operations on the QFP datapath.";
    }
    leaf cbl-req-arl-drop-octets {
      type uint64;
      units "octets";
      description
        "Total octets dropped for ARP packets during cable request operations on the QFP datapath.";
    }
    leaf cbl-rep-arl-drop-pkts {
      type uint64;
      description
        "Number of ARP packets dropped during cable reply operations on the QFP datapath.";
    }
    leaf cbl-rep-arl-drop-octets {
      type uint64;
      units "octets";
      description
        "Total octets dropped for ARP packets during cable reply operations on the QFP datapath.";
    }
    leaf appnav-acgreloaddelay-pkts {
      type uint64;
      description
        "Number of packets dropped due to APPNAV (Application Navigation) reload operations on the QFP datapath.";
    }
    leaf appnav-acgreloaddelay-octets {
      type uint64;
      units "octets";
      description
        "Total octets dropped due to APPNAV (Application Navigation) reload operations on the QFP datapath.";
    }
    leaf ngfw-policy-pkts {
      type uint64;
      description
        "Number of packets dropped by the Next Generation Firewall (NGFW) policy on the QFP datapath.";
    }
    leaf ngfw-policy-octets {
      type uint64;
      units "octets";
      description
        "Total octets in packets dropped due to next generation firewall (NGFW) policy.";
    }
    leaf ngfw-divert-pkts {
      type uint64;
      description
        "Number of packets dropped due to next generation firewall (NGFW) divert.";
    }
    leaf ngfw-divert-octets {
      type uint64;
      units "octets";
      description
        "Total octets in packets dropped due to next generation firewall (NGFW) divert.";
    }
    leaf pfrv3-blackhole-pkts {
      type uint64;
      description
        "Number of packets dropped due to performance routing version 3 (pFRv3) black hole.";
    }
    leaf pfrv3-blackhole-octets {
      type uint64;
      units "octets";
      description
        "Total octets in packets dropped due to performance routing version 3 (pFRv3) black hole.";
    }
    leaf pppoe-fctl-pkts {
      type uint64;
      description
        "Number of packets dropped due to PPP over Ethernet (PPPoE) flow control.";
    }
    leaf pppoe-fctl-octets {
      type uint64;
      units "octets";
      description
        "Total octets in packets dropped due to PPP over Ethernet (PPPoE) flow control.";
    }
    leaf lisp-sfltr-pkts {
      type uint64;
      description
        "Number of packets dropped by Locator/ID Separation Protocol (LISP) source filtering.";
    }
    leaf lisp-sfltr-octets {
      type uint64;
      units "octets";
      description
        "Total octets in packets dropped by Locator/ID Separation Protocol (LISP) source filtering.";
    }
    leaf flowspec-pkts {
      type uint64;
      description
        "Number of packets dropped by BGP Flowspec rules.";
    }
    leaf flowspec-octets {
      type uint64;
      units "octets";
      description
        "Total octets dropped by the Flowspec feature in the QFP datapath.";
    }
    leaf identity-cft-error-pkts {
      type uint64;
      description
        "Number of packets dropped due to identity common flow table error.";
    }
    leaf identity-cft-error-octets {
      type uint64;
      units "octets";
      description
        "Total octets in packets dropped due to identity common flow table error.";
    }
    leaf bad-us-jib-hdr-pkts {
      type uint64;
      description
        "Number of packets dropped due to an invalid upstream JIB header in the QFP datapath.";
    }
    leaf bad-us-jib-hdr-octets {
      type uint64;
      units "octets";
      description
        "Total octets in packets dropped due to an invalid upstream JIB header in the QFP datapath.";
    }
    leaf too-many-mpls-lookup-oce-pkts {
      type uint64;
      description
        "Number of packets dropped due to too many multiprotocol label switching (MPLS) lookup output chain element (OCE).";
    }
    leaf too-many-mpls-lookup-oce-octets {
      type uint64;
      units "octets";
      description
        "Total octets in packets dropped due to too many multiprotocol label switching (MPLS) lookup output chain element (OCE).";
    }
    leaf cable-prereg-not-cm-pkts {
      type uint64;
      description
        "Number of cable packets dropped during pre-registration because they are not associated with a Cable Modem (CM) in the QFP datapath.";
    }
    leaf cable-prereg-not-cm-octets {
      type uint64;
      units "octets";
      description
        "Total octets in cable packets dropped during pre-registration because they are not associated with a Cable Modem (CM) in the QFP datapath.";
    }
    leaf invalid-virtual-id-pkts {
      type uint64;
      description
        "Number of packets dropped due to invalid virtual interfaced ID in the datapath.";
    }
    leaf invalid-virtual-id-octets {
      type uint64;
      units "octets";
      description
        "Total octets in packets dropped due to invalid virtual interface ID in the datapath.";
    }
    leaf flow-queue-failure-id-pkts {
      type uint64;
      description
        "Number of packets dropped by the datapath due to flow queue failures.";
    }
    leaf flow-queue-failure-id-octets {
      type uint64;
      units "octets";
      description
        "Total octets in packets dropped by the datapath due to flow queue failures.";
    }
    leaf l2es-input-invalid-tag-pkts {
      type uint64;
      description
        "Number of packets dropped due to layer 2 embedded ethernet switching input invalid tag.";
    }
    leaf l2es-input-invalid-tag-octets {
      type uint64;
      units "octets";
      description
        "Total octets in packets dropped due to layer 2 embedded ethernet switching input invalid tag.";
    }
    leaf l2es-input-invalid-svi-pkts {
      type uint64;
      description
        "Number of packets dropped due to layer 2 embedded ethernet switching input invalid switched virtual interface (SVI).";
    }
    leaf l2es-input-invalid-svi-octets {
      type uint64;
      units "octets";
      description
        "Total octets in packets dropped due to layer 2 embedded ethernet switching input invalid switched virtual interface (SVI).";
    }
    leaf svi-output-invalid-l2sb-pkts {
      type uint64;
      description
        "Number of packets dropped due to switched virtual interface (SVI) output invalid layer 2 sub block.";
    }
    leaf svi-output-invalid-l2sb-octets {
      type uint64;
      units "octets";
      description
        "Total octets in packets dropped due to switched virtual interface (SVI) output invalid layer 2 sub block.";
    }
    leaf svi-input-invalid-mac-pkts {
      type uint64;
      description
        "Number of packets dropped due to switched virtual interface (SVI) input invalid MAC.";
    }
    leaf svi-input-invalid-mac-octets {
      type uint64;
      units "octets";
      description
        "Total octets in packets dropped on the Switched Virtual Interface (SVI) due to invalid MAC addresses.";
    }
    leaf svi-output-recycle-tail-pkts {
      type uint64;
      description
        "Number of packets on the Switched Virtual Interface (SVI) output dropped due to tail drop conditions during recycling.";
    }
    leaf svi-output-recycle-tail-octets {
      type uint64;
      units "octets";
      description
        "Total octets in packets on the Switched Virtual Interface (SVI) output dropped due to tail drop conditions during recycling.";
    }
    leaf svi-output-repl-pkts {
      type uint64;
      description
        "Number of packets dropped during replication on the Switched Virtual Interface (SVI) output.";
    }
    leaf svi-output-repl-octets {
      type uint64;
      units "octets";
      description
        "Total octets in packets dropped during replication on the Switched Virtual Interface (SVI) output.";
    }
    leaf svi-repl-end-pkts {
      type uint64;
      description
        "Number of packets on the Switched Virtual Interface (SVI) dropped after replication processing completed.";
    }
    leaf svi-repl-end-octets {
      type uint64;
      units "octets";
      description
        "Total octets in packets on the Switched Virtual Interface (SVI) dropped after replication processing completed.";
    }
    leaf cws-ctx-id-not-found-mob-pkts {
      type uint64;
      description
        "Number of packets dropped due to Cisco Wire Service (CWS) ctx identifier not found mobile.";
    }
    leaf cws-ctx-id-not-found-mob-octets {
      type uint64;
      units "octets";
      description
        "Total octets in packets dropped due to Cisco Wire Service (CWS) ctx identifier not found mobile.";
    }
    leaf cws-ctx-id-not-found-conn-pkts {
      type uint64;
      description
        "Number of packets dropped due to Cisco Wire Service (CWS) ctx identifier not found connection.";
    }
    leaf cws-ctx-id-not-found-conn-octets {
      type uint64;
      units "octets";
      description
        "Total octets for Cisco Wire Service (CWS) connections where the context identifier (ctx-id) was not found.";
    }
    leaf l2cp-cfg-action-pkts {
      type uint64;
      description
        "Number of packets dropped by the Layer 2 Control Protocol (L2CP) as a result of configuration actions.";
    }
    leaf l2cp-cfg-action-octets {
      type uint64;
      units "octets";
      description
        "Total octets in packets dropped by the Layer 2 Control Protocol (L2CP) as a result of configuration actions.";
    }
    leaf perf-lic-policer-lo-pkts {
      type uint64;
      description
        "Number of packets dropped by the performance license policer at the 'low' threshold.";
    }
    leaf perf-lic-policer-lo-octets {
      type uint64;
      units "octets";
      description
        "Total octets in packets dropped by the performance license policer at the 'low' threshold.";
    }
    leaf perf-lic-policer-hi-pkts {
      type uint64;
      description
        "Number of packets dropped by the performance license policer at the 'high' threshold.";
    }
    leaf perf-lic-policer-hi-octets {
      type uint64;
      units "octets";
      description
        "Total octets in packets dropped by the performance license policer at the 'high' threshold.";
    }
    leaf hqf-tx-error-pkts {
      type uint64;
      description
        "Number of packets dropped due to hierarchical queuing function transmit error.";
    }
    leaf hqf-tx-error-octets {
      type uint64;
      units "octets";
      description
        "Total octets in packets dropped due to hierarchical queuing function transmit error.";
    }
    leaf cmd-format-pkts {
      type uint64;
      description
        "Number of packets dropped by the datapath due to invalid or unsupported Cisco Meta Data (CMD) tagging in packet header.";
    }
    leaf cmd-format-octets {
      type uint64;
      units "octets";
      description
        "Total octets in packets dropped by the datapath due to invalid or unsupported Cisco Meta Data (CMD) tagging in packet header.";
    }
    leaf utd-pkts {
      type uint64;
      description
        "Number of packets dropped due to universal threat defense.";
    }
    leaf utd-octets {
      type uint64;
      units "octets";
      description
        "Total octets in packets dropped due to universal threat defense.";
    }
    leaf nat66-in2out-pkts {
      type uint64;
      description
        "Number of packets dropped due to NAT66 in to out.";
    }
    leaf nat66-in2out-octets {
      type uint64;
      units "octets";
      description
        "Total octets in packets dropped due to NAT66 in to out.";
    }
    leaf nat66-out2in-pkts {
      type uint64;
      description
        "Number of packets dropped due to NAT66 out to in.";
    }
    leaf nat66-out2in-octets {
      type uint64;
      units "octets";
      description
        "Total octets in packets dropped due to NAT66 out to in.";
    }
    leaf dsa-no-ip-pkts {
      type uint64;
      description
        "Number of packets dropped by the DNS Snooping Agent because they do not contain an IP header in the QFP datapath.";
    }
    leaf dsa-no-ip-octets {
      type uint64;
      units "octets";
      description
        "Total octets in packets dropped by the DNS Snooping Agent because they do not contain an IP header in the QFP datapath.";
    }
    leaf cws-inter-error-pkts {
      type uint64;
      description
        "Number of packets dropped due to Cisco Wire Service (CWS) inter error.";
    }
    leaf cws-inter-error-octets {
      type uint64;
      units "octets";
      description
        "Total octets in packets dropped due to inter-service errors in Cisco Wire Service (CWS) on the QFP datapath.";
    }
    leaf utd-sn-pkts {
      type uint64;
      description
        "Number of packets dropped by the Universal Threat Defense (UTD) Service Node (SN) on the QFP datapath.";
    }
    leaf utd-sn-octets {
      type uint64;
      units "octets";
      description
        "Total octets dropped by the Universal Threat Defense (UTD) Service Node (SN) on the QFP datapath.";
    }
    leaf mpls-el-invalid-tag-pkts {
      type uint64;
      description
        "Number of packets dropped due to multiprotocol label switching (MPLS) entropy label invalid tag.";
    }
    leaf mpls-el-invalid-tag-octets {
      type uint64;
      units "octets";
      description
        "Total octets in packets dropped due to multiprotocol label switching (MPLS) entropy label invalid tag.";
    }
    leaf lisp-failed-to-punt-gsmr-enabled-pkts {
      type uint64;
      description
        "Number of packets dropped because Locator/ID Separation Protocol (LISP) failed to punt them when Generalized Solicit Map Request (GSMR) is enabled.";
    }
    leaf lisp-failed-to-punt-gsmr-enabled-octets {
      type uint64;
      units "octets";
      description
        "Total octets in packets dropped because Locator/ID Separation Protocol (LISP) failed to punt them when Generalized Solicit Map Request (GSMR) is enabled.";
    }
    leaf schain-flow-action-pkts {
      type uint64;
      description
        "Number of packets dropped as part of a service chain flow action on the QFP datapath.";
    }
    leaf schain-flow-action-octets {
      type uint64;
      units "octets";
      description
        "Total octets in packets dropped as part of a service chain flow action on the QFP datapath.";
    }
    leaf opendns-pkts {
      type uint64;
      description
        "Number of packets dropped by the QFP datapath that are associated with Cisco OpenDNS services.";
    }
    leaf opendns-octets {
      type uint64;
      units "octets";
      description
        "Total octets dropped by the QFP for OpenDNS-related traffic.";
    }
    leaf capwap-err-pkts {
      type uint64;
      description
        "Number of CAPWAP packets with errors dropped by the QFP.";
    }
    leaf capwap-err-octets {
      type uint64;
      units "octets";
      description
        "Total octets in CAPWAP error packets dropped by the QFP.";
    }
    leaf capwap-no-uidb-pkts {
      type uint64;
      description
        "Number of CAPWAP packets dropped by the QFP because they could not be associated with a valid interface (UIDB).";
    }
    leaf capwap-no-uidb-octets {
      type uint64;
      units "octets";
      description
        "Total octets in CAPWAP packets dropped because they could not be associated with a valid interface (UIDB) by the QFP.";
    }
    leaf dtls-err-pkts {
      type uint64;
      description
        "Number of DTLS packets with errors dropped by the QFP.";
    }
    leaf dtls-err-octets {
      type uint64;
      units "octets";
      description
        "Total octets in DTLS error packets dropped by the QFP.";
    }
    leaf wlclnt-err-pkts {
      type uint64;
      description
        "Number of wireless client packets with errors dropped by the QFP.";
    }
    leaf wlclnt-err-octets {
      type uint64;
      units "octets";
      description
        "Total octets in wireless client error packets dropped by the QFP.";
    }
    leaf wlclnt-fnf-v9-report-pkts {
      type uint64;
      description
        "Number of packets dropped due to wireless client flexible netflow v9 report.";
    }
    leaf wlclnt-fnf-v9-report-octets {
      type uint64;
      units "octets";
      description
        "Total octets reported in Wireless Client Flexible NetFlow Version 9 (FNF v9) records by the QFP datapath.";
    }
    leaf wlclnt-fnf-v9-err-pkts {
      type uint64;
      description
        "Number of packets dropped due to errors during Wireless Client Flexible NetFlow Version 9 (FNF v9) processing on the QFP datapath.";
    }
    leaf wlclnt-fnf-v9-err-octets {
      type uint64;
      units "octets";
      description
        "Total octets in packets dropped due to errors during Wireless Client Flexible NetFlow Version 9 (FNF v9) processing on the QFP datapath.";
    }
    leaf cgacl-err-pkts {
      type uint64;
      description
        "Number of packets dropped due to CG Access Control List(CGACL) error.";
    }
    leaf cgacl-err-octets {
      type uint64;
      units "octets";
      description
        "Total octets in packets dropped due to CG Access Control List(CGACL) error.";
    }
    leaf cgacl-lookup-miss-pkts {
      type uint64;
      description
        "Number of packets dropped due to CG Access Control List(CGACL) lookup miss.";
    }
    leaf cgacl-lookup-miss-octets {
      type uint64;
      units "octets";
      description
        "Total octets in packets dropped due to CG Access Control List(CGACL) lookup miss.";
    }
    leaf cgacl-match-pkts {
      type uint64;
      description
        "Number of packets dropped due to CG Access Control List(CGACL) match.";
    }
    leaf cgacl-match-octets {
      type uint64;
      units "octets";
      description
        "Total octets in packets dropped due to CG Access Control List(CGACL) match.";
    }
    leaf cgacl-action-pkts {
      type uint64;
      description
        "Number of packets dropped due to CG Access Control List(CGACL) action.";
    }
    leaf cgacl-action-octets {
      type uint64;
      units "octets";
      description
        "Total octets in packets dropped due to configured CG Access Control List (CGACL) actions on the QFP datapath.";
    }
    leaf cwfrag-err-pkts {
      type uint64;
      description
        "Number of packets dropped due to fragment errors in Cisco wireservice on the QFP datapath.";
    }
    leaf cwfrag-err-octets {
      type uint64;
      units "octets";
      description
        "Total octets in packets dropped due to fragment errors in Cisco wireservice on the QFP datapath.";
    }
    leaf pathmgr-measurement-err-pkts {
      type uint64;
      description
        "Number of packets dropped due to measurement errors in the path manager component of the QFP datapath.";
    }
    leaf pathmgr-measurement-err-octets {
      type uint64;
      units "octets";
      description
        "Total octets in packets dropped due to measurement errors in the path manager component of the QFP datapath.";
    }
    leaf pathmgr-select-err-pkts {
      type uint64;
      description
        "Number of packets dropped due to selection errors in the path manager component of the QFP datapath.";
    }
    leaf pathmgr-select-err-octets {
      type uint64;
      units "octets";
      description
        "Total octets in packets dropped due to selection errors in the path manager component of the QFP datapath.";
    }
    leaf capwap-reass-frag-consm-pkts {
      type uint64;
      description
        "Number of packets dropped due to CAPWAP reassembly fragments consumed.";
    }
    leaf capwap-reass-frag-consm-octets {
      type uint64;
      units "octets";
      description
        "Total octets in packets dropped due to CAPWAP reassembly fragments consumed.";
    }
    leaf capwap-reass-alloc-err-pkts {
      type uint64;
      description
        "Number of packets dropped due to CAPWAP reassembly allocation error.";
    }
    leaf capwap-reass-alloc-err-octets {
      type uint64;
      units "octets";
      description
        "Total octets for CAPWAP reassembly allocation errors on the QFP datapath.";
    }
    leaf capwap-reass-frag-err-pkts {
      type uint64;
      description
        "Number of packets dropped due to fragment errors during CAPWAP reassembly on the QFP datapath.";
    }
    leaf capwap-reass-frag-err-octets {
      type uint64;
      units "octets";
      description
        "Total octets in packets dropped due to fragment errors during CAPWAP reassembly on the QFP datapath.";
    }
    leaf redistrib-err-bad-dst-pkts {
      type uint64;
      description
        "Number of packets dropped due to redistribution errors from invalid or bad destination addresses on the QFP datapath.";
    }
    leaf redistrib-err-bad-dst-octets {
      type uint64;
      units "octets";
      description
        "Total octets in packets dropped due to redistribution errors from invalid or bad destination addresses on the QFP datapath.";
    }
    leaf redistrib-err-sb-trans-fail-pkts {
      type uint64;
      description
        "Number of packets dropped due to redistribution errors from sub-block transfer failures on the QFP datapath.";
    }
    leaf redistrib-err-sb-trans-fail-octets {
      type uint64;
      units "octets";
      description
        "Total octets in packets dropped due to redistribution errors from sub-block transfer failures on the QFP datapath.";
    }
    leaf redistrib-err-ph-alc-fail-pkts {
      type uint64;
      description
        "Number of packets dropped due to redistribution errors from packet handler (PH) allocation failures on the QFP datapath.";
    }
    leaf redistrib-err-ph-alc-fail-octets {
      type uint64;
      units "octets";
      description
        "Total octets in packets dropped due to redistribution errors from packet handler (PH) allocation failures on the QFP datapath.";
    }
    leaf redistrib-err-not-sup-pkts {
      type uint64;
      description
        "Number of packets dropped due to redistribution errors from unsupported features or operations on the QFP datapath.";
    }
    leaf redistrib-err-not-sup-octets {
      type uint64;
      units "octets";
      description
        "Total octets in packets dropped due to unsupported redistribution operations or features on the QFP datapath.";
    }
    leaf redistrib-fifo-tail-drop-pkts {
      type uint64;
      description
        "Number of packets dropped due to redistribution first in first out (FIFO) tail drop.";
    }
    leaf redistrib-fifo-tail-drop-octets {
      type uint64;
      units "octets";
      description
        "Total octets in packets dropped due to redistribution first in first out (FIFO) tail drop.";
    }
    leaf redistrib-no-credits-pkts {
      type uint64;
      description
        "Number of packets dropped during redistribution due to lack of available credits.";
    }
    leaf redistrib-no-credits-octets {
      type uint64;
      units "octets";
      description
        "Total octets dropped during redistribution due to lack of available credits.";
    }
    leaf max-indirect-exceeded-pkts {
      type uint64;
      description
        "Number of packets dropped in the datapath when the maximum allowed number of gather descriptors was exceeded.";
    }
    leaf max-indirect-exceeded-octets {
      type uint64;
      units "octets";
      description
        "Total octets in packets dropped in the datapath when the maximum allowed number of gather descriptors was exceeded.";
    }
    leaf punt-intf-drop-pkts {
      type uint64;
      description
        "Number of packets dropped due to punt interface drop.";
    }
    leaf punt-intf-drop-octets {
      type uint64;
      units "octets";
      description
        "Total octets in packets dropped due to punt interface drop.";
    }
    leaf srh-pkt-truncated-in-gpm-pkts {
      type uint64;
      description
        "Number of packets dropped due to segment routing header packet truncated in global packet memory.";
    }
    leaf srh-pkt-truncated-in-gpm-octets {
      type uint64;
      units "octets";
      description
        "Total octets in packets dropped due to segment routing header packet truncated in global packet memory.";
    }
    leaf srh-invalid-extension-pkts {
      type uint64;
      description
        "Number of packets with Segment Routing Header (SRH) containing invalid extension headers dropped by the QFP.";
    }
    leaf srh-invalid-extension-octets {
      type uint64;
      units "octets";
      description
        "Total octets in packets with Segment Routing Header (SRH) containing invalid extension headers dropped by the QFP.";
    }
    leaf swport-pkts {
      type uint64;
      description
        "Number of packets dropped by the switch port on the QFP datapath.";
    }
    leaf swport-octets {
      type uint64;
      units "octets";
      description
        "Total octets dropped by the switch port on the QFP.";
    }
    leaf swport-disabled-pkts {
      type uint64;
      description
        "Number of packets dropped due to the switch port being in a disabled state on the QFP.";
    }
    leaf swport-disabled-octets {
      type uint64;
      units "octets";
      description
        "Total octets in packets dropped due to the switch port being in a disabled state on the QFP.";
    }
    leaf swport-sanity-check-pkts {
      type uint64;
      description
        "Number of packets dropped on the switch port due to sanity check failures on the QFP datapath.";
    }
    leaf swport-sanity-check-octets {
      type uint64;
      units "octets";
      description
        "Total octets in packets dropped on the switch port due to sanity check failures on the QFP datapath.";
    }
    leaf swport-vp-state-pkts {
      type uint64;
      description
        "Number of packets dropped by the switch port due to virtual port state transitions on the QFP.";
    }
    leaf swport-vp-state-octets {
      type uint64;
      units "octets";
      description
        "Total octets dropped by the switch port in the virtual port state.";
    }
    leaf swport-mac-conflict-pkts {
      type uint64;
      description
        "Number of packets dropped on the switch port due to a MAC address conflict.";
    }
    leaf swport-mac-conflict-octets {
      type uint64;
      units "octets";
      description
        "Total octets in packets dropped on the switch port due to a MAC address conflict.";
    }
    leaf swport-stby-pkts {
      type uint64;
      description
        "Number of packets dropped by the switch port while in standby mode.";
    }
    leaf swport-stby-octets {
      type uint64;
      units "octets";
      description
        "Total octets dropped by the switch port while in standby mode.";
    }
    leaf swport-tx-stby-pkts {
      type uint64;
      description
        "Number of packets dropped by the switch port while in standby mode.";
    }
    leaf swport-tx-stby-octets {
      type uint64;
      units "octets";
      description
        "Total octets dropped by the switch port while in standby mode.";
    }
    leaf switch-l2m-pkts {
      type uint64;
      description
        "Number of packets dropped due to switch layer 2 multicast.";
    }
    leaf switch-l2m-octets {
      type uint64;
      units "octets";
      description
        "Total octets in packets dropped due to switch layer 2 multicast.";
    }
    leaf switch-l2m-igmp-pkts {
      type uint64;
      description
        "Number of packets dropped due to switch layer 2 multicast internet group management protocol (IGMP).";
    }
    leaf switch-l2m-igmp-octets {
      type uint64;
      units "octets";
      description
        "Total octets in packets dropped due to switch layer 2 multicast internet group management protocol (IGMP).";
    }
    leaf switch-l2m-mld-pkts {
      type uint64;
      description
        "Number of Layer 2 multicast Multicast Listener Discovery (MLD) packets dropped by the switch.";
    }
    leaf switch-l2m-mld-octets {
      type uint64;
      units "octets";
      description
        "Total octets for Layer 2 multicast Multicast Listener Discovery (MLD) traffic dropped by the switch.";
    }
    leaf switch-l2m-lookup-miss-pkts {
      type uint64;
      description
        "Number of packets dropped due to switch layer 2 multicast lookup miss.";
    }
    leaf switch-l2m-lookup-miss-octets {
      type uint64;
      units "octets";
      description
        "Total octets in packets dropped due to switch layer 2 multicast lookup miss.";
    }
    leaf switch-l2m-sanity-check-pkts {
      type uint64;
      description
        "Number of packets dropped due to switch layer 2 multicast sanity check.";
    }
    leaf switch-l2m-sanity-check-octets {
      type uint64;
      units "octets";
      description
        "Total octets in packets dropped due to switch layer 2 multicast sanity check.";
    }
    leaf bier-invalid-replica-record-pkts {
      type uint64;
      description
        "Number of packets dropped due to bit index explicit replication (BIER) invalid replica record.";
    }
    leaf bier-invalid-replica-record-octets {
      type uint64;
      units "octets";
      description
        "Total octets in packets dropped due to bit index explicit replication (BIER) invalid replica record.";
    }
    leaf bier-snaity-pkts {
      type uint64;
      description
        "Number of Bit Index Explicit Replication (BIER) packets that failed sanity checks (validation) and were dropped.";
    }
    leaf bier-snaity-octets {
      type uint64;
      units "octets";
      description
        "Total octets in BIER (Bit Index Explicit Replication) packets dropped due to sanity check failures in the datapath.";
    }
    leaf cable-oob-us-sess-invalid-pkts {
      type uint64;
      description
        "Number of upstream packets dropped on the cable out-of-band interface due to an invalid session.";
    }
    leaf cable-oob-us-sess-invalid-octets {
      type uint64;
      units "octets";
      description
        "Total octets in upstream packets dropped on the cable out-of-band interface due to an invalid session.";
    }
    leaf cable-oob-us-src-id-invalid-pkts {
      type uint64;
      description
        "Number of upstream packets dropped on the cable out-of-band interface due to invalid source identifiers.";
    }
    leaf cable-oob-us-src-id-invalid-octets {
      type uint64;
      units "octets";
      description
        "Total octets in upstream packets dropped on the cable out-of-band interface due to invalid source identifiers.";
    }
    leaf cable-oob-us-pkt-invalid-pkts {
      type uint64;
      description
        "Number of upstream packets dropped on the cable out-of-band interface because the packets were invalid.";
    }
    leaf cable-oob-us-pkt-invalid-octets {
      type uint64;
      units "octets";
      description
        "Total octets in upstream packets dropped on the cable out-of-band interface because the packets were invalid.";
    }
    leaf cbl-oob-null-repllist-pkts {
      type uint64;
      description
        "Number of packets dropped on the cable out-of-band interface due to a null replication list.";
    }
    leaf cbl-oob-null-repllist-octets {
      type uint64;
      units "octets";
      description
        "Total octets in packets dropped on the cable out-of-band interface due to a null replication list.";
    }
    leaf cbl-oob-repl-fail-pkts {
      type uint64;
      description
        "Number of packets dropped on the cable out-of-band interface due to replication failure.";
    }
    leaf cbl-oob-repl-fail-octets {
      type uint64;
      units "octets";
      description
        "Total octets in packets dropped on the cable out-of-band interface due to replication failure.";
    }
    leaf cbl-oob-add-hdr-fail-pkts {
      type uint64;
      description
        "Number of packets dropped on the cable out-of-band interface because header addition failed in the QFP datapath.";
    }
    leaf cbl-oob-add-hdr-fail-octets {
      type uint64;
      units "octets";
      description
        "Total octets in packets dropped on the cable out-of-band interface because header addition failed in the QFP datapath.";
    }
    leaf cbl-oob-repl-end-pkts {
      type uint64;
      description
        "Number of packets dropped at the end of out-of-band replication events on the cable interface in the QFP datapath.";
    }
    leaf cbl-oob-repl-end-octets {
      type uint64;
      units "octets";
      description
        "Total octets in packets dropped at the end of out-of-band replication events on the cable interface in the QFP datapath.";
    }
    leaf cbl-oob-recycle-tail-pkts {
      type uint64;
      description
        "Number of packets dropped at the tail of the recycle queue for out-of-band cable processing in the QFP datapath.";
    }
    leaf cbl-oob-recycle-tail-octets {
      type uint64;
      units "octets";
      description
        "Total octets dropped at the tail of the recycle queue for out-of-band cable processing in the QFP datapath.";
    }
    leaf cbl-oob-repl-uidb-invalid-pkts {
      type uint64;
      description
        "Number of packets in out-of-band cable replication that failed due to an invalid interface (UIDB) in the QFP datapath.";
    }
    leaf cbl-oob-repl-uidb-invalid-octets {
      type uint64;
      units "octets";
      description
        "Total octets in out-of-band cable replication packets that failed due to an invalid interface (UIDB) in the QFP datapath.";
    }
    leaf cbl-oob-repl-sess-invalid-pkts {
      type uint64;
      description
        "Number of packets dropped during out-of-band cable replication due to an invalid session in the QFP datapath.";
    }
    leaf cbl-oob-repl-sess-invalid-octets {
      type uint64;
      units "octets";
      description
        "Total octets in packets dropped during out-of-band cable replication due to an invalid session in the QFP datapath.";
    }
    leaf cbl-oob-null-repl-info-pkts {
      type uint64;
      description
        "Number of packets dropped during out-of-band cable replication due to null replication information in the QFP datapath.";
    }
    leaf cbl-oob-null-repl-info-octets {
      type uint64;
      units "octets";
      description
        "Total octets in packets dropped during out-of-band cable replication due to null replication information in the QFP datapath.";
    }
    leaf nid-vlan-mismatch-pkts {
      type uint64;
      description
        "Number of packets dropped due to network interface device VLAN mismatch.";
    }
    leaf nid-vlan-mismatch-octets {
      type uint64;
      units "octets";
      description
        "Total octets in packets dropped due to network interface device VLAN mismatch.";
    }
    leaf pfrv3-loop-pkts {
      type uint64;
      description
        "Number of packets dropped due to performance routing version 3 (pFRv3) loop.";
    }
    leaf pfrv3-loop-octets {
      type uint64;
      units "octets";
      description
        "Total octets in packets dropped due to performance routing version 3 (pFRv3) loop.";
    }
    leaf dialer-list-pkts {
      type uint64;
      description
        "Number of packets dropped according to dialer list rules on the QFP datapath.";
    }
    leaf dialer-list-octets {
      type uint64;
      units "octets";
      description
        "Total octets in packets dropped according to dialer list rules on the QFP datapath.";
    }
    leaf udp-pkts {
      type uint64;
      description
        "Number of UDP packets dropped by the QFP datapath.";
    }
    leaf udp-octets {
      type uint64;
      units "octets";
      description
        "Total octets in UDP packets dropped by the QFP datapath.";
    }
    leaf tunnel-l2tpv3oipv6-cookie-mismatch-pkts {
      type uint64;
      description
        "Number of packets dropped due to tunnel layer 2 tunneling protocol version 3 over IPv6 (L2TPv3oIPv6) cookie mismatch.";
    }
    leaf tunnel-l2tpv3oipv6-cookie-mismatch-octets {
      type uint64;
      units "octets";
      description
        "Total octets in packets dropped due to tunnel layer 2 tunneling protocol version 3 over IPv6 (L2TPv3oIPv6) cookie mismatch.";
    }
    leaf tunnel-l2tpv3oipv6-minmtu-error-pkts {
      type uint64;
      description
        "Number of L2TPv3 over IPv6 (L2TPv3oIPv6) packets dropped due to minimum MTU (Maximum Transmission Unit) errors detected by the QFP datapath.";
    }
    leaf tunnel-l2tpv3oipv6-minmtu-error-octets {
      type uint64;
      units "octets";
      description
        "Total octets in L2TPv3 over IPv6 (L2TPv3oIPv6) packets dropped due to minimum MTU (Maximum Transmission Unit) errors detected by the QFP datapath.";
    }
    leaf tunnel-l2tpv3oipv6-cookieflag-error-pkts {
      type uint64;
      description
        "Number of packets dropped due to tunnel layer 2 tunneling protocol version 3 over IPv6 (L2TPv3oIPv6) cookie flag error.";
    }
    leaf tunnel-l2tpv3oipv6-cookieflag-error-octets {
      type uint64;
      units "octets";
      description
        "Total octets in packets dropped due to tunnel layer 2 tunneling protocol version 3 over IPv6 (L2TPv3oIPv6) cookie flag error.";
    }
    leaf tunnel-l2tpv3oipv6-mac-mismatch-pkts {
      type uint64;
      description
        "Number of packets dropped due to tunnel layer 2 tunneling protocol version 3 over IPv6 (L2TPv3oIPv6) MAC mismatch.";
    }
    leaf tunnel-l2tpv3oipv6-mac-mismatch-octets {
      type uint64;
      units "octets";
      description
        "Total octets in packets dropped due to tunnel layer 2 tunneling protocol version 3 over IPv6 (L2TPv3oIPv6) MAC mismatch.";
    }
    leaf tunnel-l2tpv3oipv6-vlanid-mismatch-pkts {
      type uint64;
      description
        "Number of packets dropped due to tunnel layer 2 tunneling protocol version 3 over IPv6 (L2TPv3oIPv6) VLAN identifier mismatch.";
    }
    leaf tunnel-l2tpv3oipv6-vlanid-mismatch-octets {
      type uint64;
      units "octets";
      description
        "Total octets in packets dropped due to tunnel layer 2 tunneling protocol version 3 over IPv6 (L2TPv3oIPv6) VLAN identifier mismatch.";
    }
    leaf tunnel-l2tpv3oipv6-unsupported-proto-pkts {
      type uint64;
      description
        "Number of packets dropped due to tunnel layer 2 tunneling protocol version 3 over IPv6 (L2TPv3oIPv6) unsupported protocol.";
    }
    leaf tunnel-l2tpv3oipv6-unsupported-proto-octets {
      type uint64;
      units "octets";
      description
        "Total octets in packets dropped due to tunnel layer 2 tunneling protocol version 3 over IPv6 (L2TPv3oIPv6) unsupported protocol.";
    }
    leaf pfrv3-stickiness-pkts {
      type uint64;
      description
        "Number of packets dropped due to performance routing version 3 (pFRv3) stickiness.";
    }
    leaf pfrv3-stickiness-octets {
      type uint64;
      units "octets";
      description
        "Total octets in packets dropped due to performance routing version 3 (pFRv3) stickiness.";
    }
    leaf cbl-sid-exceed-pkts {
      type uint64;
      description
        "Number of packets dropped because the cable service identifier (SID) exceeded the allowed limit.";
    }
    leaf cbl-sid-exceed-octets {
      type uint64;
      units "octets";
      description
        "Total octets in packets dropped because the cable service identifier (SID) exceeded the allowed limit.";
    }
    leaf sdwan-pkts {
      type uint64;
      description
        "Number of packets dropped due to software defined WAN (SDWAN).";
    }
    leaf sdwan-octets {
      type uint64;
      units "octets";
      description
        "Total octets in packets dropped due to software defined WAN (SDWAN).";
    }
    leaf sdwan-generic-pkts {
      type uint64;
      description
        "Number of packets dropped due to generic SDWAN processing on the QFP datapath.";
    }
    leaf sdwan-generic-octets {
      type uint64;
      units "octets";
      description
        "Total octets dropped by the QFP for generic SDWAN traffic.";
    }
    leaf sdwan-implicit-acl-pkts {
      type uint64;
      description
        "Number of packets dropped by the QFP that matched an implicit access control list (ACL) in SDWAN datapath.";
    }
    leaf sdwan-implicit-acl-octets {
      type uint64;
      units "octets";
      description
        "Total octets in packets dropped by the QFP that matched an implicit access control list (ACL) in SDWAN datapath.";
    }
    leaf sdwan-acl-pkts {
      type uint64;
      description
        "Number of packets dropped by the QFP that matched an explicit access control list (ACL) in SDWAN datapath.";
    }
    leaf sdwan-acl-octets {
      type uint64;
      units "octets";
      description
        "Total octets in packets dropped by the QFP that matched an explicit access control list (ACL) in SDWAN datapath.";
    }
    leaf sdwan-bfd-pkts {
      type uint64;
      description
        "Number of Bidirectional Fault Detection (BFD) packets dropped by the QFP in SDWAN datapath.";
    }
    leaf sdwan-bfd-octets {
      type uint64;
      units "octets";
      description
        "Total octets in Bidirectional Fault Detection (BFD) packets dropped by the QFP in SDWAN datapath.";
    }
    leaf sdwan-app-route-policy-pkts {
      type uint64;
      description
        "Number of packets dropped by the QFP that matched an SDWAN application route policy.";
    }
    leaf sdwan-app-route-policy-octets {
      type uint64;
      units "octets";
      description
        "Total octets in packets dropped by the QFP that matched an SDWAN application route policy.";
    }
    leaf sdwan-data-policy-pkts {
      type uint64;
      description
        "Number of packets dropped by the QFP that matched an SDWAN data policy.";
    }
    leaf sdwan-data-policy-octets {
      type uint64;
      units "octets";
      description
        "Total octets dropped by SDWAN data policies on the QFP.";
    }
    leaf sdwan-interface-policy-pkts {
      type uint64;
      description
        "Number of packets dropped by SDWAN interface policies on the QFP datapath.";
    }
    leaf sdwan-interface-policy-octets {
      type uint64;
      units "octets";
      description
        "Total octets dropped by SDWAN interface policies on the QFP.";
    }
    leaf sdwan-tunnel-lkup-pkts {
      type uint64;
      description
        "Number of packets dropped during SDWAN tunnel lookup operations on the QFP datapath.";
    }
    leaf sdwan-tunnel-lkup-octets {
      type uint64;
      units "octets";
      description
        "Total octets dropped during SDWAN tunnel lookup operations on the QFP.";
    }
    leaf sdwan-tloc-ext-pkts {
      type uint64;
      description
        "Number of packets dropped due to SDWAN tunnel locator extension (TLOC extension) processing on the QFP datapath.";
    }
    leaf sdwan-tloc-ext-octets {
      type uint64;
      units "octets";
      description
        "Total octets dropped by SDWAN tunnel locator extension (TLOC extension) on the QFP.";
    }
    leaf tunnel-vxlan-mismatch-pkts {
      type uint64;
      description
        "Number of packets dropped because the VxLAN tunnel packet did not match the expected tunnel parameters.";
    }
    leaf tunnel-vxlan-mismatch-octets {
      type uint64;
      units "octets";
      description
        "Total octets in packets dropped because the VxLAN tunnel packet did not match the expected tunnel parameters.";
    }
    leaf l2bd-mac-security-move-pkts {
      type uint64;
      description
        "Number of packets dropped due to layer 2 Bridge Domain (L2BD) MAC security move.";
    }
    leaf l2bd-mac-security-move-octets {
      type uint64;
      units "octets";
      description
        "Total octets in packets dropped due to MAC address moves detected by MAC security within the Layer 2 Bridge Domain (L2BD).";
    }
    leaf l2bd-mac-security-unknown-pkts {
      type uint64;
      description
        "Number of packets with unknown MAC addresses dropped by MAC security in the Layer 2 Bridge Domain (L2BD).";
    }
    leaf l2bd-mac-security-unknown-octets {
      type uint64;
      units "octets";
      description
        "Total octets in packets with unknown MAC addresses dropped by MAC security in the Layer 2 Bridge Domain (L2BD).";
    }
    leaf dapr-noroute-pkts {
      type uint64;
      description
        "Number of packets dropped by Dynamic Application Policy Routing (DAPR) due to missing route information.";
    }
    leaf dapr-noroute-octets {
      type uint64;
      units "octets";
      description
        "Total octets in packets dropped by Dynamic Application Policy Routing (DAPR) due to missing route information.";
    }
    leaf epbr-pkts {
      type uint64;
      description
        "Number of packets dropped by enhanced Policy-Based Routing (ePBR) in the datapath.";
    }
    leaf epbr-octets {
      type uint64;
      units "octets";
      description
        "Total octets in packets dropped by enhanced Policy-Based Routing (ePBR) in the datapath.";
    }
    leaf sdvt-sn-pkts {
      type uint64;
      description
        "Number of packets dropped by the Service Node (SN) in the Service Divert (SDVT) datapath.";
    }
    leaf sdvt-sn-octets {
      type uint64;
      units "octets";
      description
        "Total octets dropped by the Service Node (SN) in the Service Divert (SDVT) datapath.";
    }
    leaf sdvt-pkts {
      type uint64;
      description
        "Number of packets dropped by Service Divert (SDVT) in the datapath.";
    }
    leaf sdvt-octets {
      type uint64;
      units "octets";
      description
        "Total octets dropped by Service Divert (SDVT) in the QFP datapath.";
    }
    leaf tunnel-vxlan-policer-pkts {
      type uint64;
      description
        "Number of packets dropped because the VxLAN tunnel policer rejected them.";
    }
    leaf tunnel-vxlan-policer-octets {
      type uint64;
      units "octets";
      description
        "Total octets in packets dropped because the VxLAN tunnel policer rejected them.";
    }
    leaf tunnel-vrf-mux-pkts {
      type uint64;
      description
        "Number of packets dropped during tunnel VRF multiplexing.";
    }
    leaf tunnel-vrf-mux-octets {
      type uint64;
      units "octets";
      description
        "Total octets in packets dropped during tunnel VRF multiplexing.";
    }
    leaf tunnel-vrf-demux-pkts {
      type uint64;
      description
        "Number of packets dropped during tunnel VRF demultiplexing.";
    }
    leaf tunnel-vrf-demux-octets {
      type uint64;
      units "octets";
      description
        "Total octets in packets dropped during tunnel VRF demultiplexing.";
    }
    leaf cgacl-inv-stats-pkts {
      type uint64;
      description
        "Number of packets dropped due to invalid CG Access Control List (CGACL) statistics.";
    }
    leaf cgacl-inv-stats-octets {
      type uint64;
      units "octets";
      description
        "Total octets in packets dropped due to invalid CG Access Control List (CGACL) statistics.";
    }
    leaf cgacl-pkt-type-pkts {
      type uint64;
      description
        "Number of packets dropped due to an invalid CG Access Control List (CGACL) packet type.";
    }
    leaf cgacl-pkt-type-octets {
      type uint64;
      units "octets";
      description
        "Total octets in packets dropped due to an invalid CG Access Control List (CGACL) packet type.";
    }
    leaf frag-inv-pkts {
      type uint64;
      description
        "Number of IP fragment packets dropped as invalid by the QFP datapath.";
    }
    leaf frag-inv-octets {
      type uint64;
      units "octets";
      description
        "Total octets in IP fragment packets dropped as invalid by the QFP datapath.";
    }
    leaf frag-inv-ipv6-pkts {
      type uint64;
      description
        "Number of IPv6 fragment packets dropped as invalid by the QFP datapath.";
    }
    leaf frag-inv-ipv6-octets {
      type uint64;
      units "octets";
      description
        "Total octets in IPv6 fragment packets dropped as invalid by the QFP datapath.";
    }
    leaf coff-output-pkts {
      type uint64;
      description
        "Number of packets dropped by the datapath due to errors in crypto offload output processing.";
    }
    leaf coff-output-octets {
      type uint64;
      units "octets";
      description
        "Total octets in packets dropped by the datapath due to errors in crypto offload output processing.";
    }
    leaf cable-prng-exp-pkts {
      type uint64;
      description
        "Number of packets dropped due to an expected cable pseudo-random number generator drop.";
    }
    leaf cable-prng-exp-octets {
      type uint64;
      units "octets";
      description
        "Total octets in packets dropped due to an expected cable pseudo-random number generator drop.";
    }
    leaf ipv4-egr-intf-enf-pkts {
      type uint64;
      description
        "Number of IPv4 packets dropped by egress interface enforcement.";
    }
    leaf ipv4-egr-intf-enf-octets {
      type uint64;
      units "octets";
      description
        "Total octets in IPv4 packets dropped by egress interface enforcement.";
    }
    leaf ipv6-egr-intf-enf-pkts {
      type uint64;
      description
        "Number of IPv6 packets dropped by egress interface enforcement.";
    }
    leaf ipv6-egr-intf-enf-octets {
      type uint64;
      units "octets";
      description
        "Total octets in IPv6 packets dropped by egress interface enforcement.";
    }
    leaf cable-dhcp-bad-len-pkts {
      type uint64;
      description
        "Number of packets dropped due to an invalid cable DHCP packet length.";
    }
    leaf cable-dhcp-bad-len-octets {
      type uint64;
      units "octets";
      description
        "Total octets in packets dropped due to an invalid cable DHCP packet length.";
    }
    leaf l2bd-uuf-suppr-pkts {
      type uint64;
      description
        "Number of packets dropped due to layer 2 Bridge Domain (L2BD) unknown unicast flood suppression.";
    }
    leaf l2bd-uuf-suppr-octets {
      type uint64;
      units "octets";
      description
        "Total octets in packets dropped due to layer 2 Bridge Domain (L2BD) unknown unicast flood suppression.";
    }
    leaf wpan-pkts {
      type uint64;
      description
        "Number of packets dropped during Wireless Personal Area Network (WPAN) processing.";
    }
    leaf wpan-octets {
      type uint64;
      units "octets";
      description
        "Total octets in packets dropped during Wireless Personal Area Network (WPAN) processing.";
    }
    leaf l2bd-sisf-ctrl-pkts {
      type uint64;
      description
        "Number of packets dropped due to layer 2 Bridge Domain (L2BD) Switch Integrated Security Features control.";
    }
    leaf l2bd-sisf-ctrl-octets {
      type uint64;
      units "octets";
      description
        "Total octets in packets dropped due to layer 2 Bridge Domain (L2BD) Switch Integrated Security Features control.";
    }
    leaf cable-recycle-queue-pkts {
      type uint64;
      description
        "Number of packets dropped by the cable recycle queue.";
    }
    leaf cable-recycle-queue-octets {
      type uint64;
      units "octets";
      description
        "Total octets dropped by the cable recycle queue.";
    }
    leaf pcgw-pdu-sess-err-pkts {
      type uint64;
      description
        "Number of packets dropped because Packet Core Gateway (PCGW) PDU session processing failed.";
    }
    leaf pcgw-pdu-sess-err-octets {
      type uint64;
      units "octets";
      description
        "Total octets in packets dropped because Packet Core Gateway (PCGW) PDU session processing failed.";
    }
    leaf pcgw-gtpu-err-pkts {
      type uint64;
      description
        "Number of packets dropped due to GPRS Tunneling Protocol User plane (GTPU) processing errors in the Packet Core Gateway.";
    }
    leaf pcgw-gtpu-err-octets {
      type uint64;
      units "octets";
      description
        "Total octets in packets dropped due to GPRS Tunneling Protocol User plane (GTPU) processing errors in the Packet Core Gateway.";
    }
    leaf pcgw-punt-inj-err-pkts {
      type uint64;
      description
        "Number of packets dropped because Packet Core Gateway (PCGW) punt or inject processing failed.";
    }
    leaf pcgw-punt-inj-err-octets {
      type uint64;
      units "octets";
      description
        "Total octets in packets dropped because Packet Core Gateway (PCGW) punt or inject processing failed.";
    }
    leaf pcacl-pkts {
      type uint64;
      description
        "Number of packets dropped by Access Control Lists (ACLs) in the Packet Core Gateway.";
    }
    leaf pcacl-octets {
      type uint64;
      units "octets";
      description
        "Total octets in packets dropped by Packet Core access control lists (ACLs).";
    }
    leaf vtcp-err-pkts {
      type uint64;
      description
        "Number of packets dropped due to errors during Virtual TCP (VTCP) processing on the QFP datapath.";
    }
    leaf vtcp-err-octets {
      type uint64;
      units "octets";
      description
        "Total octets in packets dropped due to errors during Virtual TCP (VTCP) processing on the QFP datapath.";
    }
    leaf vtcp-inv-tx-pkts {
      type uint64;
      description
        "Number of packets dropped due to an invalid Virtual TCP transmit operation.";
    }
    leaf vtcp-inv-tx-octets {
      type uint64;
      units "octets";
      description
        "Total octets in packets dropped due to an invalid Virtual TCP transmit operation.";
    }
    leaf vtcp-pa-err-pkts {
      type uint64;
      description
        "Number of packets dropped due to virtual TCP packet abstraction error.";
    }
    leaf vtcp-pa-err-octets {
      type uint64;
      units "octets";
      description
        "Total octets in packets dropped due to virtual TCP packet abstraction error.";
    }
    leaf vtcp-mem-err-pkts {
      type uint64;
      description
        "Number of packets dropped due to a Virtual TCP memory error.";
    }
    leaf vtcp-mem-err-octets {
      type uint64;
      units "octets";
      description
        "Total octets in packets dropped due to a Virtual TCP memory error.";
    }
    leaf vtcp-punt-err-pkts {
      type uint64;
      description
        "Number of packets dropped due to virtual TCP punt error.";
    }
    leaf vtcp-punt-err-octets {
      type uint64;
      units "octets";
      description
        "Total octets in packets dropped due to errors while punting packets to the Virtual TCP (VTCP) process on the QFP datapath.";
    }
    leaf fbd-oom-err-pkts {
      type uint64;
      description
        "Number of packets dropped by the datapath due to out-of-memory conditions in the Flow Database.";
    }
    leaf fbd-oom-err-octets {
      type uint64;
      units "octets";
      description
        "Total octets in packets dropped by the datapath due to out-of-memory conditions in the Flow Database.";
    }
    leaf memory-intf-pkts {
      type uint64;
      description
        "Number of packets dropped by the datapath due to allocation failures for Service Engine shared memory buffers.";
    }
    leaf memory-intf-octets {
      type uint64;
      units "octets";
      description
        "Total octets in packets dropped by the datapath due to allocation failures for Service Engine shared memory buffers.";
    }
    leaf no-intf-res-pkts {
      type uint64;
      description
        "Number of packets dropped due to lack of interface IO resources in the datapath.";
    }
    leaf no-intf-res-octets {
      type uint64;
      units "octets";
      description
        "Total octets in packets dropped due to lack of interface IO resources in the datapath.";
    }
    leaf dlep-uncfgd-pkts {
      type uint64;
      description
        "Number of packets dropped because Dynamic Link Exchange Protocol (DLEP) is not configured.";
    }
    leaf dlep-uncfgd-octets {
      type uint64;
      units "octets";
      description
        "Total octets in packets dropped because Dynamic Link Exchange Protocol (DLEP) is not configured.";
    }
    leaf cable-arp-autoreply-pkts {
      type uint64;
      description
        "Number of packets dropped due to cable ARP automatic reply.";
    }
    leaf cable-arp-autoreply-octets {
      type uint64;
      units "octets";
      description
        "Total octets in packets dropped during automatic ARP reply processing on cable interfaces by the QFP.";
    }
    leaf unisr-no-match-pkts {
      type uint64;
      description
        "Number of packets dropped because Unicast Service Reflection did not find a matching entry in the QFP datapath.";
    }
    leaf unisr-no-match-octets {
      type uint64;
      units "octets";
      description
        "Total octets in packets dropped because Unicast Service Reflection did not find a matching entry in the QFP datapath.";
    }
    leaf unisr-src-fltrd-pkts {
      type uint64;
      description
        "Number of packets dropped by Unicast Service Reflection due to source address filtering in the QFP datapath.";
    }
    leaf unisr-src-fltrd-octets {
      type uint64;
      units "octets";
      description
        "Total octets in packets dropped by Unicast Service Reflection due to source address filtering in the QFP datapath.";
    }
    leaf dlep-mcast-inv-enc-pkts {
      type uint64;
      description
        "Number of packets dropped due to invalid DLEP multicast encapsulation information.";
    }
    leaf dlep-mcast-inv-enc-octets {
      type uint64;
      units "octets";
      description
        "Total octets in packets dropped due to invalid DLEP multicast encapsulation information.";
    }
    leaf dlep-mcast-phy2vmi-pkts {
      type uint64;
      description
        "Number of packets dropped due to a DLEP multicast PHY-to-VMI lookup failure.";
    }
    leaf dlep-mcast-phy2vmi-octets {
      type uint64;
      units "octets";
      description
        "Total octets in packets dropped due to a DLEP multicast PHY-to-VMI lookup failure.";
    }
    leaf dlep-mcast-vmi2phy-pkts {
      type uint64;
      description
        "Number of packets dropped due to a DLEP multicast VMI-to-PHY lookup failure.";
    }
    leaf dlep-mcast-vmi2phy-octets {
      type uint64;
      units "octets";
      description
        "Total octets in packets dropped due to a DLEP multicast VMI-to-PHY lookup failure.";
    }
    leaf cable-lc2sup-punt-pkts {
      type uint64;
      description
        "Number of packets dropped when punted from the cable line card (LC) to the supervisor (SUP) module.";
    }
    leaf cable-lc2sup-punt-octets {
      type uint64;
      units "octets";
      description
        "Total octets dropped when punted from the cable line card (LC) to the supervisor (SUP) module.";
    }
    leaf bad-coff-buffer-pkts {
      type uint64;
      description
        "Number of packets dropped due to an unsupported crypto offload buffer type in the datapath.";
    }
    leaf bad-coff-buffer-octets {
      type uint64;
      units "octets";
      description
        "Total octets in packets dropped due to an unsupported crypto offload buffer type in the datapath.";
    }
    leaf pa-pkt-not-suppt-pkts {
      type uint64;
      description
        "Number of packets dropped because the Packet Abstraction (PA) layer does not support their type or format.";
    }
    leaf pa-pkt-not-suppt-octets {
      type uint64;
      units "octets";
      description
        "Total octets in packets dropped because the Packet Abstraction (PA) layer does not support their type or format.";
    }
    leaf dca-drop-pkts {
      type uint64;
      description
        "Number of packets dropped by the DCA process.";
    }
    leaf dca-drop-octets {
      type uint64;
      units "octets";
      description
        "Total octets dropped by the DCA process.";
    }
    leaf queue-trans-drop-pkts {
      type uint64;
      description
        "Number of packets dropped due to queue transitions in the QFP datapath.";
    }
    leaf queue-trans-drop-octets {
      type uint64;
      units "octets";
      description
        "Total octets dropped due to queue transitions in the QFP datapath.";
    }
  }

  container qfp-stats-oper-data {
    config false;
    description
      "QFP statistics operational data";
    list location {
      key "fru slot bay chassis node";
      description
        "A list of data provider locations";
      uses common-types-ios-xe:extended-location;
      container datapath-qfp-stats {
        presence "datapath-qfp-stats";
        description
          "Datapath Quantum Flow Processor(QFP) statistics";
        uses qfp-stats-ios-xe-oper:datapath-qfp-stats;
      }
    }
  }
}
