module Cisco-IOS-XE-qfp-dp-cmn-stats-oper {
  yang-version 1.1;
  namespace "http://cisco.com/ns/yang/Cisco-IOS-XE-qfp-dp-cmn-stats-oper";
  prefix qfp-dp-cmn-stats-ios-xe-oper;

  import Cisco-IOS-XE-common-types {
    prefix common-types-ios-xe;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for the common QFP datapath statistics operational data.
     Copyright (c) 2024, 2026 by Cisco Systems, Inc.
     All rights reserved.";

  revision 2026-08-01 {
    description
      "- Added DHCPv6 Relay Punt Statistics";
    reference
      "1.1.0";
    cisco-semver:module-version "1.1.0";
  }
  revision 2024-11-01 {
    description
      "Initial revision";
    reference
      "1.0.0";
    cisco-semver:module-version "1.0.0";
  }

  grouping dp-cpu-util-stats {
    description
      "CPP datapath utilization";
    leaf load-5sec {
      type uint64;
      description
        "Datapath utilization load over last 5 secs";
    }
    leaf load-1min {
      type uint64;
      description
        "Datapath utilization load over last 1 min";
    }
    leaf load-5min {
      type uint64;
      description
        "Datapath utilization load over last 5 mins";
    }
    leaf load-60min {
      type uint64;
      description
        "Datapath utilization load over last 60 mins";
    }
    leaf input-pps-5sec {
      type uint64;
      description
        "Total input packets per second over last 5 secs";
    }
    leaf input-pps-1min {
      type uint64;
      description
        "Total input packets per second over last 1 min";
    }
    leaf input-pps-5min {
      type uint64;
      description
        "Total input packets per second over last 5 mins";
    }
    leaf input-pps-60min {
      type uint64;
      description
        "Total input packets per second over last 60 mins";
    }
    leaf output-pps-5sec {
      type uint64;
      description
        "Total output packets per second over last 5 secs";
    }
    leaf output-pps-1min {
      type uint64;
      description
        "Total output packets per second over last 1 min";
    }
    leaf output-pps-5min {
      type uint64;
      description
        "Total output packets per second over last 5 mins";
    }
    leaf output-pps-60min {
      type uint64;
      description
        "Total output packets per second over last 60 mins";
    }
    leaf input-bps-5sec {
      type uint64;
      description
        "Total input bytes per second over last 5 secs";
    }
    leaf input-bps-1min {
      type uint64;
      description
        "Total input bytes per second over last 1 min";
    }
    leaf input-bps-5min {
      type uint64;
      description
        "Total input bytes per second over last 5 mins";
    }
    leaf input-bps-60min {
      type uint64;
      description
        "Total input bytes per second over last 60 mins";
    }
    leaf output-bps-5sec {
      type uint64;
      description
        "Total output bytes per second over last 5 secs";
    }
    leaf output-bps-1min {
      type uint64;
      description
        "Total output bytes per second over last 1 min";
    }
    leaf output-bps-5min {
      type uint64;
      description
        "Total output bytes per second over last 5 min";
    }
    leaf output-bps-60min {
      type uint64;
      description
        "Total output bytes per second over last 60 mins";
    }
  }

  grouping gw-dp-global-punt-stats {
    description
      "Global gateway datapath punt statistics";
    leaf sisf-pkt-type-arp {
      type uint64;
      description
        "ARP packets punted to SISF";
    }
    leaf sisf-pkt-type-dhcp {
      type uint64;
      description
        "DHCP packets punted to SISF";
    }
    leaf sisf-pkt-type-dhcp6 {
      type uint64;
      description
        "IPv6 DHCP packets punted to SISF";
    }
    leaf sisf-pkt-type-ipv6-nd {
      type uint64;
      description
        "IPv6 neighbor discovery packets punted to SISF";
    }
    leaf sisf-pkt-type-dhcp-relay {
      type uint64;
      description
        "DHCP relay packets punted to SISF";
    }
    leaf wlclient-pkt-type-mdns {
      type uint64;
      description
        "Wireless client MDNS packets punted";
    }
    leaf quic-pkt-type-wls-ctrl {
      type uint64;
      description
        "QUIC wireless control packets punted";
    }
    leaf quic-pkt-type-mob-ctrl {
      type uint64;
      description
        "Punted QUIC mobility packets punted";
    }
    leaf l3dr-pkt-type-dstore {
      type uint64;
      description
        "dStore packets punted";
    }
    leaf vxlan-pkt-type-bfd-ka {
      type uint64;
      description
        "VxLAN BFD keepalive packets punted";
    }
    leaf vxlan-pkt-type-radius {
      type uint64;
      description
        "VxLAN Radius packets punted";
    }
    leaf vxlan-pkt-type-pdr-agnt {
      type uint64;
      description
        "VxLAN Poder Agent packets punted";
    }
    leaf sisf-pkt-type-dhcp6-relay {
      type uint64;
      description
        "DHCPv6 relay packets punted to SISF";
    }
  }

  grouping dp-prov-stats {
    description
      "Datapath provisioning statistics";
    leaf create-fp {
      type uint64;
      description
        "Create object requests by FP to CPP";
    }
    leaf modify-fp {
      type uint64;
      description
        "Modify object requests by FP to CPP";
    }
    leaf delete-fp {
      type uint64;
      description
        "Delete object requests by FP to CPP";
    }
    leaf create-ack-fp {
      type uint64;
      description
        "Create object succeeded, acks from CPP to FP";
    }
    leaf create-ack-fail-fp {
      type uint64;
      description
        "Create object succeeded, acks
         failed to send from CPP to FP";
    }
    leaf create-nack-fp {
      type uint64;
      description
        "Create object failed, nacks from CPP to FP";
    }
    leaf create-nack-fail-fp {
      type uint64;
      description
        "Create object failed, nacks
         failed to send from CPP to FP";
    }
    leaf modify-ack-fp {
      type uint64;
      description
        "Modify object succeeded, acks from CPP to FP";
    }
    leaf modify-ack-fail-fp {
      type uint64;
      description
        "Modify object succeeded, acks
         failed to send from CPP to FP";
    }
    leaf modify-nack-fp {
      type uint64;
      description
        "Modify object failed, nacks from CPP to FP";
    }
    leaf modify-nack-fail-fp {
      type uint64;
      description
        "Modify object failed, nacks
         failed to send from CPP to FP";
    }
    leaf delete-ack-fp {
      type uint64;
      description
        "Delete object succeeded, acks from CPP to FP";
    }
    leaf delete-ack-fail-fp {
      type uint64;
      description
        "Delete object succeeded, acks
         failed to send from CPP to FP";
    }
    leaf delete-nack-fp {
      type uint64;
      description
        "Delete object failed, nacks from CPP to FP";
    }
    leaf delete-nack-fail-fp {
      type uint64;
      description
        "Delete object failed, nacks
         failed to send from CPP to FP";
    }
  }

  grouping dp-tun-drop-stats-cmn {
    description
      "Global wireless tunnel common drop stats";
    leaf nosupp-linktype {
      type uint64;
      description
        "Wireless tunnel unsupported link type error";
    }
    leaf invld-tun {
      type uint64;
      description
        "Wireless tunnel invalid tunnel error";
    }
    leaf tun-input-cfg-miss {
      type uint64;
      description
        "Wireless tunnel input config missing error";
    }
    leaf tun-ingr-parse-err {
      type uint64;
      description
        "Wireless tunnel ingress parsing error";
    }
    leaf v4-tun-not-found-not-ka {
      type uint64;
      description
        "Wireless ipv4 tunnel not found and not keepalive error";
    }
    leaf v6-tun-not-found-not-ka {
      type uint64;
      description
        "Wireless ipv6 tunnel not found and not keepalive error";
    }
    leaf add-pkt-head-fail {
      type uint64;
      description
        "Wireless tunnel add to packet header error";
    }
    leaf v4-add-pkt-head-fail {
      type uint64;
      description
        "Wireless tunnel add to ipv4 packet header error";
    }
    leaf v6-add-pkt-head-fail {
      type uint64;
      description
        "Wireless tunnel add to ipv6 packet header error";
    }
    leaf mcast-add-pkt-head-fail {
      type uint64;
      description
        "Wireless multicast tunnel add to packet header error";
    }
    leaf mcast-v4-add-pkt-head-fail {
      type uint64;
      description
        "Wireless multicast tunnel add to
         ipv4 packet header error";
    }
    leaf mcast-v6-add-pkt-head-fail {
      type uint64;
      description
        "Wireless multicast tunnel add to ipv6
         packet header error";
    }
    leaf v4-encap-type-dis {
      type uint64;
      description
        "Wireless tunnel ipv4 encap type disabled";
    }
    leaf v6-encap-type-dis {
      type uint64;
      description
        "Wireless tunnel ipv6 encap type disabled";
    }
    leaf v4-input-uidb-invld {
      type uint64;
      description
        "Wireless tunnel ipv4 input UIDB invalid";
    }
    leaf v6-input-uidb-invld {
      type uint64;
      description
        "Wireless tunnel ipv6 input UIDB invalid";
    }
    leaf ingr-hdr-too-small {
      type uint64;
      description
        "Wireless tunnel invalid header length error";
    }
    leaf inv-hdr-type-err {
      type uint64;
      description
        "Wireless tunnel invalid encap header type error";
    }
    leaf mcast-nd-to-mob-tun {
      type uint64;
      description
        "Wireless tunnel blocks mcast ND from mobility
         to mobility tunnel";
    }
    leaf tun-mgmt-vnid-invld-pkt {
      type uint64;
      description
        "Wireless tunnel management VNI invalid packet error";
    }
    leaf vxlan-inj-hdr-add-err {
      type uint64;
      description
        "VxLAN inject header add error";
    }
  }

  grouping dp-wlclient-drop-stats-cmn {
    description
      "Global wireless client common drop stats";
    leaf v6-max-addrs-err {
      type uint64;
      description
        "Wireless client ipv6 max addresses drop";
    }
    leaf ipglean-ctr-inx-err {
      type uint64;
      description
        "Wireless client IP glean counter index error";
    }
    leaf ipglean-ctr-unchngd-err {
      type uint64;
      description
        "Wireless client IP glean counter unchanged error";
    }
    leaf ipglean-alloc-nomem-err {
      type uint64;
      description
        "Wireless Client IP glean no memory allocated error";
    }
    leaf ipglean-bucket-max-err {
      type uint64;
      description
        "Wireless client IP glean bucket reached max limit,
         packets dropped";
    }
    leaf iplrn-l2-invld-punt-pkt {
      type uint64;
      description
        "Wireless client IP learn l2 punt data packet skip";
    }
    leaf iplrn-v4-invld-punt-pkt {
      type uint64;
      description
        "Wireless client IP learn ipv4 punt data packet skip";
    }
    leaf iplrn-v6-invld-punt-pkt {
      type uint64;
      description
        "Wireless client IP learn ipv6 punt data packet skip";
    }
    leaf in-sb-miss {
      type uint64;
      description
        "Wireless client input subblock missing error";
    }
    leaf swport-dmac-in-sb-miss {
      type uint64;
      description
        "Wireless vlan bridging mcast/bcast destination MAC input SB missing";
    }
    leaf swport-src-svi-in-sb-miss {
      type uint64;
      description
        "Wireless vlan bridging source
         SVI input subblock missing";
    }
    leaf swport-src-wlclnt-sb-miss {
      type uint64;
      description
        "Wireless vlan bridging source wireless client
         input subblock missing";
    }
    leaf in-cfg-miss-err {
      type uint64;
      description
        "Wireless client input config missing";
    }
    leaf macaddr-fetch-err {
      type uint64;
      description
        "Wireless client global mac address fetch error";
    }
    leaf hdr-add-err {
      type uint64;
      description
        "Wireless client header add error";
    }
    leaf clnt-id-inj-no-uidb-err {
      type uint64;
      description
        "Wireless client ID inject UIDB error";
    }
    leaf clnt-id-inj-clnt-not-fnd {
      type uint64;
      description
        "Wireless client ID inject - client not found";
    }
    leaf egr-tun-outuidb-invld {
      type uint64;
      description
        "Wireless client egress tunnel output UIDB invalid";
    }
    leaf egr-prep-entry-uidb-miss {
      type uint64;
      description
        "Wireless client egress prepare entry -
         output UIDB missing";
    }
    leaf p2p-block-drop {
      type uint64;
      description
        "Wireless client P2P blocking drop";
    }
    leaf ipsk-p2p-tag-mismatch-drop {
      type uint64;
      description
        "Wireless client iPSK P2P tag mismatch";
    }
    leaf blk-mgmt-over-wls-err {
      type uint64;
      description
        "Wireless client block management over wireless error";
    }
    leaf blk-mgmt-over-wls-rte-err {
      type uint64;
      description
        "Wireless client block routed management
         over wireless error";
    }
    leaf ingr-no-bfib-entry-err {
      type uint64;
      description
        "Wireless client BFIB entry not present error";
    }
    leaf ingr-bfib-src-non-clnt-err {
      type uint64;
      description
        "BFIB source is not wireless client error";
    }
    leaf mdns-pkt-drop {
      type uint64;
      description
        "Wireless client MDNS packet drop";
    }
    leaf ingr-gue-pkt-drop {
      type uint64;
      description
        "Wireless client ingress GUE packet drop";
    }
    leaf ingr-upn-dst-non-upn-drop {
      type uint64;
      description
        "Ingress has UPN but destination is not UPN,
         packets dropped";
    }
    leaf ingr-upn-tag-mismatch {
      type uint64;
      description
        "Wireless client ingress UPN tag mismatch";
    }
    leaf ingr-upn-invld-dst-uidb {
      type uint64;
      description
        "Wireless client ingress UPN destination
         has invalid UIDB, packets dropped";
    }
    leaf ingr-clnt-no-upn-tag-drop {
      type uint64;
      description
        "Ingress has UPN but wireless client has no
         UPN tag, packets dropped";
    }
    leaf egr-upn-src-non-upn-drop {
      type uint64;
      description
        "Wireless client egress has UPN but source
         is not UPN, packets dropped";
    }
    leaf ingr-ipv6-dis-drop {
      type uint64;
      description
        "Wireless client ingress ipv6 disable drop";
    }
    leaf egr-ipv6-dis-drop {
      type uint64;
      description
        "Wireless client egress ipv6 disable drop";
    }
    leaf ipsk-p2p-no-sb-drop {
      type uint64;
      description
        "Wireless client Egress IPSK P2P no
         config subblock drop";
    }
    leaf egr-upn-src-no-sb-drop {
      type uint64;
      description
        "Wireless client egress UPN no config subblock,
         packets drop";
    }
    leaf ingr-upn-src-no-sb-drop {
      type uint64;
      description
        "Wireless client ingress UPN no config subblock,
         packets dropped";
    }
    leaf egr-v4-cant-frag-err {
      type uint64;
      description
        "Wireless client egress ipv4 can't fragment,
         packets dropped";
    }
    leaf egr-v4-frag-err {
      type uint64;
      description
        "Wireless client egress ipv4 fragmentation error";
    }
  }

  grouping gw-dp-punt-stats {
    description
      "Gateway datapath punt statistics";
    leaf req-ts {
      type yang:date-and-time;
      description
        "The time at which the datapath punt stats request was
         received / fulfilled by the datapath";
    }
    container global-punt-cntrs {
      description
        "Device longitude";
      uses qfp-dp-cmn-stats-ios-xe-oper:gw-dp-global-punt-stats;
    }
  }

  grouping gw-dp-stats {
    description
      "General gateway datapath statistics";
    leaf req-ts {
      type yang:date-and-time;
      description
        "The time at which the datapath common stats request was
         received / fulfilled by the datapath";
    }
    container cpu-stats {
      description
        "DP utilization statistics";
      uses qfp-dp-cmn-stats-ios-xe-oper:dp-cpu-util-stats;
    }
    container vxlan-prov-stats {
      description
        "VxLAN tunnel provisioning statistics";
      uses qfp-dp-cmn-stats-ios-xe-oper:dp-prov-stats;
    }
    container quic-prov-stats {
      description
        "QUIC tunnel provisioning statistics";
      uses qfp-dp-cmn-stats-ios-xe-oper:dp-prov-stats;
    }
    container wlclient-prov-stats {
      description
        "Wireless client provisioning statistics";
      uses qfp-dp-cmn-stats-ios-xe-oper:dp-prov-stats;
    }
    container vxlan-drops {
      description
        "Global VxLAN tunnel packet drops";
      uses qfp-dp-cmn-stats-ios-xe-oper:dp-tun-drop-stats-cmn;
    }
    container wlclient-drops {
      description
        "Global wireless client packet drops";
      uses qfp-dp-cmn-stats-ios-xe-oper:dp-wlclient-drop-stats-cmn;
    }
  }

  container qfp-dp-cmn-stats-oper-data {
    config false;
    description
      "QFP datapath common statistics operational data";
    list location {
      key "fru slot bay chassis node";
      description
        "A list of data provider locations";
      uses common-types-ios-xe:extended-location;
      container gw-dp-punt-stats {
        presence "gw-dp-punt-stats";
        description
          "Gateway datapath punt statistics";
        uses qfp-dp-cmn-stats-ios-xe-oper:gw-dp-punt-stats;
      }
      container gw-dp-stats {
        presence "gw-dp-stats";
        description
          "General gateway datapath statistics";
        uses qfp-dp-cmn-stats-ios-xe-oper:gw-dp-stats;
      }
    }
  }
}
