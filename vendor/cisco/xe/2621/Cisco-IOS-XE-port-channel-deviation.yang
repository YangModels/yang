module Cisco-IOS-XE-port-channel-deviation {
  yang-version 1.1;
  namespace "http://cisco.com/ns/yang/Cisco-IOS-XE-port-channel-deviation";
  prefix ios-ethernet-p;

  import Cisco-IOS-XE-native {
    prefix ios;
  }
  import Cisco-IOS-XE-ethernet {
    prefix ios-eth;
  }
  import cisco-semver {
    prefix cisco-semver;
  }

  organization
    "Cisco Systems";
  description
    "Cisco XE Native Deviation YANG module for IOS
     Copyright (c) 2020-2021 by Cisco Systems, Inc.
     All rights reserved.";

  revision 2026-08-01 {
    description
      "- Added TwoHundredGigE and FourHundredGigE interface support";
    cisco-semver:module-version "1.7.0";
  }
  revision 2025-07-01 {
    description
      "- Added FiftyGigabitEthernet interface support";
    cisco-semver:module-version "1.6.0";
  }
  revision 2024-07-01 {
    description
      "- Moved unsupported xpaths to port-channel-unsupported deviation file";
    cisco-semver:module-version "1.5.0";
  }
  revision 2022-11-01 {
    description
      "- Update yang-version to 1.1";
    cisco-semver:module-version "1.4.0";
  }
  revision 2020-11-01 {
    description
      "Added port-channel deviation";
    cisco-semver:module-version "1.2.0";
  }

  deviation "/ios:native/ios:interface/ios:Port-channel/ios:name" {
    deviate replace {
      type uint32 {
        range "1..64";
      }
    }
  }

  deviation "/ios:native/ios:interface/ios:GigabitEthernet/ios-eth:channel-group/ios-eth:number" {
    deviate replace {
      type uint16 {
        range "1..64";
      }
    }
  }

  deviation "/ios:native/ios:interface/ios:AppGigabitEthernet/ios-eth:channel-group/ios-eth:number" {
    deviate replace {
      type uint16 {
        range "1..64";
      }
    }
  }

  deviation "/ios:native/ios:interface/ios:FastEthernet/ios-eth:channel-group/ios-eth:number" {
    deviate replace {
      type uint16 {
        range "1..64";
      }
    }
  }

  deviation "/ios:native/ios:interface/ios:FiveGigabitEthernet/ios-eth:channel-group/ios-eth:number" {
    deviate replace {
      type uint16 {
        range "1..64";
      }
    }
  }

  deviation "/ios:native/ios:interface/ios:FortyGigabitEthernet/ios-eth:channel-group/ios-eth:number" {
    deviate replace {
      type uint16 {
        range "1..64";
      }
    }
  }

  deviation "/ios:native/ios:interface/ios:FiftyGigabitEthernet/ios-eth:channel-group/ios-eth:number" {
    deviate replace {
      type uint16 {
        range "1..64";
      }
    }
  }

  deviation "/ios:native/ios:interface/ios:GigabitEthernet/ios-eth:channel-group/ios-eth:number" {
    deviate replace {
      type uint16 {
        range "1..64";
      }
    }
  }

  deviation "/ios:native/ios:interface/ios:TenGigabitEthernet/ios-eth:channel-group/ios-eth:number" {
    deviate replace {
      type uint16 {
        range "1..64";
      }
    }
  }

  deviation "/ios:native/ios:interface/ios:TwentyFiveGigE/ios-eth:channel-group/ios-eth:number" {
    deviate replace {
      type uint16 {
        range "1..64";
      }
    }
  }

  deviation "/ios:native/ios:interface/ios:TwoGigabitEthernet/ios-eth:channel-group/ios-eth:number" {
    deviate replace {
      type uint16 {
        range "1..64";
      }
    }
  }

  deviation "/ios:native/ios:interface/ios:HundredGigE/ios-eth:channel-group/ios-eth:number" {
    deviate replace {
      type uint16 {
        range "1..64";
      }
    }
  }

  deviation "/ios:native/ios:interface/ios:TwoHundredGigE/ios-eth:channel-group/ios-eth:number" {
    deviate replace {
      type uint16 {
        range "1..64";
      }
    }
  }

  deviation "/ios:native/ios:interface/ios:FourHundredGigE/ios-eth:channel-group/ios-eth:number" {
    deviate replace {
      type uint16 {
        range "1..64";
      }
    }
  }
}
