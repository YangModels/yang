module Cisco-IOS-XE-bgp-route-oper {
  yang-version 1.1;
  namespace "http://cisco.com/ns/yang/Cisco-IOS-XE-bgp-route-oper";
  prefix bgp-route-ios-xe-oper;

  import Cisco-IOS-XE-bgp-common-oper {
    prefix bgp-common-ios-xe-oper;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     route for bgp route operational data.
     Copyright (c) 2016-2020, 2022, 2026 by Cisco Systems, Inc.
     All rights reserved.";

  revision 2026-08-01 {
    description
      "Updated descriptions of several model elements to clarify their meaning and purpose";
    reference
      "2.2.0";
    cisco-semver:module-version "2.2.0";
  }
  revision 2022-11-01 {
    description
      "Update yang-version to 1.1";
    reference
      "2.1.0";
    cisco-semver:module-version "2.1.0";
  }
  revision 2020-11-01 {
    description
      "Added obsolete status to invalid Peer Group Elements";
    reference
      "2.0.0";
    cisco-semver:module-version "2.0.0";
  }
  revision 2019-05-01 {
    description
      "Added semantic version";
    reference
      "1.6.0";
    cisco-semver:module-version "1.6.0";
  }
  revision 2018-10-29 {
    description
      "Cleaned up spelling errors in descriptions.";
    reference
      "1.5.0";
    cisco-semver:module-version "1.5.0";
  }
  revision 2018-04-09 {
    description
      "Added enumeration type for bgp path internal/external
       status";
    reference
      "1.4.0";
    cisco-semver:module-version "1.4.0";
  }
  revision 2017-09-25 {
    description
      "Properly indicated leaf-list ordering";
    reference
      "1.3.0";
    cisco-semver:module-version "1.3.0";
  }
  revision 2017-05-22 {
    description
      "Added the BGP Peer Group Elements";
    reference
      "1.2.0";
    cisco-semver:module-version "1.2.0";
  }
  revision 2017-05-12 {
    description
      "Added the BGP RD and Neighbor routes";
    reference
      "1.1.0";
    cisco-semver:module-version "1.1.0";
  }
  revision 2017-02-07 {
    description
      "Initial revision";
    reference
      "1.0.0";
    cisco-semver:module-version "1.0.0";
  }

  typedef bgp-origin-code {
    type enumeration {
      enum origin-igp {
        value 0;
        description
          "BGP origin code IGP";
      }
      enum origin-egp {
        value 1;
        description
          "BGP origin code EGP";
      }
      enum origin-incomplete {
        value 2;
        description
          "BGP origin code incomplete";
      }
    }
    description
      "BGP origin code";
  }

  typedef bgp-rpki-status {
    type enumeration {
      enum rpki-valid {
        value 0;
        description
          "BGP route is valid according to RPKI validation";
      }
      enum rpki-invalid {
        value 1;
        description
          "BGP route is invalid according to RPKI validation";
      }
      enum rpki-not-found {
        value 2;
        description
          "BGP route does not have a corresponding RPKI record";
      }
      enum rpki-not-enabled {
        value 3;
        description
          "RPKI validation is not enabled for the BGP route";
      }
      enum rpki-illegal {
        value 4;
        description
          "BGP route has an illegal RPKI status";
      }
    }
    description
      "BGP RPKI status";
  }

  typedef bgp-path-origin {
    type enumeration {
      enum internal-path {
        value 0;
        description
          "BGP origin internal";
      }
      enum external-path {
        value 1;
        description
          "BGP origin external";
      }
    }
    description
      "BGP path internal/external origin";
  }

  typedef bgp-route-filters {
    type enumeration {
      enum bgp-rf-all {
        value 0;
        description
          "BGP all route filter";
      }
      enum bgp-rf-cidr-only {
        value 1;
        description
          "BGP CIDR only route filter";
      }
      enum bgp-rf-label {
        value 2;
        description
          "BGP label route filter";
      }
      enum bgp-rf-rib-failure {
        value 3;
        description
          "BGP RIB failure route filter";
      }
      enum bgp-rf-injected {
        value 4;
        description
          "BGP injected route filter";
      }
      enum bgp-rf-inconsistent {
        value 5;
        description
          "BGP inconsistent route filter";
      }
      enum bgp-rf-community {
        value 6;
        description
          "BGP community route filter";
      }
      enum bgp-rf-extcommunity {
        value 7;
        description
          "BGP extcommunity route filter";
      }
      enum bgp-rf-oer-controlled {
        value 8;
        description
          "BGP OER controlled route filter";
      }
      enum bgp-rf-pending {
        value 9;
        description
          "BGP pending route filter";
      }
    }
    description
      "Enumeration of the BGP route filters that can be applied to this address family";
  }

  typedef bgp-neighbor-route-filters {
    type enumeration {
      enum bgp-nrf-post-received {
        value 0;
        description
          "BGP received routes post policy";
      }
      enum bgp-nrf-pre-received {
        value 1;
        description
          "BGP received routes pre policy";
      }
      enum bgp-nrf-pre-advertised {
        value 2;
        description
          "BGP pre advertised pre policy";
      }
      enum bgp-nrf-post-advertised {
        value 3;
        description
          "BGP post advertised post policy";
      }
    }
    description
      "Enumeration of route filters applied to BGP neighbor routes, specifying filtering criteria for routes exchanged with each neighbor";
  }

  grouping peer-group {
    description
      "Attributes of a BGP peer group configured for this address family";
    leaf name {
      type string;
      description
        "BGP peer group name";
    }
    leaf description {
      type string;
      description
        "Peer Group description string";
    }
    leaf remote-as {
      type uint32;
      description
        "Peer Group Remote AS value";
    }
    leaf bgp-version {
      type uint16;
      description
        "BGP version being used to communicate
         with the remote router";
    }
    leaf min-time {
      type uint16;
      units "seconds";
      description
        "Minimum route advertisement interval, in seconds, for this BGP peer group";
    }
    leaf num-of-sessions {
      type uint32;
      description
        "Number of Sessions for peer group";
    }
    leaf num-estab-sessions {
      type uint32;
      description
        "Number of established sessions
         for peer group";
    }
    leaf num-sso-sessions {
      type uint32;
      description
        "Number of SSO sessions for peer group";
    }
    leaf-list peer-members {
      type string;
      ordered-by user;
      description
        "List of BGP peer identifiers (such as IP addresses or names) that are members of this peer group as space separated values";
    }
    leaf fmt-grp-ix {
      type uint16;
      status obsolete;
      description
        "BGP peer group Formatted Group Index value (obsolete)";
    }
    leaf adv-ix {
      type uint16;
      status obsolete;
      description
        "BGP peer group Advertised Index value (obsolete)";
    }
    leaf aspath-in {
      type uint32;
      description
        "BGP peer group AS Path filter in value";
    }
    leaf aspath-out {
      type uint32;
      description
        "BGP peer group AS Path filter out value";
    }
    leaf routemap-in {
      type string;
      description
        "Name of the inbound route map applied to this peer group";
    }
    leaf routemap-out {
      type string;
      description
        "Name of the outbound route map applied to this peer group";
    }
    leaf updated-messages {
      type uint64;
      status obsolete;
      description
        "BGP peer group Updated Messages value (obsolete)";
    }
    leaf rep-count {
      type uint32;
      description
        "BGP peer group Replicated Count value";
    }
    leaf slowpeer-detection-value {
      type uint16;
      units "seconds";
      description
        "Slow peer detection threshold value for this BGP peer group";
    }
    leaf weight {
      type uint16;
      description
        "Default weight assigned to routes received from this BGP peer group";
    }
    leaf send-community {
      type boolean;
      description
        "Indicates whether standard BGP communities are sent to members of this peer group";
    }
    leaf extended-community {
      type boolean;
      description
        "Indicates whether extended BGP communities are sent to members of this peer group";
    }
    leaf remove-private-as {
      type boolean;
      description
        "Indicates whether private AS numbers are removed from the AS path in updates sent to members of this peer group";
    }
  }

  grouping path-status {
    description
      "BGP path status";
    leaf suppressed {
      type empty;
      description
        "Suppressed path";
    }
    leaf damped {
      type empty;
      description
        "Indicates that this BGP path is currently suppressed due to route flap damping";
    }
    leaf history {
      type empty;
      description
        "Indicates that this BGP path is retained in the history for informational or troubleshooting purposes, even though it is not currently active";
    }
    leaf valid {
      type empty;
      description
        "Indicates that this BGP path is considered valid according to BGP path selection rules and is eligible for use";
    }
    leaf sourced {
      type empty;
      description
        "Indicates that this BGP path was originated locally by the router, rather than learned from a peer";
    }
    leaf bestpath {
      type empty;
      description
        "Indicates that this BGP path has been selected as the best path for the prefix according to BGP path selection rules";
    }
    leaf internal {
      type empty;
      description
        "Indicates that this BGP path was learned from an internal BGP (iBGP) peer";
    }
    leaf rib-fail {
      type empty;
      description
        "Indicates that this BGP path failed to be installed in the Routing Information Base (RIB)";
    }
    leaf stale {
      type empty;
      description
        "Indicates that this BGP path is marked as stale, typically as a result of a graceful restart event";
    }
    leaf multipath {
      type empty;
      description
        "Indicates that this BGP path is one of multiple equal-cost paths used for load balancing (BGP multipath)";
    }
    leaf backup-path {
      type empty;
      description
        "Indicates that this BGP path is maintained as a backup and will be used if the primary path becomes unavailable";
    }
    leaf rt-filter {
      type empty;
      description
        "Indicates that this BGP path is used for route-target (RT) filtering, typically in VPN scenarios";
    }
    leaf best-external {
      type empty;
      description
        "Indicates that this BGP path is the best external path selected for advertisement to iBGP peers";
    }
    leaf additional-path {
      type empty;
      description
        "Indicates that this BGP path is advertised as an additional path using the BGP Add-Path feature";
    }
    leaf rib-compressed {
      type empty;
      description
        "Indicates that this BGP path is compressed in the Routing Information Base (RIB) for optimization purposes";
    }
  }

  grouping path-type {
    description
      "BGP path type";
    leaf nexthop {
      type string;
      description
        "Next-hop IP address for this BGP path, represented as a string in IPv4 or IPv6 address notation";
    }
    leaf metric {
      type uint32;
      description
        "Metric associated with the path";
    }
    leaf local-pref {
      type uint32;
      description
        "Local preference for this path";
    }
    leaf weight {
      type uint32;
      description
        "BGP path weight value used for route selection, with higher values preferred";
    }
    leaf as-path {
      type string;
      description
        "Sequence of Autonomous System (AS) numbers the route
         has traversed, as advertised in BGP updates";
    }
    leaf origin {
      type bgp-route-ios-xe-oper:bgp-origin-code;
      description
        "Indicates the origin of the BGP path, such as IGP, EGP, or incomplete, used in BGP route selection";
    }
    container path-status {
      description
        "Status indicators for the BGP path, such as whether the path is valid, best, suppressed, or damped";
      uses bgp-route-ios-xe-oper:path-status;
    }
    leaf rpki-status {
      type bgp-route-ios-xe-oper:bgp-rpki-status;
      description
        "Indicates the Resource Public Key Infrastructure (RPKI) validation state of this BGP path";
    }
    leaf community {
      type string;
      description
        "Space-separated string of BGP community values";
    }
    leaf mpls-in {
      type string;
      description
        "Inbound MPLS label for this BGP path";
    }
    leaf mpls-out {
      type string;
      description
        "Outbound MPLS label for this BGP path";
    }
    leaf sr-profile-name {
      type string;
      description
        "Segment Routing (SR) profile name associated with this BGP path";
    }
    leaf sr-binding-sid {
      type uint32;
      description
        "Segment Routing (SR) binding SID value for this BGP path";
    }
    leaf sr-label-indx {
      type uint32;
      description
        "Segment Routing (SR) label index for this BGP path";
    }
    leaf as4-path {
      type string;
      description
        "AS path using 4-octet AS numbers, represented as a
         space-separated string";
    }
    leaf atomic-aggregate {
      type boolean;
      description
        "Indicates whether the prefix is an atomic aggregate, meaning the originating router has aggregated routes and some path information may have been lost";
    }
    leaf aggr-as-number {
      type uint32;
      description
        "AS number of the autonomous system that performed the route aggregation";
    }
    leaf aggr-as4-number {
      type uint32;
      description
        "4-octet AS number of the autonomous system that performed the route aggregation";
    }
    leaf aggr-address {
      type string;
      description
        "IP address of the router that performed the route aggregation, represented as a string in IPv4 or IPv6 dotted-decimal notation";
    }
    leaf originator-id {
      type string;
      description
        "Router ID of the originator of the route in the local AS, represented as a string in dotted-decimal notation (e.g., '1.1.1.1')";
    }
    leaf cluster-list {
      type string;
      description
        "BGP cluster list values, represented as a
         space-separated string of route reflector cluster
         IDs in dotted-decimal notation (e.g., '1.1.1.1 2.2.2.2')";
    }
    leaf extended-community {
      type string;
      description
        "BGP extended community values associated with the route, used to carry additional information such as route targets or traffic engineering parameters";
    }
    leaf ext-aigp-metric {
      type uint64;
      description
        "Accumulated IGP (AIGP) metric for the path, representing the total IGP cost to reach the destination";
    }
    leaf path-id {
      type uint32;
      description
        "Path identifier used to uniquely identify a route when the BGP Add-Path feature is enabled";
    }
    leaf path-origin {
      type bgp-route-ios-xe-oper:bgp-path-origin;
      description
        "Indicates whether the BGP path is internal (iBGP) or external (eBGP)";
    }
  }

  grouping route-entry {
    description
      "Routing table entry details";
    leaf prefix {
      type string;
      description
        "Network prefix for the routing table entry,
         represented as a string in CIDR notation";
    }
    leaf version {
      type uint32;
      description
        "Routing table version";
    }
    leaf available-paths {
      type uint32;
      description
        "Number of paths available for BGP prefix";
    }
    leaf advertised-to {
      type string;
      description
        "Space-separated list of BGP update-group numbers to which this prefix is advertised";
    }
    container bgp-path-entries {
      description
        "Container for BGP path entries for the prefix, including next hop and associated path attributes";
      list bgp-path-entry {
        key "nexthop";
        description
          "List of BGP path entries for a given prefix, including next hop and associated path attributes";
        uses bgp-route-ios-xe-oper:path-type;
      }
    }
  }

  grouping route-filter {
    description
      "A specific BGP route filter view for an address family, along with the set of route entries that match the filter criteria";
    leaf route-filter {
      type bgp-route-ios-xe-oper:bgp-route-filters;
      description
        "Name or identifier of the BGP route filter applied to this address family";
    }
    container bgp-route-entries {
      description
        "Container for the list of BGP route entries that match the specified route filter";
      list bgp-route-entry {
        key "prefix";
        description
          "List of BGP route entries";
        uses bgp-route-ios-xe-oper:route-entry;
      }
    }
  }

  grouping neighbor-route-entry {
    description
      "Neighbor routing table entry details";
    leaf prefix {
      type string;
      description
        "Network prefix for the neighbor routing table entry,
         represented as a string in CIDR notation";
    }
    leaf version {
      type uint32;
      description
        "Neighbor routing table version";
    }
    leaf available-paths {
      type uint32;
      description
        "Number of paths available for BGP prefix";
    }
    leaf advertised-to {
      type string;
      description
        "Space-separated list of BGP update-group numbers to which this prefix is advertised";
    }
    container bgp-neighbor-path-entries {
      description
        "Container for BGP path entries associated with this neighbor route, including next hop and path attributes for the prefix";
      list bgp-neighbor-path-entry {
        key "nexthop";
        description
          "List of BGP path entries for a given prefix, including next hop and associated path attributes";
        uses bgp-route-ios-xe-oper:path-type;
      }
    }
  }

  grouping neighbor-route-filter {
    description
      "Identifier or name of the route filter applied to this BGP neighbor, used to match and control route advertisements or acceptance";
    leaf nbr-fltr {
      type bgp-route-ios-xe-oper:bgp-neighbor-route-filters;
      description
        "Identifier or name of the route filter applied to this BGP neighbor, used to match and control route advertisements or acceptance";
    }
    container bgp-neighbor-route-entries {
      description
        "Container for route entries that match the specified filter for a BGP neighbor, detailing the routes affected by this filter";
      list bgp-neighbor-route-entry {
        key "prefix";
        description
          "List of route entries for a BGP neighbor that match the associated route filter, including prefix and path information";
        uses bgp-route-ios-xe-oper:neighbor-route-entry;
      }
    }
  }

  grouping bgp-route-neighbor {
    description
      "BGP route neighbor";
    leaf nbr-id {
      type string;
      description
        "BGP neighbor ID";
    }
    container bgp-neighbor-route-filters {
      description
        "Container for route filters applied to BGP neighbor routes, specifying filtering criteria for routes exchanged with each neighbor";
      list bgp-neighbor-route-filter {
        key "nbr-fltr";
        description
          "List of route filters configured or applied to a specific BGP neighbor, used to control which routes are accepted or advertised";
        uses bgp-route-ios-xe-oper:neighbor-route-filter;
      }
    }
  }

  grouping af-record {
    description
      "BGP AF record";
    leaf afi-safi {
      type bgp-common-ios-xe-oper:afi-safi;
      description
        "Address Family Identifier (AFI) and Subsequent Address Family Identifier (SAFI) for the BGP address family";
    }
    container bgp-route-filters {
      description
        "Container for the list of BGP route filters applied to this address family";
      list bgp-route-filter {
        key "route-filter";
        description
          "List of BGP route filters";
        uses bgp-route-ios-xe-oper:route-filter;
      }
    }
    container bgp-route-neighbors {
      description
        "Container for BGP route neighbor information, including details about each neighbor associated with the address family";
      list bgp-route-neighbor {
        key "nbr-id";
        description
          "List of BGP route neighbors";
        uses bgp-route-ios-xe-oper:bgp-route-neighbor;
      }
    }
    container bgp-peer-groups {
      description
        "Container for the set of BGP peer groups configured for this address family";
      list bgp-peer-group {
        key "name";
        description
          "List of BGP peer group entries, each representing a set of neighbors that share common configuration parameters";
        uses bgp-route-ios-xe-oper:peer-group;
      }
    }
  }

  grouping vrf-record {
    description
      "VRF record";
    leaf vrf {
      type string;
      description
        "Name of the BGP Virtual Routing and Forwarding (VRF) instance";
    }
    container bgp-route-afs {
      description
        "Container for the list of BGP address families associated with the VRF";
      list bgp-route-af {
        key "afi-safi";
        description
          "List of BGP address families";
        uses bgp-route-ios-xe-oper:af-record;
      }
    }
  }

  grouping bgp-rd-neighbor-route-entry {
    description
      "RD neighbor routing table entry details";
    leaf prefix {
      type string;
      description
        "Network prefix for the RD neighbor routing table entry,
         represented as a string in CIDR notation";
    }
    leaf version {
      type uint32;
      description
        "Version number of the BGP Route Distinguisher (RD) neighbor routing table associated with this prefix entry";
    }
    leaf available-paths {
      type uint32;
      description
        "Number of  paths available for BGP prefix";
    }
    leaf advertised-to {
      type string;
      description
        "Space-separated list of BGP update-group numbers to which this prefix is advertised";
    }
    container bgp-rd-neighbor-path-entries {
      description
        "Container for BGP path entries associated with this RD neighbor route, including next hop and path attributes for the prefix";
      list bgp-rd-neighbor-path-entry {
        key "nexthop";
        description
          "List of BGP path entries for a given prefix, including next hop and associated path attributes";
        uses bgp-route-ios-xe-oper:path-type;
      }
    }
  }

  grouping bgp-rd-neighbor-route-filter {
    description
      "Route filter applied to a specific BGP neighbor within a Route Distinguisher (RD) scope, controlling which routes are accepted from or advertised to that neighbor for the given RD";
    leaf neighbor-filter {
      type bgp-route-ios-xe-oper:bgp-neighbor-route-filters;
      description
        "Route filter applied to a BGP neighbor for the specified route distinguisher (RD)";
    }
    container bgp-rd-neighbor-route-entries {
      description
        "Container for route entries learned from or advertised to a BGP neighbor for the specified route distinguisher (RD)";
      list bgp-rd-neighbor-route-entry {
        key "prefix";
        description
          "List of BGP RD neighbor route entries";
        uses bgp-route-ios-xe-oper:bgp-rd-neighbor-route-entry;
      }
    }
  }

  grouping bgp-rd-route-neighbor {
    description
      "BGP RD route neighbor";
    leaf neighbor-id {
      type string;
      description
        "BGP RD neighbor ID";
    }
    container bgp-rd-neighbor-route-filters {
      description
        "Container for route filters applied to BGP neighbors associated with the specified route distinguisher (RD)";
      list bgp-rd-neighbor-route-filter {
        key "neighbor-filter";
        description
          "List of BGP RD neighbor route filters";
        uses bgp-route-ios-xe-oper:bgp-rd-neighbor-route-filter;
      }
    }
  }

  grouping bgp-rd-route-entry {
    description
      "RD Routing table entry details";
    leaf prefix {
      type string;
      description
        "Network prefix for the RD routing table entry,
         represented as a string in CIDR notation";
    }
    leaf version {
      type uint32;
      description
        "RD Routing table version";
    }
    leaf available-paths {
      type uint32;
      description
        "Number of  paths available for BGP prefix";
    }
    leaf advertised-to {
      type string;
      description
        "Space-separated list of BGP update-group numbers to which this prefix is advertised";
    }
    container bgp-rd-path-entries {
      description
        "Container for BGP RD path entries for the prefix, including next hop and associated path attributes";
      list bgp-rd-path-entry {
        key "nexthop";
        description
          "List of BGP path entries for a given prefix, including next hop and associated path attributes";
        uses bgp-route-ios-xe-oper:path-type;
      }
    }
  }

  grouping bgp-rd-route-filter {
    description
      "Route filter applied within a BGP Route Distinguisher (RD) scope, along with the set of route entries that match the filter criteria";
    leaf route-filter {
      type bgp-route-ios-xe-oper:bgp-route-filters;
      description
        "Identifier or name of the route filter applied to the BGP RD route";
    }
    container bgp-rd-route-entries {
      description
        "Container for the set of BGP route entries matching the specified RD and route filter";
      list bgp-rd-route-entry {
        key "prefix";
        description
          "List of BGP RD route entries";
        uses bgp-route-ios-xe-oper:bgp-rd-route-entry;
      }
    }
  }

  grouping bgp-rd-route-af {
    description
      "BGP RD AF record";
    leaf afi-safi {
      type bgp-common-ios-xe-oper:afi-safi;
      description
        "Address Family Identifier (AFI) and Subsequent Address Family Identifier (SAFI) for the BGP address family";
    }
    container bgp-rd-route-filters {
      description
        "Container for the set of route filters applied to this BGP RD route address family";
      list bgp-rd-route-filter {
        key "route-filter";
        description
          "List of BGP RD route filters";
        uses bgp-route-ios-xe-oper:bgp-rd-route-filter;
      }
    }
    container bgp-rd-route-neighbors {
      description
        "Container for the list of BGP route distinguisher (RD) neighbors associated with this address family";
      list bgp-rd-route-neighbor {
        key "neighbor-id";
        description
          "List of BGP RD route neighbors";
        uses bgp-route-ios-xe-oper:bgp-rd-route-neighbor;
      }
    }
  }

  grouping bgp-rd-record {
    description
      "RD record";
    leaf rd-value {
      type string;
      description
        "Route Distinguisher (RD) value for this BGP instance";
    }
    container bgp-rd-route-afs {
      description
        "Container for address families associated with this BGP Route Distinguisher (RD)";
      list bgp-rd-route-af {
        key "afi-safi";
        description
          "List of BGP RD address families";
        uses bgp-route-ios-xe-oper:bgp-rd-route-af;
      }
    }
  }
}
