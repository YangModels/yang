module Cisco-IOS-XE-crypto-types {
  yang-version 1.1;
  namespace "http://cisco.com/ns/yang/Cisco-IOS-XE-crypto-types";
  prefix crypto-ios-xe-types;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for service-insertion operational data.
     Copyright (c) 2025 by Cisco Systems, Inc.
     All rights reserved.";

  revision 2026-02-01 {
    description
      "Initial revision";
    reference
      "1.0.0";
    cisco-semver:module-version "1.0.0";
  }

  typedef symnat-status {
    type enumeration {
      enum nat-type-none {
        value 0;
        description
          "Indicates that the interface is configured with a public IP address";
      }
      enum nat-type-friendly {
        value 1;
        description
          "Indicates that the interface is behind a friendly NAT (non-symmetric NAT, such as cone or port-restricted cone NAT), which allows easier NAT traversal";
      }
      enum nat-type-unfriendly {
        value 2;
        description
          "Indicates that the interface is behind an unfriendly NAT (symmetric NAT), which restricts NAT traversal and complicates peer-to-peer connectivity";
      }
      enum nat-type-insuf-regs {
        value 3;
        description
          "Indicates that the NAT type could not be determined due to insufficient information from the VPN registry or inability to communicate with the VPN registry";
      }
    }
    description
      "Indicates the type of NAT discovered via VPN registry for an interface";
  }
}
