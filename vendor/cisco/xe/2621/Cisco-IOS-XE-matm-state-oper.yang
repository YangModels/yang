module Cisco-IOS-XE-matm-state-oper {
  yang-version 1.1;
  namespace "http://cisco.com/ns/yang/Cisco-IOS-XE-matm-state-oper";
  prefix matm-ios-xe-state-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for MATM (MAC Address Translation Manager) state information.
     Copyright (c) 2025 by Cisco Systems, Inc.
     All rights reserved.";

  revision 2026-02-01 {
    description
      "Initial revision";
    reference
      "1.0.0";
    cisco-semver:module-version "1.0.0";
  }

  typedef e-mac-addr-type {
    type enumeration {
      enum mac-stat {
        value 0;
        description
          "Static MAC address type";
      }
      enum mac-dyn {
        value 1;
        description
          "Dynamic MAC address type";
      }
      enum mac-any {
        value 2;
        description
          "All other MAC address types";
      }
    }
    description
      "Type of MAC address";
  }

  typedef e-port-type {
    type enumeration {
      enum port-drop {
        value 0;
        description
          "Drop port type";
      }
      enum port-phys {
        value 1;
        description
          "Physical port type";
      }
      enum port-svi {
        value 2;
        description
          "SVI port type";
      }
    }
    description
      "Type of port";
  }

  grouping addr-info {
    description
      "Represents the address-related info relevant to MATM.
       It holds details of addr type and flags info about a MAC entry";
    leaf matm-addr-type {
      type matm-ios-xe-state-oper:e-mac-addr-type;
      description
        "The address type associated with this MAC entry.
         Indicates whether the MAC address is configured
         statically or learned dynamically";
    }
    leaf matm-secure-flg {
      type boolean;
      description
        "Secure MAC address flag.
         Indicates the MAC address entry is secured statically
         on a specific port";
    }
  }

  grouping port-list {
    description
      "Entry for port list";
    leaf-list port {
      type string;
      ordered-by user;
      description
        "List of physical ports associated with the MAC entry";
    }
  }

  grouping mac-addr-key {
    description
      "Unique MAC entry identifier";
    leaf vlan-id {
      type uint16;
      description
        "VLAN id associated with MAC entry";
    }
    leaf mac {
      type yang:mac-address;
      description
        "MAC associated with the VLAN";
    }
  }

  grouping mac-param {
    description
      "MAC address parameters";
    container mac-addr-info {
      description
        "MAC address info associated with this MAC entry";
      uses matm-ios-xe-state-oper:addr-info;
    }
    choice port-type-choice {
      description
        "Type of port";
      case port-drop {
        leaf drop {
          type empty;
          description
            "Drop port";
        }
      }
      case port-phys {
        container phys-ports {
          description
            "Physical port list";
          uses matm-ios-xe-state-oper:port-list;
        }
      }
      case port-svi {
        leaf svi-port {
          type string;
          description
            "SVI port";
        }
      }
    }
  }

  container matm-state-oper-data {
    config false;
    description
      "Represents MAC address entries used for packet forwarding.";
    list matm-mac {
      key "vlan-id mac";
      description
        "MAC address entries state information";
      uses matm-ios-xe-state-oper:mac-param;
      uses matm-ios-xe-state-oper:mac-addr-key;
    }
  }
}
