submodule Cisco-IOS-XE-aaa-rpc {
  yang-version 1.1;
  belongs-to Cisco-IOS-XE-rpc {
    prefix ios-xe-rpc;
  }

  import cisco-semver {
    prefix cisco-semver;
  }

  organization
    "Cisco Systems";
  contact
    "<mailto:cs-yang@cisco.com>";
  description
    "NED AAA RPC YANG module for IOS
     Copyright (c) 2016-2019 by Cisco Systems, Inc.
     All rights reserved.";

  revision 2025-03-01 {
    description
      "- Added support for Clear radius-proxy statistics
       - Added support for Clear aaa counter client statistics";
    cisco-semver:module-version "1.3.0";
  }
  revision 2023-11-01 {
    description
      "Added support for Clear aaa counters & Clear radius statistics";
    cisco-semver:module-version "1.2.0";
  }
  revision 2022-11-01 {
    description
      "- Update yang-version to 1.1";
    cisco-semver:module-version "1.1.0";
  }
  revision 2019-07-01 {
    description
      "Establish semantic version baseline";
    cisco-semver:module-version "1.0.0";
  }
  revision 2018-12-06 {
    description
      "created for NED RPC modularisation";
  }

  grouping clear-choice-aaa-case-grouping {
    container aaa {
      description
        "Clear AAA values";
      container local {
        description
          "Clear AAA local method options";
        container user {
          description
            "Clear local AAA users";
          container lockout {
            description
              "Clear locked out local AAA users";
            leaf username {
              description
                "Username of the locked-user";
              type string;
            }
          }
        }
      }
      container counters {
        description
          "Clear AAA counters";
        container servers {
          description
            "AAA servers information";
          leaf all {
            description
              "Clear all the AAA servers counters";
            type empty;
          }
          leaf radius {
            description
              "Radius servers information
                all             - Clear all the RADIUS servers id.
                <0..2147483647> - Clear specified RADIUS server id.
                  the RADIUS server id displayed by show aaa servers";
            type union {
              type string {
                pattern 'all';
              }
              type uint32 {
                range "0..2147483647";
              }
            }
          }
        }
        container client {
          presence "true";
          description
            "AAA client information";
          leaf force {
            description
              "Clear active counters with cumulative counters";
            type empty;
          }
        }
      }
    }
    container radius {
      description
        "Clears radius server information";
      leaf statistics {
        description
          "Radius statistics";
        type empty;
      }
    }
    container radius-proxy {
      description
        "Clears radius-proxy server information";
      leaf statistics {
        description
          "Radius-proxy statistics";
        type empty;
      }
    }
  }
}
