module Cisco-IOS-XE-ngfw-ctrl-actions-rpc {
  yang-version 1.1;
  namespace "http://cisco.com/ns/yang/Cisco-IOS-XE-ngfw-ctrl-actions-rpc";
  prefix ios-xe-ngfw-ctrl-actions-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     Next-Generation Firewall (NGFW) controller-initiated update RPCs.
     Copyright (c) 2025-2026 by Cisco Systems, Inc.
     All rights reserved.";

  revision 2026-08-01 {
    description
      "Initial revision";
    reference
      "1.0.0";
    cisco-semver:module-version "1.0.0";
  }

  grouping ngfw-upd-type {
    description
      "Grouping defining the input parameters for a controller-initiated NGFW update RPC, including package metadata and a download timeout.";
    leaf json {
      type string {
        length "1..8192";
        pattern '.*';
      }
      mandatory true;
      description
        "Metadata containing NGFW update package information.
         Includes package paths, protocols, and authentication credentials.";
    }
    leaf dwnld-timeout {
      type uint16;
      units "minutes";
      mandatory true;
      description
        "Download timeout, in minutes (default: 5)";
    }
  }

  grouping ngfw-upd-resp {
    description
      "Response to NGFW update action";
    leaf resp-msg {
      type string;
      description
        "Response message indicating success or failure details";
    }
  }

  rpc ngfw-upd {
    description
      "NGFW periodic update action (controller-initiated)";
    input {
      uses ios-xe-ngfw-ctrl-actions-rpc:ngfw-upd-type;
    }
    output {
      uses ios-xe-ngfw-ctrl-actions-rpc:ngfw-upd-resp;
    }
  }
}
