module Cisco-IOS-XE-switch-ptp-oper {
  yang-version 1.1;
  namespace "http://cisco.com/ns/yang/Cisco-IOS-XE-switch-ptp-oper";
  prefix switch-ptp-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for PTP (Precision Time Protocol)
     Copyright (c) 2022-2026 by Cisco Systems, Inc.
     All rights reserved.";

  revision 2026-08-01 {
    description
      "Updated descriptions of PTP operational model elements to improve clarity and context.";
    reference
      "1.1.0";
    cisco-semver:module-version "1.1.0";
  }
  revision 2023-03-01 {
    description
      "Initial revision";
    reference
      "1.0.0";
    cisco-semver:module-version "1.0.0";
  }

  typedef ptp-oper-network-transport-protocol {
    type enumeration {
      enum ptp-net-tran-proto-reserved {
        value 0;
        description
          "PTP network transport protocol reserved";
      }
      enum ptp-net-tran-proto-udp-ipv4 {
        value 1;
        description
          "PTP network transport udp ipv4";
      }
      enum ptp-net-tran-proto-udp-ipv6 {
        value 2;
        description
          "PTP network transport protocol udp ipv6";
      }
      enum ptp-net-tran-proto-802dot3 {
        value 3;
        description
          "PTP network transport protocol 802_3";
      }
    }
    description
      "PTP network transport protocol";
  }

  typedef ptp-delay-type {
    type enumeration {
      enum ptp-delay-mechanism-e2e {
        value 0;
        description
          "PTP delay mechanism end to end";
      }
      enum ptp-delay-mechanism-p2p {
        value 1;
        description
          "PTP delay mechanism p2p";
      }
      enum ptp-delay-mechanism-disabled {
        value 2;
        description
          "PTP delay mechanism disabled";
      }
    }
    description
      "PTP Delay mechanism";
  }

  typedef ptp-oper-profile {
    type enumeration {
      enum ptp-profile-default {
        value 0;
        description
          "PTP profile default";
      }
      enum ptp-profile-none {
        value 1;
        description
          "PTP profile none";
      }
      enum ptp-profile-dot1as {
        value 2;
        description
          "PTP profile dot1as";
      }
      enum ptp-profile-8275 {
        value 3;
        description
          "PTP profile 8275";
      }
    }
    description
      "PTP profile";
  }

  typedef ptp-fsm-state {
    type enumeration {
      enum ptp-port-state-unknown {
        value 0;
        description
          "PTP port state initializing";
      }
      enum ptp-port-state-initializing {
        value 1;
        description
          "PTP port state initializing";
      }
      enum ptp-port-state-faulty {
        value 2;
        description
          "PTP port state faulty";
      }
      enum ptp-port-state-disabled {
        value 3;
        description
          "PTP port state disabled";
      }
      enum ptp-port-state-listening {
        value 4;
        description
          "PTP port state listening";
      }
      enum ptp-port-state-pre-master {
        value 5;
        description
          "PTP port state pre-master";
      }
      enum ptp-port-state-master {
        value 6;
        description
          "PTP port state master";
      }
      enum ptp-port-state-passive {
        value 7;
        description
          "PTP port state passive";
      }
      enum ptp-port-state-uncalibrated {
        value 8;
        description
          "PTP port state uncalibrated";
      }
      enum ptp-port-state-slave {
        value 9;
        description
          "PTP port state slave";
      }
      enum ptp-port-state-passive-slave {
        value 10;
        description
          "PTP port state passive slave";
      }
    }
    description
      "PTP port state";
  }

  typedef ptp-device {
    type enumeration {
      enum ptp-ordinary-clock {
        value 0;
        description
          "PTP ordinary clock";
      }
      enum ptp-boundary-clock {
        value 1;
        description
          "PTP boundary clock";
      }
      enum ptp-transparent-clock-p2p {
        value 2;
        description
          "PTP transparent clock p2p";
      }
      enum ptp-transparent-clock-e2e {
        value 3;
        description
          "PTP transparent clock end to end";
      }
      enum ptp-management-node {
        value 4;
        description
          "PTP management node";
      }
      enum ptp-slave-only {
        value 5;
        description
          "PTP slave only";
      }
      enum ptp-grand-master-boundary-clock {
        value 6;
        description
          "PTP grandmaster boundary clock";
      }
      enum ptp-802-dot1as-time-aware-bridge {
        value 7;
        description
          "PTP 802 dot1as time aware bridge";
      }
      enum ptp-8275-clock-mode-bc-delay-req {
        value 8;
        description
          "PTP 8275 clock mode boundary delay req";
      }
      enum ptp-8275-clock-mode-tc-delay-req {
        value 9;
        description
          "PTP 8275 clock mode transparent delay req";
      }
      enum ptp-port-disabled {
        value 10;
        description
          "PTP port disabled";
      }
    }
    description
      "PTP device";
  }

  typedef ptp-source-address {
    type enumeration {
      enum ptp-source-ip-default {
        value 0;
        description
          "PTP source ip default";
      }
      enum ptp-source-ip-address {
        value 1;
        description
          "PTP source ip address";
      }
      enum ptp-souce-ip-interface {
        value 2;
        description
          "PTP source ip interface";
      }
    }
    description
      "PTP source address";
  }

  typedef ptp-time-source {
    type enumeration {
      enum ptp-time-source-atomic {
        value 0;
        description
          "PTP time source atomic";
      }
      enum ptp-time-source-gps {
        value 1;
        description
          "PTP time source gps";
      }
      enum ptp-time-source-ter-radio {
        value 2;
        description
          "PTP time source ter radio";
      }
      enum ptp-time-source-ptp {
        value 3;
        description
          "PTP time source ptp";
      }
      enum ptp-time-source-ntp {
        value 4;
        description
          "PTP time source ntp";
      }
      enum ptp-time-source-handset {
        value 5;
        description
          "PTP time source handset";
      }
      enum ptp-time-source-other {
        value 6;
        description
          "PTP time source other";
      }
      enum ptp-time-source-internal-oscillator {
        value 7;
        description
          "PTP time source internal oscillator";
      }
    }
    description
      "PTP time source";
  }

  typedef ptp-clock-accuracy {
    type enumeration {
      enum ptp-clock-accuracy-to-within-25-ns {
        value 0;
        description
          "Accuracy to within 25 nanoseconds";
      }
      enum ptp-clock-accuracy-to-within-100-ns {
        value 1;
        description
          "Accuracy to within 100 nanoseconds";
      }
      enum ptp-clock-accuracy-to-within-250-ns {
        value 2;
        description
          "Accuracy to within 250 nanoseconds";
      }
      enum ptp-clock-accuracy-to-within-1-us {
        value 3;
        description
          "Accuracy to within 1 microsecond";
      }
      enum ptp-clock-accuracy-to-within-2-5-us {
        value 4;
        description
          "Accuracy to within 2.5 microseconds";
      }
      enum ptp-clock-accuracy-to-within-10-us {
        value 5;
        description
          "Accuracy to within 10 microseconds";
      }
      enum ptp-clock-accuracy-to-within-25-us {
        value 6;
        description
          "Accuracy to within 25 microseconds";
      }
      enum ptp-clock-accuracy-to-within-100-us {
        value 7;
        description
          "Accuracy to within 100 microseconds";
      }
      enum ptp-clock-accuracy-to-within-250-us {
        value 8;
        description
          "Accuracy to within 250 microseconds";
      }
      enum ptp-clock-accuracy-to-within-1-ms {
        value 9;
        description
          "Accuracy to within 1 millisecond";
      }
      enum ptp-clock-accuracy-to-within-2-5-ms {
        value 10;
        description
          "Accuracy to within 2.5 milliseconds";
      }
      enum ptp-clock-accuracy-to-within-10-ms {
        value 11;
        description
          "Accuracy to within 10 milliseconds";
      }
      enum ptp-clock-accuracy-to-within-25-ms {
        value 12;
        description
          "Accuracy to within 25 milliseconds";
      }
      enum ptp-clock-accuracy-to-within-100-ms {
        value 13;
        description
          "Accuracy to within 100 milliseconds";
      }
      enum ptp-clock-accuracy-to-within-250-ms {
        value 14;
        description
          "Accuracy to within 250 milliseconds";
      }
      enum ptp-clock-accuracy-to-within-1-s {
        value 15;
        description
          "Accuracy to within 1 second";
      }
      enum ptp-clock-accuracy-to-within-10-s {
        value 16;
        description
          "Accuracy to within 10 seconds";
      }
      enum ptp-clock-accuracy-greater-than-10-s {
        value 17;
        description
          "Accuracy greater than 10 seconds";
      }
      enum ptp-clock-accuracy-unknown {
        value 18;
        description
          "Accuracy unknown";
      }
    }
    description
      "PTP clock accuracy";
  }

  grouping ptp-oper-clock-quality {
    description
      "PTP clock quality";
    leaf clock-class {
      type uint8;
      description
        "PTP clock class, indicating time-reference quality level as defined by IEEE 1588.";
    }
    leaf clock-accuracy {
      type switch-ptp-ios-xe-oper:ptp-clock-accuracy;
      description
        "PTP clock accuracy indicates the expected accuracy of the PTP Instance, as defined by IEEE 1588.";
    }
    leaf offset-scaled-log-variance {
      type uint16;
      description
        "Scaled logarithmic variance of the clock offset, used in PTP clock quality assessment.";
    }
  }

  grouping ptp-oper-port-identity {
    description
      "PTP port identity";
    leaf ptp-clk-id {
      type uint64;
      description
        "Unique identifier for the PTP clock associated with this port identity.";
    }
    leaf port-number {
      type uint16;
      description
        "Port number associated with this PTP port identity.";
    }
  }

  grouping ptp-oper-time-interval {
    description
      "PTP time interval";
    leaf nano-seconds {
      type int64;
      units "nanoseconds";
      description
        "Integer nanoseconds component of the time interval value.";
    }
    leaf fractional-nano-seconds {
      type int16;
      units "nanoseconds";
      description
        "Fractional nanoseconds component of the time interval value.";
    }
  }

  grouping ptp-oper-domain-cfg {
    description
      "PTP domain config";
    leaf transport-protocol {
      type switch-ptp-ios-xe-oper:ptp-oper-network-transport-protocol;
      description
        "Network transport protocol used for PTP message exchange, such as UDP/IPv4, or IEEE 802.3.";
    }
    leaf dscp-event {
      type uint16;
      description
        "Differentiated Services Code Point (DSCP) value used for PTP event messages.";
    }
    leaf dscp-general {
      type uint16;
      description
        "Differentiated Services Code Point (DSCP) value used for PTP general messages.";
    }
    leaf delay-mechanism {
      type switch-ptp-ios-xe-oper:ptp-delay-type;
      description
        "PTP delay mechanism used for time synchronization, such as end-to-end, peer-to-peer, or disabled.";
    }
  }

  grouping ptp-clock-default-data {
    description
      "PTP clock default data";
    leaf ptp-device-type {
      type switch-ptp-ios-xe-oper:ptp-device;
      description
        "Type of PTP device for this clock instance, such as ordinary, boundary, or transparent clock.";
    }
    leaf ptp-clk-id {
      type uint64;
      description
        "PTP clock identity";
    }
    leaf two-step-clock {
      type boolean;
      description
        "Two step clock";
    }
    leaf num-ptp-ports {
      type uint8;
      description
        "Number of PTP ports";
    }
    leaf clock-priority1 {
      type uint8;
      description
        "Clock priority 1";
    }
    leaf clock-priority2 {
      type uint8;
      description
        "Clock priority 2";
    }
    container clock-quality {
      description
        "Contains PTP clock quality parameters including clock class, accuracy, and offset scaled log variance.";
      uses switch-ptp-ios-xe-oper:ptp-oper-clock-quality;
    }
    leaf ptp-local-clock-priority {
      type uint8;
      description
        "Priority value assigned to the local PTP clock and used in best master clock selection.";
    }
    leaf holdover-timer-value {
      type uint32;
      units "seconds";
      description
        "Duration in seconds that the PTP clock maintains synchronization in hold over mode after losing its master clock.";
    }
    leaf profile {
      type switch-ptp-ios-xe-oper:ptp-oper-profile;
      description
        "PTP profile in use, defining protocol options and behavior for a specific application.";
    }
  }

  grouping ptp-clock-current-data {
    description
      "PTP clock current data";
    container offset-from-master {
      description
        "Offset from master";
      uses switch-ptp-ios-xe-oper:ptp-oper-time-interval;
    }
    container mean-path-delay {
      description
        "Average delay for PTP messages between the local clock and its peer or master.";
      uses switch-ptp-ios-xe-oper:ptp-oper-time-interval;
    }
    leaf steps-removed {
      type uint16;
      description
        "Number of network hops between the local clock and the grandmaster clock in the PTP domain.";
    }
    leaf max-offset-from-master {
      type uint64;
      units "nanoseconds";
      description
        "Maximum observed time offset, in nanoseconds, between the local clock and the master clock.";
    }
  }

  grouping switch-ptp-clock-parent-data {
    description
      "PTP clock parent data";
    leaf clock-domain {
      type uint16;
      description
        "Identifier for the PTP clock domain to which this parent data entry belongs.";
    }
    container parent-port-identity {
      description
        "Parent port identity";
      uses switch-ptp-ios-xe-oper:ptp-oper-port-identity;
    }
    leaf obs-prnt-ofst-scl-log-var {
      type uint16;
      description
        "Observed parent offset scaled log variance";
    }
    leaf obs-par-clk-phase-chg-rt {
      type int32;
      description
        "Observed parent clock phase change rate";
    }
    leaf grandmaster-identity {
      type uint64;
      description
        "Grandmaster identity";
    }
    container grandmaster-clock-quality {
      description
        "Grandmaster clock quality";
      uses switch-ptp-ios-xe-oper:ptp-oper-clock-quality;
    }
    leaf grandmaster-priority1 {
      type uint8;
      description
        "Grandmaster priority 1";
    }
    leaf grandmaster-priority2 {
      type uint8;
      description
        "Second priority value of the grandmaster clock, used in PTP best master clock selection.";
    }
  }

  grouping ptp-clock-time-property {
    description
      "PTP clock time property";
    leaf current-utc-offset {
      type int32;
      description
        "Current utc offset";
    }
    leaf current-utc-offset-valid {
      type boolean;
      description
        "Current utc offset valid bit";
    }
    leaf leap-59 {
      type boolean;
      description
        "Leap 59 valid bit";
    }
    leaf leap-61 {
      type boolean;
      description
        "Leap 61 valid bit";
    }
    leaf time-traceable {
      type boolean;
      description
        "Time traceable bit";
    }
    leaf frequency-traceable {
      type boolean;
      description
        "Frequency traceable bit";
    }
    leaf timescale-is-ptp {
      type boolean;
      description
        "PTP timescale bit";
    }
    leaf time-source {
      type switch-ptp-ios-xe-oper:ptp-time-source;
      description
        "Type of time source for the PTP clock, such as GPS, atomic clock, NTP, or other reference.";
    }
  }

  grouping switch-ptp-port-ucast-data {
    description
      "PTP port unicast data";
    leaf if-name {
      type string;
      description
        "Name of the network interface associated with the PTP unicast port.";
    }
    leaf peer-clk-ip {
      type inet:ip-address;
      description
        "IP address of the peer PTP clock in the unicast session.";
    }
    leaf src-addr-type {
      type switch-ptp-ios-xe-oper:ptp-source-address;
      description
        "Type of source address used for PTP unicast communication.";
    }
    leaf src-ip-ptp-intf-name {
      type string;
      description
        "Name of the interface whose IP address is used as the source for PTP unicast messages.";
    }
    leaf src-ip {
      type inet:ip-address;
      description
        "Source IP address used for PTP unicast communication.";
    }
    leaf vrf-id {
      type uint16;
      description
        "VRF identifier associated with the PTP unicast port.";
    }
  }

  grouping switch-ptp-port-data {
    description
      "PTP port data";
    leaf if-name {
      type string;
      description
        "Name of the network interface associated with the PTP port.";
    }
    container port-identity {
      description
        "Unique identity information for the PTP port, including clock identity and port number.";
      uses switch-ptp-ios-xe-oper:ptp-oper-port-identity;
    }
    leaf port-state {
      type switch-ptp-ios-xe-oper:ptp-fsm-state;
      description
        "Current state of the PTP port, indicating its operational status such as initializing, master, or slave.";
    }
    leaf announce-receipt-time-out {
      type uint8;
      description
        "Announce receipt timeout";
    }
    container peer-mean-path-delay {
      description
        "Peer mean path delay";
      uses switch-ptp-ios-xe-oper:ptp-oper-time-interval;
    }
    leaf log-mean-announce-interval {
      type int8;
      description
        "Log mean announce interval";
    }
    leaf log-mean-sync-interval {
      type int8;
      description
        "Log mean sync interval";
    }
    leaf lg-min-mean-pdel-req-intv {
      type int8;
      description
        "Log min mean peer delay request interval";
    }
    leaf lg-min-mean-del-req-intv {
      type int8;
      description
        "Logarithm base 2 of the minimum mean interval between delay request messages sent by the PTP port. The actual interval in seconds equals 2 raised to this value (e.g., -1 means 2 packets/sec, 1 means 1 packet every 2 seconds).";
    }
    leaf port-enabled {
      type boolean;
      description
        "Indicates whether the PTP port is currently enabled for Precision Time Protocol operation.";
    }
    leaf ptp-vlan-id {
      type uint16;
      description
        "VLAN ID used for Precision Time Protocol traffic on this port.";
    }
    leaf ptp-vlan-id-valid {
      type boolean;
      description
        "Indicates whether the configured PTP VLAN ID for this port is valid and in use.";
    }
    leaf tag-native-vlan {
      type boolean;
      description
        "Indicates whether the native VLAN is tagged for PTP traffic on this port.";
    }
    leaf sync-fault-limit {
      type uint64;
      description
        "Maximum number of synchronization faults allowed on this PTP port before corrective action is taken.";
    }
  }

  grouping switch-ptp-clock-data {
    description
      "PTP clock data";
    leaf clock-domain {
      type uint16;
      description
        "Identifier for the PTP clock domain to which this clock instance belongs.";
    }
    container clock-default-data-val {
      description
        "Clock default data";
      uses switch-ptp-ios-xe-oper:ptp-clock-default-data;
    }
    container clock-current-data-val {
      description
        "Contains current operational data of the PTP clock, such as offset from master, mean path delay, and steps removed.";
      uses switch-ptp-ios-xe-oper:ptp-clock-current-data;
    }
    container ptp-oper-domain-cfg-data {
      description
        "Operational configuration data for the PTP domain, including transport protocol, DSCP values, and delay mechanism.";
      uses switch-ptp-ios-xe-oper:ptp-oper-domain-cfg;
    }
    container clock-time-property-val {
      description
        "Contains current time properties and related status for the PTP clock, such as UTC offset, leap indicators, and time-source quality.";
      uses switch-ptp-ios-xe-oper:ptp-clock-time-property;
    }
  }

  grouping ptp-correction-entry {
    description
      "PTP correction entry";
    leaf subordinate-port {
      type string;
      description
        "Name of the subordinate port for which the PTP correction statistics are recorded.";
    }
    leaf time {
      type yang:date-and-time;
      description
        "Timestamp of data";
    }
    container offset {
      description
        "Time offset between the subordinate port and the master clock.";
      uses switch-ptp-ios-xe-oper:ptp-oper-time-interval;
    }
    container mean-path-delay {
      description
        "Mean path delay between the local and subordinate PTP ports.";
      uses switch-ptp-ios-xe-oper:ptp-oper-time-interval;
    }
  }

  grouping switch-ptp-correction-data {
    description
      "PTP correction data";
    list ptp-correction-stats {
      description
        "List of PTP correction statistics entries for subordinate ports.";
      uses switch-ptp-ios-xe-oper:ptp-correction-entry;
    }
  }

  container switch-ptp-oper-data {
    config false;
    description
      "PTP (Precision Time Protocol) operational data";
    list switch-ptp-clock-data {
      key "clock-domain";
      description
        "PTP (Precision Time Protocol) clock dataset";
      uses switch-ptp-ios-xe-oper:switch-ptp-clock-data;
    }
    list switch-ptp-ucast-data {
      key "if-name";
      description
        "PTP (Precision Time Protocol) unicast info";
      uses switch-ptp-ios-xe-oper:switch-ptp-port-ucast-data;
    }
    list switch-ptp-port-data {
      key "if-name";
      description
        "PTP (Precision Time Protocol) port dataset";
      uses switch-ptp-ios-xe-oper:switch-ptp-port-data;
    }
    list switch-ptp-parent-data {
      key "clock-domain";
      description
        "PTP (Precision Time Protocol) parent data";
      uses switch-ptp-ios-xe-oper:switch-ptp-clock-parent-data;
    }
    container switch-ptp-correction-data {
      presence "switch-ptp-correction-data";
      description
        "PTP (Precision Time Protocol) correction data";
      uses switch-ptp-ios-xe-oper:switch-ptp-correction-data;
    }
  }
}
