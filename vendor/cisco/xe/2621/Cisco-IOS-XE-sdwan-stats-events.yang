module Cisco-IOS-XE-sdwan-stats-events {
  yang-version 1.1;
  namespace "http://cisco.com/ns/yang/Cisco-IOS-XE-sdwan-stats-events";
  prefix sdwan-stats-ios-xe-events;

  import Cisco-IOS-XE-ios-common-oper {
    prefix ios-common-ios-xe-oper;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module defines the SD-WAN statistics events operational
     data model and notifications used to report drops and related
     statistics across SD-WAN subsystems (for example application,
     QoS, firewall, and system statistics). It provides a single
     container for event data and a common set of identifiers to
     classify the statistics source.
     Copyright (c) 2026 by Cisco Systems, Inc.
     All rights reserved.";

  revision 2026-08-01 {
    description
      "Initial revision";
    reference
      "1.0.0";
    cisco-semver:module-version "1.0.0";
  }

  typedef sdwan-stats-types {
    type enumeration {
      enum stats-cxp-app {
        value 1;
        description
          "Statistics for Cloud express Application";
      }
      enum stats-interface {
        value 2;
        description
          "Statistics for Interface";
      }
      enum stats-pfr {
        value 3;
        description
          "Statistics for Performance Routing";
      }
      enum stats-fnf {
        value 4;
        description
          "Statistics for Flexible NetFlow";
      }
      enum stats-svc-chain {
        value 5;
        description
          "Statistics for Service Chain";
      }
      enum stats-umts-ondemand {
        value 6;
        description
          "Statistics for Unified Management and Tracing Services";
      }
      enum stats-umts-sla {
        value 7;
        description
          "Statistics for Unified Management and Tracing Services (SLA change)";
      }
      enum stats-umts-pmtu {
        value 8;
        description
          "Statistics for Unified Management and Tracing Services (PMTU change)";
      }
      enum stats-umts-monitor {
        value 9;
        description
          "Statistics for Unified Management and Tracing Services (Monitor)";
      }
      enum stats-umbrella {
        value 10;
        description
          "Statistics for Umbrella";
      }
      enum stats-fwall-class {
        value 11;
        description
          "Statistics for Firewall Zone pair Class";
      }
      enum stats-fwall-l7-class {
        value 12;
        description
          "Statistics for Firewall Zone pair L7 class";
      }
      enum stats-fwall-app {
        value 13;
        description
          "Statistics for Firewall Zone pair Application";
      }
      enum stats-fwall-proto {
        value 14;
        description
          "Statistics for Firewall Zone pair Protocol";
      }
      enum stats-fwall-zp {
        value 15;
        description
          "Statistics for Firewall Zone pair";
      }
      enum stats-fwall-total {
        value 16;
        description
          "Statistics for Firewall total packets";
      }
      enum stats-fwall-drop {
        value 17;
        description
          "Statistics for Firewall drop packets";
      }
      enum stats-art-cxp {
        value 18;
        description
          "Statistics for Application Response Time";
      }
      enum stats-perfmon-agg {
        value 19;
        description
          "Statistics for Performance Monitor Aggregate";
      }
      enum stats-app-agg {
        value 20;
        description
          "Statistics for Application Aggregate";
      }
      enum stats-system {
        value 21;
        description
          "Statistics for System";
      }
      enum stats-qos {
        value 22;
        description
          "Statistics for Quality of Service";
      }
      enum stats-cellular {
        value 23;
        description
          "Statistics for Cellular";
      }
      enum stats-sdra {
        value 24;
        description
          "Statistics for SD-WAN Remote Access";
      }
      enum stats-envmon {
        value 25;
        description
          "Statistics for Environmental Monitor";
      }
      enum stats-crypto-dmvpn {
        value 26;
        description
          "Statistics for Crypto DMVPN";
      }
      enum stats-crypto {
        value 27;
        description
          "Statistics for IPSec crypto";
      }
      enum stats-qfp-resource {
        value 28;
        description
          "Statistics for Quantum Flow Processor Resource";
      }
      enum stats-tracker {
        value 29;
        description
          "Statistics for Endpoint Tracker";
      }
      enum stats-ssld-policy {
        value 30;
        description
          "Statistics for SSL Decryption Policy";
      }
      enum stats-redundancy {
        value 31;
        description
          "Statistics for Redundancy Application";
      }
      enum stats-utd-urlf {
        value 32;
        description
          "Statistics for URL Filtering";
      }
      enum stats-utd-amp-stat {
        value 33;
        description
          "Statistics for Advanced Malware Protection";
      }
      enum stats-utd-amp-alert {
        value 34;
        description
          "Statistics for Advanced Malware Protection Alert";
      }
      enum stats-utd-tg-stat {
        value 35;
        description
          "Statistics for Threat Grid";
      }
      enum stats-utd-tg-alert {
        value 36;
        description
          "Statistics for Threat Grid Alert";
      }
      enum stats-utd-daq {
        value 37;
        description
          "Statistics for Data Acquisition Queue";
      }
      enum stats-utd-wcapi {
        value 38;
        description
          "Statistics for Web Cache API";
      }
      enum stats-utd-tls {
        value 39;
        description
          "Statistics for Transport Layer Security";
      }
      enum stats-utd-urlf-category {
        value 40;
        description
          "Statistics for URL Filtering Category";
      }
      enum stats-utd-ips-alert {
        value 41;
        description
          "Statistics for Intrusion Prevention System Alert";
      }
      enum stats-utd-tls-category {
        value 42;
        description
          "Statistics for Transport Layer Security Category";
      }
      enum stats-utd-retro-alert {
        value 43;
        description
          "Statistics for Advanced Malware Protection Retrospective Alert";
      }
      enum stats-qfp-drop {
        value 44;
        description
          "Statistics for Quantum Flow Processor Drop";
      }
      enum stats-app-hosting-info {
        value 45;
        description
          "Statistics for App Hosting Information";
      }
      enum stats-app-hosting-intf {
        value 46;
        description
          "Statistics for App Hosting Interface";
      }
      enum stats-temp-mon {
        value 47;
        description
          "Statistics for Temperature Monitoring";
      }
      enum stats-pkt-reorder {
        value 48;
        description
          "Statistics for Packet Reorder";
      }
      enum stats-ppl {
        value 49;
        description
          "Statistics for Per Packet Load balancing";
      }
      enum stats-ngfw-ips {
        value 50;
        description
          "Statistics for NGFW Intrusion Prevention System";
      }
    }
    description
      "Defines identifiers that classify the statistics source or subsystem.";
  }

  typedef stats-drop-reason-type {
    type bits {
      bit drop-reason-quota-exceeded {
        position 0;
        description
          "Drop because a configured quota was exceeded.";
      }
      bit drop-reason-user-initiated {
        position 1;
        description
          "Drop triggered by an operator or user action.";
      }
      bit drop-reason-rate-limited {
        position 2;
        description
          "Drop caused by rate limiting.";
      }
    }
    description
      "Defines reasons why statistics records may be dropped.";
  }

  grouping stats-dropped-list {
    description
      "Details about a single statistics drop record.";
    leaf table-id {
      type sdwan-stats-ios-xe-events:sdwan-stats-types;
      description
        "Identifier of the statistics table that reported the drop.";
    }
    leaf table-name {
      type string;
      description
        "Canonical name of the statistics table.";
    }
    leaf start-time {
      type yang:date-and-time;
      description
        "Start time of the drop interval.";
    }
    leaf end-time {
      type yang:date-and-time;
      description
        "End time of the drop interval.";
    }
    leaf drop-reason {
      type sdwan-stats-ios-xe-events:stats-drop-reason-type;
      description
        "Reason(s) the statistics records were dropped.";
    }
    leaf ndropped {
      type uint32;
      description
        "Number of statistics records dropped.";
    }
  }

  grouping stats-dropped {
    description
      "Notification payload for statistics drop events.";
    leaf severity {
      type ios-common-ios-xe-oper:notification-severity;
      description
        "Severity of the drop notification.";
    }
    leaf host-name {
      type string;
      description
        "Host name of the reporting system.";
    }
    leaf system-ip {
      type inet:ip-address;
      description
        "System IP address of the reporting system.";
    }
    list stats-dropped-list {
      description
        "List of drop records included in the notification.";
      uses sdwan-stats-ios-xe-events:stats-dropped-list;
    }
  }

  notification stats-dropped {
    description
      "Notification emitted when statistics records are dropped.";
    uses sdwan-stats-ios-xe-events:stats-dropped;
  }
}
