module Cisco-IOS-XE-app-cflowd-oper {
  yang-version 1.1;
  namespace "http://cisco.com/ns/yang/Cisco-IOS-XE-app-cflowd-oper";
  prefix app-cflowd-ios-xe-oper;

  import Cisco-IOS-XE-common-types {
    prefix common-types-ios-xe;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for operational data.
     Copyright (c) 2022-2023, 2026 by Cisco Systems, Inc.
     All rights reserved.";

  revision 2026-08-01 {
    description
      "Improved YANG description quality for better clarity and completeness";
    reference
      "1.1.1";
    cisco-semver:module-version "1.1.1";
  }
  revision 2023-07-01 {
    description
      "- Added tenant-cache-statistics";
    reference
      "1.1.0";
    cisco-semver:module-version "1.1.0";
  }
  revision 2022-11-01 {
    description
      "Initial revision";
    reference
      "1.0.0";
    cisco-semver:module-version "1.0.0";
  }

  grouping cflowd-flow-keys {
    description
      "Unique identifier of a flow";
    leaf vpn-id {
      type uint32;
      description
        "Device VPN identifier";
    }
    leaf src-addr {
      type inet:ip-address;
      description
        "Source address in the IP packet header";
    }
    leaf dst-addr {
      type inet:ip-address;
      description
        "Destination address in the IP packet header";
    }
    leaf src-port {
      type uint16;
      description
        "Source port identifier in the transport header";
    }
    leaf dst-port {
      type uint16;
      description
        "Destination port identifier in the transport header";
    }
    leaf proto {
      type uint8;
      description
        "Value of the protocol number in the Protocol field of the IP packet header";
    }
    leaf is-ipv4 {
      type boolean;
      description
        "Indicates whether the flow belongs to an IPv4 flow table (true) or not (false)";
    }
  }

  grouping cflowd-flow-nonkeys {
    description
      "Flow details";
    leaf dscp {
      type uint8;
      description
        "Value of a DSCP encoded in the Differentiated Services field";
    }
    leaf tcp-cntrl-bits {
      type uint8;
      description
        "TCP control bits observed for the packets of this flow";
    }
    leaf icmp-opcode {
      type uint16;
      description
        "ICMP operation code observed in the packets of this flow, indicating the specific ICMP message type";
    }
    leaf total-pkts {
      type uint64;
      units "packets";
      description
        "Number of packets passed through";
    }
    leaf total-bytes {
      type uint64;
      units "bytes";
      description
        "Number of bytes passed through";
    }
    leaf start-time {
      type yang:date-and-time;
      description
        "Absolute timestamp of the first packet of this flow";
    }
    leaf input-intf {
      type string;
      description
        "Input interface of the flow";
    }
    leaf output-intf {
      type string;
      description
        "Output interface of the flow";
    }
    leaf app {
      type string;
      description
        "Name of the application identified for this flow";
    }
    leaf family {
      type string;
      description
        "Name of the application family or category identified for this flow";
    }
  }

  grouping cflowd-tenant-keys {
    description
      "Unique identifier of a tenant statistics";
    leaf mon-name {
      type string;
      description
        "Flow monitor name";
    }
    leaf tenant-id {
      type uint16;
      description
        "Device tenant identifier";
    }
  }

  grouping cflowd-tenant-nonkeys {
    description
      "Tenant detail statistics";
    leaf current-entries {
      type uint32;
      description
        "The current number of entries";
    }
    leaf high-watermark {
      type uint32;
      description
        "The high watermark of flows";
    }
    leaf cache-size {
      type uint32;
      description
        "The size of the cache";
    }
  }

  container app-cflowd-oper-data {
    config false;
    description
      "App cFlowd flow operational data";
    list location {
      key "fru slot bay chassis node";
      description
        "A list of data provider locations";
      uses common-types-ios-xe:extended-location;
      list app-cflowd-ipv4 {
        key "vpn-id src-addr dst-addr src-port dst-port proto is-ipv4";
        description
          "List of IPv4 flow records";
        uses app-cflowd-ios-xe-oper:cflowd-flow-keys;
        uses app-cflowd-ios-xe-oper:cflowd-flow-nonkeys;
      }
      list app-cflowd-ipv6 {
        key "vpn-id src-addr dst-addr src-port dst-port proto is-ipv4";
        description
          "List of IPv6 flow records";
        uses app-cflowd-ios-xe-oper:cflowd-flow-keys;
        uses app-cflowd-ios-xe-oper:cflowd-flow-nonkeys;
      }
      list tenant-cache-stats {
        key "mon-name tenant-id";
        description
          "List of tenant cache statistics";
        uses app-cflowd-ios-xe-oper:cflowd-tenant-keys;
        uses app-cflowd-ios-xe-oper:cflowd-tenant-nonkeys;
      }
    }
  }
}
