module Cisco-IOS-XE-environment-oper {
  yang-version 1.1;
  namespace "http://cisco.com/ns/yang/Cisco-IOS-XE-environment-oper";
  prefix environment-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for monitoring Environment of a Network Element.
     Copyright (c) 2016-2019, 2023-2024, 2026 by Cisco Systems, Inc.
     All rights reserved.";

  revision 2026-08-01 {
    description
      "-Added a signed reading leaf for current sensor reading to replace deprecated unsigned
        current-reading leaf
       -Updated description of environment related elements to clarify their meaning and purpose";
    reference
      "2.7.0";
    cisco-semver:module-version "2.7.0";
  }
  revision 2025-07-01 {
    description
      "Added support for environment related alarm thresholds and sensor states.";
    reference
      "2.6.0";
    cisco-semver:module-version "2.6.0";
  }
  revision 2025-03-01 {
    description
      "Added milliwatts in power sensor unit type";
    reference
      "2.5.0";
    cisco-semver:module-version "2.5.0";
  }
  revision 2024-03-01 {
    description
      "Added milli volts AC and milli volts DC In Sensor Unit Type";
    reference
      "2.4.0";
    cisco-semver:module-version "2.4.0";
  }
  revision 2022-11-01 {
    description
      "Update yang-version to 1.1";
    reference
      "2.3.0";
    cisco-semver:module-version "2.3.0";
  }
  revision 2019-05-01 {
    description
      "Added semantic version";
    reference
      "2.2.0";
    cisco-semver:module-version "2.2.0";
  }
  revision 2018-10-29 {
    description
      "- A new field sensor type is added
       - Cleaned up spelling errors in descriptions.";
    reference
      "2.1.0";
    cisco-semver:module-version "2.1.0";
  }
  revision 2017-11-27 {
    description
      "Sensor thresholds. RPMs as units. Changed enumeration names to be lowercase and hyphenated";
    reference
      "2.0.0";
    cisco-semver:module-version "2.0.0";
  }
  revision 2017-02-07 {
    description
      "Initial revision";
    reference
      "1.0.0";
    cisco-semver:module-version "1.0.0";
  }

  typedef sensor-type {
    type enumeration {
      enum temperature {
        value 0;
      }
      enum voltage {
        value 1;
      }
      enum current {
        value 2;
      }
      enum power {
        value 3;
      }
      enum fan {
        value 4;
      }
      enum unknown-sensor {
        value 5;
      }
    }
    description
      "Type of the Sensor";
  }

  typedef sensor-units-type {
    type enumeration {
      enum watts {
        value 0;
      }
      enum celsius {
        value 1;
      }
      enum millivolts {
        value 2;
      }
      enum amperes {
        value 3;
      }
      enum volts-dc {
        value 4;
      }
      enum volts-ac {
        value 5;
      }
      enum milliamperes {
        value 6;
      }
      enum unknown {
        value 7;
      }
      enum revolutions-per-minute {
        value 8;
      }
      enum millivolts-ac {
        value 9;
        description
          "Units used by milli volts AC sensors";
      }
      enum millivolts-dc {
        value 10;
        description
          "Units used by milli volts DC sensors";
      }
      enum milliwatts {
        value 11;
        description
          "Units used by milliwatts power sensors";
      }
    }
    description
      "Units used by various sensors";
  }

  grouping sensor-name-loc-key {
    description
      "Each sensor representing a data node is
       uniquely identified by a name and a location based key";
    leaf name {
      type string;
      description
        "Name of the sensor component.
         This includes all physical components of the chassis -
         both fixed and pluggable";
    }
    leaf location {
      type string;
      description
        "Physical or logical location of the sensor within the device chassis";
    }
  }

  grouping sensor-params {
    description
      "Sensor parameters";
    leaf state {
      type string;
      description
        "A string value representing the current state of the sensor. The following is a list of all possible values:
         'Critical Cold' for very low temperature at critical severity;
         'Cold' for low temperature above critical-cold range;
         'Cool' for cool temperature above cold range;
         'Normal' or 'Norm' for normal operating range;
         'Warning' or 'Warn' for warning condition;
         'Minor' or 'Min' for minor alarm condition;
         'Major' or 'Maj' for major alarm condition;
         'Critical' or 'Cri' for critical alarm condition;
         'Shutdown' or 'Shut' for shutdown-level condition;
         'Minor Low' or 'Minor low' for low minor threshold range;
         'Major Low' or 'Major low' for low major threshold range;
         'Critical Low' or 'Critical low' for low critical threshold range;
         'Shutdown Low' for low shutdown threshold range;
         'Minor high' for high minor threshold range;
         'Major high' for high major threshold range;
         'Critical high' for high critical threshold range;
         'Warm' for temperature above normal but below hot range;
         'Hot' for high temperature condition;
         'Critical Hot' for very high temperature at critical severity;
         'Faulty' for sensor not functioning;
         'Not Exist' for sensor not present;
         'Not Functioning' for sensor not functioning;
         'Unknown' for unknown or unmapped state.";
    }
    leaf current-reading {
      type uint32;
      status deprecated;
      description
        "Numerical value of the current sensor reading in sensor-units. This leaf is now deprecated. Use the signed reading leaf instead.";
    }
    leaf sensor-units {
      type environment-ios-xe-oper:sensor-units-type;
      description
        "Units corresponding to the current-reading value";
    }
    leaf low-critical-threshold {
      type int32;
      description
        "Alarm threshold under which a critical
         alarm will be signalled";
    }
    leaf low-normal-threshold {
      type int32;
      description
        "Threshold value above which no alarm is generated, indicating the lower bound of the normal
         operating range for the sensor";
    }
    leaf high-normal-threshold {
      type int32;
      description
        "Threshold value below which no alarm is generated, indicating the upper bound of the normal
         operating range for the sensor";
    }
    leaf high-critical-threshold {
      type int32;
      description
        "Alarm threshold over which a critical
         alarm will be signalled";
    }
    leaf sensor-name {
      type environment-ios-xe-oper:sensor-type;
      description
        "Type of the sensor, such as temperature, voltage, current, power, or fan";
    }
    leaf hi-minor-thrsld {
      type int32;
      description
        "The threshold value above which a minor alarm is triggered,
         indicating a potential issue that requires attention but is not critical.";
    }
    leaf hi-major-thrsld {
      type int32;
      description
        "The threshold value above which a major alarm is triggered,
         indicating issue that requires immediate attention.";
    }
    leaf reading {
      type int32;
      description
        "Signed numerical value of current sensor reading in sensor-units. This leaf supports both positive and negative values and replaces deprecated current-reading leaf.";
    }
  }

  grouping env-stat {
    description
      "A set of metrics monitoring environmental sensor activity and alarm severity levels, including
       the number of active alarms at different severity, as well as active,and cancelled sensors";
    leaf crit-alrm {
      type uint32;
      description
        "The threshold value that triggers a critical alarm,
         indicating a severe issue that requires immediate attention.";
    }
    leaf minor-alrm {
      type uint32;
      description
        "The threshold value that triggers a minor alarm,
         indicating a potential issue that should be monitored.";
    }
    leaf major-alrm {
      type uint32;
      description
        "The threshold value that triggers a major alarm,
         indicating a serious issue that needs prompt resolution.";
    }
    leaf cancl-snsrs {
      type uint32;
      description
        "The number of sensors that have been cancelled or are no longer active,
         indicating sensors that have been disabled or removed.";
    }
    leaf null-st-snsrs {
      type uint32;
      description
        "The number of sensors with undefined or empty sensor states,
         representing sensors that are uninitialized or unable to report valid data.";
    }
  }

  container environment-sensors {
    config false;
    description
      "Container for environmental monitoring data nodes covering sensor readings and alarm status for
       device environmental conditions such as temperature, voltage, and fan status";
    list environment-sensor {
      key "name location";
      description
        "List of environmental sensors present on the device chassis, each representing a physical
         component such as temperature, voltage, current, or fan sensors";
      uses environment-ios-xe-oper:sensor-params;
      uses environment-ios-xe-oper:sensor-name-loc-key;
    }
    container env-stat {
      presence "env-stat";
      description
        "A set of metrics monitoring environmental sensor activity and alarm severity levels, including
         the number of active alarms at different severity, as well as active, and cancelled sensors";
      uses environment-ios-xe-oper:env-stat;
    }
  }
}
