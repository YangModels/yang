module Cisco-IOS-XE-wireless-wat-oper {
  yang-version 1.1;
  namespace "http://cisco.com/ns/yang/Cisco-IOS-XE-wireless-wat-oper";
  prefix wireless-wat-oper;

  import Cisco-IOS-XE-wireless-enum-types {
    prefix wireless-enum-types;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     Wireless Active Testing (WAT) operational data.
     Copyright (c) 2026 by Cisco Systems, Inc.
     All rights reserved.";

  revision 2026-08-01 {
    description
      "Initial revision";
    reference
      "1.0.0";
    cisco-semver:module-version "1.0.0";
  }

  typedef wat-dp {
    type enumeration {
      enum wat-dp-wlc {
        value 0;
        description
          "WAT client test traffic will be sent through the WLC";
      }
      enum wat-dp-ap {
        value 1;
        description
          "WAT client test traffic will be sent through the AP";
      }
    }
    description
      "Enumeration for identifying the datapath a Wireless Active Testing
       (WAT) client will send its test traffic through";
  }

  typedef wat-cfg-src {
    type enumeration {
      enum wat-cfg-src-static-ap-tag {
        value 0;
        description
          "WAT Profile comes from the AP's configured Static AP Tag";
      }
      enum wat-cfg-src-ap-filter {
        value 1;
        description
          "WAT Profile comes from the AP's matching WAT AP Filter";
      }
      enum wat-cfg-src-site-tag {
        value 2;
        description
          "WAT Profile comes from the AP's configured Site Tag";
      }
      enum wat-cfg-src-rf-tag {
        value 3;
        description
          "WAT configuration comes from the AP's applied Radio Profile(s) in
           its configured RF Tag";
      }
    }
    description
      "Enumeration for identifying the Wireless Active Testing (WAT) AP's
       configuration source";
  }

  grouping te-status {
    description
      "ThousandEyes (TE) Endpoint Agent (EPA) status on an AP with Wireless
       Active Testing (WAT) enabled";
    leaf product {
      type string;
      description
        "TE EPA product name";
    }
    leaf type {
      type string;
      description
        "TE EPA type: ENTERPRISE, STAGING, or DEVELOPMENT";
    }
    leaf ver {
      type string;
      description
        "TE EPA version";
    }
    leaf latest-ver {
      type string;
      description
        "Latest version the TE EPA can be upgraded to";
    }
    leaf upgrade-url {
      type string;
      description
        "URL to upgrade to latest version of the TE EPA";
    }
    leaf will-upgrade {
      type boolean;
      description
        "True if the TE EPA will upgrade soon";
    }
    leaf status {
      type string;
      description
        "TE EPA status";
    }
    leaf app-state {
      type string;
      description
        "TE EPA IOx application state";
    }
    leaf app-state-time {
      type yang:date-and-time;
      description
        "Date and time the TE EPA IOx application state was last updated";
    }
    leaf start-time {
      type yang:date-and-time;
      description
        "Date and time the TE EPA was first started or last restarted";
    }
    leaf checkin-time {
      type yang:date-and-time;
      description
        "Date and time the TE EPA last checked in with the TE Platform /
         Service";
    }
  }

  grouping wat-ap {
    description
      "Wireless Active Testing (WAT) operational information and status on an
       AP with WAT enabled";
    leaf wtp-mac {
      type yang:mac-address;
      description
        "AP CAPWAP MAC Address";
    }
    leaf wat-profile-name {
      type string;
      description
        "WAT Profile name applied to this AP. If empty, the AP is still WAT
         enabled for Wireless Testing via the Radio Profile / RF Tag.";
    }
    leaf wat-profile-cfg-src {
      type wireless-wat-oper:wat-cfg-src;
      description
        "Identifies the configuration source of the WAT Profile. If the source
         is rf-tag, no WAT Profile is applied and the wat-profile-name will be
         an empty string.";
    }
    leaf wat-profile-cfg-src-name {
      type string;
      description
        "Identifies the name of the wat-profile-cfg-src. If the source is
         static-ap-tag, this will be an empty string";
    }
    leaf test-wired {
      type boolean;
      description
        "True if WAT Wired Testing is enabled";
    }
    leaf test-wireless {
      type boolean;
      description
        "True if WAT Wireless Testing (no client-serving) is enabled";
    }
    leaf status {
      type string;
      description
        "WAT status on the AP";
    }
    leaf status-time {
      type yang:date-and-time;
      description
        "Date and time the WAT status was last updated";
    }
    container te-status {
      description
        "ThousandEyes (TE) Endpoint Agent (EPA) status on the AP";
      uses wireless-wat-oper:te-status;
    }
  }

  grouping wired-client-info {
    description
      "WAT Wired Testing Client information";
    leaf wlan-id {
      type uint32;
      description
        "WLAN ID of the WLAN Profile/Policy applied for this client when
         installing in the WLC datapath";
    }
    leaf ssid {
      type string;
      description
        "SSID name of the WLAN Profile/Policy applied for this client when
         installing in the WLC datapath";
    }
    leaf slot-id {
      type uint8;
      description
        "Radio Slot ID applied for this client when installing in the WLC datapath";
    }
    leaf vap-id {
      type uint8;
      description
        "VAP ID applied for this client when installing in the WLC datapath";
    }
    leaf bssid {
      type yang:mac-address;
      description
        "BSSID applied for this client when installing in the WLC datapath";
    }
    leaf vlan {
      type uint16;
      description
        "VLAN applied for this client, which comes from the vlan-src, when
         installing in the WLC datapath";
    }
    leaf vlan-src {
      type wireless-enum-types:wat-vlan-src;
      description
        "Source of VLAN applied for this client";
    }
    leaf timeout {
      type uint32;
      units "seconds";
      description
        "Time after client is installed in the WLC datapath to automatically
         cleanup and delete the client";
    }
  }

  grouping entry {
    description
      "Requested WAT Wired Testing client entry";
    leaf wtp-mac {
      type yang:mac-address;
      description
        "WAT AP MAC Address which requested this client to be installed";
    }
    leaf client-mac {
      type yang:mac-address;
      description
        "WAT Wired Testing Client MAC Address";
    }
    container client-info {
      description
        "Information for the requested WAT Wired Testing client to be
         installed";
      uses wireless-wat-oper:wired-client-info;
    }
    leaf req-time {
      type yang:date-and-time;
      description
        "Date and time the request was received and queued";
    }
  }

  grouping wired-req {
    description
      "List of requested WAT Wired Testing clients";
    leaf num-req {
      type uint32;
      description
        "Total number of requested WAT Wired Testing clients";
    }
    list req-list {
      description
        "List of requested WAT Wired Testing clients";
      uses wireless-wat-oper:entry;
    }
  }

  grouping wired-client {
    description
      "Installed WAT Wired Testing client information";
    leaf wtp-mac {
      type yang:mac-address;
      description
        "WAT AP MAC Address which requested this client to be installed";
    }
    leaf client-mac {
      type yang:mac-address;
      description
        "WAT Wired Testing Client MAC Address";
    }
    leaf install-ifid {
      type uint32;
      description
        "Interface ID of the WAT Wired Client installed in the WLC Datapath";
    }
    container client-info {
      description
        "Information for the installed WAT Wired Testing client";
      uses wireless-wat-oper:wired-client-info;
    }
    leaf install-time {
      type yang:date-and-time;
      description
        "Date and time the client was installed";
    }
    leaf dp {
      type wireless-wat-oper:wat-dp;
      description
        "Datapath that traffic for the installed WAT Wired Testing client
         will take";
    }
  }

  container wat-oper-data {
    config false;
    description
      "Wireless Active Testing (WAT) operational data and status";
    list wat-ap {
      key "wtp-mac";
      description
        "Access Points (APs) with Wireless Active Testing (WAT) enabled";
      uses wireless-wat-oper:wat-ap;
    }
    container wat-wired-req {
      presence "wat-wired-req";
      description
        "Requested WAT Wired Testing clients";
      uses wireless-wat-oper:wired-req;
    }
    list wat-wired-client {
      key "wtp-mac";
      unique "client-mac";
      description
        "Installed WAT Wired Testing clients ";
      uses wireless-wat-oper:wired-client {
        refine "client-mac" {
          mandatory true;
        }
      }
    }
  }
}
