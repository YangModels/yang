module Cisco-IOS-XE-spanning-tree-events {
  yang-version 1.1;
  namespace "http://cisco.com/ns/yang/Cisco-IOS-XE-spanning-tree-events";
  prefix stp-ios-xe-events;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Spanning-Tree event notification.
     Copyright (c) 2023 by Cisco Systems, Inc.
     All rights reserved.";

  revision 2024-03-01 {
    description
      "- Added support for STP BPDU sender conflict event
       - Added support for STP interface role change";
    reference
      "1.1.0";
    cisco-semver:module-version "1.1.0";
  }
  revision 2023-07-01 {
    description
      "Initial revision";
    reference
      "1.0.0";
    cisco-semver:module-version "1.0.0";
  }

  typedef stp-port-guard-type {
    type enumeration {
      enum stp-bpduguard {
        value 0;
        description
          "Spanning tree BPDU Guard";
      }
      enum stp-rootguard {
        value 1;
        description
          "Spanning tree Root Guard";
      }
      enum stp-loopguard {
        value 2;
        description
          "Spanning tree Loop Guard";
      }
    }
    description
      "Spanning tree port guard types";
  }

  typedef stp-port-guard-state {
    type enumeration {
      enum stp-guard-activated {
        value 0;
        description
          "The guard is activated on the port";
      }
      enum stp-guard-deactivated {
        value 1;
        description
          "The guard is deactivated on the port";
      }
    }
    description
      "Indicates if the guard is activated or deactivated on the port";
  }

  typedef stp-port-guard-action {
    type enumeration {
      enum stp-action-blocking-port {
        value 0;
        description
          "Port is placed in STP blocking state";
      }
      enum stp-action-unblocking-port {
        value 1;
        description
          "Port is taken out of STP blocking state";
      }
      enum stp-action-disabling-port {
        value 2;
        description
          "Port is placed in disabled state";
      }
      enum stp-action-disabling-vlan {
        value 3;
        description
          "VLAN is placed in disabled state";
      }
    }
    description
      "Indicates the guard action taken by STP on the port";
  }

  typedef stp-port-state {
    type enumeration {
      enum stp-state-disabled {
        value 0;
        description
          "STP port state disabled";
      }
      enum stp-state-blocking {
        value 1;
        description
          "STP port state blocking";
      }
      enum stp-state-listening {
        value 2;
        description
          "STP port state listening ";
      }
      enum stp-state-learning {
        value 3;
        description
          "STP port learning ";
      }
      enum stp-state-forwarding {
        value 4;
        description
          "STP port forwarding ";
      }
      enum stp-state-broken {
        value 5;
        description
          "STP port broken";
      }
      enum stp-state-invalid {
        value 6;
        description
          "STP port state invalid ";
      }
    }
    description
      "Spanning Tree Protocol port states";
  }

  typedef stp-port-role {
    type enumeration {
      enum stp-role-master {
        value 0;
        description
          "STP port role master";
      }
      enum stp-role-alternate {
        value 1;
        description
          "STP port role alternate";
      }
      enum stp-role-root {
        value 2;
        description
          "STP port role root";
      }
      enum stp-role-designated {
        value 3;
        description
          "STP port role designated";
      }
      enum stp-role-backup {
        value 4;
        description
          "STP port role backup";
      }
    }
    description
      "Spanning Tree Protocol port roles";
  }

  typedef stp-bpdu-sender-conflict-event-type {
    type enumeration {
      enum stp-bpdu-sender-conflict {
        value 0;
        description
          "Spanning tree BPDU sender conflict";
      }
    }
    description
      "Spanning tree BPDU sender conflict event types";
  }

  typedef stp-bpdu-delay-event-type {
    type enumeration {
      enum stp-bpdu-delay-tx {
        value 0;
        description
          "Spanning tree BPDU transmit delay";
      }
      enum stp-bpdu-delay-rx {
        value 1;
        description
          "Spanning tree BPDU receive delay";
      }
    }
    description
      "Spanning tree BPDU delay types";
  }

  grouping stp-interface-guard-event {
    description
      "STP interface guard events";
    leaf if-name {
      type string;
      description
        "Reference to the STP ethernet interface";
    }
    leaf port-num {
      type uint16;
      description
        "The port number of the bridge port";
    }
    leaf guard-type {
      type stp-ios-xe-events:stp-port-guard-type;
      description
        "Interface spanning tree guard type";
    }
    leaf guard-state {
      type stp-ios-xe-events:stp-port-guard-state;
      description
        "Indicates the guard state of the port";
    }
    leaf action {
      type stp-ios-xe-events:stp-port-guard-action;
      description
        "Indicates the action taken by STP on the port";
    }
    choice mac-type-choice {
      description
        "mac type choice";
      case option-enabled {
        leaf client-mac {
          type yang:mac-address;
          description
            "MAC address of the BPDU source";
        }
      }
    }
    choice vlan-type-choice {
      description
        "VLAN type choice";
      case option-enabled {
        leaf vlan-id {
          type uint16;
          description
            "VLAN identifier associated with the port";
        }
      }
    }
    choice instance-type-choice {
      description
        "Instance type choice";
      case option-enabled {
        leaf mst-instance {
          type uint16;
          description
            "MST instance ID";
        }
      }
    }
  }

  grouping stp-interface-role-change {
    description
      "STP interface role change";
    leaf if-name {
      type string;
      description
        "Reference to the STP ethernet interface";
    }
    leaf port-num {
      type uint16;
      description
        "The port number of the bridge port";
    }
    leaf role {
      type stp-ios-xe-events:stp-port-role;
      description
        "The current role of the bridge port";
    }
    leaf state {
      type stp-ios-xe-events:stp-port-state;
      description
        "The current state of the bridge port";
    }
  }

  grouping stp-bpdu-sender-conflict-event {
    description
      "STP BPDU sender conflict events";
    leaf if-name {
      type string;
      description
        "Reference to the STP ethernet interface";
    }
    leaf port-num {
      type uint16;
      description
        "The port number of the bridge port";
    }
    leaf exp-mac {
      type yang:mac-address;
      description
        "MAC address of last BPDU source";
    }
    leaf rcvd-mac {
      type yang:mac-address;
      description
        "MAC address of current BPDU source";
    }
    leaf event-type {
      type stp-ios-xe-events:stp-bpdu-sender-conflict-event-type;
      description
        "The type of event (transmit/receive)";
    }
  }

  grouping stp-bpdu-delay-event {
    description
      "STP BPDU delay events";
    leaf if-name {
      type string;
      description
        "Reference to the STP ethernet interface";
    }
    leaf port-num {
      type uint16;
      description
        "The port number of the bridge port";
    }
    leaf event-type {
      type stp-ios-xe-events:stp-bpdu-delay-event-type;
      description
        "The type of event (transmit/receive)";
    }
  }

  notification stp-intf-guard-event {
    description
      "STP interface guard events notification";
    uses stp-ios-xe-events:stp-interface-guard-event;
  }

  notification stp-intf-role-change {
    description
      "STP interface role change notification";
    uses stp-ios-xe-events:stp-interface-role-change;
  }

  notification stp-intf-bpdu-sender-conflict-event {
    description
      "STP BPDU sender conflict events notification";
    uses stp-ios-xe-events:stp-bpdu-sender-conflict-event;
  }

  notification stp-intf-bpdu-delay-event {
    description
      "STP BPDU delay event notification";
    uses stp-ios-xe-events:stp-bpdu-delay-event;
  }
}
