module Cisco-IOS-XE-cable-diag-oper {
  yang-version 1.1;
  namespace "http://cisco.com/ns/yang/Cisco-IOS-XE-cable-diag-oper";
  prefix cable-diag-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for monitoring of cable diagnostic state information.
     Copyright (c) 2016-2020, 2022 by Cisco Systems, Inc.
     All rights reserved.";

  revision 2026-08-01 {
    description
      "- Refined existing leaf descriptions for clarity and consistency";
    reference
      "1.3.1";
    cisco-semver:module-version "1.3.1";
  }
  revision 2022-11-01 {
    description
      "Update yang-version to 1.1";
    reference
      "1.3.0";
    cisco-semver:module-version "1.3.0";
  }
  revision 2020-11-01 {
    description
      "Added a new leaf to capture the time of the cable diagnostic test";
    reference
      "1.2.0";
    cisco-semver:module-version "1.2.0";
  }
  revision 2019-05-01 {
    description
      "Added semantic version";
    reference
      "1.1.0";
    cisco-semver:module-version "1.1.0";
  }
  revision 2018-11-21 {
    description
      "Initial revision";
    reference
      "1.0.0";
    cisco-semver:module-version "1.0.0";
  }

  typedef diag-pair-id {
    type enumeration {
      enum diag-pair-a {
        value 0;
        description
          "Cable diagnostics pair name A";
      }
      enum diag-pair-b {
        value 1;
        description
          "Cable diagnostics pair name B";
      }
      enum diag-pair-c {
        value 2;
        description
          "Cable diagnostics pair name C";
      }
      enum diag-pair-d {
        value 3;
        description
          "Cable diagnostics pair name D";
      }
      enum diag-pair-invalid {
        value 4;
        description
          "Invalid cable diagnostic pair id";
      }
    }
    description
      "Cable diagnostic pair id";
  }

  typedef diag-result {
    type enumeration {
      enum diag-result-invalid {
        value 0;
        description
          "Invalid cable diagnostic result";
      }
      enum diag-result-not-supported {
        value 1;
        description
          "Cable diagnostic is not supported";
      }
      enum diag-result-not-completed {
        value 2;
        description
          "Cable diagnostic has not completed";
      }
      enum diag-result-fail {
        value 3;
        description
          "Cable diagnostic has failed";
      }
      enum diag-result-normal {
        value 4;
        description
          "Cable diagnostic result is normal";
      }
      enum diag-result-impedance-mismatch {
        value 5;
        description
          "Cable diagnostic identified impedance mismatch";
      }
      enum diag-result-open {
        value 6;
        description
          "An opening is detected on the cable";
      }
      enum diag-result-short {
        value 7;
        description
          "A short is detected on the cable";
      }
      enum diag-result-short-or-impedance-mismatch {
        value 8;
        description
          "A short or impedance mismatch is detected on the cable";
      }
      enum diag-result-short-or-crosstalk {
        value 9;
        description
          "A short or crosstalk is detected on the cable";
      }
      enum diag-result-forced {
        value 10;
        description
          "Cable diagnostics result is forced";
      }
    }
    description
      "Cable diagnostic result";
  }

  typedef diag-length-unit {
    type enumeration {
      enum diag-length-unit-invalid {
        value 0;
        description
          "Cable length unit is invalid";
      }
      enum diag-length-unit-centimeter {
        value 1;
        description
          "Cable length unit is in centimetres";
      }
      enum diag-length-unit-meters {
        value 2;
        description
          "Cable length unit is in meters";
      }
      enum diag-length-unit-kilometer {
        value 3;
        description
          "Cable length unit is in kilometers";
      }
    }
    description
      "Cable diagnostic length unit";
  }

  typedef diag-speed {
    type enumeration {
      enum diag-speed-10mbps {
        value 0;
        description
          "Current line speed is 10Mbps";
      }
      enum diag-speed-100mbps {
        value 1;
        description
          "Current line speed is 100Mbps";
      }
      enum diag-speed-1gbps {
        value 2;
        description
          "Current line speed is 1Gbps";
      }
      enum diag-speed-5000mbps {
        value 3;
        description
          "Current line speed is 5000Mbps";
      }
      enum diag-speed-2500mbps {
        value 4;
        description
          "Current line speed is 2500Mbps";
      }
      enum diag-speed-10gbps {
        value 5;
        description
          "Current line speed is 10Gbps";
      }
      enum diag-speed-40gbps {
        value 6;
        description
          "Current line speed is 40Gbps";
      }
      enum diag-speed-25gbps {
        value 7;
        description
          "Current line speed is 25Gbps";
      }
      enum diag-speed-100gbps {
        value 8;
        description
          "Current line speed is 100Gbps";
      }
      enum diag-speed-auto {
        value 9;
        description
          "Current line speed is auto";
      }
      enum diag-speed-unknown {
        value 10;
        description
          "Current line speed is unknown";
      }
    }
    description
      "Cable diagnostic speed information";
  }

  grouping cable-diag-oper {
    description
      "Cable diagnostic operational entry details";
    leaf pair-id {
      type cable-diag-ios-xe-oper:diag-pair-id;
      description
        "Identifier for the local wire pair being tested in the cable diagnostic operation.";
    }
    leaf result {
      type cable-diag-ios-xe-oper:diag-result;
      description
        "Diagnostic result for the specified wire pair in the cable.";
    }
    leaf length-unit {
      type cable-diag-ios-xe-oper:diag-length-unit;
      description
        "Unit of measurement for the cable length value.";
    }
    leaf remote-pair-id {
      type cable-diag-ios-xe-oper:diag-pair-id;
      description
        "Identifier for the corresponding remote wire pair detected during cable diagnostics.";
    }
    leaf length {
      type uint32;
      description
        "Measured length of the cable for the specified wire pair, in the unit indicated by length-unit.";
    }
    leaf error {
      type uint32;
      description
        "Margin of error for the cable length measurement, expressed in the same units as the length leaf.";
    }
  }

  grouping cable-diag-state {
    description
      "Cable diagnostics state information";
    leaf local-interface-name {
      type string;
      description
        "Name of the local interface on which cable diagnostics are performed.";
    }
    leaf speed {
      type cable-diag-ios-xe-oper:diag-speed;
      description
        "Current line speed";
    }
    list cable-diag-oper {
      key "pair-id";
      description
        "List of all pair information";
      uses cable-diag-ios-xe-oper:cable-diag-oper;
    }
    leaf tdr-test-time {
      type yang:date-and-time;
      description
        "This leaf records the time when the last cable-diagnostic test is performed";
    }
  }

  container cable-diag-oper-data {
    config false;
    description
      "Data nodes for cable diagnostics information";
    list cable-diag-state {
      key "local-interface-name";
      description
        "Cable diagnostics state information";
      uses cable-diag-ios-xe-oper:cable-diag-state;
    }
  }
}
