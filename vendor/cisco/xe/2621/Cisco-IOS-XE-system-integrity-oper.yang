module Cisco-IOS-XE-system-integrity-oper {
  yang-version 1.1;
  namespace "http://cisco.com/ns/yang/Cisco-IOS-XE-system-integrity-oper";
  prefix system-integrity-ios-xe-oper;

  import Cisco-IOS-XE-common-types {
    prefix common-types-ios-xe;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for system integrity operational data.
     Copyright (c) 2020, 2022, 2024, 2026 by Cisco Systems, Inc.
     All rights reserved.";

  revision 2026-08-01 {
    description
      "Updated descriptions of several model elements to clarify their meaning and purpose";
    reference
      "1.2.1";
    cisco-semver:module-version "1.2.1";
  }
  revision 2025-03-01 {
    description
      "Add TPM version 2 quote information";
    reference
      "1.2.0";
    cisco-semver:module-version "1.2.0";
  }
  revision 2022-11-01 {
    description
      "Update yang-version to 1.1";
    reference
      "1.1.0";
    cisco-semver:module-version "1.1.0";
  }
  revision 2022-07-01 {
    description
      "Initial revision";
    reference
      "1.0.0";
    cisco-semver:module-version "1.0.0";
  }

  typedef choice-integrity {
    type enumeration {
      enum choice-measurement {
        value 0;
        description
          "Enumerated value used to denote the integrity
           measurement choice.";
      }
      enum choice-trust-chain {
        value 1;
        description
          "Enumerated value used to denote the integrity trust
           chain choice.";
      }
      enum choice-compliance {
        value 2;
        description
          "Enumerated value used to denote the integrity compliance
           choice.";
      }
    }
    description
      "Enumeration used to select between measurements and
       trust chain.";
  }

  grouping boot-loader-group {
    description
      "Group of aggregate attributes describing a boot loader stage";
    leaf stage {
      type uint8;
      description
        "Indexes this stage of boot loader sequence";
    }
    leaf version {
      type string;
      description
        "Version of the current boot loader stage";
    }
    leaf hash {
      type string;
      description
        "Hash signature of current boot loader stage";
    }
  }

  grouping package-group {
    description
      "Group to aggregate attributes describing a
       package";
    leaf name {
      type string;
      description
        "Name of the package artifact included in the reported integrity measurement.";
    }
    leaf hash {
      type string;
      description
        "System-calculated hash of the package artifact included in the reported integrity measurement.";
    }
  }

  grouping operating-system-group {
    description
      "Group to aggregate attributes describing
       operating system packages";
    leaf version {
      type string;
      description
        "Version of operating system packages";
    }
    list package-integrity {
      description
        "List of package integrity group describing
         system-calculated hashes for each package artifact
         currently installed or patched to the system.  A package
         artifact in this context may consist of at least one super
         package followed by a sequence of sub-packages and optionally
         where applicable may contain additional entries for software
         maintenance update packages.";
      uses system-integrity-ios-xe-oper:package-group;
    }
  }

  grouping pcr-register-group {
    description
      "Describes a pcr register entry";
    leaf index {
      type uint8;
      description
        "Pcr register identifier.";
    }
    leaf pcr-content {
      type string;
      description
        "Current state of the pcr register.";
    }
  }

  grouping signature-group {
    description
      "Group of attributes that describe a payload signature
       consisting of both a signature and the signature
       version.";
    leaf version {
      type uint32;
      mandatory true;
      description
        "Version identifier for the signature and quote format used in this integrity response.";
    }
    leaf signature {
      type string;
      mandatory true;
      description
        "System ACT2 Signature primed by the
         nonce keyed input and signed over the state of an
         information group since last TAM reset.";
    }
    leaf quote {
      type string;
      description
        "TPM 2.0 quote included with this signature to provide
         attestation data for the reported integrity state.";
    }
  }

  grouping measurement-group {
    description
      "Integrity Measurements.";
    leaf platform {
      type string;
      description
        "Product platform identifier for the device that produced these integrity measurements.";
    }
    list boot-loader {
      description
        "List of boot loader group entries describing
         system calculated hashes for each boot loader stage.
         May consist of one or more entries depending on the
         platform.";
      uses system-integrity-ios-xe-oper:boot-loader-group;
    }
    container operating-system {
      description
        "Aggregates the attributes that describe operating
         system and platform functionality currently installed
         on the system.";
      uses system-integrity-ios-xe-oper:operating-system-group;
    }
    list register {
      description
        "List for maintaining the Platform Content
         Register (PCR) indices and content.  Currently
         only two entries are expected: index 0 and
         index 8";
      uses system-integrity-ios-xe-oper:pcr-register-group;
    }
    container signature {
      description
        "Signature over the state of the measurements, signing
         over the nonce input, signature version and the content of
         the measurements group, performed by tam services.";
      uses system-integrity-ios-xe-oper:signature-group;
    }
  }

  grouping capability-group {
    description
      "A capability group describes a particular capability
       attribute value pair associated with a participating
       operational element.";
    leaf attribute {
      type string;
      description
        "The capability attribute active on this element.";
    }
    leaf value {
      type string;
      description
        "The capability attribute value in effect on this element.";
    }
  }

  grouping compliance-group {
    description
      "This group element describes those aspects of the integrity
       output that can be considered verifiable. This can be
       determined by careful examination of the capabilities list
       and is expected to vary by product family, product family
       platform or even by participating operational element within
       a platform instance.";
    list capability {
      description
        "Each member of this list must be examined to determine
         what aspects of the known good value support are active
         with respect to this operational element.";
      uses system-integrity-ios-xe-oper:capability-group;
    }
    container signature {
      description
        "Signature over the state of the capability list, signing
         over the nonce input, signature version and the content of
         the capability group, performed by tam services.";
      uses system-integrity-ios-xe-oper:signature-group;
    }
  }

  grouping certificate-group {
    description
      "This group elements describes an element of the chain of trust";
    leaf name {
      type string;
      description
        "Name of the certificate.";
    }
    leaf value {
      type string;
      description
        "Certificate value reported for this trust-chain entry.";
    }
  }

  grouping trust-chain-group {
    description
      "Content consisting of the trust chain list and a valid signature
       obtained from the trust anchor.";
    list trust-chain {
      description
        "The list of certificates that constitute the chain
         of trust.";
      uses system-integrity-ios-xe-oper:certificate-group;
    }
    container signature {
      description
        "Signature over the state of the trust chain, signing
         over the nonce input, signature version and the content of
         the trust chain group, performed by tam services.";
      uses system-integrity-ios-xe-oper:signature-group;
    }
  }

  grouping integrity-oper-data-key {
    description
      "Compound key aggregates a mandatory nonce input value
       with the choice to retrieve the measurement, trust chain or
       compliance response.
       Security requirements dictate that the compound key value must
       be fully specified both in terms of nonce attribute and
       in terms of the request attribute in order to retrieve a
       non-empty, signed response";
    leaf nonce {
      type string;
      description
        "Signing input used in conjunction with signature on the response
         to verify that the response has not been tampered with.  In this context
         the nonce is key value that is a manufactured input
         provided by the end user.";
    }
    leaf request {
      type system-integrity-ios-xe-oper:choice-integrity;
      description
        "Enumerated input used to indicate the type of response required";
    }
  }

  grouping integrity-oper-data-group {
    description
      "Top level grouping of integrity oper data";
    choice response-choice {
      description
        "Indicates the kind of response provided.";
      case choice-measurement {
        container measurement {
          description
            "Component of integrity measurements for functioning
             elements that support Secure Boot.  These
             measurements include two or more stages of Boot
             Loader( the zero'th element in the list typically
             denotes the micro loader ), and one super-package
             measurement immediately followed by one or more
             sub-package measurements.
             The current state of the system is captured as
             Platform Configuration Register (PCR) content.";
          uses system-integrity-ios-xe-oper:measurement-group;
        }
      }
      case choice-trust-chain {
        container trust-chain {
          description
            "Component of system certificates for functioning elements
             that support Secure Boot.  The component certificate
             list consists of Cisco Root CA (CRCA) certificate,
             Cisco Manufacturing CA (CMCA) certificate, and
             ACT2 RSA Secure Unique Device Identity (SUDI) CA
             PEM certificates and SUDI generated signatures.";
          uses system-integrity-ios-xe-oper:trust-chain-group;
        }
      }
      case choice-compliance {
        container compliance {
          description
            "Component of compliance for functioning elements
             denoting the degree of element support for
             the various functional aspects of integrity.";
          uses system-integrity-ios-xe-oper:compliance-group;
        }
      }
    }
  }

  container system-integrity-oper-data {
    config false;
    description
      "Aggregates system integrity operational data from all
       system integrity capable elements in this platform";
    list location {
      key "fru slot bay chassis node";
      description
        "A list of data provider locations";
      uses common-types-ios-xe:extended-location;
      list integrity {
        key "nonce request";
        description
          "Top level integrity container consists of list indexed
           by a compound integrity operational data key.
           Security requirements dictate that on input the key
           value must be fully specified both in terms of nonce
           attribute and in terms of the request attribute in
           order to retrieve a non-empty, signed response.";
        uses system-integrity-ios-xe-oper:integrity-oper-data-key;
        uses system-integrity-ios-xe-oper:integrity-oper-data-group;
      }
    }
  }
}
