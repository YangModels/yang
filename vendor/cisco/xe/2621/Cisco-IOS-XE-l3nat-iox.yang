module Cisco-IOS-XE-l3nat-iox {
  yang-version 1.1;
  namespace "http://cisco.com/ns/yang/Cisco-IOS-XE-l3nat-iox";
  prefix l3nat-iox;

  import cisco-semver {
    prefix cisco-semver;
  }
  import ietf-inet-types {
    prefix inet;
  }
  import Cisco-IOS-XE-native {
    prefix ios;
  }

  organization
    "Cisco Systems, Inc.";
  contact
    "Cisco Systems, Inc.
     Customer Service
     Postal: 170 W Tasman Drive
     San Jose, CA 95134
     Tel: +1 1800 553-NETS
     E-mail: cs-yang@cisco.com";
  description
    "Cisco XE NAT IOX model";

  revision 2023-11-01 {
    description
      "Initial revision";
    cisco-semver:module-version "1.0.0";
  }

  grouping config-l3nat-iox-grouping {
    container l3nat-iox {
      description
        "IOX NAT Configuration";
      presence "true";
      container nat-config {
        leaf app-ip {
          description
            "Application's private IP address";
          type inet:ipv4-address;
        }
        leaf svi-ip {
          description
            "SVI  IP address";
          must '../app-ip' {
            error-message "App IP should be present";
          }
          type inet:ipv4-address;
        }
        leaf app-name {
          description
            "Application name";
          must '../svi-ip' {
            error-message "SVI IP should be present";
          }
          type enumeration {
            enum CCV-ONPREM;
          }
        }
        leaf server-ip {
          description
            "Server IP address";
          must '../app-name' {
            error-message "App Name should be present";
          }
          type inet:ipv4-address;
        }
      }
    }
  }

  augment "/ios:native" {
    uses config-l3nat-iox-grouping;
  }
}
