module Cisco-IOS-XE-audit-cfg {
  yang-version 1.1;
  namespace "http://cisco.com/ns/yang/Cisco-IOS-XE-audit-cfg";
  prefix audit-ios-xe-cfg;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Audit Monitor configuration data.
     Copyright (c) 2026 by Cisco Systems, Inc.
     All rights reserved.";

  revision 2026-08-01 {
    description
      "Initial revision";
    reference
      "1.0.0";
    cisco-semver:module-version "1.0.0";
  }

  grouping audit-ruleset-list {
    description
      "Audit Monitor rule set enables";
    leaf dns-client-files {
      type boolean;
      default "false";
      description
        "Indicates whether DNS client file audit monitoring is enabled.";
    }
    leaf krnl-mod-mgmt {
      type boolean;
      default "false";
      description
        "Indicates whether kernel module management audit monitoring is enabled.";
    }
    leaf sys-soft {
      type boolean;
      default "false";
      description
        "Indicates whether system software audit monitoring is enabled.";
    }
    leaf usr-grp-conf-files {
      type boolean;
      default "false";
      description
        "Indicates whether user group configuration file audit monitoring is enabled.";
    }
    leaf usr-priv-mgmt {
      type boolean;
      default "false";
      description
        "Indicates whether user privilege management audit monitoring is enabled.";
    }
    leaf guestshell-audit {
      type boolean;
      default "false";
      description
        "Indicates whether guest shell audit monitoring is enabled.";
    }
  }

  grouping audit-rlset-conf {
    description
      "Audit Monitor configuration parameters";
    container audit-rls-list {
      description
        "Audit Monitor rule set enables";
      uses audit-ios-xe-cfg:audit-ruleset-list;
    }
  }

  container audit-cfg-data {
    description
      "Audit Monitor configuration data";
    container audit-cfg {
      presence "audit-cfg";
      description
        "Audit Monitor configuration entry";
      uses audit-ios-xe-cfg:audit-rlset-conf;
    }
  }
}
