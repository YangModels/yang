module Cisco-IOS-XE-wireless-afc-cloud-oper {
  yang-version 1.1;
  namespace "http://cisco.com/ns/yang/Cisco-IOS-XE-wireless-afc-cloud-oper";
  prefix wireless-afc-cloud-oper;

  import Cisco-IOS-XE-wireless-afc-types {
    prefix wireless-afc-types;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Model for managing AFC cloud stats
     Copyright (c) 2022-2026 by Cisco Systems, Inc.
     All rights reserved.";

  revision 2026-08-01 {
    description
      "- Updated descriptions for clarity and accuracy";
    reference
      "1.0.1";
    cisco-semver:module-version "1.0.1";
  }
  revision 2023-11-01 {
    description
      "Initial revision";
    reference
      "1.0.0";
    cisco-semver:module-version "1.0.0";
  }

  grouping st-afc-msg-info {
    description
      "Information about an AFC channel inquiry message";
    leaf request-id {
      type uint64;
      description
        "Identifier of the AFC request associated with this message";
    }
    leaf ap-mac {
      type yang:mac-address;
      description
        "MAC address of the access point associated with this AFC message";
    }
    leaf msg-timestamp {
      type yang:date-and-time;
      description
        "Timestamp when the AFC message was sent or received";
    }
  }

  grouping st-afc-cloud-stats {
    description
      "AFC cloud service communication statistics";
    leaf num-afc-ap {
      type uint32;
      description
        "Number of access points requiring AFC service";
    }
    leaf afc-msg-sent {
      type uint64;
      description
        "Total number of AFC channel inquiry messages sent to the cloud service";
    }
    leaf afc-msg-rcvd {
      type uint64;
      description
        "Total number of successful AFC responses received from the cloud service";
    }
    leaf afc-msg-err {
      type uint64;
      description
        "Total number of AFC messages that resulted in errors";
    }
    leaf afc-msg-pending {
      type uint32;
      description
        "Number of AFC messages awaiting a response from the cloud service";
    }
    container last-msg-sent {
      description
        "Information about the last AFC channel inquiry message sent";
      uses wireless-afc-cloud-oper:st-afc-msg-info;
    }
    container last-msg-rcvd {
      description
        "Information about the last AFC channel inquiry message received";
      uses wireless-afc-cloud-oper:st-afc-msg-info;
    }
    leaf min-msg-rtt {
      type uint64;
      units "milliseconds";
      description
        "Minimum round-trip time for AFC messages to the cloud service";
    }
    leaf max-msg-rtt {
      type uint64;
      units "milliseconds";
      description
        "Maximum round-trip time for AFC messages to the cloud service";
    }
    leaf avg-rtt {
      type uint64;
      units "milliseconds";
      description
        "Average round-trip time for AFC messages to the cloud service";
    }
    container healthcheck {
      description
        "AFC cloud service health check status and details";
      uses wireless-afc-types:afc-healthcheck;
    }
    leaf num-6ghz-ap {
      type uint32;
      description
        "Number of access points with a 6 GHz radio";
    }
  }

  container afc-cloud-oper-data {
    config false;
    description
      "AFC cloud operational data";
    container afc-cloud-stats {
      presence "afc-cloud-stats";
      description
        "AFC cloud service communication statistics";
      uses wireless-afc-cloud-oper:st-afc-cloud-stats;
    }
  }
}
