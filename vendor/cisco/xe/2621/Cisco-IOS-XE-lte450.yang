module Cisco-IOS-XE-lte450 {
  yang-version 1.1;
  namespace "http://cisco.com/ns/yang/Cisco-IOS-XE-lte450";
  prefix ios-lte450;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE LTE450 Yang model to support
     LTE450 configuration commands.
     Copyright (c) 2026 by Cisco Systems, Inc.
     All rights reserved";

  revision 2026-08-01 {
    description
      "-Adding password";
    cisco-semver:module-version "1.2.0";
  }
  revision 2023-11-01 {
    description
      "Added credentials for logging into LTE450 modem";
    cisco-semver:module-version "1.1.0";
  }
  revision 2023-07-01 {
    description
      "Initial revision";
    cisco-semver:module-version "1.0.0";
  }

  grouping config-interface-lte450-grouping {
    container lte450 {
      container credential {
        description
          "LTE450 modem login credential";
        leaf username {
          description
            "Login username";
          type string;
        }
        container password {
          description
            "Login password";
          leaf encryption {
            description
              "0 - Specifies an UNENCRYPTED key will follow
               6 - Specifies an ENCRYPTED key will follow
               7 - Specifies an HIDDEN password will follow";
            type enumeration {
              enum 0;
              enum 6;
              enum 7;
            }
          }
          leaf key {
            type string;
          }
        }
      }
      leaf band {
        description
          "Band";
        type enumeration {
          enum 31 {
            value 31;
          }
          enum 72 {
            value 72;
          }
        }
      }
      list profile {
        description
          "LTE profile management commands";
        key "id";
        leaf id {
          description
            "Profile identification number configuration";
          type uint8 {
            range "1..3";
          }
        }
        leaf apn {
          description
            "Access point name configuration";
          type string;
        }
        leaf authentication {
          description
            "Select authentication type";
          type enumeration {
            enum chap;
            enum none;
            enum pap;
          }
        }
        leaf username {
          description
            "Username";
          when "../authentication and not(../authentication = 'none')";
          type string;
        }
        leaf password {
          description
            "Password";
          when "../authentication and not(../authentication = 'none')";
          type string;
        }
        leaf encryption {
          description
            "Encryption method of password";
          when "../authentication and not(../authentication = 'none')";
          type enumeration {
            enum 0 {
              description
                "Password is unencrypted";
            }
            enum 6 {
              description
                "Password is AES encrypted";
            }
            enum 7 {
              description
                "Password is encrypted";
            }
          }
        }
        leaf pdn-type {
          description
            "Select PDN type";
          type enumeration {
            enum ipv4;
            enum ipv4v6;
            enum ipv6;
          }
        }
        leaf vlan {
          description
            "APN profile VLAN ID";
          type uint16 {
            range "1..4094";
          }
        }
        leaf status {
          when '../id and not(../id = 1)';
          type enumeration {
            enum enable;
            enum disable;
          }
        }
      }
      leaf dhcp-default-gateway {
        description
          "DHCP default gateway setting";
        type enumeration {
          enum assign;
          enum dont-assign;
        }
      }
    }
  }

  augment "/ios:native/ios:interface/ios:GigabitEthernet" {
    uses config-interface-lte450-grouping;
  }
}
