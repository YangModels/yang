module Cisco-IOS-XE-bgp-oper {
  yang-version 1.1;
  namespace "http://cisco.com/ns/yang/Cisco-IOS-XE-bgp-oper";
  prefix bgp-ios-xe-oper;

  import Cisco-IOS-XE-bgp-common-oper {
    prefix bgp-common-ios-xe-oper;
  }
  import Cisco-IOS-XE-bgp-route-oper {
    prefix bgp-route-ios-xe-oper;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for bgp operational data.
     Copyright (c) 2016-2020, 2026 by Cisco Systems, Inc.
     All rights reserved.";

  revision 2026-08-01 {
    description
      "Updated descriptions of several model elements to clarify their meaning and purpose";
    reference
      "3.3.0";
    cisco-semver:module-version "3.3.0";
  }
  revision 2026-02-01 {
    description
      "Marked the BGP FSM non-negotiated neighbor state as obsolete in the BGP FSM state enumeration.";
    reference
      "3.2.0";
    cisco-semver:module-version "3.2.0";
  }
  revision 2022-11-01 {
    description
      "Update yang-version to 1.1";
    reference
      "3.1.0";
    cisco-semver:module-version "3.1.0";
  }
  revision 2020-11-01 {
    description
      "Added Peer Policy template";
    reference
      "3.0.0";
    cisco-semver:module-version "3.0.0";
  }
  revision 2019-11-01 {
    description
      "Added neighbor EVPN encapsulation preference.";
    reference
      "2.5.0";
    cisco-semver:module-version "2.5.0";
  }
  revision 2019-05-01 {
    description
      "- Added AO leaf descriptions.
       - Added semantic version";
    reference
      "2.4.0";
    cisco-semver:module-version "2.4.0";
  }
  revision 2018-10-29 {
    description
      "Cleaned up spelling errors in descriptions.";
    reference
      "2.3.0";
    cisco-semver:module-version "2.3.0";
  }
  revision 2017-09-25 {
    description
      "Properly indicated leaf-list ordering";
    reference
      "2.2.0";
    cisco-semver:module-version "2.2.0";
  }
  revision 2017-05-12 {
    description
      "Added the BGP RD description";
    reference
      "2.1.0";
    cisco-semver:module-version "2.1.0";
  }
  revision 2017-04-01 {
    description
      "Top level container name change. Enumeration name changes.";
    reference
      "2.0.0";
    cisco-semver:module-version "2.0.0";
  }
  revision 2017-02-07 {
    description
      "Initial revision";
    reference
      "1.0.0";
    cisco-semver:module-version "1.0.0";
  }

  typedef bgp-link {
    type enumeration {
      enum internal {
        value 0;
        description
          "iBGP neighbors";
      }
      enum external {
        value 1;
        description
          "eBGP neighbors";
      }
    }
    description
      "Operational state relevant to bgp global neighbor";
  }

  typedef bgp-fsm-state {
    type enumeration {
      enum fsm-idle {
        value 0;
        description
          "neighbor is in Idle state";
      }
      enum fsm-connect {
        value 1;
        description
          "neighbor is in Connect state";
      }
      enum fsm-active {
        value 2;
        description
          "neighbor is in Active state";
      }
      enum fsm-opensent {
        value 3;
        description
          "neighbor is in OpenSent state";
      }
      enum fsm-openconfirm {
        value 4;
        description
          "neighbor is in OpenConfirm state";
      }
      enum fsm-established {
        value 5;
        description
          "neighbor is in Established state";
      }
      enum fsm-nonnegotiated {
        value 6;
        status obsolete;
        description
          "Indicates that the BGP neighbor session is in a non-negotiated state, which is now obsolete and should not be used in new configurations";
      }
    }
    description
      "BGP FSM State";
  }

  typedef bgp-mode {
    type enumeration {
      enum mode-active {
        value 0;
        description
          "active connection";
      }
      enum mode-passive {
        value 1;
        description
          "passive connection";
      }
    }
    description
      "BGP mode";
  }

  typedef bgp-encaps-pref {
    type enumeration {
      enum encaps-pref-unset {
        value 0;
        description
          "Encapsulation preference is not set";
      }
      enum encaps-pref-any {
        value 1;
        description
          "No encapsulation is preferred";
      }
      enum encaps-pref-vxlan-if-vtep-up {
        value 2;
        description
          "Use VxLAN if VTEP is UP else use MPLS";
      }
      enum encaps-pref-vxlan {
        value 3;
        description
          "Prefer VxLAN encapsulation";
      }
      enum encaps-pref-mpls {
        value 4;
        description
          "Prefer MPLS encapsulation";
      }
    }
    description
      "BGP encapsulation preferences";
  }

  grouping configured-peer-policy {
    description
      "Configured Peer Policy";
    leaf distribute-list-in {
      type string;
      description
        "Incoming update network filter list name";
    }
    leaf prefix-list-in {
      type string;
      description
        "Incoming update prefix filter list name";
    }
    leaf filter-list-in {
      type uint32;
      description
        "Incoming update AS path filter list";
    }
    leaf route-map-in {
      type string;
      description
        "Name of the route map applied to incoming advertisements";
    }
    leaf prefix-list-out {
      type string;
      description
        "Outgoing update prefix filter list name";
    }
    leaf distribute-list-out {
      type string;
      description
        "Outgoing update network filter list name";
    }
    leaf filter-list-out {
      type uint32;
      description
        "Outgoing update AS path filter list";
    }
    leaf route-map-out {
      type string;
      description
        "Name of the route map applied to outgoing advertisements";
    }
    leaf unsuppress-map {
      type string;
      description
        "Name of the route map used for selective unsuppress of aggregated routes to this neighbor";
    }
    leaf default-originate {
      type boolean;
      description
        "Indicates whether a default route is originated to this neighbor";
    }
    leaf default-map {
      type string;
      description
        "Name of the route map used when originating a default route to this neighbor";
    }
    leaf weight {
      type uint32;
      description
        "Set default weight for routes from this neighbor";
    }
    leaf soft-reconfig-in {
      type boolean;
      description
        "Indicates whether inbound soft reconfiguration is enabled for this neighbor";
    }
    leaf maximum-prefix {
      type uint32;
      description
        "Maximum number of prefixes accepted from this peer";
    }
    leaf max-prefix-threshold {
      type uint32;
      units "percent";
      description
        "Threshold percentage for the maximum number of prefixes accepted from this peer before generating a warning";
    }
    leaf max-prefix-warning {
      type boolean;
      description
        "Indicates whether a warning is generated when the maximum prefix threshold is reached for this peer";
    }
    leaf max-pfx-restart-interval {
      type uint32;
      units "seconds";
      description
        "Time interval (in seconds) before attempting to re-establish the BGP session after reaching the maximum prefix limit";
    }
    leaf as-override {
      type boolean;
      description
        "Indicates whether the local AS number replaces the neighbor's AS in the AS path when sending updates";
    }
    leaf as-override-split-horizon {
      type boolean;
      description
        "Indicates whether split horizon processing is enabled for BGP updates, preventing routes learned from a peer from being advertised back to that same peer";
    }
    leaf allow-as {
      type uint32;
      description
        "Indicates whether this neighbor is configured to accept routes containing the local AS number in the AS path, overriding the default BGP loop prevention mechanism";
    }
    leaf allow-policy {
      type boolean;
      description
        "Indicates whether policy support is enabled for this iBGP neighbor";
    }
    leaf rr-client {
      type boolean;
      description
        "Indicates whether this neighbor is configured as a BGP Route Reflector client";
    }
    leaf aigp {
      type boolean;
      description
        "Indicates whether the Accumulated IGP (AIGP) attribute is sent to this neighbor in BGP updates";
    }
    leaf aigp-med {
      type boolean;
      description
        "Indicates whether the Accumulated IGP (AIGP) value is sent as the Multi-Exit Discriminator (MED) attribute to this neighbor";
    }
    leaf aigp-cost {
      type boolean;
      description
        "Indicates whether the Accumulated IGP (AIGP) value is sent as a cost-community attribute to this neighbor";
    }
    leaf internal-vpn-client {
      type boolean;
      description
        "Indicates whether this neighbor is configured as an internal VPN client for BGP routing policy";
    }
    leaf advertisement-interval {
      type uint32;
      units "seconds";
      description
        "Minimum interval, in seconds, between consecutive BGP UPDATE messages sent to this neighbor";
    }
    leaf nexthop-unchanged {
      type boolean;
      description
        "Indicates whether the iBGP path's next hop is propagated unchanged to this neighbor";
    }
    leaf nexthop-unchanged-all {
      type boolean;
      description
        "Propagate next hop unchanged for all paths to this neighbor";
    }
    leaf nexthop-self {
      type boolean;
      description
        "Indicates whether the local router's address is used as the next hop for routes sent to this neighbor";
    }
    leaf nexthop-self-all {
      type boolean;
      description
        "Indicates whether the local router is configured as the next hop for all EBGP paths sent to this neighbor";
    }
    leaf add-path-send {
      type boolean;
      description
        "Indicates whether additional BGP paths are advertised to this neighbor";
    }
    leaf add-path-rx {
      type boolean;
      description
        "Indicates whether reception of multiple BGP paths for the same prefix from this neighbor is enabled";
    }
    leaf adv-add-path-all {
      type boolean;
      description
        "Indicates whether all available BGP paths are advertised to the neighbor, rather than only the best path";
    }
    leaf adv-add-path-grp-best {
      type boolean;
      description
        "Indicates whether the best BGP paths from each path group are advertised to the neighbor";
    }
    leaf adv-add-path-bestn {
      type uint32;
      description
        "Specifies the number of best BGP paths to advertise to the neighbor";
    }
    leaf adv-diverse-path {
      type string;
      description
        "Type of diverse-path advertisement configured for this
         neighbor";
    }
    leaf adv-best-ext {
      type boolean;
      description
        "Indicates whether the best external BGP path is advertised to this neighbor";
    }
    leaf slow-peer-static {
      type boolean;
      description
        "Indicates whether the neighbor is statically configured as a slow peer for BGP update throttling";
    }
    leaf sp-detect-thold {
      type uint32;
      units "seconds";
      description
        "Specifies the threshold value, in seconds, used to detect slow BGP peers based on update processing performance";
    }
    leaf sp-dynamic {
      type boolean;
      description
        "Indicates whether the neighbor is dynamically assigned to a slow peer update group for BGP update throttling";
    }
    leaf sp-protection-permanent {
      type boolean;
      description
        "Indicates whether permanent protection is enabled for slow BGP peers in this address family";
    }
    leaf send-community {
      type string;
      description
        "Type of BGP community attribute sent to this neighbor,
         represented as a text string. Possible values are:
         'standard' - send standard communities only,
         'extended' - send extended communities only,
         'both' - send both standard and extended communities,
         or empty when communities are not sent";
    }
    leaf flow-spec-validation-off {
      type boolean;
      description
        "Indicates whether FlowSpec validation is disabled for this neighbor";
    }
    leaf valid-redirect-off {
      type boolean;
      description
        "Indicates whether validation of Redirect-IP extended community attributes is disabled for this neighbor";
    }
    leaf remove-private-as {
      type boolean;
      description
        "Indicates whether private AS numbers are removed from the AS path in outbound updates to this neighbor";
    }
    leaf remove-private-as-all {
      type boolean;
      description
        "Indicates whether all private AS numbers are removed from the AS path in outbound updates to this neighbor";
    }
    leaf rm-private-as-replace-as {
      type boolean;
      description
        "Indicates whether private AS numbers in the AS path are replaced with the local AS number in outbound BGP updates";
    }
    leaf extcommunity {
      type string;
      description
        "Extended community values to be applied to routes sent to this BGP neighbor";
    }
    leaf rpki-state-enabled {
      type boolean;
      description
        "Indicates whether the RPKI-State extended community is enabled for this neighbor";
    }
    leaf dmzlink-bw {
      type boolean;
      description
        "Indicates whether the DMZ link bandwidth extended community is propagated to this neighbor";
    }
    leaf send-label {
      type boolean;
      description
        "Indicates whether MPLS labels are sent to this peer in BGP updates";
    }
    leaf send-label-explicit-null {
      type boolean;
      description
        "Indicates whether sending of MPLS explicit null label to this peer in BGP updates is enabled";
    }
    leaf encap {
      type string;
      description
        "Preferred encapsulation for the neighbor, represented
         as a text string. Possible values are:
         'vxlan' - VXLAN encapsulation,
         'mpls' - MPLS encapsulation,
         or empty when no specific encapsulation is preferred";
    }
    leaf cap-orf-prefix-list {
      type string;
      description
        "Name of the prefix-list to be advertised as Outbound Route Filtering (ORF) capability to the BGP peer";
    }
    leaf translate-topology {
      type uint32;
      description
        "Topology identifier used for BGP route translation with this neighbor";
    }
    leaf accept-route-legacy-rt {
      type boolean;
      description
        "Indicates whether to accept routes with legacy Route Target extended communities from this neighbor";
    }
    leaf inter-as-hybrid {
      type boolean;
      description
        "Indicates whether Inter-AS hybrid mode is enabled for this BGP neighbor";
    }
    leaf suppress-ldp {
      type boolean;
      description
        "Indicates whether Label Distribution Protocol signaling is suppressed for this BGP neighbor";
    }
    leaf llgr-stale-time-send {
      type uint32;
      units "seconds";
      description
        "Stale time, in seconds, advertised to this neighbor for Long-Lived Graceful Restart";
    }
    leaf llgr-stale-time-accept {
      type uint32;
      units "seconds";
      description
        "Maximum stale time, in seconds, accepted from this neighbor for Long-Lived Graceful Restart";
    }
  }

  grouping inherited-peer-policy {
    description
      "Inherited Peer Policy";
    leaf-list name {
      type string;
      ordered-by user;
      description
        "Name of the inherited peer policy";
    }
    container configured-policies {
      description
        "Configured policies in a peer policy";
      uses bgp-ios-xe-oper:configured-peer-policy;
    }
  }

  grouping peer-policy-summary {
    description
      "Peer Policy summary";
    leaf name {
      type string;
      description
        "Name of the Peer Policy";
    }
    leaf total-inherited {
      type uint32;
      description
        "Total number of inherited policies";
    }
    leaf index {
      type uint32;
      description
        "Index of the peer policy";
    }
    container configured-policies {
      description
        "Configured policies in a peer policy";
      uses bgp-ios-xe-oper:configured-peer-policy;
    }
    container inherited-policies {
      description
        "Inherited policies in a peer policy";
      uses bgp-ios-xe-oper:inherited-peer-policy;
    }
  }

  grouping bgp-message-counters {
    description
      "BGP message counters";
    leaf opens {
      type uint32;
      description
        "OPEN message count";
    }
    leaf updates {
      type uint32;
      description
        "UPDATE message count";
    }
    leaf notifications {
      type uint32;
      description
        "NOTIFICATION message count";
    }
    leaf keepalives {
      type uint32;
      description
        "KEEPALIVE message count";
    }
    leaf route-refreshes {
      type uint32;
      description
        "Route refresh message count";
    }
  }

  grouping bgp-prefix-counters {
    description
      "Grouping for various prefix counters";
    leaf current-prefixes {
      type uint64;
      description
        "The current number of accepted prefixes";
    }
    leaf total-prefixes {
      type uint64;
      description
        "The total number of accepted prefixes";
    }
    leaf implicit-withdraw {
      type uint64;
      description
        "The number of times a prefix has been
         withdrawn and readvertised";
    }
    leaf explicit-withdraw {
      type uint64;
      description
        "The number of times a prefix has been
         withdrawn because it is no longer feasible";
    }
    leaf bestpaths {
      type uint64;
      description
        "The number of received prefixes installed as best paths";
    }
    leaf multipaths {
      type uint64;
      description
        "The number of received prefixes installed as multipaths";
    }
  }

  grouping negotiated-keepalive-timers {
    description
      "Negotiated keepalive timers details";
    leaf hold-time {
      type uint16;
      units "seconds";
      description
        "Negotiated BGP hold time interval, in seconds, for the neighbor session";
    }
    leaf keepalive-interval {
      type uint16;
      units "seconds";
      description
        "Negotiated interval, in seconds, between BGP keepalive messages for the neighbor session";
    }
  }

  grouping neighbor-summary {
    description
      "Information regarding the current state of a neighbor";
    leaf id {
      type string;
      description
        "Neighbor address, represented as a string in IPv4 or IPv6 notation";
    }
    leaf bgp-version {
      type uint32;
      description
        "BGP protocol version";
    }
    leaf messages-received {
      type uint64;
      description
        "Number of messages received from this neighbor";
    }
    leaf messages-sent {
      type uint64;
      description
        "Number of messages sent to this neighbor";
    }
    leaf table-version {
      type uint64;
      description
        "Version number of the BGP table associated with this neighbor session";
    }
    leaf input-queue {
      type uint64;
      description
        "Number of messages in input queue";
    }
    leaf output-queue {
      type uint64;
      description
        "Number of messages in output queue";
    }
    leaf up-time {
      type string;
      description
        "Duration of the neighbor session uptime, represented as a compact duration string such as weeks and days or hours and minutes (e.g., '3w2d' for 3 weeks and 2 days, or '5h30m' for 5 hours and 30 minutes)";
    }
    leaf state {
      type bgp-ios-xe-oper:bgp-fsm-state;
      description
        "BGP session state";
    }
    leaf prefixes-received {
      type uint64;
      description
        "Number of prefixes received from the neighbor";
    }
    leaf dynamically-configured {
      type boolean;
      description
        "Indication of whether the neighbor was
         dynamically configured";
    }
    leaf as {
      type uint32;
      description
        "BGP neighbor AS number";
    }
  }

  grouping bgp-connection {
    description
      "Data for current BGP connection state";
    leaf state {
      type bgp-common-ios-xe-oper:tcp-fsm-state;
      description
        "TCP FSM state";
    }
    leaf mode {
      type bgp-ios-xe-oper:bgp-mode;
      description
        "BGP transport connection mode";
    }
    leaf total-established {
      type uint32;
      description
        "The number of times a TCP and BGP
         connection has been successfully established";
    }
    leaf total-dropped {
      type uint32;
      description
        "Number of times that a valid session has failed or been taken down";
    }
    leaf last-reset {
      type string;
      description
        "Elapsed time since the peering session was last reset, represented as a compact duration string such as hours and minutes (e.g., '5h30m' for 5 hours and 30 minutes)";
    }
    leaf reset-reason {
      type string;
      description
        "Reason for the last reset of the BGP session. The following is a list of all possible reset reasons for a session:
         'BGP protocol initialization' for session reset due to BGP protocol initialization;
         'No memory' for session reset due to memory allocation failure;
         'BGP Notification received' for session reset by a BGP NOTIFICATION message from the peer;
         'BGP Notification sent' for session reset by a BGP NOTIFICATION message sent to the peer;
         'User reset' for session reset initiated by the user;
         'Peer timeout' for session reset due to hold timer expiration;
         'Error during connection collision' for session reset due to a TCP connection collision error;
         'Peer closed the session' for session reset because the peer closed the TCP connection;
         'Peer over prefix limit' for session reset because the peer exceeded the maximum prefix limit;
         'Maximum-Prefix restart timeout' for session reset due to maximum-prefix restart timer expiration;
         'Interface flap' for session reset due to the underlying interface going down;
         'Router ID changed' for session reset due to a change in the local router ID;
         'Neighbor deleted' for session reset because the neighbor configuration was removed;
         'Neighbor reset' for session reset due to a neighbor-level reset event;
         'Active open failed' for session reset due to a failed active TCP open attempt;
         'Remote connection failed' for session reset due to a failed remote TCP connection;
         'Member added to peer group' for session reset because the neighbor was added to a peer group;
         'Admin shutdown' for session reset due to administrative shutdown of the neighbor;
         'Remote AS changed' for session reset due to a change in the remote AS number;
         'Capability changed' for session reset due to a change in BGP capability configuration;
         'RR client config change' for session reset due to a Route Reflector client configuration change;
         'AIGP config change' for session reset due to an AIGP configuration change;
         'Soft reconfiguration change' for session reset due to a soft reconfiguration configuration change;
         'Local AS change' for session reset due to a change in the local AS number;
         'Address family activated' for session reset due to activation of an address family;
         'VRF config change' for session reset due to a VRF configuration change;
         'Allow-as-in change' for session reset due to an allow-as-in configuration change;
         'AS-override change' for session reset due to an AS-override configuration change;
         'NSF session restart timeout' for session reset due to NSF session restart timer expiration;
         'NSF peer closed the session' for session reset because the NSF peer closed the session;
         'NSF Switchover' for session reset due to a Non-Stop Forwarding switchover event;
         'NSF GR RELOAD' for session reset due to a Non-Stop Forwarding Graceful Restart reload;
         'Cluster ID changed' for session reset due to a change in the Route Reflector cluster ID;
         'Route to peer lost' for session reset because the route to the peer was lost;
         'BFD adjacency down' for session reset due to Bidirectional Forwarding Detection adjacency going down;
         'Maximum path limit of 255 reached' for session reset due to reaching the maximum path limit;
         'SSO Disabled' for session reset due to Stateful Switchover being disabled;
         'Passive send open failed' for session reset due to a failed passive TCP open attempt;
         'AFI/SAFI not supported' for session reset because the address family is not supported;
         'Update source changed' for session reset due to a change in the update source configuration;
         'SSO connection collision on standby' for session reset due to an SSO connection collision on the standby;
         'Unknown path error' for session reset due to an unknown path error;
         'Prefix Storage Size changed' for session reset due to a change in prefix storage size;
         'Route server context changed' for session reset due to a route server context change;
         'Internal VPN Client changed' for session reset due to an internal VPN client configuration change;
         'Legacy RT config change' for session reset due to a legacy Route Target configuration change;
         'TCP AO config change' for session reset due to a TCP Authentication Option configuration change;
         'split-horizon config change' for session reset due to a split-horizon configuration change;
         'labeled-unicast configuration changed' for session reset due to a labeled-unicast configuration change;
         'unknown' for session reset due to an unknown or unmapped reason.";
    }
  }

  grouping bgp-transport {
    description
      "BGP transport information";
    leaf path-mtu-discovery {
      type boolean;
      description
        "Indication whether path MTU discovery is enabled";
    }
    leaf local-port {
      type uint32;
      description
        "Local TCP port used for TCP session";
    }
    leaf local-host {
      type inet:ip-address;
      description
        "Local address used for the TCP session";
    }
    leaf foreign-port {
      type uint32;
      description
        "Remote port used by the peer for the TCP session";
    }
    leaf foreign-host {
      type inet:ip-address;
      description
        "Remote address of the BGP session";
    }
    leaf mss {
      type uint32;
      units "bytes";
      description
        "Maximum data segment size for the BGP TCP session";
    }
    leaf ao-keychain-name {
      type string;
      description
        "Name of the Key Chain for AO";
    }
    leaf ao-key-id {
      type int32;
      description
        "ID of the key for AO";
    }
    leaf ao-incl-tcp-opts {
      type boolean;
      description
        "Indicates whether TCP options are included in the TCP Authentication Option (AO) calculation for this BGP session";
    }
    leaf ao-accept-mismatch-conn {
      type boolean;
      description
        "Indicates whether the BGP session accepts TCP-AO (Authentication Option) connections with mismatched key parameters";
    }
  }

  grouping bgp-af-prefix-activity {
    description
      "Address family prefix statistics";
    container sent {
      description
        "Number of prefixes sent";
      uses bgp-ios-xe-oper:bgp-prefix-counters;
    }
    container received {
      description
        "Number of prefixes received";
      uses bgp-ios-xe-oper:bgp-prefix-counters;
    }
  }

  grouping bgp-neighbor-counters {
    description
      "BGP neighbor session counters";
    container sent {
      description
        "Number of messages sent";
      uses bgp-ios-xe-oper:bgp-message-counters;
    }
    container received {
      description
        "Number of messages received";
      uses bgp-ios-xe-oper:bgp-message-counters;
    }
    leaf inq-depth {
      type uint32;
      description
        "Number of messages in the input queue for the BGP neighbor session";
    }
    leaf outq-depth {
      type uint32;
      description
        "Number of messages in the output queue for the BGP neighbor session";
    }
  }

  grouping neighbor-key {
    description
      "Grouping for neighbor key";
    leaf afi-safi {
      type bgp-common-ios-xe-oper:afi-safi;
      description
        "Address Family Identifier (AFI) and Subsequent Address Family Identifier (SAFI) key used to specify the type of network layer reachability information for this BGP neighbor";
    }
    leaf vrf-name {
      type string;
      description
        "Name of the Virtual Routing and Forwarding (VRF) instance associated with this BGP address family";
    }
    leaf neighbor-id {
      type string;
      description
        "Identifier for the BGP neighbor, typically the neighbor's IP address or router ID";
    }
  }

  grouping neighbor {
    description
      "BGP neighbor state information";
    leaf description {
      type string;
      description
        "Neighbor description string";
    }
    leaf bgp-version {
      type uint16;
      description
        "BGP version being used to communicate
         with the remote router";
    }
    leaf link {
      type bgp-ios-xe-oper:bgp-link;
      description
        "Neighbor link type";
    }
    leaf up-time {
      type string;
      description
        "Duration the BGP session has been up, represented as a compact duration string such as weeks and days or hours and minutes (e.g., '3w2d' for 3 weeks and 2 days, or '5h30m' for 5 hours and 30 minutes)";
    }
    leaf last-write {
      type string;
      description
        "Elapsed time since BGP last sent a message to the
         neighbor, represented as a compact duration string such as hours and minutes (e.g., '5h30m' for 5 hours and 30 minutes)";
    }
    leaf last-read {
      type string;
      description
        "Elapsed time since BGP last received a message from
         the neighbor, represented as a compact duration string such as hours and minutes (e.g., '5h30m' for 5 hours and 30 minutes)";
    }
    leaf installed-prefixes {
      type uint32;
      description
        "Number of prefixes received from this neighbor that are currently installed in the local routing table";
    }
    leaf session-state {
      type bgp-ios-xe-oper:bgp-fsm-state;
      description
        "Current BGP finite state machine (FSM) state of the neighbor session (e.g., Idle, Connect, Active, OpenSent, OpenConfirm, Established)";
    }
    container negotiated-keepalive-timers {
      description
        "Negotiated keepalive timers status of BGP neighbor";
      uses bgp-ios-xe-oper:negotiated-keepalive-timers;
    }
    leaf-list negotiated-cap {
      type string;
      ordered-by user;
      description
        "Negotiated BGP capabilities for the neighbor session.
         Possible values include:
         '4-octet-as' - 4-octet AS number support,
         'route-refresh' - route refresh capability,
         'graceful-restart' - graceful restart capability,
         'multiprotocol' - multiprotocol extensions,
         'add-path' - advertisement of multiple paths,
         'enhanced-route-refresh' - enhanced route refresh,
         'long-lived-graceful-restart' - long-lived graceful restart,
         'extended-message' - extended message support,
         'fqdn' - fully qualified domain name capability,
         'cisco-route-refresh' - Cisco route refresh";
    }
    container bgp-neighbor-counters {
      description
        "BGP neighbor session counters";
      uses bgp-ios-xe-oper:bgp-neighbor-counters;
    }
    container connection {
      description
        "BGP neighbor connection";
      uses bgp-ios-xe-oper:bgp-connection;
    }
    container transport {
      description
        "Transport-related information for the BGP neighbor, including TCP session parameters and connection details";
      uses bgp-ios-xe-oper:bgp-transport;
    }
    container prefix-activity {
      description
        "Statistics and counters related to BGP prefix exchange activity with this neighbor, including prefixes sent and received";
      uses bgp-ios-xe-oper:bgp-af-prefix-activity;
    }
    leaf as {
      type uint32;
      description
        "BGP neighbor AS number";
    }
    leaf encaps-pref {
      type bgp-ios-xe-oper:bgp-encaps-pref;
      description
        "Preferred tunnel encapsulation type";
    }
    container peer-policy {
      description
        "Peer policy template";
      uses bgp-ios-xe-oper:peer-policy-summary;
    }
  }

  grouping entry-stats {
    description
      "BGP entry statistics";
    leaf total-entries {
      type uint64;
      description
        "Total number of BGP path entries for this address family";
    }
    leaf memory-usage {
      type uint64;
      units "bytes";
      description
        "Total memory used by BGP entries for this category";
    }
  }

  grouping activities {
    description
      "BGP activity information";
    leaf prefixes {
      type uint64;
      description
        "Total number of prefixes";
    }
    leaf paths {
      type uint64;
      description
        "Total number of paths";
    }
    leaf scan-interval {
      type string;
      description
        "Interval between BGP table scans, represented as
         a text string indicating the duration in seconds";
    }
  }

  grouping address-family-key {
    description
      "Address family key";
    leaf afi-safi {
      type bgp-common-ios-xe-oper:afi-safi;
      description
        "Specifies the Address Family Identifier (AFI) and Subsequent Address Family Identifier (SAFI) for this BGP address family";
    }
    leaf vrf-name {
      type string;
      description
        "Name of the Virtual Routing and Forwarding (VRF) instance associated with this BGP address family";
    }
  }

  grouping address-family-summary {
    description
      "Summary of address family";
    leaf router-id {
      type inet:ip-address;
      description
        "BGP router identifier (Router ID) for this address family, typically represented as an IP address";
    }
    leaf bgp-table-version {
      type uint64;
      description
        "BGP table version number";
    }
    leaf routing-table-version {
      type uint64;
      description
        "Routing table version number";
    }
    container prefixes {
      description
        "Prefix entry statistics";
      uses bgp-ios-xe-oper:entry-stats;
    }
    container path {
      description
        "Path entry statistics";
      uses bgp-ios-xe-oper:entry-stats;
    }
    container as-path {
      description
        "AS path entry statistics";
      uses bgp-ios-xe-oper:entry-stats;
    }
    container route-map {
      description
        "Route map entry statistics";
      uses bgp-ios-xe-oper:entry-stats;
    }
    container filter-list {
      description
        "Filter list entry statistics";
      uses bgp-ios-xe-oper:entry-stats;
    }
    container activities {
      description
        "BGP activity information";
      uses bgp-ios-xe-oper:activities;
    }
    leaf total-memory {
      type uint64;
      units "bytes";
      description
        "Total memory in use by this address family";
    }
    container bgp-neighbor-summaries {
      description
        "Summary information for all BGP neighbors associated with this address family";
      list bgp-neighbor-summary {
        key "id";
        description
          "List of neighbor summaries";
        uses bgp-ios-xe-oper:neighbor-summary;
      }
    }
    leaf local-as {
      type uint32;
      description
        "Local AS number";
    }
  }

  grouping bgp-state {
    description
      "BGP state information";
    container neighbors {
      description
        "BGP neighbor information";
      list neighbor {
        key "afi-safi vrf-name neighbor-id";
        description
          "List of BGP neighbors";
        uses bgp-ios-xe-oper:neighbor-key;
        uses bgp-ios-xe-oper:neighbor;
      }
    }
    container address-families {
      description
        "Address Family Identifier (AFI) and Subsequent Address Family Identifier (SAFI) for the BGP address family";
      list address-family {
        key "afi-safi vrf-name";
        description
          "List of BGP address families";
        uses bgp-ios-xe-oper:address-family-key;
        uses bgp-ios-xe-oper:address-family-summary;
      }
    }
    container bgp-route-vrfs {
      description
        "Container for the list of all BGP Virtual Routing and Forwarding (VRF) instances configured on the device";
      list bgp-route-vrf {
        key "vrf";
        description
          "List of BGP VRFs";
        uses bgp-route-ios-xe-oper:vrf-record;
      }
    }
    container bgp-route-rds {
      description
        "Container for BGP Route Distinguisher (RD) entries used for VPN address families";
      list bgp-route-rd {
        key "rd-value";
        description
          "List of BGP RDs";
        uses bgp-route-ios-xe-oper:bgp-rd-record;
      }
    }
  }

  container bgp-state-data {
    config false;
    description
      "BGP operational state data";
    uses bgp-ios-xe-oper:bgp-state;
  }
}
