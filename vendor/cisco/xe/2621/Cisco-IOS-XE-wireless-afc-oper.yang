module Cisco-IOS-XE-wireless-afc-oper {
  yang-version 1.1;
  namespace "http://cisco.com/ns/yang/Cisco-IOS-XE-wireless-afc-oper";
  prefix wireless-afc-oper;

  import Cisco-IOS-XE-wireless-afc-types {
    prefix wireless-afc-types;
  }
  import Cisco-IOS-XE-wireless-enum-types {
    prefix wireless-enum-types;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Model for managing AFC
     Copyright (c) 2022-2026 by Cisco Systems, Inc.
     All rights reserved.";

  revision 2026-08-01 {
    description
      "- Updated descriptions for clarity and accuracy";
    reference
      "1.1.1";
    cisco-semver:module-version "1.1.1";
  }
  revision 2024-03-01 {
    description
      "- Added slot to AFC AP response";
    reference
      "1.1.0";
    cisco-semver:module-version "1.1.0";
  }
  revision 2023-11-01 {
    description
      "Initial revision";
    reference
      "1.0.0";
    cisco-semver:module-version "1.0.0";
  }

  grouping afc-ap-req {
    description
      "Automated Frequency Coordination (AFC) request information for an access point";
    leaf ap-mac {
      type yang:mac-address;
      description
        "MAC address of the access point associated with the AFC request";
    }
    container req-data {
      description
        "Details of the AFC request sent for this access point";
      uses wireless-afc-types:afc-request-data;
    }
    leaf request-status {
      type wireless-enum-types:afc-request-status;
      description
        "Current status of the AFC request for this access point";
    }
    leaf request-status-ts {
      type yang:date-and-time;
      description
        "Timestamp of the last AFC request status change";
    }
    leaf req-id-sent {
      type uint64;
      description
        "Identifier of the AFC request sent to the AFC server";
    }
  }

  grouping afc-ap-resp {
    description
      "AFC response information for an access point";
    leaf ap-mac {
      type yang:mac-address;
      description
        "MAC address of the access point associated with the AFC response";
    }
    container resp-data {
      description
        "Details of the AFC response received for this access point";
      uses wireless-afc-types:afc-response-data;
    }
    leaf slot {
      type uint8;
      description
        "Radio slot identifier on the access point for which AFC is enabled";
    }
  }

  container afc-oper-data {
    config false;
    description
      "AFC Operational Data Model";
    list ewlc-afc-ap-req {
      key "ap-mac";
      description
        "AFC request information and status for an access point";
      uses wireless-afc-oper:afc-ap-req;
    }
    list ewlc-afc-ap-resp {
      key "ap-mac";
      description
        "AFC response information received for an access point";
      uses wireless-afc-oper:afc-ap-resp;
    }
  }
}
