module Cisco-IOS-XE-utd-events {
  yang-version 1.1;
  namespace "http://cisco.com/ns/yang/Cisco-IOS-XE-utd-events";
  prefix utd-ios-xe-events;

  import Cisco-IOS-XE-common-types {
    prefix common-types-ios-xe;
  }
  import Cisco-IOS-XE-ios-common-oper {
    prefix ios-common-ios-xe-oper;
  }
  import Cisco-IOS-XE-utd-common-oper {
    prefix utd-common-ios-xe-oper;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG Definitions
     for UTD event notification.
     Copyright (c) 2024 by Cisco Systems, Inc.
     All rights reserved.";

  revision 2026-08-01 {
    description
      "Added UTD FQDN destination status change alarm notification.";
    reference
      "1.1.0";
    cisco-semver:module-version "1.1.0";
  }
  revision 2024-03-01 {
    description
      "Initial revision";
    reference
      "1.0.0";
    cisco-semver:module-version "1.0.0";
  }

  typedef utd-connectivity-type-val {
    type enumeration {
      enum utd-conn-type-none {
        value 0;
        description
          "Unified Threat Defense (UTD) connectivity type is none";
      }
      enum utd-conn-type-urlf {
        value 1;
        description
          "Unified Threat Defense (UTD) connectivity type is URL-Filtering";
      }
    }
    description
      "Unified Threat Defense (UTD) connectivity type";
  }

  typedef fqdn-destination-state {
    type enumeration {
      enum utd-fqdn-state-rslvd {
        value 0;
        description
          "The destination FQDN is resolved.";
      }
      enum utd-fqdn-state-unrslvd {
        value 1;
        description
          "The destination FQDN is unresolved.";
      }
    }
    description
      "Resolution state of the destination FQDN.";
  }

  typedef fqdn-destination-error-reason {
    type enumeration {
      enum utd-fqdn-rc-none {
        value 0;
        description
          "No error reason is present.";
      }
      enum utd-fqdn-rc-not-reg {
        value 1;
        description
          "The destination FQDN is not registered with DNS.";
      }
      enum utd-fqdn-rc-no-addr-rec {
        value 2;
        description
          "No address records were returned for the destination FQDN.";
      }
      enum utd-fqdn-rc-socket {
        value 3;
        description
          "The DNS lookup failed because of a socket error.";
      }
      enum utd-fqdn-rc-mem {
        value 4;
        description
          "The DNS lookup failed because of a memory allocation error.";
      }
      enum utd-fqdn-rc-lookup-dis {
        value 5;
        description
          "The DNS lookup was disabled before completion.";
      }
      enum utd-fqdn-rc-other-dns {
        value 6;
        description
          "The DNS lookup failed for an implementation-specific reason.";
      }
      enum utd-fqdn-rc-format {
        value 7;
        description
          "The DNS server reported a format error.";
      }
      enum utd-fqdn-rc-server-fail {
        value 8;
        description
          "The DNS server reported a server failure.";
      }
      enum utd-fqdn-rc-name {
        value 9;
        description
          "The DNS server reported a name error for the destination FQDN.";
      }
      enum utd-fqdn-rc-not-impl {
        value 10;
        description
          "The DNS server reported that the request was not implemented.";
      }
      enum utd-fqdn-rc-refused {
        value 11;
        description
          "The DNS server refused the request.";
      }
      enum utd-fqdn-rc-res-fail {
        value 12;
        description
          "Resolution of the destination FQDN failed without a more specific DNS error.";
      }
      enum utd-fqdn-rc-res-pend {
        value 13;
        description
          "Resolution of the destination FQDN is still pending.";
      }
      enum utd-fqdn-rc-int {
        value 14;
        description
          "An internal error prevented the destination FQDN resolution state from being determined.";
      }
      enum utd-fqdn-rc-unknown {
        value 15;
        description
          "The destination FQDN resolution failed for an unknown reason.";
      }
    }
    description
      "Reason associated with the destination FQDN resolution state.";
  }

  grouping utd-connectivity {
    description
      "Unified Threat Defense (UTD) connectivity";
    leaf severity {
      type ios-common-ios-xe-oper:notification-severity;
      description
        "Event severity";
    }
    leaf host-name {
      type string;
      description
        "Host name";
    }
    leaf system-ip {
      type inet:ip-address;
      description
        "System IP address";
    }
    leaf type {
      type utd-ios-xe-events:utd-connectivity-type-val;
      description
        "connectivity type";
    }
    leaf timestamp {
      type yang:date-and-time;
      description
        "connectivity timestamp";
    }
    leaf status {
      type utd-common-ios-xe-oper:utd-con-state;
      description
        "connectivity status";
    }
    leaf reason {
      type utd-common-ios-xe-oper:utd-con-reason;
      description
        "connectivity down reason";
    }
  }

  grouping utd-log-fqdn-dst-status-change {
    description
      "UTD destination FQDN resolution state transition alarm notification.";
    leaf severity-level {
      type ios-common-ios-xe-oper:notification-severity;
      description
        "Severity level of the UTD FQDN destination status change alarm.";
    }
    leaf host-name {
      type string;
      description
        "Host name of the system reporting the alarm.";
    }
    leaf system-ip {
      type inet:ip-address;
      description
        "IP address of the system reporting the alarm.";
    }
    leaf fqdn {
      type string;
      description
        "Fully Qualified Domain Name (FQDN) of the destination whose resolution state changed.";
    }
    leaf ni-type {
      type common-types-ios-xe:net-inst-type;
      description
        "Network instance type. Differentiates between the default routing instance and VRFs.";
    }
    leaf ni-name {
      type string;
      description
        "Network instance name. If the type is net-inst-default, use the name default.";
    }
    leaf new-state {
      type utd-ios-xe-events:fqdn-destination-state;
      description
        "New resolution state of the destination FQDN.";
    }
    leaf dst-ip {
      type inet:ip-address;
      description
        "IP address resolved for the destination FQDN, when available.";
    }
    leaf dst-port {
      type uint16;
      description
        "Destination port associated with the resolved destination IP address.";
    }
    leaf error-reason {
      type utd-ios-xe-events:fqdn-destination-error-reason;
      description
        "Structured reason describing why the destination is unresolved; set to no-error when the destination is resolved.";
    }
  }

  notification utd-con {
    description
      "Unified Threat Defense (UTD) connectivity notification";
    uses utd-ios-xe-events:utd-connectivity;
  }

  notification utd-log-fqdn-dst-status-change {
    description
      "UTD FQDN destination status change alarm notification.";
    uses utd-ios-xe-events:utd-log-fqdn-dst-status-change;
  }
}
