module Cisco-IOS-XE-tunnel-oper {
  yang-version 1.1;
  namespace "http://cisco.com/ns/yang/Cisco-IOS-XE-tunnel-oper";
  prefix ios-tunnel-oper;

  import Cisco-IOS-XE-event-history-types {
    prefix event-history-types;
  }
  import Cisco-IOS-XE-tunnel-types {
    prefix tunnel-types;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     Tunnel domains and interfaces.
     Copyright (c) 2018-2020, 2022, 2025-2026 by Cisco Systems, Inc.
     All rights reserved.";

  revision 2026-08-01 {
    description
      "Updated descriptions of several model elements to clarify their meaning and purpose";
    reference
      "1.5.0";
    cisco-semver:module-version "1.5.0";
  }
  revision 2025-07-01 {
    description
      "Support to get the IPSEC profile attached to a tunnel interface";
    reference
      "1.4.0";
    cisco-semver:module-version "1.4.0";
  }
  revision 2022-11-01 {
    description
      "Update yang-version to 1.1";
    reference
      "1.3.0";
    cisco-semver:module-version "1.3.0";
  }
  revision 2020-07-01 {
    description
      "Deprecated EoGRE specific content. It is now moved to Cisco-IOS-XE-eogre-tunnel-oper namespace";
    reference
      "1.2.0";
    cisco-semver:module-version "1.2.0";
  }
  revision 2019-05-01 {
    description
      "Added semantic version";
    reference
      "1.1.0";
    cisco-semver:module-version "1.1.0";
  }
  revision 2018-11-01 {
    description
      "Initial revision";
    reference
      "1.0.0";
    cisco-semver:module-version "1.0.0";
  }

  grouping st-tunnel-domain {
    description
      "Tunnel domain";
    container cfg {
      description
        "Configuration parameters for the tunnel domain.";
      uses tunnel-types:tunnel-domain-common;
    }
    leaf active-tunnel-name {
      type string;
      description
        "The name of the active tunnel interface in this domain.";
    }
    container history {
      description
        "Container holding the event history for the tunnel domain, including records of significant events and state changes.";
      uses event-history-types:event-history;
    }
  }

  grouping tunnel-intf-key {
    description
      "Interface key pair";
    leaf name {
      type string;
      description
        "The unique name used as a key to identify the tunnel interface in the list.";
    }
    leaf type {
      type tunnel-types:tunnel-domain-mode;
      description
        "The type of tunnel domain mode used as a key to identify the tunnel interface.";
    }
  }

  grouping st-tunnel-interface {
    description
      "List of tunnel interfaces";
    leaf gateway-address {
      type inet:ip-address;
      description
        "Gateway IP address";
    }
    leaf admin-status {
      type tunnel-types:tunnel-intf-status;
      description
        "Administrative status";
    }
    leaf status {
      type tunnel-types:tunnel-intf-status;
      description
        "Tunnel operational status";
    }
    leaf up-timestamp {
      type yang:date-and-time;
      description
        "Last time this gateway went up";
    }
    leaf mtu {
      type uint32;
      description
        "Maximum transmission unit";
    }
    container stats {
      description
        "Tunnel Statistics";
      uses tunnel-types:tunnel-stats;
    }
    leaf source-interface {
      type string;
      description
        "Specifies the source interface used for the tunnel.";
    }
    leaf source-address {
      type inet:ip-address;
      description
        "Specifies the source IP address used for the tunnel interface.";
    }
    container history {
      description
        "Event history for this gateway";
      uses event-history-types:event-history;
    }
    leaf intf-type {
      type tunnel-types:tunnel-intf-mode;
      description
        "Specifies the type of tunnel interface (for example, GRE, IPsec, or other supported tunnel modes).";
    }
  }

  grouping tunnel-intf-stats {
    description
      "Tunnel interface statistics";
    leaf in-octets {
      type uint64;
      description
        "The total number of octets received on the interface,
         including framing characters.";
    }
    leaf in-unicast-pkts {
      type uint64;
      description
        "The total number of unicast packets received on the
         interface.";
    }
    leaf in-broadcast-pkts {
      type uint64;
      description
        "The total number of broadcast packets received on the
         interface.";
    }
    leaf in-multicast-pkts {
      type uint64;
      description
        "The total number of multicast packets received on the
         interface.";
    }
    leaf in-discards {
      type uint64;
      description
        "The number of inbound packets that were chosen to be
         discarded even though no errors.";
    }
    leaf in-errors {
      type uint64;
      description
        "The number of inbound packets that contained errors
         preventing them from being deliverable to a higher-layer
         protocol.";
    }
    leaf out-octets {
      type uint64;
      description
        "The total number of octets transmitted out of the
         interface.";
    }
    leaf out-unicast-pkts {
      type uint64;
      description
        "The total number of unicast packets that higher-level
         protocols requested be transmitted.";
    }
    leaf out-broadcast-pkts {
      type uint64;
      description
        "The total number of broadcast packets that higher-level
         protocols requested to be transmitted.";
    }
    leaf out-multicast-pkts {
      type uint64;
      description
        "The total number of multicast packets that higher-level
         protocols requested to be transmitted.";
    }
    leaf out-discards {
      type uint64;
      description
        "The number of outbound packets that were chosen to be
         discarded even though no errors had been detected to
         prevent their being transmitted.";
    }
    leaf out-errors {
      type uint64;
      description
        "The number of outbound packets that could not be
         transmitted because of errors.";
    }
    leaf rx-pps {
      type uint64;
      description
        "The receive packet per second rate on this interface";
    }
    leaf rx-kbps {
      type uint64;
      description
        "The receive kilobits per second rate on this interface";
    }
    leaf tx-pps {
      type uint64;
      description
        "The transmit packet per second rate on this interface";
    }
    leaf tx-kbps {
      type uint64;
      description
        "The transmit kilobits per second rate on this interface";
    }
  }

  grouping tunnel-common-interface {
    description
      "List of tunnel common interfaces";
    leaf name {
      type string;
      description
        "The name of the Tunnel interface.";
    }
    leaf mode {
      type tunnel-types:tunnel-intf-mode;
      description
        "The mode of the Tunnel interface.";
    }
    leaf intf-ipv4 {
      type inet:ipv4-address;
      description
        "IPv4 address configured on interface.";
    }
    leaf-list intf-ipv6 {
      type inet:ipv6-address;
      ordered-by user;
      description
        "A list of the IPv6 addresses associated with the interface.
         This contains all the IPv6 addresses, including the link local
         addresses, assigned to the interface";
    }
    leaf intf-vrf {
      type string;
      description
        "VRF to which this interface belongs to. If the
         interface is not in a VRF then it is 'Global'.";
    }
    leaf transport-vrf {
      type string;
      description
        "Transport VRF. If this
         is not mentioned, then it is 'Global'";
    }
    leaf admin-status {
      type tunnel-types:tunnel-intf-status;
      description
        "Indicates the administrative status of the tunnel interface.";
    }
    leaf status {
      type tunnel-types:tunnel-intf-status;
      description
        "Tunnel interface operational status";
    }
    leaf src-if {
      type string;
      description
        "The name of the source interface used to originate traffic for this tunnel interface.";
    }
    leaf src-addr {
      type inet:ip-address;
      description
        "Tunnel Source IP Address";
    }
    leaf dst-addr {
      type inet:ip-address;
      description
        "Tunnel Destination IP Address";
    }
    leaf src-port {
      type uint16;
      description
        "Tunnel Source Port";
    }
    leaf dst-port {
      type uint16;
      description
        "Tunnel Destination Port";
    }
    leaf tunnel-key {
      type uint32;
      description
        "Tunnel security or selector key";
    }
    leaf mtu {
      type uint32;
      units "bytes";
      description
        "Maximum transmission unit for the tunnel interface, measured in bytes";
    }
    leaf ip-mtu {
      type uint32;
      units "bytes";
      description
        "Maximum transmission unit for IP packets on the tunnel interface, measured in bytes";
    }
    leaf transport-mtu {
      type uint32;
      units "bytes";
      description
        "Tunnel transport maximum transmission unit, measured in bytes";
    }
    leaf tx-bandwidth {
      type uint32;
      units "kbps";
      description
        "Tunnel transmit bandwidth";
    }
    leaf rx-bandwidth {
      type uint32;
      units "kbps";
      description
        "Tunnel receive bandwidth";
    }
    container stats {
      description
        "Container for tunnel interface statistics.";
      uses ios-tunnel-oper:tunnel-intf-stats;
    }
    leaf ipsec-profile {
      type string;
      description
        "The IPSEC profile attached to a tunnel interface";
    }
  }

  container tunnel-oper-data {
    config false;
    description
      "Top-level container for tunnel operational data";
    list tunnel-domain {
      key "name type";
      status deprecated;
      description
        "List of tunnel domains, keyed by domain name and type";
      uses tunnel-types:tunnel-domain-index;
      uses ios-tunnel-oper:st-tunnel-domain;
    }
    list tunnel-intf {
      key "name type";
      status deprecated;
      description
        "List of tunnel interfaces";
      uses ios-tunnel-oper:tunnel-intf-key;
      uses ios-tunnel-oper:st-tunnel-interface;
    }
    list tunnel-if {
      key "name";
      description
        "List of tunnel interfaces";
      uses ios-tunnel-oper:tunnel-common-interface;
    }
  }
}
