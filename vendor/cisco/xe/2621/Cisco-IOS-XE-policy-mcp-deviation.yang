module Cisco-IOS-XE-policy-mcp-deviation {
  yang-version 1.1;
  namespace "http://cisco.com/ns/yang/Cisco-IOS-XE-policy-mcp-deviation";
  prefix ios-policy-mcp-deviate;

  import Cisco-IOS-XE-native {
    prefix ios;
  }
  import Cisco-IOS-XE-policy {
    prefix ios-policy;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Deviation Policy Map Yang model for ASR platform.
     Copyright (c) 2019-2021 by Cisco Systems, Inc.
     All rights reserved.";

  revision 2024-03-01 {
    description
      "- Added new range for cir, pir ,bc and be value for police action
         on ASR1K platform";
    cisco-semver:module-version "1.2.0";
  }
  revision 2022-11-01 {
    description
      "- Update yang-version to 1.1
       - Remove priority range deviation as range is 100G for mcp devices";
    cisco-semver:module-version "1.1.0";
  }
  revision 2021-07-01 {
    description
      "- Added priority range value";
    cisco-semver:module-version "1.0.1";
  }
  revision 2020-07-01 {
    description
      "Initial Revision";
  }

  deviation "/ios:native/ios:policy/ios-policy:policy-map/ios-policy:class/ios-policy:action-list/ios-policy:action-param/ios-policy:police-case/ios-policy:police-choice/ios-policy:police-policy-map-case/ios-policy:police-policy-map/ios-policy:police/ios-policy:cir-bc-choice/ios-policy:cir-bc/ios-policy:cir" {
    deviate replace {
      type uint64 {
        range "8000..536000000000";
      }
    }
  }

  deviation "/ios:native/ios:policy/ios-policy:policy-map/ios-policy:class/ios-policy:action-list/ios-policy:action-param/ios-policy:police-case/ios-policy:police-choice/ios-policy:police-policy-map-case/ios-policy:police-policy-map/ios-policy:police/ios-policy:cir-bc-choice/ios-policy:cir-bc/ios-policy:bc" {
    deviate replace {
      type uint32 {
        range "1000..2048000000";
      }
    }
  }

  deviation "/ios:native/ios:policy/ios-policy:policy-map/ios-policy:class/ios-policy:action-list/ios-policy:action-param/ios-policy:police-case/ios-policy:police-choice/ios-policy:police-policy-map-case/ios-policy:police-policy-map/ios-policy:police/ios-policy:be" {
    deviate replace {
      type uint32 {
        range "1000..2048000000";
      }
    }
  }

  deviation "/ios:native/ios:policy/ios-policy:policy-map/ios-policy:class/ios-policy:action-list/ios-policy:action-param/ios-policy:police-case/ios-policy:police-choice/ios-policy:police-target-bitrate-case/ios-policy:police-target-bitrate/ios-policy:police/ios-policy:bit-rate" {
    deviate replace {
      type uint64 {
        range "8000..536000000000";
      }
    }
  }

  deviation "/ios:native/ios:policy/ios-policy:policy-map/ios-policy:class/ios-policy:action-list/ios-policy:action-param/ios-policy:police-case/ios-policy:police-choice/ios-policy:police-target-bitrate-case/ios-policy:police-target-bitrate/ios-policy:police/ios-policy:confirm_burst-byte" {
    deviate replace {
      type uint64 {
        range "1000..2048000000";
      }
    }
  }

  deviation "/ios:native/ios:policy/ios-policy:policy-map/ios-policy:class/ios-policy:action-list/ios-policy:action-param/ios-policy:police-case/ios-policy:police-choice/ios-policy:police-target-bitrate-case/ios-policy:police-target-bitrate/ios-policy:police/ios-policy:excess_burst-byte" {
    deviate replace {
      type uint64 {
        range "1000..2048000000";
      }
    }
  }
}
