module Cisco-IOS-XE-mpls-ldp-oper {
  yang-version 1.1;
  namespace "http://cisco.com/ns/yang/Cisco-IOS-XE-mpls-ldp-oper";
  prefix mpls-ldp-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for MPLS LDP operational data.
     Copyright (c) 2017-2019, 2022 by Cisco Systems, Inc.
     All rights reserved.";

  revision 2026-08-01 {
    description
      "- Refined existing leaf descriptions for clarity and consistency
       - Deprecated existing password-pending leaf containing pending
         password state in favor of a new bits type leaf";
    reference
      "1.2.0";
    cisco-semver:module-version "1.2.0";
  }
  revision 2022-11-01 {
    description
      "Update yang-version to 1.1";
    reference
      "1.1.0";
    cisco-semver:module-version "1.1.0";
  }
  revision 2019-11-01 {
    description
      "Initial revision";
    reference
      "1.0.0";
    cisco-semver:module-version "1.0.0";
  }

  typedef mpls-ldp-oper-status {
    type enumeration {
      enum mpls-ldp-oper-status-unknown {
        value 0;
        description
          "Unknown";
      }
      enum mpls-ldp-oper-status-enabled {
        value 1;
        description
          "Enabled";
      }
      enum mpls-ldp-oper-status-disabled {
        value 2;
        description
          "Disabled";
      }
    }
    description
      "Information of MPLS LDP operation status";
  }

  typedef hello-adjacency-type {
    type enumeration {
      enum hello-adjacency-type-link {
        value 0;
        description
          "Link adjacency";
      }
      enum hello-adjacency-type-targeted {
        value 1;
        description
          "Targeted adjacency";
      }
    }
    description
      "Hello adjacency type";
  }

  typedef session-role {
    type enumeration {
      enum session-role-unknown {
        value 0;
        description
          "Unknown";
      }
      enum session-role-active {
        value 1;
        description
          "Active";
      }
      enum session-role-passive {
        value 2;
        description
          "Passive";
      }
    }
    description
      "MPLS LDP session role";
  }

  typedef session-state {
    type enumeration {
      enum session-state-non-existent {
        value 0;
        description
          "Non-existent";
      }
      enum session-state-initialized {
        value 1;
        description
          "Initialized";
      }
      enum session-state-open-received {
        value 2;
        description
          "Open received";
      }
      enum session-state-open-sent {
        value 3;
        description
          "Open sent";
      }
      enum session-state-operational {
        value 4;
        description
          "Operational";
      }
    }
    description
      "MPLS LDP session state";
  }

  typedef label-distribution-method {
    type enumeration {
      enum lbl-dist-method-dod {
        value 0;
        description
          "Downstream on demand";
      }
      enum lbl-dist-method-du {
        value 1;
        description
          "Downstream unsolicited";
      }
    }
    description
      "Label distribution method";
  }

  typedef adj-state {
    type enumeration {
      enum adj-state-ne {
        value 0;
        description
          "Non-existent";
      }
      enum adj-state-unsol-op-pd {
        value 1;
        description
          "Unsolicited open pending";
      }
      enum adj-state-def {
        value 2;
        description
          "Deferred";
      }
      enum adj-state-est {
        value 3;
        description
          "Established";
      }
      enum adj-state-wait-tib-exp {
        value 4;
        description
          "Waiting for TIB expansion (peer index)";
      }
      enum adj-state-dest {
        value 5;
        description
          "Destroyed";
      }
    }
    description
      "LDP peer adjacency state";
  }

  typedef tcp-hash-type {
    type enumeration {
      enum tcp-hash-type-none {
        value 0;
        description
          "No hashing algorithm used for the TCP connection";
      }
      enum tcp-hash-type-md5-password {
        value 1;
        description
          "MD5 hashing on TCP connection, LDP gives TCP the password";
      }
      enum tcp-hash-type-md5-keychain {
        value 2;
        description
          "MD5 hashing on TCP connection, LDP gives TCP the keychain";
      }
      enum tcp-hash-type-sha1 {
        value 3;
        description
          "SHA1 hashing algorithm used for the TCP connection";
      }
      enum tcp-hash-type-tcp-ao {
        value 4;
        description
          "TCP AO hashing algorithm used for the TCP connection";
      }
    }
    description
      "LDP peer tcp hash type";
  }

  typedef graceful-restart-down-neighbor-state {
    type enumeration {
      enum gr-down-nbr-state-none {
        value 0;
        description
          "None, state not available";
      }
      enum gr-down-nbr-state-wait-connect {
        value 1;
        description
          "Wait connect";
      }
      enum gr-down-nbr-state-recovering {
        value 2;
        description
          "Recovering";
      }
      enum gr-down-nbr-state-defunct {
        value 3;
        description
          "Defunct";
      }
    }
    description
      "LDP graceful restart down neighbor state";
  }

  typedef adj-flag {
    type bits {
      bit adj-flag-dir {
        position 0;
        description
          "Directed";
      }
      bit adj-flag-temp {
        position 1;
        description
          "Temporary";
      }
      bit adj-flag-force-down {
        position 2;
        description
          "Force down";
      }
      bit adj-flag-sess-up-wait {
        position 3;
        description
          "Waiting for session up";
      }
      bit adj-flag-ldp-hello {
        position 4;
        description
          "LDP hello";
      }
      bit adj-flag-tx {
        position 5;
        description
          "Transmitting";
      }
      bit adj-flag-need-route {
        position 6;
        description
          "Need route";
      }
      bit adj-flag-on-tx-q {
        position 7;
        description
          "On transmit working queue";
      }
      bit adj-flag-on-rx-q {
        position 8;
        description
          "On receive working queue";
      }
      bit adj-flag-pwd-chg-pd {
        position 9;
        description
          "Password change pending";
      }
      bit adj-flag-pwd-req {
        position 10;
        description
          "Password required";
      }
      bit adj-flag-intf-down {
        position 11;
        description
          "Interface down";
      }
      bit adj-flag-pwd-chg-ro-pd {
        position 12;
        description
          "Password change roll over pending";
      }
      bit adj-flag-exp-delayed {
        position 13;
        description
          "Expire delayed";
      }
      bit adj-flag-rd-blk {
        position 14;
        description
          "Read blocked";
      }
      bit adj-flag-rd-pdu {
        position 15;
        description
          "Reading PDU";
      }
    }
    description
      "MPLS LDP discovery adjacency flags";
  }

  typedef password-pending-flag {
    type bits {
      bit pwd-chg-pd {
        position 0;
        description
          "Password change pending";
      }
      bit pwd-chg-ro-pd {
        position 1;
        description
          "Password change roll over pending";
      }
    }
    description
      "MPLS LDP password pending flags";
  }

  typedef graceful-restart-neighbor-session-flag {
    type bits {
      bit gr-nbr-flag-need-mark {
        position 0;
        description
          "Need mark";
      }
      bit gr-nbr-flag-need-id-change {
        position 1;
        description
          "Need Identifier change";
      }
      bit gr-nbr-flag-need-delete {
        position 2;
        description
          "Needs deletion of the session";
      }
    }
    description
      "Graceful restart down neighbor session flags";
  }

  grouping local-label-binding {
    description
      "Local label binding";
    leaf label {
      type uint32;
      description
        "Local label value
         0 - 0xfffff   : Valid local label range
         (0xfffff + 2) : No local label is allocated for this prefix";
    }
    leaf withdrawn {
      type boolean;
      description
        "Indicates whether the local label binding for this FEC has been withdrawn.";
    }
    leaf wd-sent-to-peer {
      type boolean;
      description
        "Indicates whether a label withdraw message has been sent to the peer for this local label binding.";
    }
    leaf-list advertised-to {
      type string;
      ordered-by user;
      description
        "List of peer LDP identifiers to which this local label binding has been advertised.";
    }
  }

  grouping remote-label-binding {
    description
      "Remote label binding";
    leaf label {
      type uint32;
      description
        "Label value assigned by a remote LDP peer for this FEC.";
    }
    leaf ldpid {
      type string;
      description
        "LDP Identifier";
    }
    leaf is-static {
      type boolean;
      description
        "Indicates whether the remote label binding is statically or dynamically applied.";
    }
    leaf checkpointed {
      type boolean;
      description
        "Indicates whether this remote label binding has been checkpointed for NSR or stateful switchover.";
    }
    leaf stale {
      type boolean;
      description
        "Indicates whether this remote label binding is considered stale.";
    }
    leaf recovered {
      type boolean;
      description
        "Indicates whether this remote label binding has been recovered after a failure or session re-establishment.";
    }
    leaf entropy-label-capable {
      type boolean;
      description
        "Entropy label capable flag";
    }
  }

  grouping binding-fec-label {
    description
      "FEC label binding";
    leaf fec {
      type inet:ip-prefix;
      description
        "Forwarding Equivalent Class";
    }
    leaf revision {
      type uint16;
      description
        "Revision number for the FEC label binding, used to track changes.";
    }
    leaf checkpointed {
      type boolean;
      description
        "Indicates whether the FEC label binding has been checkpointed for stateful redundancy.";
    }
    leaf entropy-label-capable {
      type boolean;
      description
        "Entropy label capable flag";
    }
    container local-binding {
      description
        "Local label binding";
      uses mpls-ldp-ios-xe-oper:local-label-binding;
    }
    list remote-binding {
      description
        "Remote label bindings";
      uses mpls-ldp-ios-xe-oper:remote-label-binding;
    }
  }

  grouping capability {
    description
      "LDP capability state";
    leaf typed-wildcard {
      type boolean;
      description
        "Indicates whether the LDP Typed Wildcard FEC capability is supported.";
    }
    leaf iccp {
      type boolean;
      description
        "Indicates whether the Inter-Chassis Communication Protocol (ICCP) capability is supported for LDP.";
    }
    leaf iccp-major-version {
      type uint8;
      description
        "Specifies the major version number of the Inter-Chassis Communication Protocol (ICCP) capability.";
    }
    leaf iccp-minor-version {
      type uint8;
      description
        "Specifies the minor version number of the Inter-Chassis Communication Protocol (ICCP) capability.";
    }
    leaf dynamic-announcement {
      type boolean;
      description
        "Indicates whether the LDP dynamic announcement capability is supported.";
    }
    leaf mldp-p2mp {
      type boolean;
      description
        "Indicates whether the LDP capability for mLDP Point-to-Multipoint (P2MP) is supported.";
    }
    leaf mldp-mp2mp {
      type boolean;
      description
        "Indicates whether the LDP capability for mLDP Multipoint-to-Multipoint (MP2MP) is supported.";
    }
  }

  grouping graceful-restart {
    description
      "LDP graceful restart state";
    leaf enable {
      type boolean;
      description
        "Indicates whether MPLS LDP graceful restart is enabled.";
    }
    leaf reconnect-time {
      type uint32;
      units "seconds";
      description
        "Reconnect time in seconds";
    }
    leaf recover-time {
      type uint32;
      units "seconds";
      description
        "Recover time in seconds";
    }
    leaf forward-hold-time {
      type uint32;
      units "seconds";
      description
        "Forward hold time in seconds";
    }
  }

  grouping hello-adjacency-key {
    description
      "LDP hello adjacency key";
    leaf adjacent-address {
      type inet:ip-address;
      description
        "IP address of the adjacent LDP peer for this hello adjacency.";
    }
    leaf transport-address {
      type inet:ip-address;
      description
        "Transport address used for establishing the LDP session with the adjacent peer.";
    }
  }

  grouping hello-adjacency {
    description
      "LDP hello adjacency information";
    leaf adjacent-ldpid {
      type string;
      description
        "Adjacent LDP Identifier";
    }
    leaf flag {
      type mpls-ldp-ios-xe-oper:adj-flag;
      description
        "Flags (see: mpls ldp discovery adjacency flag)";
    }
    leaf targeted-passive {
      type boolean;
      description
        "Indicates whether this hello adjacency is a targeted passive adjacency.";
    }
    leaf hello-hold-time-adjacent {
      type uint16;
      units "seconds";
      description
        "Adjacent hello hold time in seconds";
    }
    leaf hello-hold-time-negotiated {
      type uint16;
      units "seconds";
      description
        "Negotiated hello hold time in seconds";
    }
    leaf hello-hold-time-remaining {
      type uint16;
      units "seconds";
      description
        "Remaining hello hold time in seconds";
    }
    leaf password-required {
      type boolean;
      description
        "Flag: Password required";
    }
    leaf password-pending {
      type uint16;
      status deprecated;
      description
        "A bitmask-derived flag indicating the password-related pending
         state for the adjacency. The following is a list of all possible
         values:
         '0' for no pending state set;
         '512' or '0x0200' for password change pending;
         '4096' or '0x1000' for read-only password change pending;
         '4608' or '0x1200' for both pending-state bits set.
         This legacy uint16 leaf is deprecated; use
         pwd-pend-flags for typed bitmap data.";
    }
    leaf password-source {
      type uint32;
      description
        "Password source values
         * 0       : neighbor
           This indicates that the password for the neighbor is retrieved
           from the mpls ldp neighbor [vrf vrf-name] ip-address password [0 | 7] password command.
         * 1~32767 : password option number
           This number defines the order in which the access lists are
           evaluated in the determination of a neighbor password.
         * 32768   : fall back to MD5 password for LDP sessions with peers
         * 32769   : none i.e, No password is configured for this neighbor";
    }
    leaf nexthop {
      type inet:ip-address;
      description
        "IP address of the next-hop used for the LDP hello adjacency.";
    }
    leaf no-route {
      type boolean;
      description
        "Flag: no route to transport address";
    }
    leaf no-host-route {
      type boolean;
      description
        "Flag: no host route to transport address";
    }
    leaf pwd-pend-flags {
      type mpls-ldp-ios-xe-oper:password-pending-flag;
      description
        "Indicates the pending password state for the adjacency as a set of typed flags.";
    }
  }

  grouping link-state {
    description
      "LDP hello discovery source state for linked adjacency";
    leaf igp-sync-enable {
      type boolean;
      description
        "Flag: IGP sync enabled";
    }
    leaf igp-sync-delay {
      type uint16;
      units "seconds";
      description
        "IGP sync delay in seconds";
    }
  }

  grouping targeted-state {
    description
      "LDP hello discovery source state for targeted adjacency";
    leaf hello-accept-enable {
      type boolean;
      description
        "Flag: hello accept enabled";
    }
    leaf hello-accept-neighbor-list {
      type string;
      description
        "Specifies the name of the access list that controls which neighbors are allowed to send targeted LDP hello messages.";
    }
  }

  grouping discovery-source-key {
    description
      "LDP adjacency discovery source table key";
    leaf is-targeted-adjacency {
      type uint8;
      description
        "Flag: targeted adjacency";
    }
    leaf if-index {
      type uint32;
      description
        "interface index for link adjacency;
         value 0 for targeted adjacency";
    }
  }

  grouping discovery-source {
    description
      "LDP adjacency discovery source state";
    leaf hello-hold-time {
      type uint16;
      units "seconds";
      description
        "Hello hold time in seconds";
    }
    leaf hello-interval {
      type uint16;
      units "seconds";
      description
        "Hello interval in seconds";
    }
    leaf enable {
      type boolean;
      description
        "Indicates whether LDP discovery is enabled on this source.";
    }
    leaf transport-address {
      type inet:ip-address;
      description
        "Transport address";
    }
    list mpls-ldp-disc-hello-adj {
      key "adjacent-address transport-address";
      description
        "List of LDP hello adjacencies discovered on this source.";
      uses mpls-ldp-ios-xe-oper:hello-adjacency-key;
      uses mpls-ldp-ios-xe-oper:hello-adjacency;
    }
    choice type-choice {
      description
        "Hello adjacency type";
      case hello-adjacency-type-link {
        container link-state {
          description
            "State information for LDP hello discovery sources with link adjacencies.";
          uses mpls-ldp-ios-xe-oper:link-state;
        }
      }
      case hello-adjacency-type-targeted {
        container targeted-state {
          description
            "State information for LDP hello discovery sources with targeted adjacencies.";
          uses mpls-ldp-ios-xe-oper:targeted-state;
        }
      }
    }
  }

  grouping label-advertisement-mode {
    description
      "LDP label advertisement mode";
    leaf local {
      type mpls-ldp-ios-xe-oper:label-distribution-method;
      description
        "Local label advertisement mode for the LDP peer.";
    }
    leaf negotiated {
      type mpls-ldp-ios-xe-oper:label-distribution-method;
      description
        "Label advertisement mode negotiated with the LDP peer.";
    }
  }

  grouping peer-graceful-restart {
    description
      "LDP peer graceful restart state";
    leaf enable {
      type boolean;
      description
        "Indicates whether graceful restart is enabled for the LDP peer.";
    }
    leaf reconnect-time {
      type uint16;
      units "seconds";
      description
        "Reconnect time in seconds";
    }
    leaf recovery-time {
      type uint16;
      units "seconds";
      description
        "Recovery time in seconds";
    }
  }

  grouping session-hold-time {
    description
      "LDP peer session hold time state";
    leaf negotiated {
      type uint16;
      units "seconds";
      description
        "Negotiated session hold time in seconds";
    }
  }

  grouping tcp-connection {
    description
      "LDP peer session TCP connection state";
    leaf local-address {
      type inet:ip-address;
      description
        "Local address";
    }
    leaf local-port {
      type uint16;
      description
        "Local port";
    }
    leaf remote-address {
      type inet:ip-address;
      description
        "Remote address";
    }
    leaf remote-port {
      type uint16;
      description
        "Remote port";
    }
  }

  grouping peer-events {
    description
      "LDP peer events state";
    leaf total-messages {
      type uint64;
      description
        "Total number of protocol messages exchanged with the LDP peer.";
    }
  }

  grouping peer-statistics {
    description
      "LDP peer statistic counters";
    container sent {
      description
        "Statistics for events sent to the LDP peer, including protocol message counters.";
      uses mpls-ldp-ios-xe-oper:peer-events;
    }
    container received {
      description
        "Statistics for events received from the LDP peer, including protocol message counters.";
      uses mpls-ldp-ios-xe-oper:peer-events;
    }
    leaf nsr-in-lbl-req-rec-created {
      type uint32;
      description
        "Protocol state counter: NSR incoming label request record created";
    }
    leaf nsr-in-lbl-req-rec-freed {
      type uint32;
      description
        "Protocol state counter: NSR incoming label request record freed";
    }
    leaf nsr-in-lbl-wd-rec-created {
      type uint32;
      description
        "Protocol state counter: NSR incoming label withdraw record created";
    }
    leaf nsr-in-lbl-wd-rec-freed {
      type uint32;
      description
        "Protocol state counter: NSR incoming label withdraw record freed";
    }
    leaf nsr-lcl-addr-wd-rec-created {
      type uint32;
      description
        "Protocol state counter: NSR local address withdraw record created";
    }
    leaf nsr-lcl-addr-wd-rec-freed {
      type uint32;
      description
        "Protocol state counter: NSR local address withdraw record freed";
    }
    leaf adj-last-addr-rev-sent {
      type uint64;
      description
        "The revision number of the last address information sent to the adjacent LDP peer.";
    }
  }

  grouping peer-discovery-source {
    description
      "LDP peer discovery source";
    leaf is-targeted-adjacency {
      type boolean;
      description
        "Flag: targeted adjacency";
    }
    leaf if-index {
      type uint32;
      description
        "Interface index for link adjacency, 0 for targeted adjacency";
    }
    leaf adjacent-address {
      type inet:ip-address;
      description
        "Adjacent address";
    }
    leaf transport-address {
      type inet:ip-address;
      description
        "IP address used as the transport address for the LDP peer discovery source.";
    }
  }

  grouping peer {
    description
      "LDP peer state";
    leaf peer-id {
      type string;
      description
        "Peer LDP identifier";
    }
    leaf admin-down {
      type boolean;
      description
        "Flag: admin down";
    }
    leaf state {
      type mpls-ldp-ios-xe-oper:adj-state;
      description
        "Current state of the LDP peer adjacency.";
    }
    leaf session-protocol-version {
      type uint32;
      description
        "Session protocol version";
    }
    container capability-sent {
      description
        "Capability sent";
      uses mpls-ldp-ios-xe-oper:capability;
    }
    container capability-received {
      description
        "Capability received";
      uses mpls-ldp-ios-xe-oper:capability;
    }
    leaf sess-auth-type {
      type mpls-ldp-ios-xe-oper:tcp-hash-type;
      description
        "Session authentication type";
    }
    container graceful-restart {
      description
        "Graceful restart state";
      uses mpls-ldp-ios-xe-oper:peer-graceful-restart;
    }
    leaf nsr-ready {
      type boolean;
      description
        "Flag: NSR ready";
    }
    leaf sess-ka-hold-time {
      type uint16;
      units "seconds";
      description
        "Session keepalive hold time in seconds";
    }
    leaf sess-ka-interval {
      type uint16;
      units "seconds";
      description
        "Session keepalive hold interval in seconds";
    }
    container advertisement-mode {
      description
        "Label advertisement mode used by the LDP peer, indicating how label distribution is performed.";
      uses mpls-ldp-ios-xe-oper:label-advertisement-mode;
    }
    container session-hold-time {
      description
        "Session hold time in seconds";
      uses mpls-ldp-ios-xe-oper:session-hold-time;
    }
    leaf session-protection-duration {
      type uint16;
      units "seconds";
      description
        "Session protection duration in seconds";
    }
    leaf session-protection-acl {
      type string;
      description
        "Session protection ACL name";
    }
    leaf session-state {
      type mpls-ldp-ios-xe-oper:session-state;
      description
        "Current state of the LDP session with the peer.";
    }
    leaf session-role {
      type mpls-ldp-ios-xe-oper:session-role;
      description
        "Indicates the role of the LDP session for this peer.";
    }
    container tcp-connection {
      description
        "Details of the TCP connection established for the LDP session with this peer.";
      uses mpls-ldp-ios-xe-oper:tcp-connection;
    }
    list discovery-sources {
      description
        "List of sources used to discover this LDP peer.";
      uses mpls-ldp-ios-xe-oper:peer-discovery-source;
    }
    leaf establish-time {
      type yang:date-and-time;
      description
        "The date and time when the LDP session with the peer was established.";
    }
    leaf-list address-bound {
      type inet:ip-address;
      ordered-by user;
      description
        "List of IP addresses that are bound to the LDP peer for label distribution.";
    }
    leaf password-required {
      type boolean;
      description
        "Flag: password required";
    }
    leaf password-change-pending {
      type boolean;
      description
        "Flag: password change pending";
    }
    leaf password-rollover-pending {
      type boolean;
      description
        "Flag: password rollover pending";
    }
    leaf password-source {
      type uint32;
      description
        "Password source values
         * 0       : neighbor
           This indicates that the password for the neighbor is retrieved
           from the mpls ldp neighbor [vrf vrf-name] ip-address password [0 | 7] password command.
         * 1~32767 : password option number
           This number defines the order in which the access lists are
           evaluated in the determination of a neighbor password.
         * 32768   : fall back to MD5 password for LDP sessions with peers
         * 32769   : none i.e, No password is configured for this neighbor";
    }
    leaf is-keychain {
      type boolean;
      description
        "Flag: keychain";
    }
    leaf keychain-name {
      type string;
      description
        "Name of the keychain used for authentication with this LDP peer.";
    }
    container statistics {
      description
        "Statistics and counters related to the LDP peer, including message and protocol state information.";
      uses mpls-ldp-ios-xe-oper:peer-statistics;
    }
  }

  grouping graceful-restart-neighbor-session-id {
    description
      "Graceful restart down neighbor session Identifier";
    leaf ldpid {
      type string;
      description
        "LDP Identifier associated with the session entry in the session history.";
    }
    leaf instance {
      type uint16;
      description
        "Instance Identifier
         * 0        : chassis-wide TDP Identifier
         * non-zero : Not chassis-wide TDP Identifier (i.e,for a ATM interface)";
    }
    leaf flags {
      type mpls-ldp-ios-xe-oper:graceful-restart-neighbor-session-flag;
      description
        "Flag value,
         0x01 : Request bindings marking
         0x02 : Request bindings update if a new LDP ID is being used
         0x04 : Request bindings deletion";
    }
  }

  grouping graceful-restart-down-neighbor {
    description
      "Graceful restart down neighbor data";
    leaf peer-id {
      type string;
      description
        "Peer LDP Identifier";
    }
    container old-session {
      description
        "Old session Identifier";
      uses mpls-ldp-ios-xe-oper:graceful-restart-neighbor-session-id;
    }
    container new-session {
      description
        "New session Identifier";
      uses mpls-ldp-ios-xe-oper:graceful-restart-neighbor-session-id;
    }
    list session-history {
      description
        "List of previous session identifiers and related information for the graceful restart neighbor.";
      uses mpls-ldp-ios-xe-oper:graceful-restart-neighbor-session-id;
    }
    leaf num-restarts {
      type uint8;
      description
        "Number of restarts";
    }
    leaf listed {
      type boolean;
      description
        "Flag: New record created in GR down neighbor
         database";
    }
    leaf on-task-queue {
      type boolean;
      description
        "Flag: New record added to the GR down neighbor
         bindings management task queue";
    }
    leaf down-neighbor-state {
      type mpls-ldp-ios-xe-oper:graceful-restart-down-neighbor-state;
      description
        "Current state of the graceful restart neighbor.";
    }
    leaf sso-created {
      type boolean;
      description
        "Flag: Stateful Switch Over created";
    }
    leaf-list address-list {
      type inet:ip-address;
      ordered-by user;
      description
        "List of IP addresses associated with the LDP graceful restart neighbor.";
    }
    leaf reconnect-time-left {
      type uint16;
      units "seconds";
      description
        "Reconnect time left in seconds";
    }
    leaf recovery-time-left {
      type uint16;
      units "seconds";
      description
        "Recover time left in seconds";
    }
  }

  grouping ldp-state {
    description
      "MPLS LDP state";
    leaf table-id {
      type uint64;
      description
        "Routing table Identifier";
    }
    leaf oper-status {
      type mpls-ldp-ios-xe-oper:mpls-ldp-oper-status;
      description
        "Operational status";
    }
    container capability {
      description
        "Capabilities information";
      uses mpls-ldp-ios-xe-oper:capability;
    }
    container graceful-restart {
      description
        "Graceful restart information";
      uses mpls-ldp-ios-xe-oper:graceful-restart;
    }
    leaf igp-sync-hold-down-time {
      type uint32;
      units "seconds";
      description
        "IGP sync hold down time in seconds";
    }
    leaf path-vector-limit {
      type uint32;
      description
        "Path vector limit";
    }
    leaf hop-count-limit {
      type uint32;
      description
        "Hop count limit";
    }
    leaf enable {
      type boolean;
      description
        "Indicates whether MPLS LDP is enabled for this routing table instance.";
    }
    leaf transport-address {
      type inet:ip-address;
      description
        "IP address used as the transport address for MPLS LDP sessions.";
    }
    list mpls-ldp-binding-fec-lbl {
      key "fec";
      description
        "FEC label binding";
      uses mpls-ldp-ios-xe-oper:binding-fec-label;
    }
    leaf hello-hold-time {
      type uint16;
      units "seconds";
      description
        "Discovery hello hold time in seconds";
    }
    leaf hello-interval {
      type uint16;
      units "seconds";
      description
        "Discovery hello interval in seconds";
    }
    leaf ldpid {
      type string;
      description
        "LDP identifier";
    }
    list mpls-ldp-disc-src {
      key "is-targeted-adjacency if-index";
      description
        "Discovery sources";
      uses mpls-ldp-ios-xe-oper:discovery-source-key;
      uses mpls-ldp-ios-xe-oper:discovery-source;
    }
    leaf sess-ka-hold-time {
      type uint16;
      units "seconds";
      description
        "Session keepalive hold time in seconds";
    }
    leaf sess-ka-interval {
      type uint16;
      units "seconds";
      description
        "Session keepalive interval in seconds";
    }
    list mpls-ldp-peer {
      key "peer-id";
      description
        "MPLS LDP peers";
      uses mpls-ldp-ios-xe-oper:peer;
    }
    list mpls-ldp-gr-down-nbr {
      key "peer-id";
      description
        "MPLS LDP Graceful restart down neighbors";
      uses mpls-ldp-ios-xe-oper:graceful-restart-down-neighbor;
    }
    leaf disc-num-ldp-intf {
      type uint32;
      description
        "Number of interfaces LDP is configured";
    }
    leaf disc-num-ldp-intf-active {
      type uint32;
      description
        "Number of interfaces LDP is enabled";
    }
    leaf disc-num-link-adj {
      type uint32;
      description
        "Number of LDP Link Adjacencies";
    }
    leaf disc-num-tgt-adj {
      type uint32;
      description
        "Number of LDP Targeted Adjacencies";
    }
    leaf disc-num-bad-src-addr {
      type uint32;
      description
        "Number of LDP errors with Bad Source address";
    }
    leaf disc-num-bad-hello-pdu {
      type uint32;
      description
        "Number of LDP errors with Bad Hello PDUs";
    }
    leaf disc-num-bad-xport-addr {
      type uint32;
      description
        "Number of LDP errors with Bad Transport address";
    }
    leaf disc-num-same-router-id {
      type uint32;
      description
        "Number of LDP errors with same router id";
    }
    leaf disc-num-wrong-router-id {
      type uint32;
      description
        "Number of LDP errors with wrong router id";
    }
  }

  container mpls-ldp-oper-data {
    config false;
    description
      "MPLS LDP operational data";
    list mpls-ldp-state {
      key "table-id";
      description
        "MPLS LDP state information";
      uses mpls-ldp-ios-xe-oper:ldp-state;
    }
  }
}
