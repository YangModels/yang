module Cisco-IOS-XE-cip {
  yang-version 1.1;
  namespace "http://cisco.com/ns/yang/Cisco-IOS-XE-cip";
  prefix ios-cip;

  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE CIP (Common Industrial Protocol) Yang Model.
     Copyright (c) 2025 by Cisco Systems, Inc.
     All rights reserved.";

  revision 2026-08-01 {
    description
      "- Added encryption (type 8) support for password
       - Marked insecure password leaf as deprecated";
  }
  revision 2026-02-01 {
    description
      "Initial revision.";
  }

  grouping config-interface-cip-grouping {
    container cip {
      description
        "CIP interface configuration";
      leaf enable {
        type empty;
        description
          "Enable CIP on the interface";
        must 'count(/ios:native/ios:interface/ios:Vlan/cip/enable) <= 1' {
          error-message "CIP can only be enabled on one VLAN interface at a time";
          description
            "Ensures CIP is enabled on only one VLAN interface across the system";
        }
      }
    }
  }

  grouping config-global-cip-grouping {
    container cip {
      description
        "CIP protocol configuration container";
      container security {
        description
          "CIP security configuration";
        container password-config {
          description
            "CIP security password";
          leaf encryption-type {
            description
              "Encryption type (0=not yet encrypted) (8=encrypted) password";
            type enumeration {
              enum 0 {
                description
                  "The type of key is UNENCRYPTED secret key";
              }
              enum 8 {
                description
                  "The type of key is ENCRYPTED secret key";
              }
            }
          }
          leaf password {
            type string {
              length "1..64";
              pattern '[^\n\t]*' {
                description
                  "Password cannot contain line breaks or tabs";
              }
            }
          }
        }
        leaf password {
          status deprecated;
          type string {
            length "1..32";
            pattern '[^\n\t]*' {
              description
                "Password cannot contain line breaks or tabs";
            }
          }
          description
            "CIP security password - Deprecated (Insecure)";
        }
        container window {
          description
            "CIP security window configuration";
          leaf timeout {
            type uint32 {
              range "1..3600";
            }
            units "seconds";
            description
              "CIP security window timeout value";
          }
        }
      }
      container encap {
        description
          "CIP encapsulation configuration";
        container inactivity {
          description
            "CIP encapsulation inactivity timeout";
          leaf timeout {
            type uint32 {
              range "0..3600";
            }
            units "seconds";
            description
              "CIP encapsulation inactivity timeout value";
          }
        }
      }
    }
  }

  augment "/ios:native" {
    description
      "Augments native model with global CIP configuration";
    uses config-global-cip-grouping;
  }

  augment "/ios:native/ios:interface/ios:Vlan" {
    description
      "Augments VLAN interface with CIP configuration";
    uses config-interface-cip-grouping;
  }
}
