module Cisco-IOS-XE-gnmi-cfg {
  yang-version 1.1;
  namespace "http://cisco.com/ns/yang/Cisco-IOS-XE-gnmi-cfg";
  prefix gnmi-cfg;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for gNMI configuration data.
     Copyright (c) 2021-2022, 2024-2026 by Cisco Systems, Inc.
     All rights reserved.";

  revision 2026-08-01 {
    description
      "- Improve description of top level configuration and server containers
       - Deprecated insecure gNxI server enable leaf and port leaf";
    reference
      "1.6.0";
    cisco-semver:module-version "1.6.0";
  }
  revision 2026-02-01 {
    description
      "Add gNxI ACL configuration";
    reference
      "1.5.0";
    cisco-semver:module-version "1.5.0";
  }
  revision 2025-07-01 {
    description
      "Add leaf 'vrf' to configure the gNxI server's VRF";
    reference
      "1.4.0";
    cisco-semver:module-version "1.4.0";
  }
  revision 2025-03-01 {
    description
      "- Add length and pattern constraints to secure trustpoint name
       - Add length and pattern constraints to secure client auth trustpoint name
       - Fix constraints tying secure server and trustpoint name";
    reference
      "1.3.0";
    cisco-semver:module-version "1.3.0";
  }
  revision 2024-07-01 {
    description
      "- Add 'enable-gnoi' leaf to control whether gNOI services are enabled/disabled.
       - Add 'read-only' leaf to enable/disable read-only mode";
    reference
      "1.2.0";
    cisco-semver:module-version "1.2.0";
  }
  revision 2022-11-01 {
    description
      "Update yang-version to 1.1";
    reference
      "1.1.0";
    cisco-semver:module-version "1.1.0";
  }
  revision 2021-07-01 {
    description
      "Initial revision";
    reference
      "1.0.0";
    cisco-semver:module-version "1.0.0";
  }

  grouping gnxi-acl-config {
    description
      "Service ACLs for the gNxI gRPC server";
    leaf acl-ipv4 {
      type string {
        length "0..220";
        pattern "[\\] A-Za-z0-9!\"#%&()*+,\\-./:;<=>^?@\\\\$_`{|}\\[']*";
      }
      default "";
      description
        "Validate access using an IPv4 access-list";
    }
    leaf acl-ipv6 {
      type string {
        length "0..220";
        pattern "[\\] A-Za-z0-9!\"#%&()*+,\\-./:;<=>^?@\\\\$_`{|}\\[']*";
      }
      default "";
      description
        "Validate access using an IPv6 access-list";
    }
  }

  grouping gnmi-config {
    description
      "gNMI server configuration data type.";
    leaf enable {
      type boolean;
      default "false";
      status deprecated;
      description
        "Indicates whether the insecure gNMI server is enabled. The insecure gNMI server is deprecated. Use 'secure-enable' to manage the TLS-enabled secure server instead.";
    }
    leaf port {
      type uint16 {
        range "1024 .. 65535";
      }
      must '(../port != ../secure-port)' {
        error-message "The insecure and secure port cannot share the same numeric value";
        error-app-tag "must-violation";
      }
      default "50052";
      status deprecated;
      description
        "Port number on which the insecure gNMI server listens. The insecure gNMI server is deprecated. Use 'secure-port' with 'secure-enable' instead";
    }
    leaf secure-enable {
      type boolean;
      must "(../secure-enable = 'false') or ((../secure-enable = 'true') and string-length(../secure-tsname) > 0)" {
        error-message "Secure server can only be enabled in combination with a valid secure trustpoint name.";
        error-app-tag "must-violation";
      }
      default "false";
      description
        "Enables the gNMI secure server.";
    }
    leaf secure-client-auth {
      type boolean;
      default "false";
      description
        "Enables gNMI with client authentication.";
    }
    leaf secure-port {
      type uint16 {
        range "1024 .. 65535";
      }
      default "9339";
      description
        "Port number on which the secure gNMI server listens.";
    }
    leaf secure-tsname {
      type string {
        length "1..128";
        pattern "[\\] A-Za-z0-9!\"#%&()*+,\\-./:;<=>^?@\\\\$_`{|}\\[']+";
      }
      description
        "gNMI server certificate trustpoint name.";
    }
    leaf service {
      type boolean;
      default "false";
      description
        "Starts the gNMI service.";
    }
    leaf secure-client-auth-tsname {
      type string {
        length "1..128";
        pattern "[\\] A-Za-z0-9!\"#%&()*+,\\-./:;<=>^?@\\\\$_`{|}\\[']+";
      }
      description
        "The gNMI server peer validation trustpoint name.";
    }
    leaf secure-password-auth {
      type boolean;
      default "false";
      description
        "Set gNMI with password authentication.";
    }
    leaf enable-gnoi {
      type boolean;
      default "true";
      description
        "Enable the supported set of gRPC Network Operations Interface (gNOI) services.
         If gNOI is disabled then the device wil behave as if the service is not implemented.
         All RPCs belonging to disabled services will fail with a gRPC UNIMPLEMENTED status code";
    }
    leaf read-only {
      type boolean;
      default "false";
      description
        "Operate in a read-only mode.
         - All gNOI services are disabled. The behavior will be equivalent to setting 'enable-gnoi' to 'false'
         - The gNMI/Set RPC will fail with a gRPC PERMISSION_DENIED status code.";
    }
    leaf vrf {
      type string {
        length "1..32";
        pattern "[\\] A-Za-z0-9!\"#%&()*+,\\-./:;<=>^?@\\\\$_`{|}\\[']+";
      }
      description
        "The Virtual Routing and Forwarding (VRF) instance to use for connections to the gNxI server.";
    }
    container acl {
      description
        "Service ACLs for the gNxI gRPC server";
      uses gnmi-cfg:gnxi-acl-config;
    }
  }

  container gnmi-cfg-data {
    description
      "Top-level container for all gNMI configuration data on the device.";
    container config {
      presence "config";
      description
        "Container for configuration parameters of the gNMI server instance.";
      uses gnmi-cfg:gnmi-config;
    }
  }
}
