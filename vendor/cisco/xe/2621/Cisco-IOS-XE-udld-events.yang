module Cisco-IOS-XE-udld-events {
  yang-version 1.1;
  namespace "http://cisco.com/ns/yang/Cisco-IOS-XE-udld-events";
  prefix udld-ios-xe-events;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Unidirectional link detection event notification.
     Copyright (c) 2023 by Cisco Systems, INC.
     All rights reserved.";

  revision 2024-03-01 {
    description
      "Initial revision";
    reference
      "1.0.0";
    cisco-semver:module-version "1.0.0";
  }

  typedef udld-link-state {
    type enumeration {
      enum udld-state-unknown {
        value 0;
        description
          "Unknown link state";
      }
      enum udld-state-unidir-link {
        value 1;
        description
          "Unidirectional Link";
      }
      enum udld-state-nbr-mismatch {
        value 2;
        description
          "Unidirectional link detection protocol neighbor mismatch";
      }
      enum udld-state-tx-rx-loop {
        value 3;
        description
          "Unidirectional link detection protocol transmit/receive loop";
      }
      enum udld-state-aggr-mod-fail-err-dis {
        value 4;
        description
          "Aggressive mode failure. Port will be error disabled.";
      }
      enum udld-state-aggr-mod-fail-no-err-dis {
        value 5;
        description
          "Aggressive mode failure but port will not be error disabled, it is still in connected state.";
      }
    }
    description
      "Get the link state of the port";
  }

  typedef udld-event-type {
    type enumeration {
      enum udld-port-unknown-event {
        value 0;
        description
          "Unknown event type.";
      }
      enum udld-port-dis {
        value 1;
        description
          "Port is disabled";
      }
      enum udld-port-fail {
        value 2;
        description
          "Port is failed and cannot send unidirectional link detection packets to other devices.";
      }
      enum udld-port-alrt-fail {
        value 3;
        description
          "Port is configured for alert mode only.";
      }
    }
    description
      "Unidirectional event type";
  }

  grouping udld-interface-event {
    description
      "Event details when unidirectional link is detected.";
    leaf if-name {
      type string;
      description
        "Interface of the device where event has occurred.";
    }
    leaf neighbor-id {
      type string;
      description
        "Neighbor id connected to the device.";
    }
    leaf port-blocked {
      type boolean;
      description
        "Port is blocked or not.";
    }
    leaf neighbor-port {
      type string;
      description
        "Neighbor port connected to the device.";
    }
    leaf state {
      type udld-ios-xe-events:udld-link-state;
      description
        "Link state of the connected neighbors.";
    }
    leaf event-type {
      type udld-ios-xe-events:udld-event-type;
      description
        "Event type of unidirectional link detection protocol.";
    }
  }

  notification udld-intf-event {
    description
      "Unidirectional link detection event notification.";
    uses udld-ios-xe-events:udld-interface-event;
  }
}
