module cisco-policy-target {
  yang-version 1;
  namespace "urn:ietf:params:xml:ns:yang:cisco-policy-target";
  prefix cisco-policy-target;

  import cisco-semver {
    prefix cisco-semver;
  }
  import ietf-interfaces {
    prefix if;
  }
  import ietf-diffserv-target {
    prefix ietf-target;
  }
  import policy-types {
    prefix policy-types;
  }

  organization
    "Cisco Systems, Inc.";
  contact
    "Cisco Systems, Inc.
     Customer Service

     Postal: 170 W Tasman Drive
     San Jose, CA 95134

     Tel: +1 1800 553-NETS

     E-mail: cs-yang@cisco.com

     Editor:   Nazanin Magharei
               <mailto:nmaghare@cisco.com>";
  description
    "This module contains a collection of YANG definitions
     extending policy activation module based on IETF-diffserv
     target.
     Copyright (c) 2016 by Cisco Systems, Inc.
     All rights reserved.";

  revision 2019-07-01 {
    description
      "Establish semantic version baseline";
    cisco-semver:module-version "1.0.0";
  }
  revision 2016-03-30 {
    description
      "Update description with copyright notice.";
  }
  revision 2015-04-27 {
    description
      "First revision";
    reference
      "TBD";
  }

  augment "/if:interfaces/if:interface/ietf-target:diffserv-target-entry" {
    description
      "Augment policy type entry to Diffserv Target Entry";
    leaf service-policy-type {
      type identityref {
        base policy-types:policy-type;
      }
      default "policy-types:qos";
      description
        "Type of the service-policy";
    }
  }
}
