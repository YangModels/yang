module Cisco-IOS-XE-ngfw-actions-rpc {
  yang-version 1.1;
  namespace "http://cisco.com/ns/yang/Cisco-IOS-XE-ngfw-actions-rpc";
  prefix ngfw-actions-rpc;

  import Cisco-IOS-XE-ngfw-common-oper {
    prefix ngfw-common-ios-xe-oper;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     Next-Generation Firewall (NGFW) RPC.
     Copyright (c) 2025-2026 by Cisco Systems, Inc.
     All rights reserved.";

  revision 2026-08-01 {
    description
      "Initial revision";
    reference
      "1.0.0";
    cisco-semver:module-version "1.0.0";
  }

  grouping ngfw-upd-file-type {
    description
      "Next-Generation Firewall (NGFW) update file related grouping";
    leaf type {
      type ngfw-common-ios-xe-oper:ngfw-update-type-val;
      mandatory true;
      description
        "Specifies the Next-Generation Firewall (NGFW) update type, either LSP or VDB.";
    }
    leaf file-name {
      type string {
        length "1..255";
        pattern '(bootflash:|flash:|harddisk:)[-A-Za-z_.0-9/]*' {
          error-message "Invalid filename. Must be in format 'bootflash:/path/file', 'flash:/path/file', or 'harddisk:/path/file'";
          error-app-tag "invalid-ngfw-filename";
        }
      }
      mandatory true;
      description
        "Next-Generation Firewall (NGFW) file name";
    }
  }

  grouping ngfw-cust-sig-prof-type {
    description
      "Defines input fields for RPCs that operate on an NGFW custom-signature profile.";
    leaf profile-name {
      type string {
        length "1..128";
        pattern '[-A-Za-z_0-9]+' {
          error-message "Invalid profile name";
          error-app-tag "invalid-ngfw-custom-sig-profile-name";
        }
      }
      mandatory true;
      description
        "Specifies the NGFW custom-signature profile name used by the RPC.";
    }
    leaf file-name {
      type string {
        length "1..128";
        pattern '((boot)?flash|harddisk):[/A-Za-z0-9_-]+\.(rules|txt)' {
          error-message "Invalid file name. Must be in format 'bootflash:/path/file', or 'flash:/path/file' with a '.rules' or '.txt' extension";
          error-app-tag "invalid-ngfw-custom-sig-file-name";
        }
      }
      description
        "Specifies the path to the custom-signature file used by the RPC.";
    }
  }

  grouping ngfw-cust-sig-file-type {
    description
      "Defines input fields for RPCs that operate on an NGFW custom-signature file.";
    leaf file-name {
      type string {
        length "1..128";
        pattern '((boot)?flash|harddisk):[/A-Za-z0-9_-]+\.(rules|txt)' {
          error-message "Invalid file name. Must be in format 'bootflash:/path/file', or 'flash:/path/file' with a '.rules' or '.txt' extension";
          error-app-tag "invalid-ngfw-custom-sig-file-name";
        }
      }
      description
        "Specifies the path to the custom-signature file used by the RPC.";
    }
  }

  rpc ngfw-upd-file {
    description
      "Next-Generation Firewall (NGFW) update file action RPC.";
    input {
      uses ngfw-actions-rpc:ngfw-upd-file-type;
    }
  }

  rpc ngfw-cust-sig-apply {
    description
      "Applies a custom-signature file to an NGFW profile.";
    input {
      uses ngfw-actions-rpc:ngfw-cust-sig-prof-type;
    }
  }

  rpc ngfw-cust-sig-load {
    description
      "Loads a custom-signature file for an NGFW profile.";
    input {
      uses ngfw-actions-rpc:ngfw-cust-sig-prof-type;
    }
  }

  rpc ngfw-cust-sig-valdt {
    description
      "Validates a custom-signature file for NGFW.";
    input {
      uses ngfw-actions-rpc:ngfw-cust-sig-file-type;
    }
  }

  rpc ngfw-cust-sig-glbl-apply {
    description
      "Applies a custom-signature file globally in NGFW.";
    input {
      uses ngfw-actions-rpc:ngfw-cust-sig-file-type;
    }
  }

  rpc ngfw-cust-sig-glbl-load {
    description
      "Loads a custom-signature file globally in NGFW.";
    input {
      uses ngfw-actions-rpc:ngfw-cust-sig-file-type;
    }
  }
}
