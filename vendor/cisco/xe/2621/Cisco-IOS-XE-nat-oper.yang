module Cisco-IOS-XE-nat-oper {
  yang-version 1.1;
  namespace "http://cisco.com/ns/yang/Cisco-IOS-XE-nat-oper";
  prefix nat-ios-xe-oper;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for NAT operational data.
     Copyright (c) 2017-2019, 2022, 2026 by Cisco Systems, Inc.
     All rights reserved.";

  revision 2026-08-01 {
    description
      "Updated descriptions for several model elements to clarify their meaning and purpose.";
    reference
      "2.3.1";
    cisco-semver:module-version "2.3.1";
  }
  revision 2022-11-01 {
    description
      "Update yang-version to 1.1";
    reference
      "2.3.0";
    cisco-semver:module-version "2.3.0";
  }
  revision 2019-05-01 {
    description
      "Added semantic version";
    reference
      "2.2.0";
    cisco-semver:module-version "2.2.0";
  }
  revision 2018-10-29 {
    description
      "Cleaned up spelling errors in descriptions.";
    reference
      "2.1.0";
    cisco-semver:module-version "2.1.0";
  }
  revision 2018-03-17 {
    description
      "The second generally available version";
    reference
      "2.0.0";
    cisco-semver:module-version "2.0.0";
  }
  revision 2017-11-01 {
    description
      "Initial revision";
    reference
      "1.0.0";
    cisco-semver:module-version "1.0.0";
  }

  grouping ip-nat-statistics {
    description
      "ip nat global statistics";
    leaf initialized {
      type boolean;
      description
        "Indicates if the NAT feature has been initialized";
    }
    leaf entries {
      type uint64;
      description
        "Total number of NAT translation entries currently present";
    }
    leaf statics {
      type uint64;
      description
        "Total static translations";
    }
    leaf-list statics-sorted {
      type uint64;
      max-elements 4;
      ordered-by user;
      description
        "Sorted static translations by domain";
    }
    leaf flows {
      type uint64;
      description
        "Total number of active NAT flows";
    }
    leaf insides {
      type uint64;
      description
        "Number of inside interfaces";
    }
    leaf outsides {
      type uint64;
      description
        "Number of outside interfaces";
    }
    leaf entry-timeouts {
      type uint64;
      description
        "Number of entries which timed out ";
    }
    leaf hits {
      type uint64;
      description
        "Successful searches with matching NAT session";
    }
    leaf misses {
      type uint64;
      description
        "Unsuccessful searches without matching NAT session";
    }
    leaf interrupt-switched {
      type uint64;
      description
        "Translated in interrupt switching";
    }
    leaf packets-punted {
      type uint64;
      description
        "Packets punted to process";
    }
    leaf frag-pak-count {
      type uint64;
      description
        "Counter for saved fragment packets";
    }
    leaf pool-stats-drop {
      type uint64;
      description
        "Number of NAT pool statistics entries dropped by the platform due to resource limitations or errors.";
    }
    leaf mapping-stats-drop {
      type uint64;
      description
        "Number of NAT mapping statistics entries dropped by the platform due to resource constraints or errors.";
    }
    leaf portlist-req-fail {
      type uint64;
      description
        "Counter for port block allocation request failures";
    }
    leaf ipalias-add-fail {
      type uint64;
      description
        "Counter for failed attempts to add IP aliases in NAT processing.";
    }
    leaf limit-entry-add-fail {
      type uint64;
      description
        "Counter for failed attempts to add limit entries in NAT processing.";
    }
    leaf in2out-drops {
      type uint64;
      description
        "Counter for NAT inside->outside drops";
    }
    leaf out2in-drops {
      type uint64;
      description
        "Counter for NAT outside->inside drops";
    }
    leaf mib-addr-binds {
      type uint32;
      description
        "MIB counter for address binds";
    }
    leaf mib-addport-binds {
      type uint32;
      description
        "MIB counter for address port binds";
    }
  }

  grouping nat-translation-key {
    description
      "NAT translation key";
    leaf inside-local-addr {
      type inet:ipv4-address;
      description
        "Inside local address";
    }
    leaf outside-local-addr {
      type inet:ipv4-address;
      description
        "Outside local address";
    }
    leaf inside-local-port {
      type uint16;
      description
        "Inside local port";
    }
    leaf outside-local-port {
      type uint16;
      description
        "Outside local port";
    }
    leaf vrfid {
      type uint16;
      description
        "VRF ID";
    }
    leaf protocol {
      type uint8;
      description
        "IP protocol number (such as 6 (TCP), 17 (UDP), or 1 (ICMP)) associated with this NAT translation.";
    }
  }

  grouping nat-translation-param {
    description
      "NAT translation parameters";
    leaf inside-global-addr {
      type inet:ipv4-address;
      description
        "The global IP address assigned to a device on the inside network by NAT for external communication.";
    }
    leaf outside-global-addr {
      type inet:ipv4-address;
      description
        "The IP address of an external device as it appears to the inside network after NAT translation.";
    }
    leaf inside-global-port {
      type uint16;
      description
        "The port number assigned by NAT to represent the inside local port on the global network.";
    }
    leaf outside-global-port {
      type uint16;
      description
        "The port number used by an external device as it appears to the inside network after NAT translation.";
    }
    leaf flags {
      type uint32;
      description
        "Flags indicating specific properties or states of the NAT translation entry.";
    }
    leaf application-type {
      type uint8;
      description
        "Specifies the type of application associated with this NAT translation, such as FTP, SIP, or other protocol-specific applications.";
    }
    leaf vrf-name {
      type string;
      description
        "Virtual Routing and Forwarding name";
    }
  }

  container nat-data {
    config false;
    description
      "Container for all NAT operational statistics and data.";
    container ip-nat-statistics {
      presence "ip-nat-statistics";
      description
        "Global NAT statistics";
      uses nat-ios-xe-oper:ip-nat-statistics;
    }
    list ip-nat-translation {
      key "inside-local-addr outside-local-addr inside-local-port outside-local-port vrfid protocol";
      description
        "List of current IP NAT translation entries, each representing a mapping between inside and outside addresses and ports.";
      uses nat-ios-xe-oper:nat-translation-param;
      uses nat-ios-xe-oper:nat-translation-key;
    }
  }
}
