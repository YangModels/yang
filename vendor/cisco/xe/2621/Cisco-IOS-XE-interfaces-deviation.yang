module Cisco-IOS-XE-interfaces-deviation {
  yang-version 1.1;
  namespace "http://cisco.com/ns/yang/Cisco-IOS-XE-interfaces-deviation";
  prefix ios-interfaces-d;

  import Cisco-IOS-XE-native {
    prefix ios;
  }
  import cisco-semver {
    prefix cisco-semver;
  }

  organization
    "Cisco Systems";
  description
    "Cisco XE Interfaces Deviation YANG module for IOS
     Copyright (c) 2024 by Cisco Systems, Inc.
     All rights reserved.";

  revision 2026-08-01 {
    description
      "- Added interface deviations for ip-forward feature";
    cisco-semver:module-version "1.2.0";
  }
  revision 2025-07-01 {
    description
      "Added MTU range for cellular interfaces";
    cisco-semver:module-version "1.1.0";
  }
  revision 2024-07-01 {
    description
      "Make shutdown leaf not supported for L2LISP-subinterface";
    cisco-semver:module-version "1.0.0";
  }

  deviation "/ios:native/ios:interface/ios:L2LISP-subinterface/ios:L2LISP/ios:shutdown" {
    deviate not-supported;
  }

  deviation "/ios:native/ios:interface/ios:LISP-subinterface/ios:LISP/ios:vrf-choice/ios:vrf/ios:vrf/ios:forwarding" {
    deviate delete {
      must '/ios:native/ios:vrf/ios:definition[ios:name=current()]' {
        error-message "VRF must be created 1st, deleted last";
      }
    }
  }

  deviation "/ios:native/ios:interface/ios:Cellular/ios:mtu" {
    deviate replace {
      type uint16 {
        range "64..2000";
      }
    }
  }

  deviation "/ios:native/ios:interface/ios:AppNav-Compress/ios:ip/ios:address-choice/ios:forward/ios:forward" {
    deviate not-supported;
  }

  deviation "/ios:native/ios:interface/ios:AppNav-UnCompress/ios:ip/ios:address-choice/ios:forward/ios:forward" {
    deviate not-supported;
  }

  deviation "/ios:native/ios:interface/ios:ATM/ios:ip/ios:address-choice/ios:forward/ios:forward" {
    deviate not-supported;
  }

  deviation "/ios:native/ios:interface/ios:ATM-subinterface/ios:ATM/ios:ip/ios:address-choice/ios:forward/ios:forward" {
    deviate not-supported;
  }

  deviation "/ios:native/ios:interface/ios:BDI/ios:ip/ios:address-choice/ios:forward/ios:forward" {
    deviate not-supported;
  }

  deviation "/ios:native/ios:interface/ios:Embedded-Service-Engine/ios:ip/ios:address-choice/ios:forward/ios:forward" {
    deviate not-supported;
  }

  deviation "/ios:native/ios:interface/ios:ucse/ios:ip/ios:address-choice/ios:forward/ios:forward" {
    deviate not-supported;
  }

  deviation "/ios:native/ios:interface/ios:Ethernet-Internal/ios:ip/ios:address-choice/ios:forward/ios:forward" {
    deviate not-supported;
  }

  deviation "/ios:native/ios:interface/ios:Service-Engine/ios:ip/ios:address-choice/ios:forward/ios:forward" {
    deviate not-supported;
  }

  deviation "/ios:native/ios:interface/ios:AppGigabitEthernet/ios:ip/ios:address-choice/ios:forward/ios:forward" {
    deviate not-supported;
  }

  deviation "/ios:native/ios:interface/ios:Loopback/ios:ip/ios:address-choice/ios:forward/ios:forward" {
    deviate not-supported;
  }

  deviation "/ios:native/ios:interface/ios:LORAWAN/ios:ip/ios:address-choice/ios:forward/ios:forward" {
    deviate not-supported;
  }

  deviation "/ios:native/ios:interface/ios:WPAN/ios:ip/ios:address-choice/ios:forward/ios:forward" {
    deviate not-supported;
  }

  deviation "/ios:native/ios:interface/ios:Virtual-WPAN/ios:ip/ios:address-choice/ios:forward/ios:forward" {
    deviate not-supported;
  }

  deviation "/ios:native/ios:interface/ios:L2LISP/ios:ip/ios:address-choice/ios:forward/ios:forward" {
    deviate not-supported;
  }

  deviation "/ios:native/ios:interface/ios:L2LISP-subinterface/ios:L2LISP/ios:ip/ios:address-choice/ios:forward/ios:forward" {
    deviate not-supported;
  }

  deviation "/ios:native/ios:interface/ios:LISP/ios:ip/ios:address-choice/ios:forward/ios:forward" {
    deviate not-supported;
  }

  deviation "/ios:native/ios:interface/ios:LISP-subinterface/ios:LISP/ios:ip/ios:address-choice/ios:forward/ios:forward" {
    deviate not-supported;
  }

  deviation "/ios:native/ios:interface/ios:nve/ios:ip/ios:address-choice/ios:forward/ios:forward" {
    deviate not-supported;
  }

  deviation "/ios:native/ios:interface/ios:PRP-channel/ios:ip/ios:address-choice/ios:forward/ios:forward" {
    deviate not-supported;
  }

  deviation "/ios:native/ios:interface/ios:SM/ios:ip/ios:address-choice/ios:forward/ios:forward" {
    deviate not-supported;
  }

  deviation "/ios:native/ios:interface/ios:Cellular/ios:ip/ios:address-choice/ios:forward/ios:forward" {
    deviate not-supported;
  }

  deviation "/ios:native/ios:interface/ios:Dialer/ios:ip/ios:address-choice/ios:forward/ios:forward" {
    deviate not-supported;
  }

  deviation "/ios:native/ios:interface/ios:GMPLS/ios:ip/ios:address-choice/ios:forward/ios:forward" {
    deviate not-supported;
  }

  deviation "/ios:native/ios:interface/ios:Group-Async/ios:ip/ios:address-choice/ios:forward/ios:forward" {
    deviate not-supported;
  }

  deviation "/ios:native/ios:interface/ios:Multilink/ios:ip/ios:address-choice/ios:forward/ios:forward" {
    deviate not-supported;
  }

  deviation "/ios:native/ios:interface/ios:Serial/ios:ip/ios:address-choice/ios:forward/ios:forward" {
    deviate not-supported;
  }

  deviation "/ios:native/ios:interface/ios:Async/ios:ip/ios:address-choice/ios:forward/ios:forward" {
    deviate not-supported;
  }

  deviation "/ios:native/ios:interface/ios:Tunnel/ios:ip/ios:address-choice/ios:forward/ios:forward" {
    deviate not-supported;
  }

  deviation "/ios:native/ios:interface/ios:vmi/ios:ip/ios:address-choice/ios:forward/ios:forward" {
    deviate not-supported;
  }

  deviation "/ios:native/ios:interface/ios:Virtual-Template/ios:ip/ios:address-choice/ios:forward/ios:forward" {
    deviate not-supported;
  }

  deviation "/ios:native/ios:interface/ios:Virtual-PPP/ios:ip/ios:address-choice/ios:forward/ios:forward" {
    deviate not-supported;
  }

  deviation "/ios:native/ios:interface/ios:VirtualPortGroup/ios:ip/ios:address-choice/ios:forward/ios:forward" {
    deviate not-supported;
  }

  deviation "/ios:native/ios:interface/ios:vasileft/ios:ip/ios:address-choice/ios:forward/ios:forward" {
    deviate not-supported;
  }

  deviation "/ios:native/ios:interface/ios:vasiright/ios:ip/ios:address-choice/ios:forward/ios:forward" {
    deviate not-supported;
  }

  deviation "/ios:native/ios:interface/ios:Vif/ios:ip/ios:address-choice/ios:forward/ios:forward" {
    deviate not-supported;
  }

  deviation "/ios:native/ios:interface/ios:Wlan-GigabitEthernet/ios:ip/ios:address-choice/ios:forward/ios:forward" {
    deviate not-supported;
  }

  deviation "/ios:native/ios:interface/ios:BD-VIF/ios:ip/ios:address-choice/ios:forward/ios:forward" {
    deviate not-supported;
  }

  deviation "/ios:native/ios:interface/ios:MFR/ios:ip/ios:address-choice/ios:forward/ios:forward" {
    deviate not-supported;
  }

  deviation "/ios:native/ios:interface/ios:Serial-subinterface/ios:Serial/ios:ip/ios:address-choice/ios:forward/ios:forward" {
    deviate not-supported;
  }

  deviation "/ios:native/ios:interface/ios:MFR-subinterface/ios:MFR/ios:ip/ios:address-choice/ios:forward/ios:forward" {
    deviate not-supported;
  }

  deviation "/ios:native/ios:interface/ios:Bundle/ios:ip/ios:address-choice/ios:forward/ios:forward" {
    deviate not-supported;
  }

  deviation "/ios:native/ios:interface/ios:HSR-ring/ios:ip/ios:address-choice/ios:forward/ios:forward" {
    deviate not-supported;
  }
}
