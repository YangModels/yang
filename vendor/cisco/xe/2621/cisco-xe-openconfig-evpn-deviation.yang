module cisco-xe-openconfig-evpn-deviation {
  namespace "http://cisco.com/ns/cisco-xe-openconfig-evpn-deviation";
  prefix oc-evpn-devs;

  import openconfig-network-instance {
    prefix oc-netinst;
  }

  organization
    "Cisco Systems, Inc.";
  contact
    "Cisco Systems, Inc.
     Customer Service

     Postal: 170 W Tasman Drive
     San Jose, CA 95134

     Tel: +1 1800 553-NETS

     E-mail: cs-yang@cisco.com";
  description
    "This module defines deviation statements for openconfig-evpn module.
     Copyright (c) 2024 by Cisco Systems, Inc.
     All rights reserved.";

  revision 2025-07-01 {
    description
      "Disabled vpws service and vni list. Added L2L3 in evpn when statement";
  }
  revision 2025-03-01 {
    description
      "Enabled evpn with some deviations";
  }
  revision 2024-07-01 {
    description
      "Removed vxlan deviation";
  }
  revision 2023-11-01 {
    description
      "Initial Revision";
  }

  deviation "/oc-netinst:network-instances/oc-netinst:network-instance/oc-netinst:evpn/oc-netinst:evpn-instances/oc-netinst:evpn-instance/oc-netinst:config/oc-netinst:encapsulation-type" {
    deviate not-supported;
    description
      "XE supports only operational model";
  }

  deviation "/oc-netinst:network-instances/oc-netinst:network-instance/oc-netinst:evpn/oc-netinst:evpn-instances/oc-netinst:evpn-instance/oc-netinst:config/oc-netinst:multicast-group" {
    deviate not-supported;
    description
      "XE supports only operational model";
  }

  deviation "/oc-netinst:network-instances/oc-netinst:network-instance/oc-netinst:evpn/oc-netinst:evpn-instances/oc-netinst:evpn-instance/oc-netinst:config/oc-netinst:multicast-mask" {
    deviate not-supported;
    description
      "XE supports only operational model";
  }

  deviation "/oc-netinst:network-instances/oc-netinst:network-instance/oc-netinst:evpn/oc-netinst:evpn-instances/oc-netinst:evpn-instance/oc-netinst:config/oc-netinst:replication-mode" {
    deviate not-supported;
    description
      "XE supports only operational model";
  }

  deviation "/oc-netinst:network-instances/oc-netinst:network-instance/oc-netinst:evpn/oc-netinst:evpn-instances/oc-netinst:evpn-instance/oc-netinst:config/oc-netinst:route-distinguisher" {
    deviate not-supported;
    description
      "XE supports only operational model";
  }

  deviation "/oc-netinst:network-instances/oc-netinst:network-instance/oc-netinst:evpn/oc-netinst:evpn-instances/oc-netinst:evpn-instance/oc-netinst:config/oc-netinst:control-word-enabled" {
    deviate not-supported;
    description
      "XE supports only operational model";
  }

  deviation "/oc-netinst:network-instances/oc-netinst:network-instance/oc-netinst:evpn/oc-netinst:evpn-instances/oc-netinst:evpn-instance/oc-netinst:config/oc-netinst:local-vpws-service-id" {
    deviate not-supported;
    description
      "XE supports only operational model";
  }

  deviation "/oc-netinst:network-instances/oc-netinst:network-instance/oc-netinst:evpn/oc-netinst:evpn-instances/oc-netinst:evpn-instance/oc-netinst:config/oc-netinst:remote-vpws-service-id" {
    deviate not-supported;
    description
      "XE supports only operational model";
  }

  deviation "/oc-netinst:network-instances/oc-netinst:network-instance/oc-netinst:evpn/oc-netinst:evpn-instances/oc-netinst:evpn-instance/oc-netinst:import-export-policy/oc-netinst:config" {
    deviate not-supported;
    description
      "XE supports only operational model";
  }

  deviation "/oc-netinst:network-instances/oc-netinst:network-instance/oc-netinst:evpn/oc-netinst:evpn-instances/oc-netinst:evpn-instance/oc-netinst:vxlan/oc-netinst:config" {
    deviate not-supported;
    description
      "XE supports only operational model";
  }

  deviation "/oc-netinst:network-instances/oc-netinst:network-instance/oc-netinst:evpn/oc-netinst:evpn-instances/oc-netinst:evpn-instance/oc-netinst:vxlan/oc-netinst:anycast-source-interface" {
    deviate not-supported;
    description
      "Currently not supported";
  }

  deviation "/oc-netinst:network-instances/oc-netinst:network-instance/oc-netinst:evpn/oc-netinst:evpn-instances/oc-netinst:evpn-instance/oc-netinst:state/oc-netinst:multicast-group" {
    deviate not-supported;
    description
      "Currently not supported";
  }

  deviation "/oc-netinst:network-instances/oc-netinst:network-instance/oc-netinst:evpn/oc-netinst:evpn-instances/oc-netinst:evpn-instance/oc-netinst:state/oc-netinst:multicast-mask" {
    deviate not-supported;
    description
      "Currently not supported";
  }

  deviation "/oc-netinst:network-instances/oc-netinst:network-instance/oc-netinst:evpn/oc-netinst:evpn-instances/oc-netinst:evpn-instance/oc-netinst:state/oc-netinst:control-word-enabled" {
    deviate not-supported;
    description
      "Currently not supported";
  }

  deviation "/oc-netinst:network-instances/oc-netinst:network-instance/oc-netinst:evpn/oc-netinst:evpn-instances/oc-netinst:evpn-instance/oc-netinst:state/oc-netinst:local-vpws-service-id" {
    deviate not-supported;
    description
      "Currently not supported";
  }

  deviation "/oc-netinst:network-instances/oc-netinst:network-instance/oc-netinst:evpn/oc-netinst:evpn-instances/oc-netinst:evpn-instance/oc-netinst:state/oc-netinst:remote-vpws-service-id" {
    deviate not-supported;
    description
      "Currently not supported";
  }

  deviation "/oc-netinst:network-instances/oc-netinst:network-instance/oc-netinst:evpn/oc-netinst:evpn-instances/oc-netinst:evpn-instance/oc-netinst:vxlan/oc-netinst:state/oc-netinst:vni-list" {
    deviate not-supported;
    description
      "Currently not supported";
  }

  deviation "/oc-netinst:network-instances/oc-netinst:network-instance/oc-netinst:evpn/oc-netinst:evpn-instances/oc-netinst:evpn-instance/oc-netinst:vxlan/oc-netinst:state/oc-netinst:multicast-mask" {
    deviate not-supported;
    description
      "Currently not supported";
  }

  deviation "/oc-netinst:network-instances/oc-netinst:network-instance/oc-netinst:evpn/oc-netinst:evpn-instances/oc-netinst:evpn-instance/oc-netinst:pbb" {
    deviate not-supported;
    description
      "Currently not supported";
  }

  deviation "/oc-netinst:network-instances/oc-netinst:network-instance/oc-netinst:connection-points/oc-netinst:connection-point/oc-netinst:endpoints/oc-netinst:endpoint/oc-netinst:vxlan/oc-netinst:config" {
    deviate not-supported;
    description
      "XE supports only operational model";
  }

  deviation "/oc-netinst:network-instances/oc-netinst:network-instance/oc-netinst:connection-points/oc-netinst:connection-point/oc-netinst:endpoints/oc-netinst:endpoint/oc-netinst:vxlan/oc-netinst:endpoint-peers/oc-netinst:endpoint-peer/oc-netinst:state/oc-netinst:counters" {
    deviate not-supported;
    description
      "Currently not supported";
  }

  deviation "/oc-netinst:network-instances/oc-netinst:network-instance/oc-netinst:connection-points/oc-netinst:connection-point/oc-netinst:endpoints/oc-netinst:endpoint/oc-netinst:vxlan/oc-netinst:endpoint-vnis/oc-netinst:endpoint-vni/oc-netinst:ipv4" {
    deviate not-supported;
    description
      "Currently not supported";
  }

  deviation "/oc-netinst:network-instances/oc-netinst:network-instance/oc-netinst:connection-points/oc-netinst:connection-point/oc-netinst:endpoints/oc-netinst:endpoint/oc-netinst:vxlan/oc-netinst:endpoint-vnis/oc-netinst:endpoint-vni/oc-netinst:ipv6" {
    deviate not-supported;
    description
      "Currently not supported";
  }

  deviation "/oc-netinst:network-instances/oc-netinst:network-instance/oc-netinst:connection-points/oc-netinst:connection-point/oc-netinst:endpoints/oc-netinst:endpoint/oc-netinst:vxlan/oc-netinst:local-endpoint-vnis" {
    deviate not-supported;
    description
      "Currently not supported";
  }
}
