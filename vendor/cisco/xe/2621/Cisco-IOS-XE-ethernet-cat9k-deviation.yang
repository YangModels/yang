module Cisco-IOS-XE-ethernet-cat9k-deviation {
  yang-version 1.1;
  namespace "http://cisco.com/ns/yang/Cisco-IOS-XE-ethernet-cat9k-deviation";
  prefix ios-ethernet-d;

  import Cisco-IOS-XE-native {
    prefix ios;
  }
  import Cisco-IOS-XE-ethernet {
    prefix ios-eth;
  }

  organization
    "Cisco Systems";
  description
    "Cisco XE Native Deviation YANG module for IOS
     Copyright (c) 2020 by Cisco Systems, Inc.
     All rights reserved.";

  revision 2026-02-01 {
    description
      "- Add deviation file to Cat9k";
  }

  deviation "/ios:native/ios:interface/ios:Port-channel/ios-eth:lacp/ios-eth:max-bundle" {
    deviate replace {
      type uint8 {
        range "1..8";
      }
    }
  }
}
