module Cisco-IOS-XE-wireless-general-oper {
  yang-version 1.1;
  namespace "http://cisco.com/ns/yang/Cisco-IOS-XE-wireless-general-oper";
  prefix wireless-general-oper;

  import Cisco-IOS-XE-wireless-enum-types {
    prefix wireless-enum-types;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for general operational data.
     Copyright (c) 2017, 2019, 2022 by Cisco Systems, Inc.
     All rights reserved.";

  revision 2026-08-01 {
    description
      "Modified the descriptions of few leafs";
    reference
      "1.2.1";
    cisco-semver:module-version "1.2.1";
  }
  revision 2022-11-01 {
    description
      "Update yang-version to 1.1";
    reference
      "1.2.0";
    cisco-semver:module-version "1.2.0";
  }
  revision 2019-05-01 {
    description
      "- Add MFP stats container.
       - Added semantic version";
    reference
      "1.1.0";
    cisco-semver:module-version "1.1.0";
  }
  revision 2018-09-04 {
    description
      "Initial revision";
    reference
      "1.0.0";
    cisco-semver:module-version "1.0.0";
  }

  typedef mfp-event-frames {
    type bits {
      bit mfp-frame-assoc-req {
        position 0;
        description
          "Association request frame";
      }
      bit mfp-frame-assoc-resp {
        position 1;
        description
          "Association response frame";
      }
      bit mfp-frame-reassoc-req {
        position 2;
        description
          "Reassociation request frame";
      }
      bit mfp-frame-reassoc-resp {
        position 3;
        description
          "Reassociation response frame";
      }
      bit mfp-frame-probe-req {
        position 4;
        description
          "Probe request frame";
      }
      bit mfp-frame-probe-resp {
        position 5;
        description
          "Probe response frame";
      }
      bit mfp-frame-reserved1 {
        position 6;
        description
          "Reserved";
      }
      bit mfp-frame-reserved2 {
        position 7;
        description
          "Reserved";
      }
      bit mfp-frame-beacon {
        position 8;
        description
          "Beacon frame";
      }
      bit mfp-frame-atim {
        position 9;
        description
          "ATIM frame";
      }
      bit mfp-frame-disassoc {
        position 10;
        description
          "Disassociation frame";
      }
      bit mfp-frame-auth {
        position 11;
        description
          "Authentication frame";
      }
      bit mfp-frame-deauth {
        position 12;
        description
          "Deauthentication frame";
      }
      bit mfp-frame-action {
        position 13;
        description
          "Action frame";
      }
      bit mfp-frame-aes-notify {
        position 14;
        description
          "AES notify frame";
      }
    }
    description
      "MFP event frame types";
  }

  grouping st-mfp-event {
    description
      "MFP event";
    leaf count {
      type uint32;
      description
        "Number of occurrences of this event";
    }
    leaf event {
      type wireless-enum-types:mfp-event;
      description
        "Specifies the type of Management Frame Protection (MFP) event detected for the associated BSSID, such as authentication, deauthentication, or association events.";
    }
    leaf frames {
      type wireless-general-oper:mfp-event-frames;
      description
        "List of frames seen with this event";
    }
  }

  grouping st-mfp-stats {
    description
      "MFP stats data";
    leaf bssid {
      type yang:mac-address;
      description
        "BSSID detected as anomalous";
    }
    leaf wtp-mac {
      type yang:mac-address;
      description
        "Last AP's mac which detected the anomaly";
    }
    leaf last-src-mac-addr {
      type yang:mac-address;
      description
        "Last source mac address";
    }
    leaf ap-name {
      type string;
      description
        "Name of the access point (AP) that detected the anomalous event.";
    }
    leaf slot-id {
      type wireless-enum-types:slot-id-type;
      description
        "Slot number of the access point (AP) radio that detected the anomaly.";
    }
    leaf radio-type {
      type wireless-enum-types:enm-radio-type;
      description
        "Type of radio (e.g., 2.4 GHz, 5 GHz) on the access point (AP) that detected the anomaly.";
    }
    leaf last-report-time {
      type uint32;
      description
        "Last report time, seconds from system boot";
    }
    list event {
      max-elements 4;
      description
        "Information about specific Management Frame Protection (MFP) events detected for the anomalous BSSID.";
      uses wireless-general-oper:st-mfp-event;
    }
  }

  grouping st-wlmgmt-ipv6 {
    description
      "Controller management interface IPv6 information";
    leaf addr {
      type inet:ip-prefix;
      description
        "Controller management interface IPv6 prefix";
    }
  }

  grouping st-wlmgmt-intf {
    description
      "Controller management interface information";
    leaf intf-name {
      type string;
      description
        "Controller management interface name";
    }
    leaf intf-type {
      type string;
      description
        "Controller management interface type";
    }
    leaf intf-id {
      type uint32;
      description
        "Controller management interface id";
    }
    leaf mgmt-ip {
      type inet:ipv4-address;
      description
        "Controller management IPv4 address";
    }
    leaf net-mask {
      type inet:ipv4-address;
      description
        "Controller management interface netmask";
    }
    leaf mgmt-mac {
      type yang:mac-address;
      description
        "Controller management interface MAC";
    }
    list interface-ipv6-list {
      key "addr";
      description
        "Controller management interface IPv6 information";
      uses wireless-general-oper:st-wlmgmt-ipv6;
    }
  }

  container general-oper-data {
    config false;
    description
      "Controller general operational data";
    container mgmt-intf-data {
      presence "mgmt-intf-data";
      description
        "Controller wireless interface data";
      uses wireless-general-oper:st-wlmgmt-intf;
    }
    list mfp-stats {
      key "bssid";
      description
        "List of Management Frame Protection (MFP) statistics detected by the controller, including information about anomalous BSSIDs and related events.";
      uses wireless-general-oper:st-mfp-stats;
    }
  }
}
