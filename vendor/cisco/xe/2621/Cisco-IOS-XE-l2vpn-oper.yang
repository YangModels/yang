module Cisco-IOS-XE-l2vpn-oper {
  yang-version 1.1;
  namespace "http://cisco.com/ns/yang/Cisco-IOS-XE-l2vpn-oper";
  prefix l2vpn-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for L2VPN services operational data.
     Copyright (c) 2022-2026 by Cisco Systems, Inc.
     All rights reserved.";

  revision 2026-08-01 {
    description
      "Updated descriptions of several model elements to clarify their meaning and purpose.";
    reference
      "1.1.1";
    cisco-semver:module-version "1.1.1";
  }
  revision 2023-03-01 {
    description
      "- Added more detailed PW info to the l2vpn-atom-vc-data
       - Added MAC withdraw counters to VC statistics";
    reference
      "1.1.0";
    cisco-semver:module-version "1.1.0";
  }
  revision 2022-11-01 {
    description
      "Initial revision";
    reference
      "1.0.0";
    cisco-semver:module-version "1.0.0";
  }

  typedef l2vpn-service-type {
    type enumeration {
      enum l2vpn-service-invalid {
        value 0;
        description
          "Invalid L2VPN service type.";
      }
      enum l2vpn-service-vpws {
        value 1;
        description
          "L2VPN service type Virtual Private Wire Service (VPWS).";
      }
      enum l2vpn-service-vpls {
        value 2;
        description
          "L2VPN service type Virtual Private LAN Service (VPLS).";
      }
      enum l2vpn-service-transport {
        value 3;
        description
          "L2VPN service type Transport.";
      }
      enum l2vpn-service-bd {
        value 4;
        description
          "L2VPN service type Bridge Domain (BD).";
      }
      enum l2vpn-service-evpn {
        value 5;
        description
          "L2VPN service type Ethernet Virtual Private Network (EVPN).";
      }
    }
    description
      "L2VPN service type.";
  }

  typedef l2vpn-ac-circuit-type {
    type enumeration {
      enum ac-circuit-invalid {
        value 0;
        description
          "Invalid attachment circuit type";
      }
      enum ac-circuit-fr-dlci {
        value 1;
        description
          "L2VPN attachment circuit type Frame Relay (FR) Data Link Connection Identifier (DLCI).";
      }
      enum ac-circuit-fr-dlci-local {
        value 2;
        description
          "L2VPN attachment circuit type Frame Relay (FR) Data Link Connection Identifier (DLCI) local.";
      }
      enum ac-circuit-atm-aal5 {
        value 3;
        description
          "L2VPN attachment circuit type Asynchronous Transfer Mode (ATM) Adaptation Layer 5 (AAL5).";
      }
      enum ac-circuit-atm-cell {
        value 4;
        description
          "L2VPN attachment circuit type Asynchronous Transfer Mode (ATM) cell.";
      }
      enum ac-circuit-ether-vlan {
        value 5;
        description
          "L2VPN attachment circuit type Ethernet VLAN.";
      }
      enum ac-circuit-ether {
        value 6;
        description
          "L2VPN attachment circuit type Ethernet.";
      }
      enum ac-circuit-hdlc {
        value 7;
        description
          "L2VPN attachment circuit type High-Level Data Link Control (HDLC).";
      }
      enum ac-circuit-ppp {
        value 8;
        description
          "L2VPN attachment circuit type Point-to-Point Protocol (PPP).";
      }
      enum ac-circuit-cem {
        value 9;
        description
          "L2VPN attachment circuit type Circuit Emulation (CEM).";
      }
      enum ac-circuit-atm-vcc-cell {
        value 10;
        description
          "L2VPN attachment circuit type Asynchronous Transfer Mode (ATM) Virtual Channel Connection (VCC) cell.";
      }
      enum ac-circuit-atm-vpc-cell {
        value 11;
        description
          "L2VPN attachment circuit type Asynchronous Transfer Mode (ATM) Virtual Path Connection (VPC) cell.";
      }
      enum ac-circuit-ip {
        value 12;
        description
          "L2VPN attachment circuit type IP.";
      }
      enum ac-circuit-vfi {
        value 13;
        description
          "L2VPN attachment circuit type Virtual Forwarding Instance (VFI).";
      }
      enum ac-circuit-satop-e1 {
        value 15;
        description
          "L2VPN attachment circuit type Structure-Agnostic TDM over Packet (SAToP) E1.";
      }
      enum ac-circuit-satop-t1 {
        value 16;
        description
          "L2VPN attachment circuit type Structure-Agnostic TDM over Packet (SAToP) T1.";
      }
      enum ac-circuit-satop-e3 {
        value 17;
        description
          "L2VPN attachment circuit type Structure-Agnostic TDM over Packet (SAToP) E3.";
      }
      enum ac-circuit-satop-t3 {
        value 18;
        description
          "L2VPN attachment circuit type Structure-Agnostic TDM over Packet (SAToP) T3.";
      }
      enum ac-circuit-ces-psn-basic {
        value 19;
        description
          "L2VPN attachment circuit type Circuit Emulation Service over Packet Switched Network (CES PSN) basic.";
      }
      enum ac-circuit-ces-psn-cas {
        value 20;
        description
          "L2VPN attachment circuit type Circuit Emulation Service over Packet Switched Network (CES PSN) Channel Associated Signaling (CAS).";
      }
      enum ac-circuit-atm-vc-unknown {
        value 21;
        description
          "L2VPN attachment circuit type Asynchronous Transfer Mode (ATM) Virtual Circuit (VC) unknown.";
      }
      enum ac-circuit-atm-vp-unknown {
        value 22;
        description
          "L2VPN attachment circuit type Asynchronous Transfer Mode (ATM) Virtual Path (VP) unknown.";
      }
      enum ac-circuit-atom {
        value 23;
        description
          "L2VPN attachment circuit type Any Transport over MPLS (ATOM).";
      }
      enum ac-circuit-l2tpv2 {
        value 24;
        description
          "L2VPN attachment circuit type Layer 2 Tunneling Protocol Version 2 (L2TPv2).";
      }
      enum ac-circuit-l2tpv3 {
        value 25;
        description
          "L2VPN attachment circuit type Layer 2 Tunneling Protocol Version 3 (L2TPv3).";
      }
      enum ac-circuit-pw-udp {
        value 26;
        description
          "L2VPN attachment circuit type Pseudowire (PW) over UDP.";
      }
      enum ac-circuit-dossis {
        value 27;
        description
          "L2VPN attachment circuit type Data Over Cable Service Interface Specification (DOCSIS).";
      }
      enum ac-circuit-dossis-vlan {
        value 28;
        description
          "L2VPN attachment circuit type Data Over Cable Service Interface Specification (DOCSIS) VLAN.";
      }
    }
    description
      "L2VPN attachment circuit type.";
  }

  typedef l2vpn-pw-encap-type {
    type enumeration {
      enum l2vpn-pw-encap-invalid {
        value 0;
        description
          "Invalid L2VPN PW encapsulation type.";
      }
      enum l2vpn-pw-encap-l2tpv3 {
        value 1;
        description
          "L2VPN PW encapsulation type Layer 2 Tunneling Protocol Version 3 (L2TPv3).";
      }
      enum l2vpn-pw-encap-l2tpv2 {
        value 2;
        description
          "L2VPN PW encapsulation type Layer 2 Tunneling Protocol Version 2 (L2TPv2).";
      }
      enum l2vpn-pw-encap-mpls {
        value 3;
        description
          "L2VPN PW encapsulation type Multiprotocol Label Switching (MPLS).";
      }
      enum l2vpn-pw-encap-udp {
        value 4;
        description
          "L2VPN PW encapsulation type UDP.";
      }
    }
    description
      "L2VPN pseudowire (PW) encapsulation type.";
  }

  typedef l2vpn-xconnect-segment-state {
    type enumeration {
      enum xconnect-segment-state-undefined {
        value 0;
        description
          "L2VPN xconnect segment state undefined.";
      }
      enum xconnect-segment-state-up {
        value 1;
        description
          "L2VPN xconnect segment state up.";
      }
      enum xconnect-segment-state-down {
        value 2;
        description
          "L2VPN xconnect segment state down.";
      }
      enum xconnect-segment-state-admin-down {
        value 3;
        description
          "L2VPN xconnect segment state admin down.";
      }
      enum xconnect-segment-state-recovering {
        value 4;
        description
          "L2VPN xconnect segment state recovering.";
      }
      enum xconnect-segment-state-standby {
        value 5;
        description
          "L2VPN xconnect segment state standby.";
      }
      enum xconnect-segment-state-hot-standby {
        value 6;
        description
          "L2VPN xconnect segment state hot standby.";
      }
      enum xconnect-segment-state-inactive {
        value 7;
        description
          "L2VPN xconnect segment state inactive.";
      }
    }
    description
      "L2VPN xconnect segment state.";
  }

  typedef l2vpn-xconnect-state {
    type enumeration {
      enum xconnect-state-undefined {
        value 0;
        description
          "L2VPN xconnect state undefined.";
      }
      enum xconnect-state-up {
        value 1;
        description
          "L2VPN xconnect state up.";
      }
      enum xconnect-state-down {
        value 2;
        description
          "L2VPN xconnect state down.";
      }
      enum xconnect-state-admin-down {
        value 3;
        description
          "L2VPN xconnect state admin down.";
      }
      enum xconnect-state-recovering {
        value 4;
        description
          "L2VPN xconnect state recovering.";
      }
      enum xconnect-state-standby {
        value 5;
        description
          "L2VPN xconnect state standby.";
      }
      enum xconnect-state-hot-standby {
        value 6;
        description
          "L2VPN xconnect state hot standby.";
      }
      enum xconnect-state-incomplete {
        value 7;
        description
          "L2VPN xconnect state incomplete.";
      }
      enum xconnect-state-no-hardware {
        value 8;
        description
          "L2VPN xconnect state no hardware.";
      }
    }
    description
      "L2VPN xconnect state.";
  }

  typedef l2vpn-fwd-type {
    type enumeration {
      enum l2vpn-fwd-type-invalid {
        value 0;
        description
          "Invalid L2VPN forwarder type.";
      }
      enum l2vpn-fwd-type-ac {
        value 1;
        description
          "Attachment circuit (AC).";
      }
      enum l2vpn-fwd-type-pw {
        value 2;
        description
          "L2VPN forwarder type pseudowire (PW).";
      }
      enum l2vpn-fwd-type-vfi {
        value 3;
        description
          "L2VPN forwarder type Virtual Forwarding Instance (VFI).";
      }
      enum l2vpn-fwd-type-bd {
        value 4;
        description
          "L2VPN forwarder type bridge domain (BD).";
      }
    }
    description
      "L2VPN forwarder type.";
  }

  typedef l2vpn-vc-status {
    type enumeration {
      enum l2vpn-vc-undefined {
        value 0;
        description
          "L2VPN VC status undefined.";
      }
      enum l2vpn-vc-up {
        value 1;
        description
          "L2VPN VC status up.";
      }
      enum l2vpn-vc-down {
        value 2;
        description
          "L2VPN VC status down.";
      }
      enum l2vpn-vc-admin-down {
        value 3;
        description
          "L2VPN VC status admin down.";
      }
      enum l2vpn-vc-recovering {
        value 4;
        description
          "L2VPN VC status recovering.";
      }
      enum l2vpn-vc-standby {
        value 5;
        description
          "L2VPN VC status standby.";
      }
      enum l2vpn-vc-hot-standby {
        value 6;
        description
          "L2VPN VC status hot standby.";
      }
      enum l2vpn-vc-state-max {
        value 7;
        description
          "Maximum L2VPN VC status state.";
      }
    }
    description
      "L2VPN virtual circuit (VC) status.";
  }

  typedef l2vpn-atom-service-type {
    type enumeration {
      enum l2vpn-atom-invalid {
        value 0;
        description
          "Invalid L2VPN ATOM service type.";
      }
      enum l2vpn-atom-p2p {
        value 1;
        description
          "L2VPN ATOM service type point-to-point (P2P).";
      }
      enum l2vpn-atom-vfi {
        value 2;
        description
          "L2VPN ATOM service type Virtual Forwarding Instance (VFI).";
      }
      enum l2vpn-atom-transport {
        value 3;
        description
          "L2VPN ATOM service type transport.";
      }
      enum l2vpn-atom-bd {
        value 4;
        description
          "L2VPN ATOM service type Bridge Domain (BD).";
      }
      enum l2vpn-atom-evpn {
        value 5;
        description
          "L2VPN ATOM service type Ethernet Virtual Private Network (EVPN).";
      }
    }
    description
      "L2VPN service type Any Transport over MPLS (ATOM).";
  }

  typedef l2vpn-atom-vc-protocol-type {
    type enumeration {
      enum l2vpn-atom-vc-proto-ldp {
        value 0;
        description
          "L2VPN ATOM VC signaling protocol type Label Distribution Protocol (LDP).";
      }
      enum l2vpn-atom-vc-proto-none {
        value 1;
        description
          "No L2VPN ATOM VC signalling protocol.";
      }
      enum l2vpn-atom-vc-proto-bgp {
        value 2;
        description
          "L2VPN ATOM VC signaling protocol type Border Gateway Protocol (BGP).";
      }
      enum l2vpn-atom-vc-proto-cnt {
        value 3;
        description
          "Invalid L2VPN ATOM VC signaling protocol type.";
      }
    }
    description
      "L2VPN Any Transport over MPLS (ATOM) virtual circuit (VC) signaling protocol type.";
  }

  typedef l2vpn-atom-pw-cw {
    type enumeration {
      enum l2vpn-atom-pw-cw-off {
        value 0;
        description
          "L2VPN ATOM PW control word off.";
      }
      enum l2vpn-atom-pw-cw-on {
        value 1;
        description
          "L2VPN ATOM PW control word on.";
      }
      enum l2vpn-atom-pw-cw-unkn {
        value 2;
        description
          "L2VPN ATOM PW control word unknown.";
      }
    }
    description
      "L2VPN Any Transport over MPLS (ATOM) pseudowire (PW) control word.";
  }

  typedef l2vpn-cw-auto-sense {
    type enumeration {
      enum l2vpn-cw-autosense-off {
        value 0;
        description
          "L2VPN ATOM PW control word auto sense off.";
      }
      enum l2vpn-cw-autosense-on {
        value 1;
        description
          "L2VPN ATOM PW control word auto sense on.";
      }
      enum l2vpn-cw-autosense-unkn {
        value 2;
        description
          "L2VPN ATOM PW control word auto sense unknown.";
      }
    }
    description
      "L2VPN Any Transport over MPLS (ATOM) pseudowire (PW) control word auto sense.";
  }

  typedef l2vpn-pw-lb-mode {
    type enumeration {
      enum l2vpn-pw-def-lb-mode {
        value 0;
        description
          "L2VPN PW load-balance mode default.";
      }
      enum l2vpn-pw-lb-mode-ecmp {
        value 1;
        description
          "L2VPN PW load-balance mode Equal-Cost Multi-Path (ECMP).";
      }
    }
    description
      "L2VPN pseudowire (PW) load-balance mode.";
  }

  typedef l2vpn-pw-lb-fc {
    type enumeration {
      enum l2vpn-pw-default-lb-fc {
        value 0;
        description
          "L2VPN PW load-balance flow classification default.";
      }
      enum l2vpn-pw-lb-fc-eth-src-mac {
        value 1;
        description
          "L2VPN PW load-balance flow classification Ethernet source MAC.";
      }
      enum l2vpn-pw-lb-fc-eth-dst-mac {
        value 2;
        description
          "L2VPN PW load-balance flow classification Ethernet destination MAC.";
      }
      enum l2vpn-pw-lb-fc-eth-src-dst-mac {
        value 3;
        description
          "L2VPN PW load-balance flow classification Ethernet source and destination MAC.";
      }
      enum l2vpn-pw-lb-fc-ip-src-addr {
        value 4;
        description
          "L2VPN PW load-balance flow classification source IP address.";
      }
      enum l2vpn-pw-lb-fc-ip-dst-addr {
        value 5;
        description
          "L2VPN PW load-balance flow classification destination IP address.";
      }
      enum l2vpn-pw-lb-fc-ip-src-dst-addr {
        value 6;
        description
          "L2VPN PW load-balance flow classification source and destination IP address.";
      }
    }
    description
      "L2VPN pseudowire (PW) load-balance flow classification.";
  }

  typedef l2vpn-atom-vc-type {
    type enumeration {
      enum l2vpn-atom-vc-type-inv {
        value 0;
        description
          "Invalid virtual circuit type";
      }
      enum l2vpn-atom-vc-type-fr-dlci {
        value 1;
        description
          "L2VPN ATOM VC type Frame Relay (FR) Data Link Connection Identifier (DLCI).";
      }
      enum l2vpn-atom-vc-type-atm-aal5 {
        value 2;
        description
          "L2VPN ATOM VC type Asynchronous Transfer Mode (ATM) Adaptation Layer 5 (AAL5).";
      }
      enum l2vpn-atom-vc-type-atm-cell {
        value 3;
        description
          "L2VPN ATOM VC type Asynchronous Transfer Mode (ATM) cell.";
      }
      enum l2vpn-atom-vc-type-ether-vlan {
        value 4;
        description
          "L2VPN ATOM VC type Ethernet VLAN.";
      }
      enum l2vpn-atom-vc-type-ether {
        value 5;
        description
          "L2VPN ATOM VC type Ethernet.";
      }
      enum l2vpn-atom-vc-type-hdlc {
        value 6;
        description
          "L2VPN ATOM VC type High-Level Data Link Control (HDLC).";
      }
      enum l2vpn-atom-vc-type-ppp {
        value 7;
        description
          "L2VPN ATOM VC type Point-to-Point Protocol (PPP).";
      }
      enum l2vpn-atom-vc-type-cem {
        value 8;
        description
          "L2VPN ATOM VC type Circuit Emulation (CEM).";
      }
      enum l2vpn-atom-vc-type-atm-vcc-cell {
        value 9;
        description
          "L2VPN ATOM VC type Asynchronous Transfer Mode (ATM) Virtual Channel Connection (VCC) cell.";
      }
      enum l2vpn-atom-vc-type-atm-vpc-cell {
        value 10;
        description
          "L2VPN ATOM VC type Asynchronous Transfer Mode (ATM) Virtual Path Connection (VPC) cell.";
      }
      enum l2vpn-atom-vc-type-ip {
        value 11;
        description
          "L2VPN ATOM VC type IP.";
      }
      enum l2vpn-atom-vc-type-satop-e1 {
        value 17;
        description
          "L2VPN ATOM VC type Structure-Agnostic TDM over Packet (SAToP) E1.";
      }
      enum l2vpn-atom-vc-type-satop-t1 {
        value 18;
        description
          "L2VPN ATOM VC type Structure-Agnostic TDM over Packet (SAToP) T1.";
      }
      enum l2vpn-atom-vc-type-satop-e3 {
        value 19;
        description
          "L2VPN ATOM VC type Structure-Agnostic TDM over Packet (SAToP) E3.";
      }
      enum l2vpn-atom-vc-type-satop-t3 {
        value 20;
        description
          "L2VPN ATOM VC type Structure-Agnostic TDM over Packet (SAToP) T3.";
      }
      enum l2vpn-atom-vc-type-cesopsn-basic {
        value 21;
        description
          "L2VPN ATOM VC type Circuit Emulation Service over Packet Switched Network (CES PSN) basic.";
      }
      enum l2vpn-atom-vc-type-cesopsn-tdm-cas {
        value 22;
        description
          "L2VPN ATOM VC type Circuit Emulation Service over Packet Switched Network (CES PSN) TDM Channel Associated Signaling (CAS).";
      }
    }
    description
      "L2VPN Any Transport over MPLS (ATOM) virtual circuit (VC) type.";
  }

  typedef l2vpn-atom-mgr-vc-last-error {
    type enumeration {
      enum l2vpn-vc-err-none {
        value 0;
        description
          "No L2VPN ATOM manager VC error.";
      }
      enum l2vpn-vc-no-lcl-bdg-err {
        value 1;
        description
          "L2VPN ATOM manager VC no local binding error.";
      }
      enum l2vpn-vc-no-rmt-bdg-err {
        value 2;
        description
          "L2VPN ATOM manager VC no remote binding error.";
      }
      enum l2vpn-vc-mis-cw-err {
        value 3;
        description
          "L2VPN ATOM manager VC missing control word error.";
      }
      enum l2vpn-vc-cbit-mism-err {
        value 4;
        description
          "L2VPN ATOM manager VC control bit (CBIT) mismatch error.";
      }
      enum l2vpn-vc-type-mism-err {
        value 5;
        description
          "L2VPN ATOM manager VC type mismatch error.";
      }
      enum l2vpn-vc-mtu-mism-err {
        value 6;
        description
          "L2VPN ATOM manager VC Maximum Transmission Unit (MTU) mismatch error.";
      }
      enum l2vpn-vc-imp-rw-mism-err {
        value 7;
        description
          "L2VPN ATOM manager VC imposition rewrite mismatch error.";
      }
      enum l2vpn-vc-tdm-mism-err {
        value 8;
        description
          "L2VPN ATOM manager VC Time-Division Multiplexing (TDM) mismatch error.";
      }
      enum l2vpn-vc-lcl-ac-not-rdy-err {
        value 9;
        description
          "L2VPN ATOM manager VC local AC not ready error";
      }
      enum l2vpn-vc-rmt-not-rdy-err {
        value 10;
        description
          "L2VPN ATOM manager VC remote not ready error";
      }
      enum l2vpn-vc-lcl-ac-down-err {
        value 11;
        description
          "L2VPN ATOM manager VC local AC Down error";
      }
      enum l2vpn-vc-rmt-ac-down-err {
        value 12;
        description
          "L2VPN ATOM manager VC remote AC Down error";
      }
      enum l2vpn-vc-lcl-ac-hard-down-err {
        value 13;
        description
          "L2VPN ATOM manager VC local AC Hard Down error";
      }
      enum l2vpn-vc-dp-flt-err {
        value 14;
        description
          "L2VPN ATOM manager VC dataplane fault error";
      }
      enum l2vpn-vc-bfd-flt-err {
        value 15;
        description
          "L2VPN ATOM manager VC BFD fault error";
      }
      enum l2vpn-vc-adj-down-err {
        value 16;
        description
          "L2VPN ATOM manager VC adjacency down error";
      }
      enum l2vpn-vc-lcl-bdg-aloc-no-ac-pw-err {
        value 17;
        description
          "L2VPN ATOM manager error in allocating VC local binding no AC PW type";
      }
      enum l2vpn-vc-lcl-bdg-alloc-no-cap-err {
        value 18;
        description
          "L2VPN ATOM manager error in allocating VC local binding no CAP";
      }
      enum l2vpn-vc-lcl-bdg-aloc-no-vc-type-err {
        value 19;
        description
          "L2VPN ATOM manager error in allocating VC local binding no VC type";
      }
      enum l2vpn-vc-lcl-bdg-mtu-err {
        value 20;
        description
          "L2VPN ATOM manager VC local binding MTU error";
      }
      enum l2vpn-vc-lcl-bdg-tdm-err {
        value 21;
        description
          "L2VPN ATOM manager VC local binding TDM error";
      }
      enum l2vpn-vc-lcl-bdg-dyn-lbl-err {
        value 22;
        description
          "L2VPN ATOM manager VC local binding Dynamic label error";
      }
      enum l2vpn-vc-lcl-bdg-stat-lbl-err {
        value 23;
        description
          "L2VPN ATOM manager VC local binding Static label error";
      }
      enum l2vpn-vc-lcl-bdg-rrp-no-cp-info-err {
        value 24;
        description
          "L2VPN ATOM manager VC local binding RRP no checkpoint info error";
      }
      enum l2vpn-vc-lcl-bdg-rrp-no-cp-lbl-err {
        value 25;
        description
          "L2VPN ATOM manager VC local binding RRP no checkpoint label error";
      }
      enum l2vpn-vc-lcl-bdg-rrp-cp-lbl-aloc-err {
        value 26;
        description
          "L2VPN ATOM manager VC local binding RRP checkpoint label allocation error";
      }
      enum l2vpn-vc-lcl-bdg-rrp-cp-lb-mt-err {
        value 27;
        description
          "L2VPN ATOM manager VC local binding RRP checkpoint label mismatch error";
      }
      enum l2vpn-vc-lcl-xc-sh-down-err {
        value 28;
        description
          "L2VPN ATOM manager VC local XC shut down error";
      }
      enum l2vpn-vc-lcl-pw-sh-down-err {
        value 29;
        description
          "L2VPN ATOM manager VC local PW shut down error";
      }
      enum l2vpn-vc-lcl-pw-bw-not-admt-err {
        value 30;
        description
          "L2VPN ATOM manager VC local PW BW not admitted error";
      }
      enum l2vpn-vc-lcl-bdg-cbit-err {
        value 31;
        description
          "L2VPN ATOM manager VC local binding CBIT error";
      }
    }
    description
      "L2VPN ATOM manager VC last error.";
  }

  typedef l2vpn-vc-next-hop-type {
    type enumeration {
      enum l2vpn-vc-no-nh {
        value 0;
        description
          "No L2VPN VC next hop.";
      }
      enum l2vpn-vc-nh-p2p {
        value 1;
        description
          "L2VPN VC next hop type point-to-point (P2P) link.";
      }
      enum l2vpn-vc-nh-ipv4-addr {
        value 2;
        description
          "L2VPN VC next hop type IPv4 address.";
      }
      enum l2vpn-vc-nh-ipv6-addr {
        value 3;
        description
          "L2VPN VC next hop type IPv6 address.";
      }
    }
    description
      "L2VPN virtual circuit (VC) next hop type.";
  }

  typedef l2vpn-pref-path-type {
    type enumeration {
      enum l2vpn-pref-not-conf {
        value 0;
        description
          "L2VPN preferred path type not configured.";
      }
      enum l2vpn-pref-no-route {
        value 1;
        description
          "L2VPN preferred path type no route available.";
      }
      enum l2vpn-pref-out-if {
        value 2;
        description
          "L2VPN preferred path type output tunnel interface.";
      }
      enum l2vpn-pref-next-hop-addr {
        value 3;
        description
          "L2VPN preferred path type next hop IP address.";
      }
    }
    description
      "L2VPN preferred path type.";
  }

  typedef l2vpn-def-path-state {
    type enumeration {
      enum l2vpn-def-path-none {
        value 0;
        description
          "No L2VPN default path state.";
      }
      enum l2vpn-def-path-disabled {
        value 1;
        description
          "L2VPN default path state disabled.";
      }
      enum l2vpn-def-path-active {
        value 2;
        description
          "L2VPN default path state active.";
      }
      enum l2vpn-def-path-no-route {
        value 3;
        description
          "L2VPN default path state no route.";
      }
      enum l2vpn-def-path-ready {
        value 4;
        description
          "L2VPN default path state ready.";
      }
    }
    description
      "L2VPN default path state.";
  }

  typedef l2vpn-vc-status-tlv {
    type enumeration {
      enum l2vpn-vc-stat-tlv-dis {
        value 0;
        description
          "L2VPN VC status TLV disabled.";
      }
      enum l2vpn-vc-stat-tlv-en {
        value 1;
        description
          "L2VPN VC status TLV enabled.";
      }
      enum l2vpn-vc-stat-tlv-unkn {
        value 2;
        description
          "L2VPN VC status TLV unknown.";
      }
      enum l2vpn-vc-stat-tlv-sup {
        value 3;
        description
          "L2VPN VC status TLV supported.";
      }
      enum l2vpn-vc-stat-tlv-not-sup {
        value 4;
        description
          "L2VPN VC status TLV not supported.";
      }
    }
    description
      "L2VPN virtual circuit (VC) status Type-Length-Value (TLV).";
  }

  typedef l2vpn-atom-ldp-status {
    type enumeration {
      enum l2vpn-atom-ldp-def {
        value 0;
        description
          "L2VPN ATOM LDP status default.";
      }
      enum l2vpn-atom-ldp-down {
        value 1;
        description
          "L2VPN ATOM LDP status down.";
      }
      enum l2vpn-atom-ldp-down-no-sig {
        value 2;
        description
          "L2VPN ATOM LDP status down no signal.";
      }
      enum l2vpn-atom-ldp-down-no-bind {
        value 3;
        description
          "L2VPN ATOM LDP status down no binding.";
      }
      enum l2vpn-atom-ldp-up {
        value 4;
        description
          "L2VPN ATOM LDP status up.";
      }
    }
    description
      "L2VPN Any Transport over MPLS (ATOM) Label Distribution Protocol (LDP) status.";
  }

  typedef l2vpn-atom-mgr-state {
    type enumeration {
      enum l2vpn-atom-mgr-state-idle {
        value 0;
        description
          "L2VPN ATOM manager state idle.";
      }
      enum l2vpn-atom-mgr-state-prov {
        value 1;
        description
          "L2VPN ATOM manager state provisioned.";
      }
      enum l2vpn-atom-mgr-state-stdby-lcl-rdy {
        value 2;
        description
          "L2VPN ATOM manager state standby local ready.";
      }
      enum l2vpn-atom-mgr-state-ldp-ready {
        value 3;
        description
          "L2VPN ATOM manager state LDP ready.";
      }
      enum l2vpn-atom-mgr-state-lcl-rdy {
        value 4;
        description
          "L2VPN ATOM manager state local ready.";
      }
      enum l2vpn-atom-mgr-state-rmt-rdy {
        value 5;
        description
          "L2VPN ATOM manager state remote ready.";
      }
      enum l2vpn-atom-mgr-state-rmt-inv {
        value 6;
        description
          "L2VPN ATOM manager state remote is invalid.";
      }
      enum l2vpn-atom-mgr-state-est {
        value 7;
        description
          "L2VPN ATOM manager state establishing.";
      }
      enum l2vpn-atom-mgr-state-act {
        value 8;
        description
          "L2VPN ATOM manager state activating.";
      }
      enum l2vpn-atom-mgr-state-ested {
        value 9;
        description
          "L2VPN ATOM manager state established.";
      }
    }
    description
      "L2VPN Any Transport over MPLS (ATOM) manager state.";
  }

  typedef l2vpn-atom-mgr-fsm-state {
    type enumeration {
      enum lndrnd {
        value 0;
        description
          "Local not ready down and remote not ready down";
      }
      enum lnurnd {
        value 1;
        description
          "Local not ready up and remote not ready down";
      }
      enum lrdrnd {
        value 2;
        description
          "Local ready down and remote not ready down";
      }
      enum lrurnd {
        value 3;
        description
          "Local ready up and remote not ready down";
      }
      enum lndrrd {
        value 4;
        description
          "Local ready down and remote ready down";
      }
      enum lndrra {
        value 5;
        description
          "Local not ready down and remote ready adjacency down";
      }
      enum lndrraa {
        value 6;
        description
          "Local not ready down, remote ready adjacency down and remote down";
      }
      enum lndrru {
        value 7;
        description
          "Local not ready down and remote ready up";
      }
      enum lnurrd {
        value 8;
        description
          "Local not ready up and remote ready down";
      }
      enum lnurra {
        value 9;
        description
          "Local not ready up and remote ready adjacency down";
      }
      enum lnurraa {
        value 10;
        description
          "Local not ready up, remote ready adjacency down and remote down";
      }
      enum lnurru {
        value 11;
        description
          "Local not ready up and remote ready up";
      }
      enum lrdrrd {
        value 12;
        description
          "Local ready up and remote ready down";
      }
      enum lrdrra {
        value 13;
        description
          "Local ready down and remote ready adjacency down";
      }
      enum lrdrraa {
        value 14;
        description
          "Local ready down, remote ready adjacency down and remote down";
      }
      enum lrdrru {
        value 15;
        description
          "Local ready down and remote ready up";
      }
      enum lrurrd {
        value 16;
        description
          "Local ready up and remote ready down";
      }
      enum lrurra {
        value 17;
        description
          "Local ready up and remote ready adjacency down";
      }
      enum lrurraa {
        value 18;
        description
          "Local ready up, remote ready adjacency down and remote down";
      }
      enum lrurru {
        value 19;
        description
          "Local ready up and remote ready up";
      }
      enum lndrnddp {
        value 20;
        description
          "Local not ready down and remote not ready down DP fault";
      }
      enum lnurnddp {
        value 21;
        description
          "Local not ready up and remote not ready down DP fault";
      }
      enum lrdrnddp {
        value 22;
        description
          "Local ready down and remote not ready down DP fault";
      }
      enum lrurnddp {
        value 23;
        description
          "Local ready up and remote not ready down DP fault";
      }
      enum lndrrddp {
        value 24;
        description
          "Local not ready down and remote ready down DP fault";
      }
      enum lndrradp {
        value 25;
        description
          "Local not ready down and remote ready adjacency down DP fault";
      }
      enum lndrraadp {
        value 26;
        description
          "Local not ready down, remote ready adjacency down DP fault and remote down";
      }
      enum lndrrudp {
        value 27;
        description
          "Local not ready down and remote ready up DP fault";
      }
      enum lnurrddp {
        value 28;
        description
          "Local not ready up and remote ready down DP fault";
      }
      enum lnurradp {
        value 29;
        description
          "Local not ready up and remote ready adjacency down DP fault";
      }
      enum lnurraadp {
        value 30;
        description
          "Local not ready up, remote ready adjacency down DP fault and remote down";
      }
      enum lnurrudp {
        value 31;
        description
          "Local not ready up and remote ready up DP fault";
      }
      enum lrdrrddp {
        value 32;
        description
          "Local ready down and remote ready down DP fault";
      }
      enum lrdrradp {
        value 33;
        description
          "Local ready down and remote ready adjacency down DP fault";
      }
      enum lrdrraadp {
        value 34;
        description
          "Local ready down, remote ready adjacency down DP fault and remote down";
      }
      enum lrdrrudp {
        value 35;
        description
          "Local ready down and remote ready up DP fault";
      }
      enum lrurrddp {
        value 36;
        description
          "Local ready up and remote ready down DP fault";
      }
      enum lrurradp {
        value 37;
        description
          "Local ready up and remote ready adjacency down DP fault";
      }
      enum lrurraadp {
        value 38;
        description
          "Local ready up, remote ready adjacency down DP fault and remote down";
      }
      enum lrurrudp {
        value 39;
        description
          "Local ready up and remote ready up DP fault";
      }
      enum slndrnd {
        value 40;
        description
          "VC shut, Local not ready down and remote not ready down";
      }
      enum slnurnd {
        value 41;
        description
          "VC shut, Local not ready up and remote not ready down";
      }
      enum slrdrnd {
        value 42;
        description
          "VC shut, Local ready down and remote not ready down";
      }
      enum slrurnd {
        value 43;
        description
          "VC shut, Local ready up and remote not ready down";
      }
      enum slndrrd {
        value 44;
        description
          "VC shut, Local not ready down and remote ready down";
      }
      enum slndrra {
        value 45;
        description
          "VC shut, Local not ready down and remote ready adjacency down";
      }
      enum slndrraa {
        value 46;
        description
          "VC shut, Local not ready down, remote ready adjacency down and remote down";
      }
      enum slndrru {
        value 47;
        description
          "VC shut, Local not ready down, remote ready up";
      }
      enum slnurrd {
        value 48;
        description
          "VC shut, Local not ready up and remote ready down";
      }
      enum slnurra {
        value 49;
        description
          "VC shut, Local not ready up and remote ready adjacency down";
      }
      enum slnurraa {
        value 50;
        description
          "VC shut, Local not ready up, remote ready adjacency down and remote down";
      }
      enum slnurru {
        value 51;
        description
          "VC shut, Local not ready up and remote ready up";
      }
      enum slrdrrd {
        value 52;
        description
          "VC shut, Local ready down and remote ready down";
      }
      enum slrdrra {
        value 53;
        description
          "VC shut, Local ready down and remote ready adjacency down";
      }
      enum slrdrraa {
        value 54;
        description
          "VC shut, Local ready down, remote ready adjacency down and remote down";
      }
      enum slrdrru {
        value 55;
        description
          "VC shut, Local ready down and remote ready up";
      }
      enum slrurrd {
        value 56;
        description
          "VC shut, Local ready up and remote ready down";
      }
      enum slrurra {
        value 57;
        description
          "VC shut, Local ready up and remote ready adjacency down";
      }
      enum slrurraa {
        value 58;
        description
          "VC shut, Local ready up, remote ready adjacency down and remote down";
      }
      enum slrurru {
        value 59;
        description
          "VC shut, Local ready up and remote ready up";
      }
      enum slndrnddp {
        value 60;
        description
          "VC shut, Local not ready down and remote not ready down DP fault";
      }
      enum slnurnddp {
        value 61;
        description
          "VC shut, Local not ready up and remote not ready down DP fault";
      }
      enum slrdrnddp {
        value 62;
        description
          "VC shut, Local ready down and remote not ready down DP fault";
      }
      enum slrurnddp {
        value 63;
        description
          "VC shut, Local ready up and remote not ready down DP fault";
      }
      enum slndrrddp {
        value 64;
        description
          "VC shut, Local not ready down and remote ready down DP fault";
      }
      enum slndrradp {
        value 65;
        description
          "VC shut, Local not ready down and remote ready adjacency down DP fault";
      }
      enum slndrraadp {
        value 66;
        description
          "VC shut, Local not ready down, remote ready adjacency down DP fault and remote down";
      }
      enum slndrrudp {
        value 67;
        description
          "VC shut, Local not ready down and remote ready up DP fault";
      }
      enum slnurrddp {
        value 68;
        description
          "VC shut, Local not ready up and remote ready down DP fault";
      }
      enum slnurradp {
        value 69;
        description
          "VC shut, Local not ready up and remote ready adjacency down DP fault";
      }
      enum slnurraadp {
        value 70;
        description
          "VC shut, Local not ready up, remote ready adjacency down DP fault and remote down";
      }
      enum slnurrudp {
        value 71;
        description
          "VC shut, Local not ready up and remote ready up DP fault";
      }
      enum slrdrrddp {
        value 72;
        description
          "VC shut, Local not ready down and remote ready down DP fault";
      }
      enum slrdrradp {
        value 73;
        description
          "VC shut, Local ready down and remote ready adjacency down DP fault";
      }
      enum slrdrraadp {
        value 74;
        description
          "VC shut, Local ready down, remote ready adjacency down DP fault and remote down";
      }
      enum slrdrrudp {
        value 75;
        description
          "VC shut, Local ready down and remote ready up DP fault";
      }
      enum slrurrddp {
        value 76;
        description
          "VC shut, Local ready up and remote ready down DP fault";
      }
      enum slrurradp {
        value 77;
        description
          "VC shut, Local ready up and remote ready adjacency down DP fault";
      }
      enum slrurraadp {
        value 78;
        description
          "VC shut, Local ready up, remote ready adjacency down DP fault and remote down";
      }
      enum slrurrudp {
        value 79;
        description
          "VC shut, Local ready up and remote ready up DP fault";
      }
    }
    description
      "L2VPN Any Transport over MPLS (ATOM) manager finite state machine (FSM) state.";
  }

  typedef l2vpn-feat-conf {
    type enumeration {
      enum l2vpn-feat-not-conf {
        value 0;
        description
          "L2VPN feature not configured.";
      }
      enum l2vpn-feat-conf {
        value 1;
        description
          "L2VPN feature configured.";
      }
    }
    description
      "L2VPN feature configuration.";
  }

  typedef l2vpn-feat-en {
    type enumeration {
      enum l2vpn-feat-not-en {
        value 0;
        description
          "L2VPN feature disabled.";
      }
      enum l2vpn-feat-en {
        value 1;
        description
          "L2VPN feature enabled.";
      }
      enum l2vpn-feat-not-appl {
        value 2;
        description
          "L2VPN feature not applicable.";
      }
    }
    description
      "L2VPN feature enablement.";
  }

  typedef l2vpn-atom-fec-type {
    type enumeration {
      enum l2vpn-atomvc-fec-unkn {
        value 0;
        description
          "L2VPN ATOM FEC type unknown.";
      }
      enum l2vpn-atomvc-fec-128 {
        value 1;
        description
          "L2VPN ATOM FEC type 128.";
      }
      enum l2vpn-atomvc-fec-129 {
        value 2;
        description
          "L2VPN ATOM FEC type 129.";
      }
    }
    description
      "L2VPN Any Transport over MPLS (ATOM) Forwarding Equivalence Class (FEC) type.";
  }

  typedef l2vpn-circuit-status {
    type enumeration {
      enum l2vpn-ckt-stat-none {
        value 0;
        description
          "No L2VPN circuit status.";
      }
      enum l2vpn-ckt-stat-up {
        value 1;
        description
          "L2VPN circuit up status.";
      }
      enum l2vpn-ckt-stat-down {
        value 2;
        description
          "L2VPN circuit down status.";
      }
      enum l2vpn-ckt-stat-ac-rx-tx-flt {
        value 3;
        description
          "L2VPN circuit status: attachment circuit (AC) Rx/Tx fault.";
      }
      enum l2vpn-ckt-stat-pw-rx-tx-flt {
        value 4;
        description
          "L2VPN circuit status: pseudowire (PW) interface Rx/Tx fault.";
      }
      enum l2vpn-ckt-stat-ac-pw-rx-tx-flt {
        value 5;
        description
          "L2VPN circuit status: attachment circuit (AC) and pseudowire (PW) interface Rx/Tx fault.";
      }
      enum l2vpn-ckt-stat-hard-down {
        value 6;
        description
          "L2VPN circuit hard down status.";
      }
      enum l2vpn-ckt-stat-not-rdy {
        value 7;
        description
          "L2VPN circuit not ready status.";
      }
      enum l2vpn-ckt-stat-ckt-stdby {
        value 8;
        description
          "L2VPN circuit standby status.";
      }
      enum l2vpn-ckt-stat-go-active {
        value 9;
        description
          "L2VPN circuit go active status.";
      }
      enum l2vpn-ckt-stat-recovering {
        value 10;
        description
          "L2VPN circuit recovering status.";
      }
      enum l2vpn-ckt-stat-admin-down {
        value 11;
        description
          "L2VPN circuit admin down status.";
      }
      enum l2vpn-ckt-stat-no-fault {
        value 12;
        description
          "L2VPN circuit no fault status.";
      }
      enum l2vpn-ckt-stat-not-sent {
        value 13;
        description
          "L2VPN circuit not sent status.";
      }
      enum l2vpn-ckt-stat-not-appl {
        value 14;
        description
          "L2VPN circuit not applicable status.";
      }
    }
    description
      "L2VPN circuit status.";
  }

  typedef l2vpn-pw-sequence {
    type enumeration {
      enum l2vpn-pw-seq-off {
        value 0;
        description
          "L2VPN ATOM PW sequencing off.";
      }
      enum l2vpn-pw-seq-tx {
        value 1;
        description
          "L2VPN ATOM PW sequencing transmit.";
      }
      enum l2vpn-pw-seq-rx {
        value 2;
        description
          "L2VPN ATOM PW sequencing receive.";
      }
      enum l2vpn-pw-seq-trans {
        value 3;
        description
          "L2VPN ATOM PW sequencing transparent.";
      }
      enum l2vpn-pw-seq-both {
        value 4;
        description
          "L2VPN ATOM PW sequencing both.";
      }
    }
    description
      "L2VPN Any Transport over MPLS (ATOM) pseudowire (PW) sequencing.";
  }

  typedef l2vpn-iw-type {
    type enumeration {
      enum l2vpn-iw-inv {
        value 0;
        description
          "Invalid interworking type";
      }
      enum l2vpn-iw-fr-dlci {
        value 1;
        description
          "L2VPN interworking type Frame Relay (FR) Data Link Connection Identifier (DLCI).";
      }
      enum l2vpn-iw-fr-dlci-lcl {
        value 2;
        description
          "L2VPN interworking type Frame Relay (FR) Data Link Connection Identifier (DLCI) local.";
      }
      enum l2vpn-iw-atm-aal5 {
        value 3;
        description
          "L2VPN interworking type Asynchronous Transfer Mode (ATM) Adaptation Layer 5 (AAL5).";
      }
      enum l2vpn-iw-atm-cell {
        value 4;
        description
          "L2VPN interworking type Asynchronous Transfer Mode (ATM) cell.";
      }
      enum l2vpn-iw-eth-vlan {
        value 5;
        description
          "L2VPN interworking type Ethernet VLAN.";
      }
      enum l2vpn-iw-eth {
        value 6;
        description
          "L2VPN interworking type Ethernet.";
      }
      enum l2vpn-iw-hdlc {
        value 7;
        description
          "L2VPN interworking type High-Level Data Link Control (HDLC).";
      }
      enum l2vpn-iw-ppp {
        value 8;
        description
          "L2VPN interworking type Point-to-Point Protocol (PPP).";
      }
      enum l2vpn-iw-cem {
        value 9;
        description
          "L2VPN interworking type Circuit Emulation (CEM).";
      }
      enum l2vpn-iw-atm-vcc-cell {
        value 10;
        description
          "L2VPN interworking type Asynchronous Transfer Mode (ATM) Virtual Channel Connection (VCC) cell.";
      }
      enum l2vpn-iw-atm-vpc-cell {
        value 11;
        description
          "L2VPN interworking type Asynchronous Transfer Mode (ATM) Virtual Path Connection (VPC) cell.";
      }
      enum l2vpn-iw-ip {
        value 12;
        description
          "L2VPN interworking type IP.";
      }
      enum l2vpn-iw-vfi {
        value 13;
        description
          "L2VPN interworking type Virtual Forwarding Instance (VFI).";
      }
      enum l2vpn-iw-satop-e1 {
        value 15;
        description
          "L2VPN interworking type Structure-Agnostic TDM over Packet (SAToP) E1.";
      }
      enum l2vpn-iw-satop-t1 {
        value 16;
        description
          "L2VPN interworking type Structure-Agnostic TDM over Packet (SAToP) T1.";
      }
      enum l2vpn-iw-satop-e3 {
        value 17;
        description
          "L2VPN interworking type Structure-Agnostic TDM over Packet (SAToP) E3.";
      }
      enum l2vpn-iw-satop-t3 {
        value 18;
        description
          "L2VPN interworking type Structure-Agnostic TDM over Packet (SAToP) T3.";
      }
      enum l2vpn-iw-ces-psn-basic {
        value 19;
        description
          "L2VPN interworking type Circuit Emulation Service over Packet Switched Network (CES PSN) basic.";
      }
      enum l2vpn-iw-ces-psn-cas {
        value 20;
        description
          "L2VPN interworking type Circuit Emulation Service over Packet Switched Network (CES PSN) Channel Associated Signaling (CAS).";
      }
      enum l2vpn-iw-atm-vc-unknown {
        value 21;
        description
          "L2VPN interworking type Asynchronous Transfer Mode (ATM) Virtual Circuit (VC) unknown.";
      }
      enum l2vpn-iw-atm-vp-unknown {
        value 22;
        description
          "L2VPN interworking type Asynchronous Transfer Mode (ATM) Virtual Path (VP) unknown.";
      }
      enum l2vpn-iw-atom {
        value 23;
        description
          "L2VPN interworking type Any Transport over MPLS (ATOM).";
      }
      enum l2vpn-iw-l2tpv2 {
        value 24;
        description
          "L2VPN interworking type Layer 2 Tunneling Protocol Version 2 (L2TPv2).";
      }
      enum l2vpn-iw-l2tpv3 {
        value 25;
        description
          "L2VPN interworking type Layer 2 Tunneling Protocol Version 3 (L2TPv3).";
      }
      enum l2vpn-iw-pw-udp {
        value 26;
        description
          "L2VPN interworking type Pseudowire (PW) over UDP.";
      }
      enum l2vpn-iw-docsis {
        value 27;
        description
          "L2VPN interworking type Data Over Cable Service Interface Specification (DOCSIS).";
      }
      enum l2vpn-iw-docsis-vlan {
        value 28;
        description
          "L2VPN interworking type Data Over Cable Service Interface Specification (DOCSIS) VLAN.";
      }
    }
    description
      "L2VPN interworking type.";
  }

  typedef l2vpn-service-state {
    type enumeration {
      enum l2vpn-serv-undef {
        value 0;
        description
          "L2VPN service state undefined.";
      }
      enum l2vpn-serv-up {
        value 1;
        description
          "L2VPN service state up.";
      }
      enum l2vpn-serv-down {
        value 2;
        description
          "L2VPN service state down.";
      }
      enum l2vpn-serv-admin-down {
        value 3;
        description
          "L2VPN service state admin down.";
      }
      enum l2vpn-serv-recovering {
        value 4;
        description
          "L2VPN service state recovering.";
      }
      enum l2vpn-serv-stdby {
        value 5;
        description
          "L2VPN service state standby.";
      }
      enum l2vpn-serv-hot-stdby {
        value 6;
        description
          "L2VPN service state hot standby.";
      }
    }
    description
      "L2VPN service state.";
  }

  typedef l2vpn-vccv-cc-type-flags {
    type bits {
      bit vccv-cc-cw {
        position 0;
        description
          "L2VPN VCCV CC type control word.";
      }
      bit vccv-cc-ra {
        position 1;
        description
          "L2VPN VCCV CC type router alert.";
      }
      bit vccv-cc-ttl {
        position 2;
        description
          "L2VPN VCCV CC type Time-To-Live (TTL).";
      }
    }
    description
      "L2VPN Virtual Circuit Connectivity Verification (VCCV) control channel (CC) type flags.";
  }

  typedef l2vpn-vccv-cv-type-flags {
    type bits {
      bit vccv-cv-icmp {
        position 0;
        description
          "L2VPN VCCV CV type Internet Control Message Protocol (ICMP).";
      }
      bit vccv-cv-lspv {
        position 1;
        description
          "L2VPN VCCV CV type Label Switched Path Verification (LSPV).";
      }
      bit vccv-cv-bfd-udp {
        position 2;
        description
          "L2VPN VCCV CV type Bidirectional Forwarding Detection (BFD) over UDP.";
      }
      bit vccv-cv-bfd-udp-sig {
        position 3;
        description
          "L2VPN VCCV CV type Bidirectional Forwarding Detection (BFD) over UDP with signalling.";
      }
      bit vccv-cv-bfd-raw {
        position 4;
        description
          "L2VPN VCCV CV type Bidirectional Forwarding Detection (BFD) RAW.";
      }
      bit vccv-cv-bfd-raw-sig {
        position 5;
        description
          "L2VPN VCCV CV type Bidirectional Forwarding Detection (BFD) RAW with signalling.";
      }
    }
    description
      "L2VPN Virtual Circuit Connectivity Verification (VCCV) connectivity verification (CV) type flags.";
  }

  grouping fwd-info-ac {
    description
      "L2VPN forwarder info for attachment circuit";
    leaf if-name {
      type string;
      description
        "Name of the interface used as the attachment circuit for this L2VPN xconnect segment.";
    }
    leaf group-name {
      type string;
      description
        "Name of the group to which the attachment circuit belongs, used for grouping related circuits in L2VPN configuration.";
    }
    leaf encap {
      type l2vpn-ios-xe-oper:l2vpn-ac-circuit-type;
      description
        "Type of encapsulation used on the attachment circuit for this L2VPN xconnect segment, such as Ethernet or VLAN tagging.";
    }
    leaf state {
      type l2vpn-ios-xe-oper:l2vpn-xconnect-segment-state;
      description
        "Current operational state of the attachment circuit for this L2VPN xconnect segment, such as up, down, or administratively down.";
    }
    leaf state-in-l2vpn-service {
      type l2vpn-ios-xe-oper:l2vpn-xconnect-state;
      description
        "Operational state of the attachment circuit as it pertains specifically to its role within the L2VPN service.";
    }
    leaf priority {
      type uint32;
      description
        "Priority value assigned to the attachment circuit for determining failover or selection order within the L2VPN configuration.";
    }
  }

  grouping fwd-info-pw {
    description
      "L2VPN forwarder info for pseudo-wire";
    leaf if-name {
      type string;
      description
        "Name of the interface associated with the L2VPN pseudo-wire.";
    }
    leaf group-name {
      type string;
      description
        "Name of the pseudo-wire group to which this L2VPN pseudo-wire belongs.";
    }
    leaf encap {
      type l2vpn-ios-xe-oper:l2vpn-pw-encap-type;
      description
        "Indicates the encapsulation type used for the L2VPN pseudo-wire, such as MPLS or L2TPv3.";
    }
    leaf peer-address {
      type inet:ipv4-address;
      description
        "Pseudo-wire peer ipv4 address";
    }
    leaf vcid {
      type uint32;
      description
        "Pseudo-wire virtual circuit id";
    }
    leaf state {
      type l2vpn-ios-xe-oper:l2vpn-xconnect-segment-state;
      description
        "Indicates the current operational state of the pseudowire, such as up, down, or administratively shut.";
    }
    leaf state-in-l2vpn-service {
      type l2vpn-ios-xe-oper:l2vpn-xconnect-state;
      description
        "Indicates the operational state of the pseudo-wire as it relates to the overall L2VPN service.";
    }
    leaf priority {
      type uint32;
      description
        "Specifies the priority value assigned to the L2VPN pseudo-wire, which determines its selection order in failover or load balancing scenarios.";
    }
  }

  grouping fwd-info-vfi {
    description
      "L2VPN forwarder info for Virtual Forwarding Instance (VFI).";
    leaf if-name {
      type string;
      description
        "Name of the interface associated with the VPLS Virtual Forwarding Instance (VFI).";
    }
    leaf group-name {
      type string;
      description
        "Name of the VPLS group to which this VFI segment belongs.";
    }
    leaf encap {
      type l2vpn-ios-xe-oper:l2vpn-pw-encap-type;
      description
        "Specifies the encapsulation type used for the VPLS Virtual Forwarding Instance (VFI), such as MPLS.";
    }
    leaf state {
      type l2vpn-ios-xe-oper:l2vpn-xconnect-segment-state;
      description
        "Current operational state of the VPLS Virtual Forwarding Instance (VFI) segment.";
    }
    leaf state-in-l2vpn-service {
      type l2vpn-ios-xe-oper:l2vpn-xconnect-state;
      description
        "Current state of this VPLS Virtual Forwarding Instance (VFI) segment within the overall L2VPN service.";
    }
    leaf priority {
      type uint32;
      description
        "Priority value assigned to this VPLS Virtual Forwarding Instance (VFI) segment for traffic handling or failover.";
    }
  }

  grouping fwd-info-bd {
    description
      "L2VPN forwarder info for bridge domain.";
    leaf if-name {
      type string;
      description
        "Name of the interface associated with this L2VPN bridge domain.";
    }
    leaf group-name {
      type string;
      description
        "Name of the group to which this L2VPN bridge domain belongs.";
    }
    leaf encap {
      type l2vpn-ios-xe-oper:l2vpn-pw-encap-type;
      description
        "Type of encapsulation used for this L2VPN bridge domain segment.";
    }
    leaf state {
      type l2vpn-ios-xe-oper:l2vpn-xconnect-segment-state;
      description
        "Operational state of the bridge domain in the L2VPN xconnect segment (e.g., up, down, or other status).";
    }
    leaf state-in-l2vpn-service {
      type l2vpn-ios-xe-oper:l2vpn-xconnect-state;
      description
        "Operational state of the bridge domain as it pertains to the overall L2VPN service (e.g., active, standby, or failed).";
    }
    leaf priority {
      type uint32;
      description
        "Specifies the priority value assigned to the bridge domain for L2VPN operations, which may influence forwarding decisions or failover behavior.";
    }
  }

  grouping forwarder {
    description
      "L2VPN forwarder info";
    choice fwd-type-choice {
      description
        "Type of the L2VPN forwarder";
      case l2vpn-fwd-type-ac {
        container attachment-circuit {
          description
            "L2VPN attachment-circuit information";
          uses l2vpn-ios-xe-oper:fwd-info-ac;
        }
      }
      case l2vpn-fwd-type-pw {
        container pseudowire {
          description
            "L2VPN pseudo-wire information";
          uses l2vpn-ios-xe-oper:fwd-info-pw;
        }
      }
      case l2vpn-fwd-type-vfi {
        container vfi {
          description
            "Contains information related to the Virtual Private LAN Service (VPLS) Virtual Forwarding Instance (VFI) for L2VPN.";
          uses l2vpn-ios-xe-oper:fwd-info-vfi;
        }
      }
      case l2vpn-fwd-type-bd {
        container bridge-domain {
          description
            "L2VPN bridge domain information";
          uses l2vpn-ios-xe-oper:fwd-info-bd;
        }
      }
    }
  }

  grouping l2vpn-xconnect-key {
    description
      "L2VPN xconnect key";
    leaf peer-address {
      type inet:ipv4-address;
      description
        "L2VPN xconnect peer ipv4 address";
    }
    leaf vcid {
      type uint32;
      description
        "L2VPN xconnect virtual circuit id";
    }
  }

  grouping standby-segments {
    description
      "L2VPN xconnect standby segments";
    container segment1 {
      description
        "Represents the first standby segment for L2VPN xconnect, used as a backup path in case the primary segment fails.";
      uses l2vpn-ios-xe-oper:forwarder;
    }
    container segment2 {
      description
        "L2VPN xconnect standby segment 2";
      uses l2vpn-ios-xe-oper:forwarder;
    }
  }

  grouping l2vpn-xconnect-data {
    description
      "L2VPN xconnect data";
    leaf xconnect-name {
      type string;
      description
        "L2VPN xconnect service name";
    }
    leaf service-type {
      type l2vpn-ios-xe-oper:l2vpn-service-type;
      description
        "L2VPN xconnect service type";
    }
    leaf xconnect-state {
      type l2vpn-ios-xe-oper:l2vpn-xconnect-state;
      description
        "L2VPN xconnect state";
    }
    leaf description {
      type string;
      description
        "L2VPN xconnect description";
    }
    container segment1 {
      description
        "First segment of the L2VPN xconnect, representing one endpoint of the point-to-point connection";
      uses l2vpn-ios-xe-oper:forwarder;
    }
    container segment2 {
      description
        "Represents the second segment of the L2VPN xconnect, which may correspond to the remote or secondary connection endpoint in a point-to-point Layer 2 VPN service.";
      uses l2vpn-ios-xe-oper:forwarder;
    }
    list standby {
      description
        "A List of L2VPN xconnect standby segments if present";
      uses l2vpn-ios-xe-oper:standby-segments;
    }
  }

  grouping l2vpn-services {
    description
      "Container for operational data of configured Layer 2 VPN (L2VPN) services on the device.";
    list l2vpn-xconnect {
      key "peer-address vcid";
      description
        "List of Layer 2 VPN (L2VPN) point-to-point cross-connect (xconnect) services and their operational data.";
      uses l2vpn-ios-xe-oper:l2vpn-xconnect-key;
      uses l2vpn-ios-xe-oper:l2vpn-xconnect-data;
    }
  }

  grouping l2vpn-vc-next-hop {
    description
      "L2VPN Next hop info";
    choice next-hop-type-choice {
      description
        "Type of the Next hop";
      case l2vpn-vc-no-nh {
        leaf no-nh {
          type empty;
          description
            "L2VPN VC no next hop";
        }
      }
      case l2vpn-vc-nh-p2p {
        leaf p2p {
          type empty;
          description
            "L2VPN VC next hop P2P";
        }
      }
      case l2vpn-vc-nh-ipv4-addr {
        leaf nh-ipv4-addr {
          type inet:ipv4-address;
          description
            "L2VPN VC next hop IPV4 address";
        }
      }
      case l2vpn-vc-nh-ipv6-addr {
        leaf nh-ipv6-addr {
          type inet:ipv6-address;
          description
            "L2VPN VC next hop IPV6 address";
        }
      }
    }
  }

  grouping l2vpn-vc-pref-path {
    description
      "L2VPN VC preferred path information";
    choice pref-path-type-choice {
      description
        "Type of the preferred path";
      case l2vpn-pref-not-conf {
        leaf not-conf {
          type empty;
          description
            "L2VPN VC preferred path not configured";
        }
      }
      case l2vpn-pref-no-route {
        leaf no-route {
          type empty;
          description
            "L2VPN VC no route to preferred path";
        }
      }
      case l2vpn-pref-out-if {
        leaf out-if {
          type string;
          description
            "L2VPN VC output tunnel interface";
        }
      }
      case l2vpn-pref-next-hop-addr {
        leaf nh-addr {
          type inet:ipv4-address;
          description
            "L2VPN VC next hop IPV4 address";
        }
      }
    }
  }

  grouping l2vpn-atom-bgp-info {
    description
      "L2VPN ATOM BGP signaling info";
    leaf local-ve-id {
      type uint32;
      description
        "Local VE identifier";
    }
    leaf remote-ve-id {
      type uint32;
      description
        "Remote VE identifier";
    }
  }

  grouping l2vpn-atom-ldp-info {
    description
      "L2VPN ATOM LDP signaling info";
    leaf tgt-hello-src {
      type inet:ipv4-address;
      description
        "IP address used as the source for LDP targeted hello messages.";
    }
    leaf tgt-hello-dest {
      type inet:ipv4-address;
      description
        "IP address used as the destination for LDP targeted hello messages.";
    }
    leaf status {
      type l2vpn-ios-xe-oper:l2vpn-atom-ldp-status;
      description
        "Status of the LDP";
    }
    leaf gr-config {
      type l2vpn-ios-xe-oper:l2vpn-feat-conf;
      description
        "Indicates the configuration state of the Graceful Restart (GR) feature for LDP-based L2VPN pseudowire signaling.";
    }
    leaf gr {
      type l2vpn-ios-xe-oper:l2vpn-feat-en;
      description
        "Indicates whether the Graceful Restart (GR) feature is enabled for LDP-based L2VPN pseudowire signaling.";
    }
    leaf nsr-config {
      type l2vpn-ios-xe-oper:l2vpn-feat-conf;
      description
        "Indicates the configuration state of the Non-Stop Routing (NSR) feature for LDP-based L2VPN pseudowire signaling.";
    }
    leaf nsr {
      type l2vpn-ios-xe-oper:l2vpn-feat-en;
      description
        "Indicates whether the Non-Stop Routing (NSR) feature is enabled for LDP-based L2VPN pseudowire signaling.";
    }
    leaf fec-type {
      type l2vpn-ios-xe-oper:l2vpn-atom-fec-type;
      description
        "Specifies the type of Forwarding Equivalence Class (FEC) used for LDP-based L2VPN pseudowire signaling.";
    }
  }

  grouping l2vpn-atom-vpws-info {
    description
      "L2VPN ATOM VPWS information";
    leaf assoc-member-if {
      type string;
      description
        "Associated member interface name";
    }
    leaf group-name {
      type string;
      description
        "Name of the group to which this L2VPN VPWS service belongs.";
    }
    leaf status {
      type l2vpn-ios-xe-oper:l2vpn-service-state;
      description
        "Status of service";
    }
    leaf iw-type {
      type l2vpn-ios-xe-oper:l2vpn-iw-type;
      description
        "Specifies the type of interworking configured for this L2VPN VPWS service (e.g., Ethernet, IP).";
    }
  }

  grouping l2vpn-atom-vpls-info {
    description
      "L2VPN ATOM VPLS information";
    leaf bd-id {
      type uint32;
      description
        "Identifier of the bridge domain associated with this VPLS service instance.";
    }
  }

  grouping l2vpn-service-info {
    description
      "L2VPN service information";
    leaf service-name {
      type string;
      description
        "Specifies the configured name of the L2VPN service associated with this pseudowire.";
    }
    leaf service-id {
      type uint32;
      description
        "Unique identifier for the L2VPN service associated with this pseudowire.";
    }
    choice atom-service-type-choice {
      description
        "Type of L2VPN ATOM service";
      case l2vpn-service-vpws {
        container vpws-info {
          description
            "L2VPN VPWS service information";
          uses l2vpn-ios-xe-oper:l2vpn-atom-vpws-info;
        }
      }
      case l2vpn-service-vpls {
        container vpls-info {
          description
            "L2VPN VPLS service information";
          uses l2vpn-ios-xe-oper:l2vpn-atom-vpls-info;
        }
      }
    }
  }

  grouping signalling-proto-info {
    description
      "L2VPN signalling protocol info";
    leaf ldp-route-watch {
      type l2vpn-ios-xe-oper:l2vpn-feat-en;
      description
        "LDP route watch status";
    }
    leaf label-state {
      type l2vpn-ios-xe-oper:l2vpn-atom-mgr-state;
      description
        "Operational status of the MPLS label assigned to this pseudowire.";
    }
    leaf fsm-state {
      type l2vpn-ios-xe-oper:l2vpn-atom-mgr-fsm-state;
      description
        "Current state of the finite state machine (FSM) managing the pseudowire signaling process.";
    }
    leaf local-dp-status-rcv {
      type l2vpn-ios-xe-oper:l2vpn-circuit-status;
      description
        "Local dataplane status received";
    }
    leaf bfd-dp-status-rcv {
      type l2vpn-ios-xe-oper:l2vpn-circuit-status;
      description
        "BFD dataplane status received";
    }
    leaf bfd-dp-pm-status-rcv {
      type l2vpn-ios-xe-oper:l2vpn-circuit-status;
      description
        "BFD peer monitor status received";
    }
    leaf status-rcv-ac {
      type l2vpn-ios-xe-oper:l2vpn-circuit-status;
      description
        "Status received from access circuit";
    }
    leaf status-sent-ac {
      type l2vpn-ios-xe-oper:l2vpn-circuit-status;
      description
        "Status sent to access circuit";
    }
    leaf status-rcv-pw {
      type l2vpn-ios-xe-oper:l2vpn-circuit-status;
      description
        "Status received from pseudowire interface";
    }
    leaf status-sent-nw-peer {
      type l2vpn-ios-xe-oper:l2vpn-circuit-status;
      description
        "Status sent to network peer";
    }
    leaf status-rcv-nw-peer {
      type l2vpn-ios-xe-oper:l2vpn-circuit-status;
      description
        "Status received from network peer";
    }
    leaf adj-status-remote-peer {
      type l2vpn-ios-xe-oper:l2vpn-circuit-status;
      description
        "Adjacency status of remote peer";
    }
    choice signalling-choice {
      description
        "Type of signalling for L2VPN negotiations";
      case l2vpn-atom-vc-proto-ldp {
        container ldp-info {
          description
            "L2VPN LDP signalling information";
          uses l2vpn-ios-xe-oper:l2vpn-atom-ldp-info;
        }
      }
      case l2vpn-atom-vc-proto-bgp {
        container bgp-info {
          description
            "L2VPN BGP signalling information";
          uses l2vpn-ios-xe-oper:l2vpn-atom-bgp-info;
        }
      }
    }
  }

  grouping l2vpn-binding-params {
    description
      "L2VPN binding parameters";
    leaf label {
      type uint32;
      description
        "MPLS label value assigned to the virtual circuit (VC) for the pseudowire.";
    }
    leaf group-id {
      type uint32;
      description
        "Identifier for the group to which this pseudowire belongs, used for grouping related virtual circuits in L2VPN.";
    }
    leaf if-name {
      type string;
      description
        "Name of the interface associated with the L2VPN virtual circuit.";
    }
    leaf mtu {
      type uint16;
      description
        "Maximum Transmission Unit (MTU) configured for the pseudowire binding.";
    }
    leaf control-word {
      type l2vpn-ios-xe-oper:l2vpn-atom-pw-cw;
      description
        "Indicates the control word configuration or status for the pseudowire binding.";
    }
    leaf cw-auto-sense {
      type l2vpn-ios-xe-oper:l2vpn-cw-auto-sense;
      description
        "Indicates whether automatic detection of control word usage is enabled for the remote pseudowire binding.";
    }
    leaf vc-type {
      type l2vpn-ios-xe-oper:l2vpn-atom-vc-type;
      description
        "Specifies the type of virtual circuit (VC) used for the pseudowire binding, such as Ethernet, Frame Relay, or ATM.";
    }
    leaf vccv-cv-type {
      type l2vpn-ios-xe-oper:l2vpn-vccv-cv-type-flags;
      description
        "Flag indicating the type of Connectivity Verification (CV) supported for Virtual Circuit Connectivity Verification (VCCV) on this pseudowire.";
    }
    leaf vccv-cc-type {
      type l2vpn-ios-xe-oper:l2vpn-vccv-cc-type-flags;
      description
        "Indicates the type of Control Channel (CC) used for Virtual Circuit Connectivity Verification (VCCV) on the pseudowire binding.";
    }
    leaf status-tlv {
      type l2vpn-ios-xe-oper:l2vpn-vc-status-tlv;
      description
        "Specifies the configuration of the Status Type-Length-Value (TLV) used for signaling the status of the pseudowire in L2VPN.";
    }
  }

  grouping l2vpn-pw-data-params {
    description
      "L2vpn PW binding data parameters";
    container local-binding {
      description
        "Binding details of the local node";
      uses l2vpn-ios-xe-oper:l2vpn-binding-params;
    }
    container remote-binding {
      description
        "Binding details of the remote node";
      uses l2vpn-ios-xe-oper:l2vpn-binding-params;
    }
  }

  grouping l2vpn-atom-dataplane-params {
    description
      "VC statistics data";
    leaf segment-id {
      type uint32;
      description
        "Identifier for the Segment Switching Module (SSM) segment associated with the L2VPN dataplane. Used to uniquely identify the dataplane segment for the virtual circuit.";
    }
    leaf switch-id {
      type uint32;
      description
        "Identifier for the Segment Switching Module (SSM) switch associated with the L2VPN dataplane. Used to uniquely identify the switch instance for the virtual circuit.";
    }
    leaf pwid {
      type uint32;
      description
        "Pseudowire (PW) identifier used to uniquely identify the L2VPN pseudowire in the dataplane.";
    }
  }

  grouping l2vpn-atom-vc-statistics {
    description
      "L2vpn dataplane parameters";
    leaf rx-pkts {
      type uint64;
      description
        "Number of packets received (RX) on the L2VPN virtual circuit.";
    }
    leaf rx-bytes {
      type uint64;
      description
        "Number of bytes received (RX) on the L2VPN virtual circuit.";
    }
    leaf rx-drops {
      type uint64;
      description
        "Number of received packets dropped on the virtual circuit (VC) due to errors or resource limitations.";
    }
    leaf seq-err-pkts {
      type uint64;
      description
        "RX sequential error packets";
    }
    leaf tx-pkts {
      type uint64;
      description
        "Total number of packets transmitted on the virtual circuit (VC).";
    }
    leaf tx-bytes {
      type uint64;
      description
        "Total number of bytes transmitted on the virtual circuit (VC).";
    }
    leaf tx-drops {
      type uint64;
      description
        "Number of transmitted packets dropped on the virtual circuit (VC) due to errors or resource limitations.";
    }
    leaf mwc-tx {
      type uint64;
      description
        "MAC withdraw TX counter";
    }
    leaf mwc-rx {
      type uint64;
      description
        "MAC withdraw RX counter";
    }
  }

  grouping l2vpn-atom-vc-data {
    description
      "L2VPN L2 atom VC data";
    leaf local-if-name {
      type string;
      description
        "Local Interface name";
    }
    leaf circuit-type {
      type l2vpn-ios-xe-oper:l2vpn-ac-circuit-type;
      description
        "Specifies the type of attachment circuit used in the L2VPN virtual circuit (e.g., Ethernet, VLAN).";
    }
    leaf if-name {
      type string;
      description
        "Name of the interface associated with the remote pseudowire binding.";
    }
    leaf service-type {
      type l2vpn-ios-xe-oper:l2vpn-atom-service-type;
      description
        "Specifies the type of L2VPN service (e.g., Ethernet, ATM, Frame Relay) associated with this virtual circuit.";
    }
    leaf service-name {
      type string;
      description
        "Name of the L2VPN service associated with this virtual circuit, used for identification and management purposes.";
    }
    leaf vc-status {
      type l2vpn-ios-xe-oper:l2vpn-vc-status;
      description
        "Indicates the current operational status of the L2VPN virtual circuit (VC), such as up, down, or administratively down.";
    }
    leaf create-time {
      type yang:date-and-time;
      description
        "L2VPN VC Create time";
    }
    leaf last-status-change {
      type yang:date-and-time;
      description
        "L2VPN VC last status change";
    }
    leaf last-fsm-change {
      type yang:date-and-time;
      description
        "L2VPN VC last FSM change";
    }
    leaf last-error {
      type l2vpn-ios-xe-oper:l2vpn-atom-mgr-vc-last-error;
      description
        "L2VPN VC last error";
    }
    leaf output-if {
      type string;
      description
        "L2VPN VC output interface";
    }
    leaf-list label-stack {
      type uint32;
      ordered-by user;
      description
        "L2VPN imposed label stack";
    }
    container preferred-path {
      description
        "L2VPN VC preferred path";
      uses l2vpn-ios-xe-oper:l2vpn-vc-pref-path;
    }
    leaf default-path {
      type l2vpn-ios-xe-oper:l2vpn-def-path-state;
      description
        "Indicates the default path state for the L2VPN Virtual Circuit (VC), used when no preferred path is configured or available.";
    }
    container next-hop {
      description
        "Specifies the next hop information for the L2VPN Virtual Circuit (VC), used to determine the forwarding path.";
      uses l2vpn-ios-xe-oper:l2vpn-vc-next-hop;
    }
    leaf lb-mode {
      type l2vpn-ios-xe-oper:l2vpn-pw-lb-mode;
      description
        "Specifies the load-balancing mode used for L2VPN pseudowires, determining how traffic is distributed across available paths.";
    }
    leaf lb-flow-class {
      type l2vpn-ios-xe-oper:l2vpn-pw-lb-fc;
      description
        "Indicates the flow classification mode used for load balancing in L2VPN pseudowires, specifying how traffic flows are identified for distribution.";
    }
    container service-info {
      description
        "Contains detailed information about the L2VPN service associated with the pseudowire, including service type, identifiers, and configuration details.";
      uses l2vpn-ios-xe-oper:l2vpn-service-info;
    }
    leaf signalling-proto {
      type l2vpn-ios-xe-oper:l2vpn-atom-vc-protocol-type;
      description
        "Signalling protocol type";
    }
    container signalling-info {
      description
        "Pseudowire signalling information";
      uses l2vpn-ios-xe-oper:signalling-proto-info;
    }
    leaf rx-sequence {
      type l2vpn-ios-xe-oper:l2vpn-pw-sequence;
      description
        "Indicates the receive-side sequencing configuration or status for L2VPN pseudowire data packets.";
    }
    leaf tx-sequence {
      type l2vpn-ios-xe-oper:l2vpn-pw-sequence;
      description
        "Indicates the transmit-side sequencing configuration or status for L2VPN pseudowire data packets.";
    }
    container pw-binding-data {
      description
        "Contains operational data related to the binding of a pseudowire, including parameters and state information relevant to the L2VPN service.";
      uses l2vpn-ios-xe-oper:l2vpn-pw-data-params;
    }
    container dataplane-data {
      description
        "Contains operational dataplane parameters and identifiers for the L2VPN atom virtual circuit, such as segment ID, switch ID, and pseudowire ID.";
      uses l2vpn-ios-xe-oper:l2vpn-atom-dataplane-params;
    }
    container vc-stats {
      description
        "Contains statistics for the virtual circuit (VC) in the L2VPN atom, including packet and byte counters for received and transmitted traffic.";
      uses l2vpn-ios-xe-oper:l2vpn-atom-vc-statistics;
    }
  }

  grouping l2vpn-atom-key {
    description
      "L2VPN atom vc table key";
    leaf peer-address {
      type inet:ipv4-address;
      description
        "L2VPN vc peer ipv4 address";
    }
    leaf vcid {
      type uint32;
      description
        "L2VPN virtual circuit id";
    }
  }

  container l2vpn-oper-data {
    config false;
    description
      "Container for operational data related to Layer 2 Virtual Private Network (L2VPN) services, including status and statistics.";
    container l2vpn-services {
      presence "l2vpn-services";
      description
        "Container for operational data of configured Layer 2 VPN (L2VPN) services on the device.";
      uses l2vpn-ios-xe-oper:l2vpn-services;
    }
    list l2vpn-atom-vc-info {
      key "peer-address vcid";
      description
        "L2VPN atom VC Info";
      uses l2vpn-ios-xe-oper:l2vpn-atom-key;
      uses l2vpn-ios-xe-oper:l2vpn-atom-vc-data;
    }
  }
}
