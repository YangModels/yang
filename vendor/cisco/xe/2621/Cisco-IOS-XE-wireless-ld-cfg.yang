module Cisco-IOS-XE-wireless-ld-cfg {
  yang-version 1.1;
  namespace "http://cisco.com/ns/yang/Cisco-IOS-XE-wireless-ld-cfg";
  prefix ios-xe-ld-cfg;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     global Live-Detect (LD) configurational data.
     Copyright (c) 2026 by Cisco Systems, Inc.
     All rights reserved.";

  revision 2026-08-01 {
    description
      "Initial revision";
    reference
      "1.0.0";
    cisco-semver:module-version "1.0.0";
  }

  grouping ld-config {
    description
      "Live-Detect Configuration";
    leaf sensor-ip {
      type inet:ip-address;
      default "0.0.0.0";
      description
        "IP address used by the DDN agent for communication
         with the Ultra-Sensor";
    }
    leaf dnld-url {
      type string {
        length "0..204" {
          error-message "DDN download URL must not be greater than 204 characters";
          error-app-tag "must-violation";
        }
        pattern '(((https?)://[A-Za-z0-9@.:/?=%,&-]+)|(((([0-1]?[0-9]{1,2})|([2]?[0-5]{1,2})|([2]?[0-4][0-9]))[.]){3}(([0-1]?[0-9]{1,2})|([2]?[0-5]{1,2})|([2]?[0-4][1-9]))))*' {
          error-message "DDN download URL must be a valid https or http URL";
          error-app-tag "pattern-violation";
        }
      }
      default "https://containers.cisco.com";
      description
        "DDN endpoint URL from which the DDN agent IOx
         container is downloaded";
    }
  }

  container ld-cfg-data {
    description
      "Container for global Live-Detect (LD) configuration data";
    container ld-config {
      presence "ld-config";
      description
        "Live-Detect (LD) configuration";
      uses ios-xe-ld-cfg:ld-config;
    }
  }
}
