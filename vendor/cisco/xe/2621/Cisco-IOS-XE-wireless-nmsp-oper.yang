module Cisco-IOS-XE-wireless-nmsp-oper {
  yang-version 1.1;
  namespace "http://cisco.com/ns/yang/Cisco-IOS-XE-wireless-nmsp-oper";
  prefix wireless-nmsp-oper;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for wireless nmsp operational data.
     Copyright (c) 2016-2019, 2022 by Cisco Systems, Inc.
     All rights reserved.";

  revision 2026-08-01 {
    description
      "Updated descriptions of several model elements to clarify their meaning and purpose";
    reference
      "4.2.1";
    cisco-semver:module-version "4.2.1";
  }
  revision 2022-11-01 {
    description
      "Update yang-version to 1.1";
    reference
      "4.2.0";
    cisco-semver:module-version "4.2.0";
  }
  revision 2019-05-01 {
    description
      "Added semantic version";
    reference
      "4.1.0";
    cisco-semver:module-version "4.1.0";
  }
  revision 2018-09-19 {
    description
      "- Change type of boolean leafs in nmsp-services to empty
       - Remove rssi-ms-associated-only from nmsp-services";
    reference
      "4.0.0";
    cisco-semver:module-version "4.0.0";
  }
  revision 2018-04-13 {
    description
      "Added support for CMX AP filtering";
    reference
      "3.0.0";
    cisco-semver:module-version "3.0.0";
  }
  revision 2018-01-31 {
    description
      "CMX cloud support";
    reference
      "2.1.0";
    cisco-semver:module-version "2.1.0";
  }
  revision 2018-01-24 {
    description
      "The first generally available version";
    reference
      "2.0.0";
    cisco-semver:module-version "2.0.0";
  }
  revision 2017-05-05 {
    description
      "Initial revision";
    reference
      "1.0.0";
    cisco-semver:module-version "1.0.0";
  }

  typedef enm-nmsp-transport-type {
    type enumeration {
      enum default-class-type2 {
        value 0;
        description
          "TLS transport protocol";
      }
      enum manual-changed-class-type1 {
        value 1;
        description
          "HTTPS transport protocol";
      }
    }
    description
      "Enumeration of all the supported transport protocols";
  }

  typedef enm-nmsp-cloud-connectivity-type {
    type enumeration {
      enum nmsp-connectivity-down {
        value 0;
        description
          "It represents the connectivity status DOWN";
      }
      enum nmsp-connectivity-https {
        value 1;
        description
          "It represents the status UP for the HTTPS connection";
      }
    }
    description
      "Enumeration of all the combinations of connectivity and status";
  }

  grouping nmsp-services {
    description
      "NMSP capabilities of the wireless controller, or service subscriptions established by CMX";
    leaf mask {
      type uint64;
      description
        "NMSP subservice bitmask: combination of all the subservices";
    }
    leaf rssi-ms {
      type empty;
      description
        "Indicates support for reporting Received Signal Strength Indicator (RSSI) data for mobile stations";
    }
    leaf rssi-rfid {
      type empty;
      description
        "Indicates support for reporting Received Signal Strength Indicator (RSSI) data for RFID tags";
    }
    leaf rssi-rogue {
      type empty;
      description
        "Indicates support for reporting Received Signal Strength Indicator (RSSI) data for rogue devices";
    }
    leaf rssi-interferer {
      type empty;
      description
        "Indicates support for reporting Received Signal Strength Indicator (RSSI) data for interferers";
    }
    leaf rssi-hs {
      type empty;
      description
        "Indicates support for reporting Received Signal Strength Indicator (RSSI) data for handover clients";
    }
    leaf rssi-ms-associated-only {
      type empty;
      description
        "Indicates support for reporting Received Signal Strength Indicator (RSSI) data exclusively for associated mobile stations";
    }
    leaf spectrum-interferer {
      type empty;
      description
        "Indicates support for detecting and reporting spectrum interferers";
    }
    leaf spectrum-air-quality {
      type empty;
      description
        "Indicates support for reporting air quality metrics related to spectrum usage as part of the NMSP service subscription";
    }
    leaf spectrum-aggregate-interferer {
      type empty;
      description
        "Indicates support for detecting and reporting aggregated spectrum interferer information as part of the NMSP service subscription";
    }
    leaf info-ms {
      type empty;
      description
        "Indicates support for providing detailed information about mobile stations as part of the NMSP service subscription";
    }
    leaf info-rfid {
      type empty;
      description
        "Indicates support for providing detailed information about RFID tags as part of the NMSP service subscription";
    }
    leaf info-rogue {
      type empty;
      description
        "Indicates support for providing detailed information about rogue devices detected in the network as part of the NMSP service subscription";
    }
    leaf info-hs {
      type empty;
      description
        "Indicates support for providing detailed information about handover clients as part of the NMSP service subscription.";
    }
    leaf stats-ms {
      type empty;
      description
        "Indicates support for collecting and reporting statistics related to mobile stations as part of the NMSP service subscription";
    }
    leaf stats-rfid {
      type empty;
      description
        "Indicates that the NMSP client supports collecting and reporting statistics for RFID tags";
    }
    leaf stats-rogue {
      type empty;
      description
        "Indicates that the NMSP client supports collecting and reporting statistics for rogue devices";
    }
    leaf attach {
      type empty;
      description
        "Indicates that the NMSP client supports reporting mobile station attachment events.";
    }
    leaf location {
      type empty;
      description
        "Indicates that the NMSP client supports location services";
    }
    leaf fmchs {
      type empty;
      description
        "Indicates that the NMSP client supports handover services";
    }
    leaf ap-monitor {
      type empty;
      description
        "Indicates that the NMSP client supports AP monitor services";
    }
    leaf wips {
      type empty;
      description
        "Wireless Intrusion Detection System capability";
    }
    leaf on-demand {
      type empty;
      description
        "Indicates that the NMSP client supports on-demand services";
    }
    leaf ap-info {
      type empty;
      description
        "Indicates that the NMSP client supports providing detailed information about access points.";
    }
  }

  grouping nmsp-client-registration-info {
    description
      "Registration data for EWLC applications acting as NMSP clients";
    leaf client-id {
      type uint32;
      description
        "NMSP client identifier";
    }
    container services {
      description
        "NMSP capabilities provided by EWLC application (NMSP client)";
      uses wireless-nmsp-oper:nmsp-services;
    }
  }

  grouping nmsp-cmx-message-counter {
    description
      "Counter for message exchanged between NMSPd and CMX";
    leaf counter {
      type uint64;
      description
        "Amount of messages sent or received";
    }
    leaf msg-id {
      type uint16;
      description
        "NMSP protocol message identifier";
    }
  }

  grouping nmsp-cmx-connection-stats {
    description
      "Statistics of connection from CMX to NMSP daemon";
    list tx-msg-counter {
      description
        "Counters for all the messages transmitted from NMSPd to CMX";
      uses wireless-nmsp-oper:nmsp-cmx-message-counter;
    }
    list rx-msg-counter {
      description
        "Counters for all the messages received by NMSPd from CMX";
      uses wireless-nmsp-oper:nmsp-cmx-message-counter;
    }
    leaf unsupported-msg-count {
      type uint64;
      description
        "Number of unsupported messages received by NMSP daemon from CMX";
    }
    leaf tx-data-frames {
      type uint64;
      description
        "Number of data frames transferred from NMSP daemon to CMX";
    }
    leaf rx-data-frames {
      type uint64;
      description
        "Number of data frames received by NMSP daemon from CMX";
    }
    leaf connections {
      type uint64;
      description
        "Amount of successful connections";
    }
    leaf disconnections {
      type uint64;
      description
        "Amount of disconnections";
    }
  }

  grouping nmsp-cmx-information {
    description
      "CMX connection information";
    leaf peer-ip {
      type inet:ip-address;
      description
        "IP address of the CMX";
    }
    leaf connection-id {
      type uint64;
      description
        "Internal connection ID of the CMX";
    }
    leaf active {
      type boolean;
      description
        "Flag indicating whether CMX connection is active";
    }
    container con-stats {
      description
        "Statistics of messages sent/received";
      uses wireless-nmsp-oper:nmsp-cmx-connection-stats;
    }
    container subscriptions {
      description
        "Service subscriptions established by given CMX";
      uses wireless-nmsp-oper:nmsp-services;
    }
    leaf transport {
      type wireless-nmsp-oper:enm-nmsp-transport-type;
      description
        "The transport used for this CMX connection";
    }
  }

  grouping nmsp-statistics-ssl {
    description
      "Statistics of the SSL connection between CMX and NMSP daemon";
    leaf verify-count {
      type uint64;
      description
        "Total amount of SSL certificate verifications";
    }
    leaf verify-fail {
      type uint64;
      description
        "Amount of SSL certificate verification failures";
    }
    leaf verify-success {
      type uint64;
      description
        "Amount of successful certificate verification attempts";
    }
    leaf connection-created {
      type uint64;
      description
        "Amount of CMX to NMSPd connections created";
    }
    leaf connection-closed {
      type uint64;
      description
        "Amount of CMX to NMSPd connections closed";
    }
    leaf accept-attempts {
      type uint64;
      description
        "Total amount of connection accept attempts";
    }
    leaf accept-fail {
      type uint64;
      description
        "Failures in accepting incoming connections";
    }
    leaf accept-reject {
      type uint64;
      description
        "Amount of incoming connections rejected during acceptance phase";
    }
    leaf accept-success {
      type uint64;
      description
        "Amount of accepted incoming connections";
    }
    leaf accept-register-fail {
      type uint64;
      description
        "Amount of failed registrations";
    }
  }

  grouping nmsp-statistics-aaa {
    description
      "NMSP statistics for AUthentication, AUthorization and Accounting (AAA)";
    leaf aaa-request {
      type uint64;
      description
        "Total amount of AAA requests";
    }
    leaf aaa-send-fail {
      type uint64;
      description
        "Amount of requests, that were failed to transmit to AAA module";
    }
    leaf aaa-send-success {
      type uint64;
      description
        "Amount of requests successfully transmitted to AAA module";
    }
    leaf aaa-response {
      type uint64;
      description
        "Amount of responses received from AAA module";
    }
    leaf aaa-validation-total {
      type uint64;
      description
        "Amount of received responses from AAA that are subject of further validation";
    }
    leaf aaa-validation-fail {
      type uint64;
      description
        "Number of responses received from AAA that failed validation";
    }
    leaf aaa-validation-success {
      type uint64;
      description
        "Amount of received responses from AAA, that were successfully validated";
    }
  }

  grouping nmsp-statistics-srv {
    description
      "NMSP daemon statistics";
    leaf srv-restarts {
      type uint64;
      description
        "Number of NMSP daemon restarts";
    }
  }

  grouping nmsp-statistics {
    description
      "Global NMSP service statistics";
    container ssl-stats {
      description
        "NMSP SSL statistics";
      uses wireless-nmsp-oper:nmsp-statistics-ssl;
    }
    container aaa-stats {
      description
        "NMSP AAA statistics";
      uses wireless-nmsp-oper:nmsp-statistics-aaa;
    }
    container srv-stats {
      description
        "NMSP daemon statistics";
      uses wireless-nmsp-oper:nmsp-statistics-srv;
    }
  }

  grouping nmsp-cmx-cloud-stats {
    description
      "Statistics of connection from CMX to NMSP daemon via cloud services";
    leaf tx-dataframes {
      type uint32;
      description
        "Number of data frames sent";
    }
    leaf rx-dataframes {
      type uint32;
      description
        "Number of data frames received";
    }
    leaf tx-heartbeat-req {
      type uint32;
      description
        "Number of HTTP heartbeats sent";
    }
    leaf heartbeat-timeout {
      type uint32;
      description
        "Number of heartbeat timeouts";
    }
    leaf rx-subscriber-req {
      type uint32;
      description
        "Number of requests from subscriber";
    }
    leaf tx-databytes {
      type uint32;
      description
        "Number of bytes sent";
    }
    leaf rx-databytes {
      type uint32;
      description
        "Number of bytes received";
    }
    leaf tx-heartbeat-fail {
      type uint32;
      description
        "Count of failures sending heartbeat";
    }
    leaf rx-data-fail {
      type uint32;
      description
        "Number of failures receiving data";
    }
    leaf tx-data-fail {
      type uint32;
      description
        "Number of failures sending data";
    }
  }

  grouping nmsp-cmx-cloud-status {
    description
      "Statistics for CMX cloud";
    leaf ip-address {
      type inet:ip-address;
      description
        "The resolved IP address of the CMX cloud server";
    }
    leaf connectivity {
      type wireless-nmsp-oper:enm-nmsp-cloud-connectivity-type;
      description
        "Enum representing the status UP/DOWN of the  HTTP connection to the cloud services";
    }
    leaf service-up {
      type boolean;
      description
        "True if NMSP connectivity towards CMX cloud is UP";
    }
    leaf last-request-status {
      type string;
      description
        "Text description of the status of the most recent request sent to the CMX cloud server.";
    }
    leaf heartbeat-status-ok {
      type boolean;
      description
        "True if the last heartbeat to the CMX cloud server was successful";
    }
  }

  grouping nmsp-cmx-cloud-info {
    description
      "Information about the CMX cloud services";
    container cloud-status {
      description
        "Status of the cloud connection";
      uses wireless-nmsp-oper:nmsp-cmx-cloud-status;
    }
    container cloud-stats {
      description
        "Statistics of the cloud connection";
      uses wireless-nmsp-oper:nmsp-cmx-cloud-stats;
    }
  }

  container nmsp-oper-data {
    config false;
    description
      "Container for operational data related to the Network Mobility Services Protocol (NMSP), providing information about NMSP clients, connections, and service statistics";
    list client-registration {
      key "client-id";
      description
        "Table of controller applications providing certain NMSP services (also known as NMSP clients)";
      uses wireless-nmsp-oper:nmsp-client-registration-info;
    }
    list cmx-connection {
      key "peer-ip";
      description
        "CMX connection table";
      uses wireless-nmsp-oper:nmsp-cmx-information;
    }
    container cmx-cloud-info {
      presence "nmsp-cmx-cloud-info-tbl";
      description
        "Table of information describing NMSP services over HTTPS transport";
      uses wireless-nmsp-oper:nmsp-cmx-cloud-info;
    }
    container statistics {
      presence "nmsp-statistics-tbl";
      description
        "NMSP statistics table";
      uses wireless-nmsp-oper:nmsp-statistics;
    }
  }
}
