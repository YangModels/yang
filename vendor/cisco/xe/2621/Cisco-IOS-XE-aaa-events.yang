module Cisco-IOS-XE-aaa-events {
  yang-version 1.1;
  namespace "http://cisco.com/ns/yang/Cisco-IOS-XE-aaa-events";
  prefix aaa-ios-events-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains YANG definitions for AAA
     event notifications generated from executing
     the RPC.
     Copyright (c) 2021-2022 by Cisco Systems, Inc.
     All rights reserved.";

  revision 2022-11-01 {
    description
      "Update yang-version to 1.1";
    reference
      "1.1.0";
    cisco-semver:module-version "1.1.0";
  }
  revision 2021-07-01 {
    description
      "Initial revision";
    reference
      "1.0.0";
    cisco-semver:module-version "1.0.0";
  }

  typedef auth-result-type {
    type enumeration {
      enum auth-status-pass {
        value 0;
        description
          "User was successfully authenticated.";
      }
      enum auth-status-fail {
        value 1;
        description
          "User authentication request was rejected by server.";
      }
      enum auth-status-error {
        value 2;
        description
          "Error while executing the authentication request.";
      }
    }
    description
      "AAA auth result types";
  }

  grouping aaa-command {
    description
      "Notification for the test aaa command for authentication.";
    leaf id {
      type uint32;
      description
        "The ID is an integer used to map the rpc request
         with the corresponding event notification.";
    }
    leaf auth-result {
      type aaa-ios-events-ios-xe-oper:auth-result-type;
      description
        "Authentication result for the test aaa command.";
    }
  }

  notification test-aaa-authentication-update {
    description
      "Contains the notification after the test aaa authentication
       completes. Contains two fields. Result can be either: pass/fail/error.
       The id field is to be used to map the rpc
       request with the corresponding event notification.";
    uses aaa-ios-events-ios-xe-oper:aaa-command;
  }
}
