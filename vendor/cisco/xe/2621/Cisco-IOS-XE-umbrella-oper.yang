module Cisco-IOS-XE-umbrella-oper {
  yang-version 1.1;
  namespace "http://cisco.com/ns/yang/Cisco-IOS-XE-umbrella-oper";
  prefix umbrella-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains collection of YANG
     definitions for Umbrella operational data.
     Copyright (c) 2018-2019, 2022, 2026 by Cisco Systems, Inc.
     All rights reserved.";

  revision 2026-08-01 {
    description
      "Updated descriptions for several model elements to clarify their meaning and purpose";
    reference
      "1.2.1";
    cisco-semver:module-version "1.2.1";
  }
  revision 2022-11-01 {
    description
      "Update yang-version to 1.1";
    reference
      "1.2.0";
    cisco-semver:module-version "1.2.0";
  }
  revision 2019-05-01 {
    description
      "Added semantic version";
    reference
      "1.1.0";
    cisco-semver:module-version "1.1.0";
  }
  revision 2018-04-19 {
    description
      "Initial revision";
    reference
      "1.0.0";
    cisco-semver:module-version "1.0.0";
  }

  grouping umbrella-dev-reg-data {
    description
      "Contains device registration data for Cisco Umbrella";
    leaf name {
      type string;
      description
        "Name of the device associated with the Cisco Umbrella registration record";
    }
    leaf status {
      type string;
      description
        "Current registration status of the device in Cisco Umbrella";
    }
    leaf tag {
      type string;
      description
        "Tag assigned to the device for identification or grouping within Cisco Umbrella";
    }
    leaf device-id {
      type string;
      description
        "Unique identifier assigned to the device for Cisco Umbrella registration";
    }
    leaf description {
      type string;
      description
        "Description or notes regarding the device's registration with Cisco Umbrella";
    }
  }

  grouping umbrella-overview {
    description
      "Overview of Umbrella";
    leaf registrations-completed {
      type uint16;
      description
        "Total number of completed Cisco Umbrella device registrations";
    }
    leaf registrations-requested {
      type uint16;
      description
        "Total number of requested Cisco Umbrella device registrations";
    }
    leaf dnscrypt {
      type boolean;
      description
        "Indicates whether DNSCrypt is enabled or disabled for Umbrella";
    }
    leaf last-success-attempt {
      type yang:date-and-time;
      description
        "Timestamp of the last successful DNSCrypt operation for Cisco Umbrella";
    }
  }

  container umbrella-ios-oper-data {
    config false;
    description
      "Operational data of Umbrella";
    list umbrella-dev-reg-data {
      key "name";
      description
        "List of Cisco Umbrella device registration records";
      uses umbrella-ios-xe-oper:umbrella-dev-reg-data;
    }
    container umbrella-overview {
      presence "umbrella-overview";
      description
        "A container for general Umbrella registration information";
      uses umbrella-ios-xe-oper:umbrella-overview;
    }
  }
}
