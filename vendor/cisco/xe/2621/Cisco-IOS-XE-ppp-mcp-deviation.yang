module Cisco-IOS-XE-ppp-mcp-deviation {
  yang-version 1.1;
  namespace "http://cisco.com/ns/yang/Cisco-IOS-XE-ppp-mcp-deviation";
  prefix ios-ppp-mcp-d;

  import Cisco-IOS-XE-native {
    prefix ios;
  }
  import Cisco-IOS-XE-ppp {
    prefix ios-ppp;
  }

  organization
    "Cisco Systems";
  description
    "Cisco XE Native Deviation YANG module for IOS
     Copyright (c) 2016 by Cisco Systems, Inc.
     All rights reserved.";

  revision 2024-07-01 {
    description
      "- Initial Revision";
  }

  deviation "/ios:native/ios:ppp/ios-ppp:hold-queue" {
    deviate replace {
      default "262144";
    }
  }
}
