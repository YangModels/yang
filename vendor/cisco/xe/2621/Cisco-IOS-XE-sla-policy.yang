module Cisco-IOS-XE-sla-policy {
  yang-version 1.1;
  namespace "http://cisco.com/ns/yang/Cisco-IOS-XE-sla-policy";
  prefix ios-sla-policy;

  import cisco-semver {
    prefix cisco-semver;
  }
  import Cisco-IOS-XE-native {
    prefix ios;
  }

  organization
    "Cisco Systems, Inc.";
  contact
    "Cisco Systems, Inc.
     Customer Service
     Postal: 170 W Tasman Drive
     San Jose, CA 95134
     Tel: +1 1800 553-NETS
     E-mail: cs-yang@cisco.com";
  description
    "Cisco XE Native SLA Policy YANG model.
     Copyright (c) 2026 by Cisco Systems, Inc.
     All rights reserved.";

  revision 2026-08-01 {
    description
      "Initial revision for SLA Policy configuration";
    cisco-semver:module-version "1.0.0";
  }

  grouping config-sla-policy-grouping {
    container global-preference {
      description
        "SLA Policy Global Preference Configurations Commands";
      presence "true";
      leaf failover {
        description
          "Configure failover behavior";
        type enumeration {
          enum graceful {
            description
              "Graceful Failover";
          }
          enum immediate {
            description
              "Immediate Failover";
          }
        }
        default "graceful";
      }
      leaf load-balance {
        description
          "Configure load balancing behavior";
        type enumeration {
          enum enable {
            description
              "Enable Load Balance";
          }
          enum disable {
            description
              "Disable Load Balance";
          }
        }
        default "enable";
      }
    }
  }

  augment "/ios:native/ios:sla-policy" {
    uses config-sla-policy-grouping;
  }
}
