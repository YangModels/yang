module cisco-xe-ietf-routing-ext {
  namespace "http://cisco.com/ns/yang/cisco-xe-ietf-routing-ext";
  prefix "cisco-ietf-routing";

  import ietf-routing {
    prefix rt;
  }

  import ietf-yang-types {
    prefix ietf-types;
  }

  organization "Cisco Systems, Inc.";

  contact
    "Cisco Systems, Inc.
     Customer Service

     Postal: 170 W Tasman Drive
     San Jose, CA 95134

     Tel: +1 1800 553-NETS

     E-mail: cs-yang@cisco.com";

  description
    "Cisco augmentation to support multiple nexthops under IETF routes.
     Copyright (c) 2023 by Cisco Systems, Inc.
     All rights reserved.";

  revision 2024-03-01 {
    description
      "- Added support for routes to return all next hops for the ietf-routing
         model";
  }

  /*
   * Grouping for the next-hop-list that provides all of the next hops under
   * the route.
   */
  grouping next-hop-list-grouping {
    description
      "Case for choice statement that will be populated with a list of next
       hops if the route has multiple paths";

    list next-hop-list {
      description
        "An entry in a next-hop list.

        Modules for address families MUST augment this list
        with a leaf containing a next-hop address of that
        address family.";
      key "index";
      leaf index {
        description
          "A user-specified identifier utilized to uniquely
          reference the next-hop entry in the next-hop list.
          The value of this index has no semantic meaning
          other than for referencing the entry.";
        type uint8;
      }
      choice next-hop-options {
        description
          "Specifies the type for the next hop.";
        mandatory "true";
        case simple-next-hop {
          description
            "Next hop that defines a gateway IP/IPv6 address and/or
             an outgoing interface.";
          leaf outgoing-interface {
            description
              "Name of the outgoing interface.";
            type string;
          }
          leaf next-hop-address {
            description
              "IP Address.";
            type string;
          }
          leaf uptime {
            description
              "Timestamp of the uptime for the next hop. Time since
               last update.";
            type ietf-types:date-and-time;
          }
        }
        case special-next-hop {
          uses rt:special-next-hop;
        }
      }
    }
  }

  /*
   * Grouping for the uptime leaf that is added to the existing single next-hop
   * field in the model.
   */
  grouping simple-next-hop-uptime-grouping {
    description
      "Grouping for timestamp of last update for a next hop.";

    leaf uptime {
      description
        "Timestamp of the uptime for the next hop. Time since
         last update.";
      type ietf-types:date-and-time;
    }
  }

  augment "/rt:routing-state/rt:routing-instance/rt:ribs/rt:rib/rt:routes/rt:route/rt:next-hop" {
    uses next-hop-list-grouping;
  }

  augment "/rt:routing-state/rt:routing-instance/rt:ribs/rt:rib/rt:routes/rt:route/rt:next-hop/rt:next-hop-options/rt:simple-next-hop" {
    uses simple-next-hop-uptime-grouping;
  }
}
