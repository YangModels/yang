module Cisco-IOS-XE-ospf-oper {
  yang-version 1.1;
  namespace "http://cisco.com/ns/yang/Cisco-IOS-XE-ospf-oper";
  prefix ospf-ios-xe-oper;

  import Cisco-IOS-XE-ospf-common {
    prefix ospf-ios-xe-common;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     monitoring the operation of ospf protocol in a Network Element.
     Copyright (c) 2016-2020, 2022 by Cisco Systems, Inc.
     All rights reserved.";

  revision 2026-08-01 {
    description
      "Updated descriptions of several model elements to clarify their meaning and purpose";
    reference
      "1.6.0";
    cisco-semver:module-version "1.6.0";
  }
  revision 2022-11-01 {
    description
      "Update yang-version to 1.1";
    reference
      "1.5.0";
    cisco-semver:module-version "1.5.0";
  }
  revision 2020-07-01 {
    description
      "Added OSPFv3 interface, neighbor and LS database";
    reference
      "1.4.0";
    cisco-semver:module-version "1.4.0";
  }
  revision 2019-05-01 {
    description
      "Added semantic version";
    reference
      "1.3.0";
    cisco-semver:module-version "1.3.0";
  }
  revision 2018-10-29 {
    description
      "Cleaned up spelling errors in descriptions.";
    reference
      "1.2.0";
    cisco-semver:module-version "1.2.0";
  }
  revision 2018-02-01 {
    description
      "Add Link State data";
    reference
      "1.1.0";
    cisco-semver:module-version "1.1.0";
  }
  revision 2017-10-10 {
    description
      "Initial revision";
    reference
      "1.0.0";
    cisco-semver:module-version "1.0.0";
  }

  typedef address-family {
    type enumeration {
      enum address-family-ipv4 {
        value 0;
      }
      enum address-family-ipv6 {
        value 1;
      }
    }
    description
      "Address family type";
  }

  typedef ospf-operation-mode {
    type enumeration {
      enum ospf-ships-in-the-night {
        value 0;
        description
          "Ships-in-the-night operation mode in which each OSPF instance carries only one address family";
      }
    }
    description
      "OSPF operational mode";
  }

  typedef ospf-network-type {
    type enumeration {
      enum ospf-broadcast {
        value 0;
        description
          "OSPF broadcast multi-access network";
      }
      enum ospf-non-broadcast {
        value 1;
        description
          "OSPF Non-Broadcast Multi-Access (NBMA) network";
      }
      enum ospf-point-to-multipoint {
        value 2;
        description
          "OSPF point-to-multipoint network";
      }
      enum ospf-point-to-point {
        value 3;
        description
          "OSPF point-to-point network";
      }
    }
    description
      "OSPF network type";
  }

  typedef ospf-auth-type {
    type enumeration {
      enum ospf-auth-ipsec {
        value 0;
      }
      enum ospf-auth-trailer-keychain {
        value 1;
      }
      enum ospf-auth-trailer-key {
        value 2;
      }
      enum ospf-auth-type-none {
        value 3;
      }
    }
    description
      "OSPF Authentication type";
  }

  typedef nbr-state-type {
    type enumeration {
      enum ospf-nbr-down {
        value 1;
        description
          "Initial state of the neighbor conversation where no recent information has been received from the neighbor";
      }
      enum ospf-nbr-attempt {
        value 2;
        description
          "State applicable to NBMA networks where the router is sending Hello packets to the neighbor but has not yet received a Hello from the neighbor";
      }
      enum ospf-nbr-init {
        value 3;
        description
          "State where a Hello packet has been received from the neighbor but bi-directional communication has not yet been established";
      }
      enum ospf-nbr-two-way {
        value 4;
        description
          "State where bi-directional communication has been established with the neighbor; DR and BDR election occurs in this state";
      }
      enum ospf-nbr-exchange-start {
        value 5;
        description
          "First step in forming an adjacency where the primary/secondary relationship and initial DD sequence number are negotiated";
      }
      enum ospf-nbr-exchange {
        value 6;
        description
          "State where the router is describing its summary of link state database by sending Database Description packets to the neighbor";
      }
      enum ospf-nbr-loading {
        value 7;
        description
          "State where Link State Request packets are sent to the neighbor asking for the more recent LSAs that have been discovered during the Exchange state";
      }
      enum ospf-nbr-full {
        value 8;
        description
          "State where the neighboring routers are fully adjacent with synchronized link state databases";
      }
    }
    description
      "OSPF neighbor state type";
  }

  typedef ospfv2-lsa-type {
    type enumeration {
      enum ospfv2-lsa-type-unsupported-lsa-type {
        value 0;
      }
      enum ospfv2-lsa-type-router {
        value 1;
      }
      enum ospfv2-lsa-type-network {
        value 2;
      }
      enum ospfv2-lsa-type-summary-net {
        value 3;
      }
      enum ospfv2-lsa-type-summary-router {
        value 4;
      }
      enum ospfv2-lsa-type-as-external {
        value 5;
      }
      enum ospfv2-lsa-type-nssa {
        value 6;
      }
      enum ospfv2-lsa-type-link-scope-opaque {
        value 7;
      }
      enum ospfv2-lsa-type-area-scope-opaque {
        value 8;
      }
      enum ospfv2-lsa-type-as-scope-opaque {
        value 9;
      }
    }
    description
      "Specifies the type of Link State Advertisement (LSA) as defined by OSPF, indicating the function and content of the LSA.";
  }

  typedef ospf-external-metric-type {
    type enumeration {
      enum ospf-ext-metric-type-1 {
        value 0;
      }
      enum ospf-ext-metric-type-2 {
        value 1;
      }
    }
    description
      "External metric type";
  }

  typedef ospfv2-intf-state {
    type enumeration {
      enum ospfv2-interface-state-down {
        value 0;
        description
          "The interface is in the down state. It is not operational and is not participating in OSPF routing";
      }
      enum ospfv2-interface-state-loopback {
        value 1;
        description
          "The interface is in loopback mode. It is advertised as a stub host route with a /32 prefix length";
      }
      enum ospfv2-interface-state-waiting {
        value 2;
        description
          "The interface is in the waiting state, listening for Hello packets from other routers to determine the Designated Router (DR) and Backup Designated Router (BDR) before entering a fully operational state";
      }
      enum ospfv2-interface-state-point-to-mpoint {
        value 3;
        description
          "The interface is operating in point-to-multipoint mode. The router treats the interface as a collection of point-to-point links and communicates with multiple neighbors without DR/BDR election";
      }
      enum ospfv2-interface-state-point-to-point {
        value 4;
        description
          "The interface is operating in point-to-point mode. It has a single neighbor and no DR/BDR election is performed";
      }
      enum ospfv2-interface-state-dr {
        value 5;
        description
          "The interface is fully operational and this router has been elected as the Designated Router (DR) on the network segment";
      }
      enum ospfv2-interface-state-backup {
        value 6;
        description
          "The interface is fully operational and this router has been elected as the Backup Designated Router (BDR) on the network segment";
      }
      enum ospfv2-interface-state-other {
        value 7;
        description
          "The interface is fully operational but this router is neither the Designated Router nor the Backup Designated Router on the network segment; it participates as a DR Other router on the segment";
      }
    }
    description
      "The possible states that an interface can be in";
  }

  typedef ospfv2-auth-type-selection {
    type enumeration {
      enum ospfv2-auth-none {
        value 0;
        description
          "No authentication configured";
      }
      enum ospfv2-auth-trailer-key {
        value 1;
        description
          "Authentication uses the trailer key";
      }
      enum ospfv2-auth-trailer-key-chain {
        value 2;
        description
          "Authentication uses a trailer key chain";
      }
    }
    description
      "The authentication type";
  }

  typedef ospfv2-crypto-algorithm {
    type enumeration {
      enum ospfv2-crypto-cleartest {
        value 0;
        description
          "The OSPFv2 authentication is sent as cleartext";
      }
      enum ospfv2-crypto-md5 {
        value 1;
        description
          "The OSPFv2 authentication is encrypted using
           Message Digest 5";
      }
    }
    description
      "The algorithm in use";
  }

  typedef ospfv3-lsa-type {
    type enumeration {
      enum ospfv3-lsa-type-unsupported {
        value 0;
        description
          "OSPFv3 unsupported LSA";
      }
      enum ospfv3-lsa-type-router {
        value 1;
        description
          "OSPFv3 Router-LSA";
      }
      enum ospfv3-lsa-type-network {
        value 2;
        description
          "OSPFv3 Network-LSA";
      }
      enum ospfv3-lsa-type-inter-area-prefix {
        value 3;
        description
          "OSPFv3 Inter-Area-Prefix-LSA";
      }
      enum ospfv3-lsa-type-inter-area-router {
        value 4;
        description
          "OSPFv3 Inter-Area-Router-LSA";
      }
      enum ospfv3-lsa-type-nssa {
        value 5;
        description
          "OSPFv3-NSSA-LSA";
      }
      enum ospfv3-lsa-type-prefix {
        value 6;
        description
          "OSPFv3 Intra-Area-Prefix-LSA";
      }
    }
    description
      "Specifies the type of Link State Advertisement (LSA) as defined by OSPF, indicating the function and content of the LSA.";
  }

  typedef ospfv3-rtr-lsa-lnk-type {
    type enumeration {
      enum link-type-unknown {
        value 0;
        description
          "Link type unknown";
      }
      enum link-type-router {
        value 1;
        description
          "Link type router";
      }
      enum link-type-transit-network {
        value 2;
        description
          "Link type transit network";
      }
      enum link-type-reserved {
        value 3;
        description
          "Link type reserved";
      }
      enum link-type-virtual {
        value 4;
        description
          "Link type virtual";
      }
    }
    description
      "OSPFv3 router LSA link type";
  }

  typedef ospfv3-ase-metric-type {
    type enumeration {
      enum metric-type-unknown {
        value 0;
        description
          "Unknown metric type";
      }
      enum metric-type1 {
        value 1;
        description
          "Metric type 1, comparable directly to link state metric ";
      }
      enum metric-type2 {
        value 2;
        description
          "Metric type 2, larger than any link state path.";
      }
    }
    description
      "OSPFv3 external LSA metric type";
  }

  typedef ospfv3-ipsec-auth-algo {
    type enumeration {
      enum invalid {
        value 0;
        description
          "Invalid authentication";
      }
      enum md5 {
        value 1;
        description
          "MD5 authentication";
      }
      enum sha1 {
        value 2;
        description
          "SHA1 authentication";
      }
    }
    description
      "IPSEC authentication algorithm type";
  }

  typedef lsa-flag-options {
    type bits {
      bit lsa-flag-options-dc {
        position 0;
      }
      bit lsa-flag-options-p {
        position 1;
      }
      bit lsa-flag-options-mc {
        position 2;
      }
      bit lsa-flag-options-e {
        position 3;
      }
      bit lsa-flag-options-upward {
        position 4;
      }
      bit lsa-flag-options-mt {
        position 5;
      }
      bit lsa-flag-options-r {
        position 6;
      }
      bit lsa-flag-options-af {
        position 7;
      }
    }
    description
      "Specifies the option flags set in the OSPFv3 Link State Advertisement (LSA), indicating supported OSPFv3 features and capabilities.";
  }

  typedef ospfv2-lsa-body-flags-options {
    type bits {
      bit ospv2-lsa-body-flag-options-v {
        position 0;
      }
      bit ospv2-lsa-body-flag-options-e {
        position 1;
      }
      bit ospv2-lsa-body-flag-options-b {
        position 2;
      }
    }
    description
      "OSPFv2 LSA body flags";
  }

  typedef ospfv3-lsa-options {
    type bits {
      bit ospfv3-lsa-flag-dc {
        position 0;
      }
      bit ospfv3-lsa-flag-r {
        position 1;
      }
      bit ospfv3-lsa-flag-n {
        position 2;
      }
      bit ospfv3-lsa-flag-e {
        position 3;
      }
      bit ospfv3-lsa-flag-v6 {
        position 4;
      }
      bit ospfv3-lsa-flag-af {
        position 5;
      }
    }
    description
      "The flags associated with the OSPFv3 LSA";
  }

  typedef ospfv3-lsa-body-flag-options {
    type bits {
      bit ospfv3-lsa-body-flag-options-v {
        position 0;
      }
      bit ospfv3-lsa-body-flag-options-e {
        position 1;
      }
      bit ospfv3-lsa-body-flag-options-b {
        position 2;
      }
      bit ospfv3-lsa-body-flag-options-nt {
        position 3;
      }
    }
    description
      "OSPFv3 LSA body flags";
  }

  typedef ospfv2-lsa-flag-options {
    type bits {
      bit ospfv2-lsa-flag-options-mt {
        position 0;
      }
      bit ospfv2-lsa-flag-options-e {
        position 1;
      }
      bit ospfv2-lsa-flag-options-mc {
        position 2;
      }
      bit ospfv2-lsa-flag-options-np {
        position 3;
      }
      bit ospfv2-lsa-flag-options-l {
        position 4;
      }
      bit ospfv2-lsa-flag-options-dc {
        position 5;
      }
      bit ospfv2-lsa-flag-options-o {
        position 6;
      }
      bit ospfv2-lsa-flag-options-dn {
        position 7;
      }
    }
    description
      "Link State Advertisement options";
  }

  typedef ospfv2-router-lsa-bits {
    type bits {
      bit ospfv2-router-lsa-bits-v {
        position 0;
      }
      bit ospfv2-router-lsa-bits-e {
        position 1;
      }
      bit ospfv2-router-lsa-bits-b {
        position 2;
      }
      bit ospfv2-router-lsa-bits-nt {
        position 3;
      }
    }
    description
      "Router Link State Advertisement bits";
  }

  typedef ospfv3-rtr-lsa-bits {
    type bits {
      bit ospfv3-rtr-lsa-bits-v {
        position 0;
        description
          "OSPFv3 router LSA bit for virtual endpoint";
      }
      bit ospfv3-rtr-lsa-bits-e {
        position 1;
        description
          "OSPFv3 router LSA bit for AS border endpoint";
      }
      bit ospfv3-rtr-lsa-bits-b {
        position 2;
        description
          "OSPFv3 router LSA bit for area border";
      }
      bit ospfv3-rtr-lsa-bits-nt {
        position 3;
        description
          "OSPFv3 router LSA bit for NSSA translation";
      }
    }
    description
      "OSPFv3 router link state advertisement bits";
  }

  typedef ospfv3-lsa-pfx-opts {
    type bits {
      bit nu-bit {
        position 0;
        description
          "NU Bit, when set, the prefix should be  excluded from IPv6 unicast calculations.";
      }
      bit la-bit {
        position 1;
        description
          "LA bit, when set, the prefix is actually an IPv6 interface address of the Advertising Router.";
      }
      bit p-bit {
        position 2;
        description
          "P bit, when set, the NSSA area prefix should be translated to an AS External LSA and advertised by the translating NSSA Border Router.";
      }
      bit dn-bit {
        position 3;
        description
          "DN bit, when set, the inter-area-prefix LSA or AS-external LSA prefix has been advertised as an L3 VPN prefix.";
      }
    }
    description
      "OSPFv3 LSA prefix options";
  }

  typedef ospfv3-lsa-flag-opts {
    type bits {
      bit af-bit {
        position 0;
        description
          "AF bit, when set, the router supports OSPFv3 Address Families as in RFC 5838.";
      }
      bit dc-bit {
        position 1;
        description
          "DC bit, when set,the router supports demand circuits.";
      }
      bit r-bit {
        position 2;
        description
          "R bit, when set, the originator is an active router.";
      }
      bit n-bit {
        position 3;
        description
          "N bit, when set, the router is attached to an NSSA";
      }
      bit e-bit {
        position 4;
        description
          "E bit, this bit describes the way AS-external LSAs are flooded";
      }
      bit v6-bit {
        position 5;
        description
          "V6 bit, if clear, the router or link should be excluded from IPv6 routing calculation";
      }
    }
    description
      "Specifies the OSPFv3 Link State Advertisement (LSA) options field, indicating supported capabilities and features for the LSA.";
  }

  grouping ospfv2-unknown-sub-tlv {
    description
      "OSPF V2 unknown Sub TLV";
    leaf type {
      type uint16;
      description
        "Specifies the type field of the unknown sub-TLV that is found within OSPFv2 Link TLVs.";
    }
    leaf length {
      type uint16;
      description
        "Indicates the length field of the unknown sub-TLV that is present within OSPFv2 Link TLVs.";
    }
    leaf-list value {
      type uint8;
      ordered-by user;
      description
        "The raw value of the unknown sub-TLV found within OSPFv2 Link TLVs.";
    }
  }

  grouping ospfv2-link-tlv {
    description
      "OSPF V2 Link TLV";
    leaf link-type {
      type uint8;
      description
        "Specifies the type of OSPF link as indicated in the TLV.";
    }
    leaf link-id {
      type uint32;
      description
        "Identifier for the OSPF link as specified in the Type-Length-Value (TLV) structure.";
    }
    leaf-list local-if-ipv4-addr {
      type inet:ip-address;
      ordered-by user;
      description
        "List of local interface IPv4 addresses";
    }
    leaf-list local-remote-ipv4-addr {
      type inet:ip-address;
      ordered-by user;
      description
        "List of remote interface IPv4 addresses";
    }
    leaf te-metric {
      type uint32;
      description
        "Traffic Engineering (TE) metric value for the OSPF link, used in path computation for TE applications.";
    }
    leaf max-bandwidth {
      type decimal64 {
        fraction-digits 2;
      }
      units "bytes per second";
      description
        "Specifies the maximum bandwidth, in bytes per second, that can be used on this OSPF link for traffic engineering purposes.";
    }
    leaf max-reservable-bandwidth {
      type decimal64 {
        fraction-digits 2;
      }
      units "bytes per second";
      description
        "Maximum bandwidth, in bytes per second, that can be reserved on the OSPF link for Traffic Engineering.";
    }
    leaf unreserved-bandwidth {
      type decimal64 {
        fraction-digits 2;
      }
      units "bytes per second";
      description
        "Specifies the amount of bandwidth, in bytes per second, that is currently unreserved and available for new traffic engineering reservations on this OSPF link.";
    }
    leaf admin-group {
      type uint32;
      description
        "Specifies the administrative group (also known as resource class or color) assigned to this OSPF link, used for traffic engineering path selection.";
    }
  }

  grouping ospfv2-unknown-tlv {
    description
      "OSPFv2 unknown type TLV";
    leaf type {
      type uint16;
      description
        "Specifies the type field of the unknown TLV (Type-Length-Value) structure found in OSPFv2 link-scope LSAs.";
    }
    leaf length {
      type uint16;
      description
        "Indicates the length field of the unknown TLV (Type-Length-Value) structure present in OSPFv2 link-scope LSAs.";
    }
    leaf-list value {
      type uint8;
      ordered-by user;
      description
        "Contains the value field of the unknown TLV (Type-Length-Value) structure found in OSPFv2 link-scope LSAs.";
    }
  }

  grouping ospfv2-external {
    description
      "Container for OSPFv2 external LSA information, including external route metrics, forwarding addresses, and route tags.";
    leaf mt-id {
      type uint32;
      description
        "MT-ID for topology enabled on the link";
    }
    leaf metric {
      type uint32;
      description
        "OSPF cost metric for the external route in this topology, used to determine the shortest path for OSPF routing.";
    }
    leaf forwarding-address {
      type inet:ip-address;
      description
        "Specifies the forwarding address to which packets should be sent for this OSPFv2 external LSA, if different from the advertising router.";
    }
    leaf external-route-tag {
      type uint32;
      description
        "32-bit tag value associated with the external route, used for route filtering or policy.";
    }
  }

  grouping ospfv2-topology {
    description
      "OSPFv2 topology";
    leaf mt-id {
      type uint32;
      description
        "MT-ID for topology enabled link";
    }
    leaf metric {
      type uint16;
      description
        "OSPF cost metric associated with this topology for the given link, used to determine the shortest path in OSPF routing.";
    }
  }

  grouping ospfv2-link-key {
    description
      "OSPFv2 link key";
    leaf link-id {
      type uint32;
      description
        "Identifier for the OSPFv2 link, representing the neighboring router ID, network address, or interface identification depending on the link type.";
    }
    leaf link-data {
      type uint32;
      description
        "Additional data for the OSPFv2 link, such as the interface address or subnet mask, depending on the link type.";
    }
  }

  grouping ospfv2-link {
    description
      "OSPFv2 link";
    leaf type {
      type uint8;
      description
        "Type of OSPFv2 link (e.g., point-to-point, transit network, stub network, or virtual link).";
    }
    list ospfv2-topology {
      key "mt-id";
      description
        "Contains OSPFv2 topology information for a specific link, including metrics and identifiers relevant to each supported topology.";
      uses ospf-ios-xe-oper:ospfv2-topology;
    }
  }

  grouping link-scope-lsa-key {
    description
      "Link scope LSA key";
    leaf lsa-id {
      type uint32;
      description
        "Identifier for the OSPF Link State Advertisement (LSA) within the link scope.";
    }
    leaf adv-router {
      type inet:ip-address;
      description
        "Specifies the Router ID of the OSPF router that originated (advertised) this link-scope LSA.";
    }
  }

  grouping ospfv2-network {
    description
      "OSPFv2 network info";
    leaf network-mask {
      type inet:ip-address;
      description
        "IP network mask";
    }
    leaf-list attached-router {
      type uint32;
      ordered-by user;
      description
        "List of the routers attached to the network";
    }
  }

  grouping ospfv2-lsa-body {
    description
      "OSPFv2 LSA body";
    leaf num-of-links {
      type uint16;
      description
        "Number of router links described in the OSPFv2 Router LSA.";
    }
    container network {
      description
        "OSPFv2 Network LSA body containing attached routers and network mask.";
      uses ospf-ios-xe-oper:ospfv2-network;
    }
    leaf summary-mask {
      type inet:ip-address;
      description
        "Subnet mask for the route advertised in the OSPFv2 summary LSA.";
    }
    leaf external-mask {
      type inet:ip-address;
      description
        "Subnet mask for the external route advertised in the OSPFv2 external LSA.";
    }
    leaf body-flag-options {
      type ospf-ios-xe-oper:ospfv2-lsa-body-flags-options;
      description
        "OSPFv2 LSA option flags indicating specific LSA properties.";
    }
  }

  grouping lsa-header {
    description
      "Container for the OSPFv3 LSA header fields, including age, type, advertising router, sequence number, and checksum.";
    leaf age {
      type uint16;
      units "seconds";
      description
        "Age of the OSPFv3 LSA in seconds, indicating how long the LSA has been in the OSPFv3 database.";
    }
    leaf type {
      type uint16;
      description
        "Indicates the type of OSPFv3 Link State Advertisement (LSA), which determines the structure and purpose of the LSA within the OSPFv3 protocol.";
    }
    leaf adv-router {
      type uint32;
      description
        "Specifies the Router ID of the OSPFv3 router that originated and advertised this Link State Advertisement (LSA).";
    }
    leaf seq-num {
      type string;
      description
        "Indicates the sequence number of the OSPFv3 Link State Advertisement (LSA), used to detect newer or older versions of the LSA.";
    }
    leaf checksum {
      type string;
      description
        "Checksum value for the OSPFv3 Link State Advertisement (LSA) header, used to verify the integrity of the LSA data.";
    }
    leaf length {
      type uint16;
      units "bytes";
      description
        "Specifies the total length of the OSPFv3 Link State Advertisement (LSA) in bytes, including the header and body.";
    }
  }

  grouping ospfv2-header {
    description
      "OSPFv2 header";
    leaf lsa-id {
      type inet:ip-address;
      description
        "Identifier for the OSPFv2 LSA, typically representing a network, router, or other entity depending on the LSA type.";
    }
    leaf opaque-type {
      type uint8;
      description
        "Specifies the OSPF opaque LSA type, used to identify the format and function of the opaque LSA.";
    }
    leaf opaque-id {
      type uint32;
      description
        "Identifier for the OSPF opaque LSA, uniquely identifying the LSA within its opaque type.";
    }
    leaf age {
      type uint16;
      units "seconds";
      description
        "Age of the LSA in seconds since origination, used to determine LSA refresh and expiration in OSPF.";
    }
    leaf type {
      type uint16;
      description
        "Specifies the type of OSPF Link State Advertisement (LSA), indicating the function and format of the LSA.";
    }
    leaf adv-router {
      type uint32;
      description
        "Router ID of the advertising router that originated this LSA.";
    }
    leaf seq-num {
      type string;
      description
        "Indicates the sequence number of the LSA, used to detect newer or older versions of the LSA.";
    }
    leaf checksum {
      type string;
      description
        "Checksum value used for error detection in the OSPF LSA header and body.";
    }
    leaf length {
      type uint16;
      units "bytes";
      description
        "Total length of the OSPF LSA in bytes, including the header and body.";
    }
    leaf flag-options {
      type ospf-ios-xe-oper:lsa-flag-options;
      description
        "Option flags in the OSPF LSA header indicating supported OSPF capabilities and features.";
    }
  }

  grouping ospfv2-lsa {
    description
      "Container for the decoded OSPFv2 Link State Advertisement (LSA) data.";
    container header {
      description
        "Decoded OSPFv2 LSA header data";
      uses ospf-ios-xe-oper:ospfv2-header;
    }
    container lsa-body {
      description
        "Decoded OSPFv2 LSA body data";
      uses ospf-ios-xe-oper:ospfv2-lsa-body;
    }
  }

  grouping ospfv3-header {
    description
      "OSPFv3 header";
    leaf lsa-id {
      type inet:ip-address;
      description
        "Identifier for the OSPFv3 Link State Advertisement, typically representing a network, router, or other entity.";
    }
    container lsa-header {
      description
        "Container for the OSPFv3 Link State Advertisement (LSA) header fields, which include metadata such as age, type, and sequence number.";
      uses ospf-ios-xe-oper:lsa-header;
    }
    leaf lsa-hdr-options {
      type ospf-ios-xe-oper:ospfv3-lsa-options;
      description
        "Specifies the OSPFv3 Link State Advertisement (LSA) options field, indicating supported capabilities and features for the LSA.";
    }
  }

  grouping ospfv3-network {
    description
      "OSPFv3 network LSA";
    leaf-list attached-router {
      type uint32;
      ordered-by user;
      description
        "List of the routers attached to the network";
    }
    leaf lsa-net-options {
      type ospf-ios-xe-oper:ospfv3-lsa-options;
      description
        "Specifies the options field for the OSPFv3 Network LSA, indicating supported features and capabilities for the network.";
    }
  }

  grouping ospfv3-inter-area-prefix {
    description
      "OSPFv3 inter area router LSA";
    leaf metric {
      type uint32;
      description
        "Cost metric for the OSPFv3 inter-area prefix route, used in shortest path calculation for routes between OSPF areas.";
    }
    leaf ia-prefix {
      type string;
      description
        "IPv6 prefix advertised in the OSPFv3 inter-area prefix LSA.";
    }
    leaf ia-prefix-options {
      type string;
      description
        "Specifies the options associated with the OSPFv3 inter-area prefix, such as route type or additional attributes.";
    }
  }

  grouping ospfv3-inter-area-router {
    description
      "OSPFv3 inter area router info";
    leaf metric {
      type uint32;
      description
        "Cost metric for the OSPFv3 inter-area route.";
    }
    leaf destination-router-id {
      type uint32;
      description
        "Router ID of the router being described by the LSA";
    }
    leaf lsa-ia-options {
      type ospf-ios-xe-oper:ospfv3-lsa-options;
      description
        "OSPFv3 LSA options specific to inter-area router LSAs, indicating supported OSPFv3 features for this LSA.";
    }
  }

  grouping ospfv3-lsa-external-flags {
    description
      "OSPFv3 LSA external flags";
    leaf e-flag {
      type boolean;
      description
        "When set, the metric specified is a Type 2 external metric";
    }
  }

  grouping ospfv3-lsa-external {
    description
      "OSPFv3 AS-External and NSSA LSA";
    leaf metric {
      type uint32;
      description
        "Cost metric associated with the external route advertised in the OSPFv3 LSA.";
    }
    container flags {
      description
        "Flags for the OSPFv3 External LSA, indicating specific properties or behaviors of the LSA.";
      uses ospf-ios-xe-oper:ospfv3-lsa-external-flags;
    }
    leaf referenced-ls-type {
      type uint16;
      description
        "Specifies the type of the referenced Link State Advertisement (LSA) in OSPFv3.";
    }
    leaf external-prefix {
      type string;
      description
        "External prefix advertised in the OSPFv3 LSA.";
    }
    leaf external-prefix-options {
      type string;
      description
        "Options associated with the external prefix in the OSPFv3 external LSA.";
    }
    leaf forwarding-address {
      type inet:ip-address;
      description
        "Specifies the forwarding address to which packets should be sent for this OSPFv3 external LSA, if different from the advertising router.";
    }
    leaf external-route-tag {
      type uint32;
      description
        "32-bit tag value associated with the external route, used for route identification or policy application.";
    }
    leaf referenced-link-state-id {
      type uint32;
      description
        "Specifies the Link State ID referenced by this OSPFv3 external LSA, used to identify the associated link state advertisement.";
    }
  }

  grouping ospfv3-nssa {
    description
      "OSPFv3 NSSA LSA";
    container lsa-nssa-external {
      description
        "Represents an OSPFv3 NSSA (Not-So-Stubby Area) external LSA, which advertises external routes within an NSSA area.";
      uses ospf-ios-xe-oper:ospfv3-lsa-external;
    }
  }

  grouping ospfv3-link-data {
    description
      "OSPFv3 Link Data";
    leaf rtr-priority {
      type uint8;
      description
        "Router priority of the interface";
    }
    leaf link-local-interface-address {
      type inet:ip-address;
      description
        "The originating router's link-local interface address on the link.";
    }
    leaf num-of-prefixes {
      type uint32;
      description
        "Specifies the number of IPv6 address prefixes associated with this OSPFv3 link data.";
    }
    leaf lsa-id-options {
      type ospf-ios-xe-oper:ospfv3-lsa-options;
      description
        "Specifies the OSPFv3 Link-LSA options field, indicating supported OSPFv3 capabilities and features for the link.";
    }
  }

  grouping ospfv3-intra-area-prefix {
    description
      "OSPFv3 intra area prefix LSA";
    leaf referenced-ls-type {
      type uint16;
      description
        "Specifies the type of the referenced Link State Advertisement (LSA) in OSPFv3, identifying the LSA to which this Intra-Area-Prefix LSA is associated.";
    }
    leaf referenced-link-state-id {
      type uint32;
      description
        "Specifies the Link State ID of the LSA that is referenced by this OSPFv3 Intra-Area-Prefix-LSA, identifying the associated Router or Network LSA.";
    }
    leaf referenced-adv-router {
      type inet:ip-address;
      description
        "Specifies the Router ID of the advertising router for the LSA referenced by this OSPFv3 Intra-Area-Prefix-LSA.";
    }
    leaf num-of-prefixes {
      type uint16;
      description
        "Indicates the number of IPv6 prefixes included in this OSPFv3 intra-area prefix LSA.";
    }
  }

  grouping ospfv3-lsa-body {
    description
      "Decoded OSPFv3 LSA body data";
    container network {
      description
        "Represents the OSPFv3 network information contained within the LSA body, including attached routers and network options.";
      uses ospf-ios-xe-oper:ospfv3-network;
    }
    container prefix {
      description
        "OSPFv3 inter-area prefix information in the LSA body.";
      uses ospf-ios-xe-oper:ospfv3-inter-area-prefix;
    }
    container ia-router {
      description
        "Represents the OSPFv3 Inter-Area Router LSA body, which describes routes to routers in other OSPF areas.";
      uses ospf-ios-xe-oper:ospfv3-inter-area-router;
    }
    container lsa-external {
      description
        "Represents an OSPFv3 AS-External-LSA, which advertises external routes imported into the OSPFv3 routing domain.";
      uses ospf-ios-xe-oper:ospfv3-lsa-external;
    }
    container nssa {
      description
        "Contains OSPFv3 Not-So-Stubby Area (NSSA) LSA information, including external routes advertised within NSSA areas.";
      uses ospf-ios-xe-oper:ospfv3-nssa;
    }
    container link-data {
      description
        "Contains the OSPFv3 link-specific data as advertised in the Link-LSA, including interface parameters and attributes relevant to the link.";
      uses ospf-ios-xe-oper:ospfv3-link-data;
    }
    container ia-prefix {
      description
        "Contains the list of OSPFv3 intra-area IPv6 address prefixes advertised within this area.";
      uses ospf-ios-xe-oper:ospfv3-intra-area-prefix;
    }
    leaf lsa-flag-options {
      type ospf-ios-xe-oper:ospfv3-lsa-options;
      description
        "Specifies the option flags set in the OSPFv3 Link State Advertisement (LSA), indicating supported OSPFv3 features and capabilities.";
    }
    leaf lsa-body-flags {
      type ospf-ios-xe-oper:ospfv3-lsa-body-flag-options;
      description
        "Flags associated with the OSPFv3 LSA body, indicating specific properties or behaviors of the LSA.";
    }
  }

  grouping ospfv3-lsa {
    description
      "Container for OSPFv3 Link State Advertisements (LSAs) within the area-scope LSA database.";
    container header {
      description
        "Decoded OSPFv3 LSA header";
      uses ospf-ios-xe-oper:ospfv3-header;
    }
    container lsa-body {
      description
        "Decoded OSPFv3 LSA body";
      uses ospf-ios-xe-oper:ospfv3-lsa-body;
    }
  }

  grouping ospfv3-link-key {
    description
      "OSPFv3 link key";
    leaf interface-id {
      type uint32;
      description
        "Identifier for the local interface participating in the OSPFv3 link.";
    }
    leaf neighbor-interface-id {
      type uint32;
      description
        "Identifier for the neighbor's interface on this OSPFv3 link.";
    }
    leaf neighbor-router-id {
      type uint32;
      description
        "Router ID of the neighboring OSPFv3 router associated with this link.";
    }
  }

  grouping ospfv3-link {
    description
      "OSPFv3 link";
    leaf type {
      type uint8;
      description
        "Type of OSPFv3 link (e.g., point-to-point, transit, stub, or virtual link) as described in the LSA.";
    }
    leaf metric {
      type uint16;
      description
        "OSPFv3 cost metric associated with the link, used for route calculation.";
    }
  }

  grouping ospfv3-prefix-list {
    description
      "OSPFv3 prefix list";
    leaf prefix {
      type string;
      description
        "IPv6 prefix advertised in the OSPFv3 LSA.";
    }
    leaf prefix-options {
      type string;
      description
        "Options associated with the OSPFv3 prefix, such as route type or flags.";
    }
  }

  grouping multi-topology {
    description
      "Multi topology";
    leaf name {
      type string;
      description
        "Name of the OSPF multi-topology that is enabled on this interface";
    }
  }

  grouping link-scope-lsa {
    description
      "Link scope LSA";
    leaf decoded-completed {
      type boolean;
      description
        "The OSPF LSA body is fully decoded";
    }
    leaf-list raw-data {
      type uint8;
      ordered-by user;
      description
        "The complete LSA in network byte order as received/sent over the wire";
    }
    leaf version {
      type uint32;
      description
        "Specifies the version number of the OSPF link-scope LSA.";
    }
    container ospfv2-lsa {
      description
        "Container for OSPFv2 Link State Advertisement (LSA) data, including header and body information.";
      uses ospf-ios-xe-oper:ospfv2-lsa;
    }
    list ospfv2-link {
      key "link-id link-data";
      description
        "OSPFv2 LSA link";
      uses ospf-ios-xe-oper:ospfv2-link-key;
      uses ospf-ios-xe-oper:ospfv2-link;
    }
    list ospfv2-topology {
      key "mt-id";
      description
        "List of OSPFv2 topology-specific entries within a Summary LSA, each containing metrics and multi-topology identifiers.";
      uses ospf-ios-xe-oper:ospfv2-topology;
    }
    list ospfv2-external {
      key "mt-id";
      description
        "List of OSPFv2 external LSA entries, each containing external route metrics, forwarding addresses, and route tags.";
      uses ospf-ios-xe-oper:ospfv2-external;
    }
    list ospfv2-unknown-tlv {
      key "type";
      description
        "OSPFv2 Unknown TLV";
      uses ospf-ios-xe-oper:ospfv2-unknown-tlv;
    }
    container ospfv3-lsa-val {
      description
        "Contains the decoded contents of an OSPFv3 Link State Advertisement (LSA), including header and body fields.";
      uses ospf-ios-xe-oper:ospfv3-lsa;
    }
    list ospfv3-link {
      key "interface-id neighbor-interface-id neighbor-router-id";
      description
        "List of OSPFv3 links describing the connections between interfaces and neighboring routers for this link-scope LSA.";
      uses ospf-ios-xe-oper:ospfv3-link-key;
      uses ospf-ios-xe-oper:ospfv3-link;
    }
    list ospfv3-prefix-list {
      key "prefix";
      description
        "List of IPv6 prefixes advertised in this OSPFv3 link-scope LSA.";
      uses ospf-ios-xe-oper:ospfv3-prefix-list;
    }
    list ospfv3-ia-prefix {
      key "prefix";
      description
        "List of IPv6 prefixes advertised within the OSPFv3 area (intra-area prefixes).";
      uses ospf-ios-xe-oper:ospfv3-prefix-list;
    }
    list multi-topology {
      key "name";
      description
        "OSPF multi-topology interface augmentation";
      uses ospf-ios-xe-oper:multi-topology;
    }
    leaf router-address {
      type inet:ip-address;
      description
        "The OSPF router's address as advertised in the link-state advertisement (LSA).";
    }
    container tlv {
      description
        "Container for the Type-Length-Value (TLV) structure describing link attributes in OSPF link-scope LSAs.";
      uses ospf-ios-xe-oper:ospfv2-link-tlv;
    }
    list unknown-sub-tlv {
      key "type";
      description
        "OSPFv2 Unknown sub TLV";
      uses ospf-ios-xe-oper:ospfv2-unknown-sub-tlv;
    }
  }

  grouping area-scope-lsa-key {
    description
      "OSPF area scope LSA key";
    leaf lsa-type {
      type uint32;
      description
        "Specifies the OSPF LSA type code that identifies the function and format of the Link State Advertisement, used as the primary key for this area-scope LSA entry.";
    }
    leaf adv-router {
      type inet:ip-address;
      description
        "Router ID of the advertising router that originated this LSA.";
    }
  }

  grouping area-scope-lsa {
    description
      "OSPF area scope LSA";
    leaf decoded-completed {
      type boolean;
      description
        "The OSPF LSA body is fully decoded";
    }
    leaf-list raw-data {
      type uint8;
      ordered-by user;
      description
        "The complete LSA in network byte order as received/sent over the wire";
    }
    container ospfv2-lsa {
      description
        "Container for the decoded OSPFv2 Link State Advertisement (LSA) data.";
      uses ospf-ios-xe-oper:ospfv2-lsa;
    }
    list ospfv2-link {
      key "link-id link-data";
      description
        "Represents a link entry in the OSPF Router LSA, describing a connection from the router to another network or router.";
      uses ospf-ios-xe-oper:ospfv2-link-key;
      uses ospf-ios-xe-oper:ospfv2-link;
    }
    list ospfv2-topology {
      key "mt-id";
      description
        "Contains OSPFv2 topology specific information, including metrics and topology identifiers for the area-scope LSA.";
      uses ospf-ios-xe-oper:ospfv2-topology;
    }
    list ospfv2-external {
      key "mt-id";
      description
        "Contains information about OSPFv2 external LSAs, including metrics, forwarding addresses, and topology identifiers.";
      uses ospf-ios-xe-oper:ospfv2-external;
    }
    container ospfv3-lsa {
      description
        "Container for OSPFv3 Link State Advertisements (LSAs) within the area scope.";
      uses ospf-ios-xe-oper:ospfv3-lsa;
    }
    list ospfv3-link {
      key "interface-id neighbor-interface-id neighbor-router-id";
      description
        "List of OSPFv3 links representing the connections between routers and their neighbors within an OSPFv3 area.";
      uses ospf-ios-xe-oper:ospfv3-link-key;
      uses ospf-ios-xe-oper:ospfv3-link;
    }
    list ospfv3-prefix {
      key "prefix";
      description
        "List of OSPFv3 prefixes advertised in the area-scope LSA for this interface.";
      uses ospf-ios-xe-oper:ospfv3-prefix-list;
    }
    list ospfv3-ia-prefix {
      key "prefix";
      description
        "List of OSPFv3 intra-area prefixes advertised within the area-scope LSA for this interface.";
      uses ospf-ios-xe-oper:ospfv3-prefix-list;
    }
  }

  grouping area-scope-lsas {
    description
      "OSPF area scope LSA";
    leaf lsa-type {
      type uint32;
      description
        "Specifies the type of OSPF Link State Advertisement (LSA) within the area scope, identifying the format and purpose of the LSA.";
    }
    list area-scope-lsa {
      key "lsa-type adv-router";
      description
        "List of OSPF area-scope Link State Advertisements (LSAs) for this interface, each identified by LSA type and advertising router.";
      uses ospf-ios-xe-oper:area-scope-lsa-key;
      uses ospf-ios-xe-oper:area-scope-lsa;
    }
  }

  grouping link-scope-lsas {
    description
      "Link scope lsas";
    leaf lsa-type {
      type uint32;
      description
        "Specifies the type of OSPF Link State Advertisement (LSA) within the link scope, identifying the format and purpose of the LSA.";
    }
    list link-scope-lsa {
      key "lsa-id adv-router";
      description
        "List of OSPF Link Scope Link State Advertisements (LSAs) for this interface, each identified by LSA ID and advertising router.";
      uses ospf-ios-xe-oper:link-scope-lsa-key;
      uses ospf-ios-xe-oper:link-scope-lsa;
    }
    list area-scope-lsa {
      key "lsa-type adv-router";
      description
        "List OSPF area scope LSA databases";
      uses ospf-ios-xe-oper:area-scope-lsa-key;
      uses ospf-ios-xe-oper:area-scope-lsa;
    }
  }

  grouping ospf-static-neighbor {
    description
      "OSPF neighbor info";
    leaf address {
      type inet:ip-address;
      description
        "Neighbor IP address";
    }
    leaf cost {
      type uint16;
      description
        "Neighbor cost";
    }
    leaf poll-interval {
      type uint16;
      units "seconds";
      description
        "Neighbor polling interval in seconds";
    }
  }

  grouping ospf-nbr-stat {
    description
      "OSPF neighbor statistics";
    leaf nbr-event-count {
      type uint32;
      description
        "The number of times this OSPF neighbor has changed state or experienced an error.";
    }
    leaf nbr-retrans-qlen {
      type uint32;
      description
        "The current length of the retransmission queue";
    }
  }

  grouping ospf-neighbor {
    description
      "OSPF neighbor details";
    leaf neighbor-id {
      type inet:ip-address;
      description
        "OSPF neighbor ID";
    }
    leaf address {
      type inet:ip-address;
      description
        "Specifies the IP address of the OSPF neighbor.";
    }
    leaf dr {
      type inet:ip-address;
      description
        "IP address of the Designated Router elected on this OSPF interface segment.";
    }
    leaf bdr {
      type inet:ip-address;
      description
        "IP address of the Backup Designated Router elected on this OSPF interface segment.";
    }
    leaf state {
      type ospf-ios-xe-oper:nbr-state-type;
      description
        "Current state of the OSPF neighbor relationship.";
    }
    container stats {
      description
        "Per-neighbor statistics";
      uses ospf-ios-xe-oper:ospf-nbr-stat;
    }
  }

  grouping fast-reroute {
    description
      "Fast Reroute details";
    leaf candidate-disabled {
      type boolean;
      description
        "Prevent the interface to be used as backup";
    }
    leaf enabled {
      type boolean;
      description
        "Activates LFA. This model assumes activation of per-prefix LFA";
    }
    leaf remote-lfa-enabled {
      type boolean;
      description
        "Activates remote LFA";
    }
  }

  grouping multi-area {
    description
      "Multi Area info";
    leaf multi-area-id {
      type uint32;
      description
        "Specifies the OSPF area ID to which this interface is additionally assigned as part of multi-area configuration.";
    }
    leaf cost {
      type uint16;
      description
        "Interface cost for multi-area";
    }
  }

  grouping ospf-crypto-algorithm {
    description
      "Crypto Algorithm";
    leaf hmac-sha1-12 {
      type empty;
      description
        "HMAC-SHA1-12 algorithm";
    }
    leaf hmac-sha1-20 {
      type empty;
      description
        "HMAC-SHA1-20 algorithm";
    }
    leaf md5 {
      type empty;
      description
        "MD5 algorithm";
    }
    leaf sha-1 {
      type empty;
      description
        "SHA-1 algorithm";
    }
    leaf hmac-sha-1 {
      type empty;
      description
        "HMAC-SHA-1 authentication algorithm";
    }
    leaf hmac-sha-256 {
      type empty;
      description
        "HMAC-SHA-256 authentication algorithm";
    }
    leaf hmac-sha-384 {
      type empty;
      description
        "HMAC-SHA-384 authentication algorithm";
    }
    leaf hmac-sha-512 {
      type empty;
      description
        "HMAC-SHA-512 authentication algorithm";
    }
  }

  grouping ospf-authentication {
    description
      "OSPF authentication info";
    choice auth-type-selection-choice {
      description
        "OSPF authentication type";
      case ospf-auth-ipsec {
        leaf sa {
          type string;
          description
            "Name of the Security Association (SA) used for OSPF IPsec authentication on this interface.";
        }
      }
      case ospf-auth-trailer-keychain {
        leaf key-chain {
          type string;
          description
            "Specifies the name of the key-chain used for OSPF interface authentication.";
        }
      }
      case ospf-auth-trailer-key {
        leaf key-string {
          type string;
          description
            "Key string in ASCII format";
        }
        container crypto-algorithm-val {
          description
            "Specifies the cryptographic algorithm used for OSPF interface authentication.";
          uses ospf-ios-xe-oper:ospf-crypto-algorithm;
        }
      }
      case ospf-auth-type-none {
        leaf no-auth {
          type uint32;
          description
            "No authentication enabled";
        }
      }
    }
  }

  grouping ttl-security {
    description
      "TTL security configuration for OSPF on this interface, used to protect against forged OSPF packets by checking the IP Time-To-Live (TTL) value.";
    leaf enabled {
      type boolean;
      description
        "Enable/Disable TTL security check";
    }
    leaf hops {
      type uint8;
      description
        "Maximum number of hops that a OSPF packet may have travelled";
    }
  }

  grouping ospf-interface {
    description
      "OSPF interface";
    leaf name {
      type string;
      description
        "Name of the interface participating in OSPF within this area.";
    }
    leaf network-type {
      type ospf-ios-xe-oper:ospf-network-type;
      description
        "Specifies the OSPF network type for this interface (such as broadcast, non-broadcast, point-to-point, or point-to-multipoint).";
    }
    leaf passive {
      type boolean;
      description
        "Indicates whether the OSPF interface is configured as passive, meaning it does not send or receive OSPF hello packets but advertises the network.";
    }
    leaf demand-circuit {
      type boolean;
      description
        "Indicates whether OSPF demand circuit mode is enabled on this interface, allowing OSPF to suppress periodic hello and LSA refreshes to reduce traffic over on-demand circuits.";
    }
    container multi-area {
      description
        "Container for OSPF multi-area interface configuration, allowing the interface to participate in multiple OSPF areas.";
      uses ospf-ios-xe-oper:multi-area;
    }
    list static-neighbor {
      key "address";
      description
        "Statically configured neighbors";
      uses ospf-ios-xe-oper:ospf-static-neighbor;
    }
    leaf node-flag {
      type boolean;
      description
        "Indicates whether the prefix on this interface is used as the representative prefix for the OSPF node, typically for OSPF prefix-SID or node-SID advertisement.";
    }
    container fast-reroute {
      description
        "Configuration parameters related to OSPF fast reroute (FRR) for this interface, including LFA and remote LFA settings.";
      uses ospf-ios-xe-oper:fast-reroute;
    }
    leaf cost {
      type uint16;
      description
        "Specifies the OSPF cost (metric) assigned to this interface, used in OSPF path calculation.";
    }
    leaf hello-interval {
      type uint16;
      description
        "Time between hello packets";
    }
    leaf dead-interval {
      type uint16;
      description
        "Interval after which a neighbor is declared dead";
    }
    leaf retransmit-interval {
      type uint16;
      description
        "Time between retransmitting unacknowledged Link State Advertisements (LSAs)";
    }
    leaf transmit-delay {
      type uint16;
      description
        "Estimated time needed to send link-state update";
    }
    leaf mtu-ignore {
      type boolean;
      description
        "Enable/Disable ignoring of MTU in DBD packets";
    }
    leaf lls {
      type boolean;
      description
        "Enable/Disable link-local signalling (LLS) support";
    }
    leaf prefix-suppression {
      type boolean;
      description
        "Indicates whether advertisement of interface IP prefixes in OSPF is suppressed on this interface.";
    }
    leaf bfd {
      type boolean;
      description
        "Indicates whether Bidirectional Forwarding Detection (BFD) is enabled for OSPF on this interface.";
    }
    container ttl-security {
      description
        "TTL security configuration for OSPF on this interface, used to protect against forged OSPF packets by checking the IP Time-To-Live (TTL) value.";
      uses ospf-ios-xe-oper:ttl-security;
    }
    leaf enable {
      type boolean;
      description
        "Indicates whether OSPF protocol operation is enabled on this interface.";
    }
    container authentication {
      description
        "OSPF authentication configuration for this interface.";
      uses ospf-ios-xe-oper:ospf-authentication;
    }
    leaf state {
      type string;
      description
        "A string value representing the operational state of the OSPF interface.
         This leaf uses unstructured string data. The following is the complete
         list of all possible values:
         'Down' - The interface is in the down state. It is not operational and
         is not participating in OSPF routing;
         'Loopback' - The interface is in loopback mode. It is advertised as a
         stub host route with a /32 prefix length;
         'Waiting' - The interface is in the waiting state, listening for Hello
         packets from other routers to determine the Designated Router (DR) and
         Backup Designated Router (BDR) before entering a fully
         operational state;
         'Point-to-Point' - The interface is operating in point-to-point mode.
         It has a single neighbor and no DR/BDR election is performed;
         'DR' - The interface is fully operational and this router has been
         elected as the Designated Router (DR) on the network segment;
         'BDR' - The interface is fully operational and this router has been
         elected as the Backup Designated Router (BDR) on the network segment;
         'DR-Other' - The interface is fully operational but this router is
         neither the Designated Router nor the Backup Designated Router on the
         network segment. It is also known as the DR Other state;
         'Unknown' - The interface state could not be determined. This value
         is returned for any unrecognized operational state, including
         point-to-multipoint interfaces.";
    }
    leaf hello-timer {
      type uint32;
      units "seconds";
      description
        "Current value, in seconds, of the OSPF Hello timer for this interface, indicating the time remaining until the next Hello packet is sent.";
    }
    leaf wait-timer {
      type uint32;
      units "seconds";
      description
        "The OSPF Wait Timer value, in seconds, indicating how long the router waits to hear from a Designated Router (DR) or Backup Designated Router before initiating an election.";
    }
    leaf dr {
      type inet:ip-address;
      description
        "IP address of the Designated Router (DR) elected on this OSPF interface segment.";
    }
    leaf bdr {
      type inet:ip-address;
      description
        "IP address of the Backup Designated Router elected on this OSPF interface segment.";
    }
    list ospf-neighbor {
      key "neighbor-id";
      description
        "List of OSPF neighbors";
      uses ospf-ios-xe-oper:ospf-neighbor;
    }
    list intf-link-scope-lsas {
      key "lsa-type";
      description
        "List of OSPF Link Scope Link State Advertisements (LSAs) associated with this interface.";
      uses ospf-ios-xe-oper:link-scope-lsas;
    }
    list intf-multi-topology {
      key "name";
      description
        "List of OSPF topologies enabled on this interface.";
      uses ospf-ios-xe-oper:multi-topology;
    }
    leaf priority {
      type uint8;
      description
        "OSPF router priority value used for designated router election on this interface.";
    }
  }

  grouping ospf-area {
    description
      "OSPF area";
    leaf area-id {
      type uint32;
      description
        "OSPF area ID";
    }
    list ospf-interface {
      key "name";
      description
        "List of OSPF interfaces";
      uses ospf-ios-xe-oper:ospf-interface;
    }
    list area-scope-lsa {
      key "lsa-type";
      description
        "List of OSPF area scope LSA";
      uses ospf-ios-xe-oper:area-scope-lsas;
    }
  }

  grouping ospf-instance-rev1-key {
    description
      "OSPF instance key type";
    leaf af {
      type ospf-ios-xe-oper:address-family;
      description
        "Address-family of the instance";
    }
    leaf router-id {
      type uint32;
      description
        "Defined in RFC 2328. A 32-bit number that uniquely identifies the router";
    }
  }

  grouping ospf-instance-rev1 {
    description
      "OSPF instance";
    list ospf-area {
      key "area-id";
      description
        "List of ospf areas";
      uses ospf-ios-xe-oper:ospf-area;
    }
    list link-scope-lsas {
      key "lsa-type";
      description
        "List OSPF link scope LSA";
      uses ospf-ios-xe-oper:link-scope-lsas;
    }
    list multi-topology {
      key "name";
      description
        "OSPF multi-topology interface augmentation";
      uses ospf-ios-xe-oper:multi-topology;
    }
    leaf process-id {
      type uint16;
      description
        "The process identifier used to refer to this instance";
    }
  }

  grouping ospf-rev1 {
    description
      "OSPF operational data";
    leaf op-mode {
      type ospf-ios-xe-oper:ospf-operation-mode;
      description
        "Specifies the current operation mode of the OSPF protocol (e.g., standard, stub, or other supported modes).";
    }
    list ospf-instance {
      key "af router-id";
      description
        "OSPF routing protocol instance";
      uses ospf-ios-xe-oper:ospf-instance-rev1-key;
      uses ospf-ios-xe-oper:ospf-instance-rev1;
    }
  }

  grouping ospfv2-lsa-info-key {
    description
      "Link State Advertisement information key";
    leaf lsa-type {
      type uint8;
      description
        "Specifies the type of Link State Advertisement (LSA) as defined by OSPF, indicating the function and content of the LSA.";
    }
    leaf lsa-id {
      type uint32;
      description
        "Specifies the unique identifier for the Link State Advertisement (LSA) within the OSPF area, used to distinguish individual LSAs.";
    }
    leaf advertising-router {
      type uint32;
      description
        "Specifies the Router ID (IPv4 address) of the OSPF router that originated and advertised this Link State Advertisement (LSA).";
    }
  }

  grouping ospfv2-unsupported-lsa {
    description
      "Unsupported Link State Advertisement";
    leaf-list lsa-data {
      type uint8;
      ordered-by user;
      description
        "Link State Advertisement data";
    }
  }

  grouping ospfv2-router-link-key {
    description
      "Router Link key";
    leaf link-type {
      type uint8;
      description
        "Specifies the type of link described in the OSPF Router LSA, such as point-to-point, transit network, stub network, or virtual link.";
    }
    leaf link-id {
      type uint32;
      description
        "Identifier for the link as used in the OSPF Router LSA. The meaning depends on the link type (e.g., neighbor router ID, network segment ID).";
    }
    leaf link-data {
      type uint32;
      description
        "Additional data associated with the link in the OSPF Router LSA, such as the interface IP address or subnet mask, depending on the link type.";
    }
  }

  grouping ospfv2-router-link-topo {
    description
      "Router link topology";
    leaf mt-id {
      type uint8;
      description
        "Identifier for the OSPF multi-topology to which this summary LSA entry applies.";
    }
    leaf topo-metric {
      type uint16;
      description
        "OSPF metric (cost) associated with this link for the specified multi-topology.";
    }
  }

  grouping ospfv2-router-link {
    description
      "Router Link";
    list link-topo {
      description
        "List of topologies associated with this OSPF Router LSA link, typically used for multi-topology OSPF extensions.";
      uses ospf-ios-xe-oper:ospfv2-router-link-topo;
    }
  }

  grouping ospfv2-router-lsa {
    description
      "Router Link State Advertisement";
    leaf router-lsa-bits {
      type ospf-ios-xe-oper:ospfv2-router-lsa-bits;
      description
        "Router Link State Advertisement bits";
    }
    leaf router-lsa-number-links {
      type uint16;
      description
        "Specifies the number of links described in this OSPF Router Link State Advertisement (LSA), representing the interfaces or connections advertised by the router.";
    }
  }

  grouping ospfv2-network-lsa {
    description
      "Network Link State Advertisement";
    leaf network-lsa-mask {
      type uint32;
      description
        "Specifies the subnet mask associated with the OSPF Network Link State Advertisement (LSA), used to define the network segment described by this LSA.";
    }
    leaf-list network-attached-routers {
      type uint32;
      ordered-by user;
      description
        "List of router IDs for routers attached to the network described in this OSPF Network Link State Advertisement (LSA).";
    }
  }

  grouping ospfv2-summary-lsa-topo {
    description
      "Summary Link State Advertisement topology";
    leaf mt-id {
      type uint8;
      description
        "Identifier for the OSPF multi-topology to which this summary LSA entry applies.";
    }
    leaf topo-metric {
      type uint32;
      description
        "OSPF cost metric value for the specified topology in the summary LSA.";
    }
  }

  grouping ospfv2-summary-lsa {
    description
      "Summary Link State Advertisement";
    leaf summary-lsa-mask {
      type uint32;
      description
        "Specifies the subnet mask for the network described in this OSPF summary Link State Advertisement (LSA).";
    }
    list summary-topo {
      description
        "List of topologies associated with this OSPF Summary Link State Advertisement (LSA), each containing topology-specific metrics.";
      uses ospf-ios-xe-oper:ospfv2-summary-lsa-topo;
    }
  }

  grouping ospfv2-external-lsa-topo {
    description
      "The external Link State Advertisement topology information";
    leaf mt-id {
      type uint8;
      description
        "Identifier for the OSPF multi-topology associated with this external LSA entry. Used to distinguish between different topologies in OSPF multi-topology routing.";
    }
    leaf topo-metric-type {
      type ospf-ios-xe-oper:ospf-external-metric-type;
      description
        "The topology metric type associated with the
         Link State Advertisement";
    }
    leaf topo-metric {
      type uint32;
      description
        "OSPF cost metric value for the external route in the specified topology of the external LSA.";
    }
    leaf topo-forwarding-address {
      type inet:ip-address;
      description
        "The forwarding address for the external route in this OSPF topology, used to specify the next-hop IP address for routing.";
    }
    leaf topo-route-tag {
      type uint32;
      description
        "32-bit tag value associated with the external route, used for route filtering or policy.";
    }
  }

  grouping ospfv2-external-lsa {
    description
      "The external Link State Advertisement";
    leaf external-lsa-mask {
      type uint32;
      description
        "Specifies the network mask for the external route described by the OSPF external Link State Advertisement (LSA).";
    }
    list external-topo {
      description
        "List of external topology information for the OSPF external LSA, including metrics and multi-topology identifiers.";
      uses ospf-ios-xe-oper:ospfv2-external-lsa-topo;
    }
  }

  grouping ospfv2-lsa-info {
    description
      "The Link State Advertisement information";
    leaf lsa-age {
      type uint16;
      description
        "The age of the Link State Advertisement";
    }
    leaf lsa-options {
      type ospf-ios-xe-oper:ospfv2-lsa-flag-options;
      description
        "Specifies the OSPF options field of the Link State Advertisement (LSA), indicating supported OSPF capabilities and features.";
    }
    leaf lsa-seq-number {
      type uint32;
      description
        "The sequence number for the Link State Advertisement";
    }
    leaf lsa-checksum {
      type uint16;
      description
        "The checksum of the Link State Advertisement";
    }
    leaf lsa-length {
      type uint16;
      description
        "The length, in bytes, of the Link State Advertisement";
    }
    list ospfv2-router-lsa-links {
      key "link-type link-id link-data";
      description
        "List of links described in the OSPF Router Link State Advertisement (LSA), representing the router's interfaces and their connectivity within the OSPF area.";
      uses ospf-ios-xe-oper:ospfv2-router-link-key;
      uses ospf-ios-xe-oper:ospfv2-router-link;
    }
    choice lsa-union-type-choice {
      description
        "The type of Link State Advertisement";
      case ospfv2-lsa-type-unsupported-lsa-type {
        container unsupported-lsa {
          description
            "The unsupported Link State Advertisements";
          uses ospf-ios-xe-oper:ospfv2-unsupported-lsa;
        }
      }
      case ospfv2-lsa-type-router {
        container router-lsa {
          description
            "The router Link State Advertisements";
          uses ospf-ios-xe-oper:ospfv2-router-lsa;
        }
      }
      case ospfv2-lsa-type-network {
        container network-lsa {
          description
            "The network Link State Advertisements";
          uses ospf-ios-xe-oper:ospfv2-network-lsa;
        }
      }
      case ospfv2-lsa-type-summary-net {
        container network-summary-lsa {
          description
            "The network summary Link State Advertisements";
          uses ospf-ios-xe-oper:ospfv2-summary-lsa;
        }
      }
      case ospfv2-lsa-type-summary-router {
        container router-summary-lsa {
          description
            "The router summary Link State Advertisements";
          uses ospf-ios-xe-oper:ospfv2-summary-lsa;
        }
      }
      case ospfv2-lsa-type-as-external {
        container external-lsa {
          description
            "The external Link State Advertisements";
          uses ospf-ios-xe-oper:ospfv2-external-lsa;
        }
      }
      case ospfv2-lsa-type-nssa {
        container nssa-lsa {
          description
            "The Not So Stubby Area Link state advertisements";
          uses ospf-ios-xe-oper:ospfv2-external-lsa;
        }
      }
    }
  }

  grouping ospfv2-nbr {
    description
      "Neighbor information";
    leaf nbr-id {
      type uint32;
      description
        "Specifies the OSPF Router ID of the neighbor.";
    }
    leaf address {
      type inet:ip-address;
      description
        "Specifies the IP address of the OSPF neighbor.";
    }
    leaf dr {
      type uint32;
      description
        "The neighbor's Designated Router identifier ";
    }
    leaf bdr {
      type uint32;
      description
        "The neighbor's Backup Designated Router identifier";
    }
    leaf dr-ip {
      type inet:ip-address;
      description
        "The designated routers' IP address";
    }
    leaf bdr-ip {
      type inet:ip-address;
      description
        "The backup designated routers' IP address";
    }
    leaf event-count {
      type uint32;
      description
        "The number of OSPF neighbor state change events that have occurred.";
    }
    leaf retrans-count {
      type uint32;
      description
        "A count of the retransmission events";
    }
    leaf state {
      type ospf-ios-xe-oper:nbr-state-type;
      description
        "Current state of the OSPF neighbor relationship.";
    }
    leaf dead-timer {
      type uint32;
      description
        "The dead timer in seconds";
    }
  }

  grouping ospfv2-ttl-security {
    description
      "Time to live security information";
    leaf enable {
      type boolean;
      description
        "Indicates whether time to live security is enabled";
    }
    leaf hops {
      type int32;
      description
        "Number of hops for time to live security";
    }
  }

  grouping ospfv2-auth-trailer-key {
    description
      "Trailer key information";
    leaf key-id {
      type uint8;
      description
        "The key identifier";
    }
    leaf-list key-string {
      type uint8;
      ordered-by user;
      description
        "List of key string values used for OSPF authentication on this interface; each entry is one byte of the key string.";
    }
    leaf crypto-algo {
      type ospf-ios-xe-oper:ospfv2-crypto-algorithm;
      description
        "The algorithm in use";
    }
  }

  grouping ospfv2-key-chain {
    description
      "Grouping that holds the OSPF key-chain authentication data for this interface.";
    leaf-list key-chain {
      type uint8;
      ordered-by user;
      description
        "List of key chain names used for OSPF authentication on this interface; each entry identifies a key chain by name.";
    }
  }

  grouping ospfv2-auth {
    description
      "OSPFv2 authentication information";
    choice auth-type-sel-choice {
      description
        "Authentication used";
      case ospfv2-auth-none {
        leaf no-auth {
          type uint32;
          description
            "No authentication in use";
        }
      }
      case ospfv2-auth-trailer-key {
        container auth-key {
          description
            "Trailer key chain information";
          uses ospf-ios-xe-oper:ospfv2-auth-trailer-key;
        }
      }
      case ospfv2-auth-trailer-key-chain {
        container key-chain {
          description
            "Trailer key information";
          uses ospf-ios-xe-oper:ospfv2-key-chain;
        }
      }
    }
  }

  grouping ospfv2-interface {
    description
      "Interface information";
    leaf name {
      type string;
      description
        "Name of the interface";
    }
    leaf network-type {
      type ospf-ios-xe-oper:ospf-network-type;
      description
        "Specifies the OSPF network type for this interface (such as broadcast, non-broadcast, point-to-point, or point-to-multipoint).";
    }
    leaf enable {
      type boolean;
      description
        "If the interface is enabled";
    }
    leaf passive {
      type boolean;
      description
        "If the interface is in passive mode";
    }
    leaf demand-circuit {
      type boolean;
      description
        "If this is a demand circuit";
    }
    leaf mtu-ignore {
      type boolean;
      description
        "If the MTU is being ignored";
    }
    leaf prefix-suppresion {
      type boolean;
      description
        "Indicates whether OSPF prefix suppression is enabled on this interface (prevents advertising the interface's network prefix in OSPF LSAs).";
    }
    leaf cost {
      type uint16;
      description
        "The OSPFv2 cost";
    }
    leaf hello-interval {
      type uint16;
      description
        "The hello interval in seconds";
    }
    leaf dead-interval {
      type uint16;
      description
        "The dead interval in seconds";
    }
    leaf retransmit-interval {
      type uint16;
      description
        "The retransmit interval in seconds";
    }
    leaf transmit-delay {
      type uint16;
      units "seconds";
      description
        "The estimated time in seconds required to transmit a Link State Advertisement (LSA) over this interface.";
    }
    leaf hello-timer {
      type uint32;
      description
        "The current hello timer in seconds";
    }
    leaf wait-timer {
      type uint32;
      units "seconds";
      description
        "The OSPF Wait Timer value, in seconds, indicating how long the router waits to hear from a Designated Router (DR) or Backup Designated Router before initiating an election.";
    }
    leaf dr {
      type uint32;
      description
        "The designated router identifier";
    }
    leaf bdr {
      type uint32;
      description
        "The backup designated router identifier";
    }
    leaf dr-ip {
      type inet:ip-address;
      description
        "The address of the designated router";
    }
    leaf bdr-ip {
      type inet:ip-address;
      description
        "The address of the backup designated router";
    }
    leaf state {
      type ospf-ios-xe-oper:ospfv2-intf-state;
      description
        "Current operational state of the OSPF interface.";
    }
    container ttl-security-val {
      description
        "Information related to OSPF TTL (Time To Live) security, which helps protect against certain types of attacks by verifying the TTL value in received OSPF packets.";
      uses ospf-ios-xe-oper:ospfv2-ttl-security;
    }
    container auth-val {
      description
        "The authentication information";
      uses ospf-ios-xe-oper:ospfv2-auth;
    }
    list ospfv2-neighbor {
      key "nbr-id";
      description
        "All the neighbors on the interface";
      uses ospf-ios-xe-oper:ospfv2-nbr;
    }
  }

  grouping ospfv2-area {
    description
      "List of OSPFv2 areas and their associated operational information for this OSPF instance";
    leaf area-id {
      type uint32;
      description
        "The area identifier";
    }
    list ospfv2-lsdb-area {
      key "lsa-type lsa-id advertising-router";
      description
        "The OSPF Link State Database information for this area";
      uses ospf-ios-xe-oper:ospfv2-lsa-info-key;
      uses ospf-ios-xe-oper:ospfv2-lsa-info;
    }
    list ospfv2-interface {
      key "name";
      description
        "A list of interfaces that belong to the area";
      uses ospf-ios-xe-oper:ospfv2-interface;
    }
  }

  grouping ospfv2-instance {
    description
      "The OSPFv2 instance";
    leaf instance-id {
      type uint32;
      description
        "The routing instance identifier assigned to the
         OSPF instance";
    }
    leaf vrf-name {
      type string;
      description
        "The name of the Virtual Routing and Forwarding
         instance that the OSPF instance is operating within";
    }
    leaf router-id {
      type uint32;
      description
        "The router identifier assigned to the OSPF instance";
    }
    list ospfv2-area {
      key "area-id";
      description
        "List of OSPFv2 areas and their associated operational information for this OSPF instance";
      uses ospf-ios-xe-oper:ospfv2-area;
    }
    list ospfv2-lsdb-external {
      key "lsa-type lsa-id advertising-router";
      description
        "Contains information about the OSPFv2 external Link State Database (LSDB), which holds LSAs describing routes external to the OSPF autonomous system.";
      uses ospf-ios-xe-oper:ospfv2-lsa-info-key;
      uses ospf-ios-xe-oper:ospfv2-lsa-info;
    }
  }

  grouping ospfv3-router {
    description
      "OSPFv3 router";
    leaf process-id {
      type uint16;
      description
        "OSPFv3 process id";
    }
    list ospfv3-afi {
      key "af vrf";
      description
        "List of OSPFv3 address families (such as IPv4 or IPv6) configured for this OSPFv3 instance, each identified by address family and VRF.";
      uses ospf-ios-xe-oper:ospfv3-afi;
      uses ospf-ios-xe-oper:ospfv3-address-family-key;
    }
  }

  grouping ospfv3-address-family-key {
    description
      "OSPFv3 AF instance";
    leaf af {
      type ospf-ios-xe-common:ospfv3-address-family-types;
      description
        "Specifies the OSPFv3 address family (such as IPv4 or IPv6) for this instance.";
    }
    leaf vrf {
      type string;
      description
        "Name of the VRF (Virtual Routing and Forwarding) instance associated with this OSPFv3 address family.";
    }
  }

  grouping ospfv3-router-link-topo {
    description
      "OSPFv3 router link topo";
    leaf mt-id {
      type uint8;
      description
        "Identifier for the OSPFv3 multi-topology associated with this router link.";
    }
    leaf metric {
      type uint16;
      description
        "OSPFv3 metric value for this router link in the specified multi-topology.";
    }
  }

  grouping ospfv3-router-lsa-link-key {
    description
      "Key fields that uniquely identify a link entry in the OSPFv3 Router LSA, comprising the link type, local interface ID, neighbor interface ID, and neighbor router ID.";
    leaf link-type {
      type ospf-ios-xe-oper:ospfv3-rtr-lsa-lnk-type;
      description
        "Specifies the type of link described in the OSPFv3 Router LSA (e.g., point-to-point, transit network, stub network, or virtual link).";
    }
    leaf link-intf-id {
      type uint32;
      description
        "Identifier of the local interface for the link as described in the OSPFv3 Router LSA.";
    }
    leaf nbr-intf-id {
      type uint32;
      description
        "Identifier of the neighboring router's interface for this link as described in the OSPFv3 Router LSA.";
    }
    leaf nbr-rtr-id {
      type inet:ipv4-address;
      description
        "Router ID of the neighboring router for this link as described in the OSPFv3 Router LSA.";
    }
  }

  grouping ospfv3-router-lsa-link {
    description
      "Grouping for a single link entry in the OSPFv3 Router LSA, containing topology-specific metrics and attributes for the link.";
    list link-topo {
      description
        "Topology-specific information for the link as described in the OSPFv3 Router LSA, such as metrics for different topologies.";
      uses ospf-ios-xe-oper:ospfv3-router-link-topo;
    }
  }

  grouping ospfv3-router-lsa {
    description
      "OSPFv3 router link state advertisement";
    leaf bits {
      type ospf-ios-xe-oper:ospfv3-rtr-lsa-bits;
      description
        "Bit flags in the OSPFv3 Router LSA indicating router capabilities and roles (e.g., V, E, B bits).";
    }
    leaf options {
      type ospf-ios-xe-oper:ospfv3-lsa-flag-opts;
      description
        "Option flags in the OSPFv3 Router LSA indicating supported OSPFv3 features and capabilities.";
    }
    leaf num-links {
      type uint32;
      description
        "Number of OSPFv3 router LSA links";
    }
  }

  grouping ospfv3-network-lsa {
    description
      "OSPFv3 network link state advertisement";
    leaf-list attached-rtrs {
      type inet:ipv4-address;
      ordered-by user;
      description
        "List of router IDs for routers attached to the network described by this OSPFv3 Network LSA.";
    }
    leaf options {
      type ospf-ios-xe-oper:ospfv3-lsa-flag-opts;
      description
        "Option flags in the OSPFv3 Network LSA indicating supported OSPFv3 features and capabilities.";
    }
  }

  grouping ospfv3-lsa-prefix-info {
    description
      "The prefix info for intra-area LSA";
    leaf options {
      type ospf-ios-xe-oper:ospfv3-lsa-pfx-opts;
      description
        "The options advertised for the prefix in the LSA";
    }
    leaf prefix {
      type inet:ip-prefix;
      description
        "Network prefix being advertised in the OSPFv3 AS-External LSA.";
    }
    leaf metric {
      type uint16;
      description
        "Metric for the prefix";
    }
  }

  grouping ospfv3-lsa-prefixtype {
    description
      "The prefix type in link state advertisement";
    leaf options {
      type ospf-ios-xe-oper:ospfv3-lsa-pfx-opts;
      description
        "The options advertised for the prefix in the LSA";
    }
    leaf prefix {
      type inet:ip-prefix;
      description
        "Network prefix being advertised in the OSPFv3 AS-External LSA.";
    }
  }

  grouping ospfv3-iapfx-lsa {
    description
      "OSPFv3 inter-area prefix link state advertisement";
    leaf metric {
      type uint32;
      description
        "Metric for inter-area prefix LSA";
    }
    container prefix {
      description
        "Advertised prefix in inter-area prefix LSA";
      uses ospf-ios-xe-oper:ospfv3-lsa-prefixtype;
    }
  }

  grouping ospfv3-iartr-lsa {
    description
      "OSPFv3 inter-area router link state advertisement";
    leaf metric {
      type uint32;
      description
        "Metric for inter-area router LSA";
    }
    leaf options {
      type ospf-ios-xe-oper:ospfv3-lsa-flag-opts;
      description
        "Options advertised in inter-area router LSA";
    }
    leaf rtr-id {
      type inet:ipv4-address;
      description
        "Advertising router in inter-area router LSA";
    }
  }

  grouping ospfv3-ex-lsa {
    description
      "The external link state advertisement";
    container prefix {
      description
        "The prefix for the external LSA";
      uses ospf-ios-xe-oper:ospfv3-lsa-prefixtype;
    }
    leaf metric-type {
      type ospf-ios-xe-oper:ospfv3-ase-metric-type;
      description
        "Metric type: 2 (larger than any link state path), Metric type: 1 (comparable directly to link state metric)";
    }
    leaf metric {
      type uint32;
      description
        "Specifies the metric value for the external route as advertised in the NSSA (Not-So-Stubby Area) LSA.";
    }
  }

  grouping ospfv3-link-lsa {
    description
      "The link link state advertisement";
    leaf router-priority {
      type uint8;
      description
        "The router priority for the link LSA";
    }
    leaf options {
      type ospf-ios-xe-oper:ospfv3-lsa-flag-opts;
      description
        "OSPFv3 option flags advertised in the Link LSA, indicating supported capabilities and features on the interface.";
    }
    leaf local-addr {
      type inet:ip-address;
      description
        "The IPv6 link-local address of the interface as advertised in the OSPFv3 Link LSA.";
    }
    list prefix {
      description
        "Details of the prefixes in link LSA";
      uses ospf-ios-xe-oper:ospfv3-lsa-prefixtype;
    }
  }

  grouping ospfv3-prefix-lsa {
    description
      "The intra-area prefix link state advertisement";
    leaf ref-ls-type {
      type uint16;
      description
        "Specifies the type of the referenced LSA (Link State Advertisement) to which this Prefix LSA is associated.";
    }
    leaf ref-ls-id {
      type uint32;
      description
        "Specifies the Link State ID of the LSA referenced by this Prefix LSA.";
    }
    leaf ref-adv-rtr {
      type inet:ipv4-address;
      description
        "Specifies the Router ID of the advertising router for the LSA referenced by this Prefix LSA.";
    }
    list prefix {
      description
        "Contains information about IPv6 prefixes advertised in the OSPFv3 intra-area Prefix LSA.";
      uses ospf-ios-xe-oper:ospfv3-lsa-prefix-info;
    }
  }

  grouping ospfv3-lsa-header-info {
    description
      "Contains header information for the OSPFv3 link state advertisement (LSA).";
    leaf lsa-age {
      type uint16;
      units "seconds";
      description
        "Age of the link state advertisement";
    }
    leaf lsa-seq-number {
      type uint32;
      description
        "Sequence number for the link state advertisement";
    }
    leaf lsa-checksum {
      type uint16;
      description
        "Checksum of the link state advertisement";
    }
    leaf lsa-length {
      type uint16;
      units "bytes";
      description
        "The length of the link state advertisement";
    }
  }

  grouping ospfv3-lsa-info {
    description
      "OSPFv3 link state advertisement information";
    container lsa-header-info {
      description
        "The link state advertisement header info";
      uses ospf-ios-xe-oper:ospfv3-lsa-header-info;
    }
    list ospfv3-router-lsa-link {
      key "link-type link-intf-id nbr-intf-id nbr-rtr-id";
      description
        "List of links described in the OSPFv3 Router Link State Advertisement (LSA), including details about each link's type, interface, and neighboring router.";
      uses ospf-ios-xe-oper:ospfv3-router-lsa-link-key;
      uses ospf-ios-xe-oper:ospfv3-router-lsa-link;
    }
    choice area-scope-lsa-type-choice {
      description
        "The type of link state advertisement";
      case ospfv3-lsa-type-router {
        description
          "Router LSA";
        container router-lsa {
          description
            "The router link state advertisement";
          uses ospf-ios-xe-oper:ospfv3-router-lsa;
        }
      }
      case ospfv3-lsa-type-network {
        description
          "Network LSA";
        container network-lsa {
          description
            "The network link state advertisement";
          uses ospf-ios-xe-oper:ospfv3-network-lsa;
        }
      }
      case ospfv3-lsa-type-inter-area-prefix {
        description
          "Inter-area prefix LSA";
        container iapfx-lsa {
          description
            "The inter-area prefix link state advertisement";
          uses ospf-ios-xe-oper:ospfv3-iapfx-lsa;
        }
      }
      case ospfv3-lsa-type-inter-area-router {
        description
          "Inter-area router LSA";
        container iartr-lsa {
          description
            "The inter-area router link state advertisement";
          uses ospf-ios-xe-oper:ospfv3-iartr-lsa;
        }
      }
      case ospfv3-lsa-type-nssa {
        description
          "Represents an OSPFv3 NSSA (Not-So-Stubby Area) external LSA, which advertises external routes within an NSSA area.";
        container nssa-lsa {
          description
            "The not-so-stubby-area link state advertisement";
          uses ospf-ios-xe-oper:ospfv3-ex-lsa;
        }
      }
      case ospfv3-lsa-type-prefix {
        description
          "Prefix LSA";
        container prefix-lsa {
          description
            "The intra-area prefix link state advertisement";
          uses ospf-ios-xe-oper:ospfv3-prefix-lsa;
        }
      }
    }
  }

  grouping ospfv3-lsa-info-key {
    description
      "OSPFv3 link state advertisement information key";
    leaf lsa-type {
      type uint16;
      description
        "Link state advertisement type";
    }
    leaf lsa-id {
      type uint32;
      description
        "Link state advertisement identifier";
    }
    leaf advertising-router {
      type inet:ipv4-address;
      description
        "Router ID (IPv4 address) of the OSPFv3 router that originated this link-state advertisement (LSA).";
    }
  }

  grouping ospfv3-as-scope-lsa {
    description
      "OSPFv3 as scope LSA";
    container lsa-header-info {
      description
        "Contains header information for the OSPFv3 link state advertisement (LSA).";
      uses ospf-ios-xe-oper:ospfv3-lsa-header-info;
    }
    container ase-lsa {
      description
        "Contains information about the OSPFv3 Autonomous System External (AS-External) Link State Advertisement, which is used to advertise routes external to the OSPF autonomous system.";
      uses ospf-ios-xe-oper:ospfv3-ex-lsa;
    }
  }

  grouping ospfv3-afi {
    description
      "Address Family";
    leaf router-id {
      type inet:ipv4-address;
      description
        "The unique router ID for the OSPFv3 process, represented as an IPv4 address.";
    }
    list ospfv3-as-scope-lsa {
      key "lsa-type lsa-id advertising-router";
      description
        "OSPFv3 AS scope LSA";
      uses ospf-ios-xe-oper:ospfv3-lsa-info-key;
      uses ospf-ios-xe-oper:ospfv3-as-scope-lsa;
    }
    list ospfv3-area {
      key "area-id";
      description
        "Represents an OSPFv3 area, a logical grouping of routers within an OSPFv3 routing domain.";
      uses ospf-ios-xe-oper:ospfv3-area;
    }
  }

  grouping ospfv3-area {
    description
      "Represents an OSPFv3 area, a logical grouping of routers within an OSPFv3 routing domain.";
    leaf area-id {
      type uint32;
      description
        "Identifier for the OSPFv3 area to which this configuration or interface belongs. Used to segment the OSPFv3 routing domain into multiple areas.";
    }
    list ospfv3-intf {
      key "name";
      description
        "List of interfaces configured for OSPFv3 operation within the specified area.";
      uses ospf-ios-xe-oper:ospfv3-intf;
    }
    list ospfv3-area-scope-lsa {
      key "lsa-type lsa-id advertising-router";
      description
        "OSPFv3 link state database information in this area";
      uses ospf-ios-xe-oper:ospfv3-lsa-info-key;
      uses ospf-ios-xe-oper:ospfv3-lsa-info;
    }
  }

  grouping ospfv3-ttl-security {
    description
      "OSPFV3 TTL security on interface";
    leaf enable {
      type boolean;
      description
        "Enable TTL security on interface";
    }
    leaf hops {
      type uint8;
      description
        "Number of Hops Count";
    }
  }

  grouping ipsec-key {
    description
      "OSPFv3 IPSEC authentication";
    leaf algorithm {
      type ospf-ios-xe-oper:ospfv3-ipsec-auth-algo;
      description
        "IPSEC authentication algorithm";
    }
    leaf spi {
      type uint32;
      description
        "Security parameter index";
    }
    leaf key-string {
      type string;
      description
        "Key for IPSEC algorithm";
    }
  }

  grouping ospfv3-auth {
    description
      "OSPFv3 authentication";
    leaf trailer-key-chain {
      type string;
      description
        "Key chain name";
    }
    container ipsec-key {
      description
        "IPSEC authentication";
      uses ospf-ios-xe-oper:ipsec-key;
    }
  }

  grouping ospfv3-link-scope-lsa {
    description
      "OSPFV3 link scope lsa info ";
    container lsa-header-info {
      description
        "LSA header details";
      uses ospf-ios-xe-oper:ospfv3-lsa-header-info;
    }
    container link-lsa {
      description
        "Contains information from the OSPFv3 Link LSA, which advertises the router's link-local address and prefixes on a specific interface.";
      uses ospf-ios-xe-oper:ospfv3-link-lsa;
    }
  }

  grouping ospfv3-intf {
    description
      "OSPFv3 interface";
    leaf name {
      type string;
      description
        "Name of the interface participating in OSPFv3 within this area.";
    }
    leaf network-type {
      type ospf-ios-xe-common:ospfv3-network-type;
      description
        "Specifies the OSPFv3 network type configured on the interface (e.g., broadcast, point-to-point, non-broadcast).";
    }
    leaf enable {
      type boolean;
      description
        "Indicates whether OSPFv3 is enabled or disabled on the interface";
    }
    leaf passive {
      type boolean;
      description
        "Indicates whether interface is passive or not";
    }
    leaf demand-circuit {
      type boolean;
      description
        "Indicates whether demand circuit is enabled or disabled";
    }
    leaf mtu-ignore {
      type boolean;
      description
        "Indicates whether ignoring of MTU in DBD packets is enabled or disabled";
    }
    leaf prefix-suppression {
      type boolean;
      description
        "Indicates whether advertisement of interface IP prefixes in OSPF is suppressed on this interface.";
    }
    leaf cost {
      type uint16;
      description
        "OSPFv3 cost (metric) assigned to the interface, used to determine the shortest path for routing.";
    }
    leaf hello-interval {
      type uint16;
      units "seconds";
      description
        "Time between hello packets";
    }
    leaf dead-interval {
      type uint16;
      units "seconds";
      description
        "Interval to declare neighbor as dead";
    }
    leaf retransmit-interval {
      type uint16;
      units "seconds";
      description
        "Time between retransmitting unacknowledged link-state advertisements (LSAs)";
    }
    leaf transmit-delay {
      type uint16;
      units "seconds";
      description
        "Estimated time needed to send link-state update";
    }
    leaf hello-timer {
      type uint32;
      units "seconds";
      description
        "Current value, in seconds, of the OSPFv3 Hello timer for this interface, indicating the time remaining until the next Hello packet is sent.";
    }
    leaf wait-timer {
      type uint32;
      units "seconds";
      description
        "Current value, in seconds, of the OSPFv3 wait timer for this interface, indicating the time remaining before the router transitions out of the waiting state during neighbor discovery.";
    }
    leaf dr {
      type inet:ipv4-address;
      description
        "IPv4 address of the OSPFv3 Designated Router (DR) for this interface.";
    }
    leaf bdr {
      type inet:ipv4-address;
      description
        "IPv4 address of the OSPFv3 Backup Designated Router for this interface.";
    }
    leaf dr-ip {
      type inet:ipv6-address;
      description
        "Designated router IP address";
    }
    leaf bdr-ip {
      type inet:ipv6-address;
      description
        "Backup designated router IP address";
    }
    leaf if-state {
      type ospf-ios-xe-common:ospfv3-if-state;
      description
        "Operational state of the OSPFv3 interface, indicating its current status within the OSPF protocol (e.g., Down, Waiting, Point-to-Point, etc.).";
    }
    container ttl-security {
      description
        "TTL (Time To Live) security on the OSPFv3 interface, used to protect against certain types of attacks by checking the TTL value of received packets.";
      uses ospf-ios-xe-oper:ospfv3-ttl-security;
    }
    container authentication {
      description
        "OSPFv3 authentication configuration and operational state for the interface.";
      uses ospf-ios-xe-oper:ospfv3-auth;
    }
    list ospfv3-link-scope-lsa {
      key "lsa-type lsa-id advertising-router";
      description
        "Represents a Link State Advertisement (LSA) with link-local scope in OSPFv3, used to describe information specific to a particular interface.";
      uses ospf-ios-xe-oper:ospfv3-lsa-info-key;
      uses ospf-ios-xe-oper:ospfv3-link-scope-lsa;
    }
    list ospfv3-nbr {
      key "nbr-id";
      description
        "OSPFv3 neighbors";
      uses ospf-ios-xe-oper:ospfv3-nbr;
    }
  }

  grouping ospfv3-nbr {
    description
      "OSPF neighbor details";
    leaf nbr-id {
      type inet:ipv4-address;
      description
        "OSPFv3 neighbor ID";
    }
    leaf address {
      type inet:ipv6-address;
      description
        "IPv6 link-local address";
    }
    leaf dr {
      type inet:ipv4-address;
      description
        "IPv4 address of the Designated Router (DR) for the OSPFv3 interface.";
    }
    leaf bdr {
      type inet:ipv4-address;
      description
        "IPv4 address of the backup designated router for this OSPFv3 neighbor.";
    }
    leaf event-count {
      type uint32;
      description
        "OSPFv3 neighbor event count";
    }
    leaf retrans-count {
      type uint32;
      description
        "OSPFv3 neighbor retransmission count";
    }
    leaf nbr-state {
      type ospf-ios-xe-common:ospfv3-nbr-state;
      description
        "OSPFv3 neighbor state";
    }
    leaf dead-timer {
      type uint32;
      units "seconds";
      description
        "Dead timer for the neighbor";
    }
  }

  container ospf-oper-data {
    config false;
    description
      "Operational state of ospf";
    container ospf-state {
      presence "tbl-ospf";
      description
        "OSPF operational state";
      uses ospf-ios-xe-oper:ospf-rev1;
    }
    list ospfv2-instance {
      key "instance-id";
      description
        "List of OSPFv2 protocol instances configured on the device";
      uses ospf-ios-xe-oper:ospfv2-instance;
    }
    list ospfv3-router {
      key "process-id";
      description
        "The OSPFv3 router instance";
      uses ospf-ios-xe-oper:ospfv3-router;
    }
  }
}
