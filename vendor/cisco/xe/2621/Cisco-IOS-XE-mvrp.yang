module Cisco-IOS-XE-mvrp {
  yang-version 1.1;
  namespace "http://cisco.com/ns/yang/Cisco-IOS-XE-mvrp";
  prefix ios-mvrp;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Multiple VLAN Registration Protocol Yang Model.
     Copyright (c) 2016-2026 by Cisco Systems, Inc.
     All rights reserved.";

  revision 2026-08-01 {
    description
      "- Deprecated timer containers (join, leave, leave-all) with presence statements
       - Added new timer leaf nodes without presence (join-timer, leave-timer, leave-all-timer)";
    cisco-semver:module-version "1.4.0";
  }
  revision 2026-02-01 {
    description
      "- Added support for mvrp on 200 GigabitEthernet and 400 GigabitEthernet interface";
    cisco-semver:module-version "1.3.0";
  }
  revision 2025-07-01 {
    description
      "- Added FiftyGigabitEthernet interface support";
    cisco-semver:module-version "1.2.0";
  }
  revision 2022-11-01 {
    description
      "- Update yang-version to 1.1";
    cisco-semver:module-version "1.1.0";
  }
  revision 2019-07-01 {
    description
      "Establish semantic version baseline";
    cisco-semver:module-version "1.0.0";
  }
  revision 2019-02-26 {
    description
      "Added leaf for App-hosting Gigabit Ethernet interface";
  }
  revision 2017-11-27 {
    description
      "Added Change 25GE name";
  }
  revision 2017-11-14 {
    description
      "Added Fast, 2, 5, 25, 100GE interface support";
  }
  revision 2017-09-19 {
    description
      "Initial revision";
  }

  grouping config-mvrp-grouping {
    leaf global {
      type empty;
    }
    container mac-learning {
      leaf auto {
        type empty;
      }
    }
    container vlan {
      leaf create {
        type empty;
      }
    }
  }

  grouping config-interface-mvrp-grouping {
    container mvrp {
      presence "true";
      leaf mvrp {
        type empty;
      }
      container registration {
        leaf fixed {
          type empty;
        }
        leaf forbidden {
          type empty;
        }
        leaf normal {
          type empty;
        }
      }
      container timer {
        description
          "Configure mvrp timers on this interface";
        leaf join-timer {
          description
            "Join timer interval for MVRP (Multiple VLAN Registration Protocol).
             Controls the transmission frequency of VLAN registration messages.";
          type uint32 {
            range "20..214748364";
          }
          default "20";
        }
        leaf leave-timer {
          description
            "Leave timer interval for MVRP (Multiple VLAN Registration Protocol).
             Controls the hold time before removing VLAN registrations when
             leave messages are received.";
          type uint32 {
            range "60..214748364";
          }
          default "60";
        }
        leaf leave-all-timer {
          description
            "Leave-all timer interval for MVRP (Multiple VLAN Registration Protocol).
             Specifies how often the device triggers a refresh of all VLAN
             registrations to prevent stale entries.";
          type uint32 {
            range "1000..214748364";
          }
          default "1000";
        }
        container join {
          status deprecated;
          presence "true";
          leaf _range {
            status deprecated;
            type uint32 {
              range "20..214748364";
            }
          }
        }
        container leave {
          status deprecated;
          presence "true";
          leaf _range {
            status deprecated;
            type uint32 {
              range "60..214748364";
            }
          }
        }
        container leave-all {
          status deprecated;
          presence "true";
          leaf _range {
            status deprecated;
            type uint32 {
              range "1000..214748364";
            }
          }
        }
        leaf periodic {
          type empty;
        }
      }
    }
  }

  augment "/ios:native/ios:mvrp" {
    uses config-mvrp-grouping;
  }

  augment "/ios:native/ios:interface/ios:GigabitEthernet" {
    uses config-interface-mvrp-grouping;
  }

  augment "/ios:native/ios:interface/ios:TenGigabitEthernet" {
    uses config-interface-mvrp-grouping;
  }

  augment "/ios:native/ios:interface/ios:FortyGigabitEthernet" {
    uses config-interface-mvrp-grouping;
  }

  augment "/ios:native/ios:interface/ios:FiftyGigabitEthernet" {
    uses config-interface-mvrp-grouping;
  }

  augment "/ios:native/ios:interface/ios:FastEthernet" {
    uses config-interface-mvrp-grouping;
  }

  augment "/ios:native/ios:interface/ios:TwoGigabitEthernet" {
    uses config-interface-mvrp-grouping;
  }

  augment "/ios:native/ios:interface/ios:FiveGigabitEthernet" {
    uses config-interface-mvrp-grouping;
  }

  augment "/ios:native/ios:interface/ios:AppGigabitEthernet" {
    uses config-interface-mvrp-grouping;
  }

  augment "/ios:native/ios:interface/ios:TwentyFiveGigE" {
    uses config-interface-mvrp-grouping;
  }

  augment "/ios:native/ios:interface/ios:HundredGigE" {
    uses config-interface-mvrp-grouping;
  }

  augment "/ios:native/ios:interface/ios:TwoHundredGigE" {
    uses config-interface-mvrp-grouping;
  }

  augment "/ios:native/ios:interface/ios:FourHundredGigE" {
    uses config-interface-mvrp-grouping;
  }

  augment "/ios:native/ios:interface/ios:Port-channel" {
    uses config-interface-mvrp-grouping;
  }
}
