module Cisco-IOS-XE-sd-vxlan-oper {
  yang-version 1.1;
  namespace "http://cisco.com/ns/yang/Cisco-IOS-XE-sd-vxlan-oper";
  prefix sd-vxlan-ios-xe-oper;

  import Cisco-IOS-XE-ios-common-oper {
    prefix ios-common-ios-xe-oper;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for SD-VXLAN operational data.
     Copyright (c) 2018-2019, 2022, 2026 by Cisco Systems, Inc.
     All rights reserved.";

  revision 2026-08-01 {
    description
      "Updated descriptions for several leaves to better explain their meaning and purpose";
    reference
      "2.0.0";
    cisco-semver:module-version "2.0.0";
  }
  revision 2022-11-01 {
    description
      "Update yang-version to 1.1";
    reference
      "1.1.0";
    cisco-semver:module-version "1.1.0";
  }
  revision 2020-03-01 {
    description
      "Initial revision";
    reference
      "1.0.0";
    cisco-semver:module-version "1.0.0";
  }

  typedef vxlan-rp-mode-enum {
    type enumeration {
      enum mode-gpe {
        value 0;
        description
          "VxLAN route profile mode of VxLAN generic protocol extension";
      }
      enum mode-default-mac {
        value 1;
        description
          "VxLAN route profile mode of VxLAN default MAC";
      }
    }
    description
      "VxLAN route profile mode enumeration";
  }

  typedef vxlan-rp-hash-mode-enum {
    type enumeration {
      enum three-tuple {
        value 0;
        description
          "Calculate outer UDP source Port based on inner source IP, destination IP and Protocol";
      }
      enum three-tuple-frag {
        value 1;
        description
          "Calculate outer UDP source Port by three-tuple mode for fragmented packets, or by five-tuple mode for non-fragmented packets";
      }
      enum five-tuple {
        value 2;
        description
          "Calculate outer UDP source port based on inner source IP, destination IP, source Port, destination Port, and Protocol";
      }
    }
    description
      "VxLAN route profile hash mode enumeration";
  }

  typedef vxlan-sr-summary-key-enum {
    type enumeration {
      enum vxlan-static-route-summary-key {
        value 0;
        description
          "VxLAN static route summary entry key";
      }
    }
    description
      "Defines the type of VxLAN static route summary entry key";
  }

  grouping per-vni-vrf-key {
    description
      "Key for statistics for per VNI per VRF of VxLAN";
    leaf vrf-name {
      type string;
      description
        "Name of VRF the statistics belongs to";
    }
    leaf vni {
      type uint32;
      description
        "VNI the statistics belongs to";
    }
  }

  grouping per-vni-vrf-stats {
    description
      "VxLAN static route per-VNI and per-VRF statistics";
    leaf egress-packets {
      type uint64;
      units "packets";
      description
        "Number of egress packets per VNI per VRF for VxLAN";
    }
    leaf egress-bytes {
      type uint64;
      units "bytes";
      description
        "Number of egress bytes per VNI per VRF for VxLAN";
    }
    leaf ingress-packets {
      type uint64;
      units "packets";
      description
        "Number of ingress packets per VNI per VRF for VxLAN";
    }
    leaf ingress-bytes {
      type uint64;
      units "bytes";
      description
        "Number of ingress bytes per VNI per VRF for VxLAN";
    }
  }

  grouping per-vni-vrf-policer {
    description
      "Policer statistics for per VNI per VRF of VxLAN";
    leaf cir {
      type uint64;
      units "bps";
      description
        "Configured committed information rate (CIR) in bits per second for the policer";
    }
    leaf bc {
      type uint64;
      units "bytes";
      description
        "Configured burst size in bytes";
    }
    leaf confirmed-packets {
      type uint64;
      units "packets";
      description
        "Number of confirmed packets per VNI per VRF for VxLAN";
    }
    leaf confirmed-bytes {
      type uint64;
      units "bytes";
      description
        "Number of confirmed bytes per VNI per VRF for VxLAN";
    }
    leaf exceeded-packets {
      type uint64;
      units "packets";
      description
        "Number of exceeded packets per VNI per VRF for VxLAN";
    }
    leaf exceeded-bytes {
      type uint64;
      units "bytes";
      description
        "Number of exceeded bytes per VNI per VRF for VxLAN";
    }
  }

  grouping per-vni-stats {
    description
      "VxLAN static route per-VNI statistics";
    leaf vni {
      type uint32;
      description
        "VNI the statistics belongs to";
    }
    leaf vni-packets {
      type uint64;
      units "packets";
      description
        "Number of egress packets per VNI for software-defined VxLAN";
    }
    leaf vni-bytes {
      type uint64;
      units "bytes";
      description
        "Number of egress bytes per VNI for software-defined VxLAN";
    }
  }

  grouping per-vrf-pfx-stats {
    description
      "Statistics for each vrf prefix entry";
    leaf prefix {
      type inet:ip-prefix;
      description
        "Prefix the statistics belongs to";
    }
    leaf packets {
      type uint64;
      units "packets";
      description
        "Number of egress packets per VRF per prefix for VxLAN";
    }
    leaf bytes {
      type uint64;
      units "bytes";
      description
        "Number of egress bytes per VRF per prefix for VxLAN";
    }
  }

  grouping per-vrf-pfx-entries {
    description
      "Statistics for per VRF per prefix of VxLAN static routes";
    leaf vrf-name {
      type string;
      description
        "VRF name the statistics belongs to";
    }
    leaf ipv4-total-packets {
      type uint64;
      units "packets";
      description
        "Number of IPv4 total packets per VRF";
    }
    leaf ipv4-total-bytes {
      type uint64;
      units "bytes";
      description
        "Number of IPv4 total bytes per VRF";
    }
    leaf ipv6-total-packets {
      type uint64;
      units "packets";
      description
        "Number of IPv6 total packets per VRF";
    }
    leaf ipv6-total-bytes {
      type uint64;
      units "bytes";
      description
        "Number of IPv6 total bytes per VRF";
    }
    list per-vrf-pfx-v4 {
      key "prefix";
      description
        "List of VxLAN statistics by IPv4 route prefix within the VRF. Each entry includes packet and byte counts for the prefix.";
      uses sd-vxlan-ios-xe-oper:per-vrf-pfx-stats;
    }
    list per-vrf-pfx-v6 {
      key "prefix";
      description
        "List of VxLAN statistics by IPv6 route prefix within the VRF. Each entry includes packet and byte counts for the prefix.";
      uses sd-vxlan-ios-xe-oper:per-vrf-pfx-stats;
    }
  }

  grouping vxlan-sr-entry-key {
    description
      "Key for VxLAN static route entry data";
    leaf vrf-name {
      type string;
      description
        "VRF name the static route belongs to";
    }
    leaf prefix {
      type inet:ip-prefix;
      description
        "Prefix the static route belongs to";
    }
  }

  grouping vxlan-sr-nh-data {
    description
      "VxLAN static route nexthop entry data";
    leaf link-type {
      type ios-common-ios-xe-oper:ios-linktype;
      description
        "Link type of the nexthop entry";
    }
    leaf vni {
      type uint32;
      description
        "VNI of the nexthop entry";
    }
    leaf nh-addr {
      type inet:ip-address;
      description
        "Nexthop address of the nexthop entry";
    }
    leaf bind-label {
      type uint32;
      description
        "Binding label of the nexthop entry";
    }
    leaf conn-id {
      type uint32;
      description
        "Connection ID of the nexthop entry";
    }
    leaf tunnel-name {
      type string;
      description
        "Auto tunnel name of the nexthop entry";
    }
  }

  grouping vxlan-sr-entry {
    description
      "VxLAN static route entry data";
    list nexthop-entry {
      key "conn-id";
      description
        "Nexthop entries of the static route";
      uses sd-vxlan-ios-xe-oper:vxlan-sr-nh-data;
    }
  }

  grouping vxlan-rp-entry {
    description
      "VxLAN route profile entry data";
    leaf name {
      type string;
      description
        "Name of the VxLAN route profile entry";
    }
    leaf reserve-word-1 {
      type uint16;
      description
        "Reserved word 1(16 bits) of the VxLAN route profile entry";
    }
    leaf reserve-word-2 {
      type uint8;
      description
        "Reserved word 2(8 bits) of the VxLAN route profile entry";
    }
    leaf dscp {
      type uint8;
      description
        "DSCP value of the VxLAN route profile entry";
    }
    leaf src-mac {
      type yang:mac-address;
      description
        "Source MAC address of the VxLAN route profile entry";
    }
    leaf src-port-start {
      type uint16;
      description
        "Tunnel source port start of the VxLAN route profile entry";
    }
    leaf src-port-end {
      type uint16;
      description
        "Tunnel source port end of the VxLAN route profile entry";
    }
    leaf src-port-hash-mode {
      type sd-vxlan-ios-xe-oper:vxlan-rp-hash-mode-enum;
      description
        "Tunnel source port hash mode of the VxLAN route profile entry";
    }
    leaf mode {
      type sd-vxlan-ios-xe-oper:vxlan-rp-mode-enum;
      description
        "VxLAN mode of the VxLAN route profile entry";
    }
    leaf src-interface {
      type string;
      description
        "Tunnel source interface of the VxLAN route profile entry";
    }
    leaf dst-port {
      type uint16;
      description
        "VxLAN destination port of the VxLAN route profile entry";
    }
    leaf mtu {
      type uint16;
      description
        "Tunnel mtu of the VxLAN route profile entry";
    }
    leaf persistent {
      type boolean;
      description
        "Indicates whether the VxLAN route profile entry is persistent after reloads";
    }
  }

  grouping vxlan-rp-auto-tunnel-entry {
    description
      "VxLAN route profile auto tunnel entry data";
    leaf name {
      type string;
      description
        "Name of the VxLAN route profile auto tunnel entry";
    }
    leaf v4-auto-tunnel {
      type string;
      description
        "IPv4 auto tunnel of the VxLAN route profile auto tunnel entry";
    }
    leaf v6-auto-tunnel {
      type string;
      description
        "IPv6 auto tunnel of the VxLAN route profile auto tunnel entry";
    }
  }

  grouping vxlan-rp-auto-tunnel-symmetric-entry-key {
    description
      "VxLAN route profile auto tunnel symmetric entry key";
    leaf name {
      type string;
      description
        "Name of the VxLAN route profile auto tunnel symmetric entry";
    }
    leaf vrf-name {
      type string;
      description
        "VRF name of the VxLAN route profile auto tunnel symmetric entry";
    }
  }

  grouping vxlan-rp-auto-tunnel-symmetric-entry {
    description
      "VxLAN route profile auto tunnel symmetric entry data";
    leaf v4-auto-tunnel {
      type string;
      description
        "IPv4 auto tunnel of the VxLAN route profile auto tunnel symmetric entry";
    }
    leaf v6-auto-tunnel {
      type string;
      description
        "IPv6 auto tunnel of the VxLAN route profile auto tunnel symmetric entry";
    }
  }

  grouping vxlan-sr-summary-entry-key {
    description
      "Key that identifies the VxLAN static route summary entry";
    leaf entry-key {
      type sd-vxlan-ios-xe-oper:vxlan-sr-summary-key-enum;
      description
        "Key value for the VxLAN static route summary entry";
    }
  }

  grouping vxlan-sr-summary-entry {
    description
      "Summary statistics, tunnel range information, and P2P accounting/policing state for VxLAN static routes";
    leaf prefix-cnt {
      type uint32;
      description
        "Specifies the number of prefix entries in VxLAN static routes";
    }
    leaf persist-prefix-cnt {
      type uint32;
      description
        "Specifies the number of persistent prefix entries in VxLAN static routes";
    }
    leaf route-profile-cnt {
      type uint32;
      description
        "Specifies the number of VxLAN route profile entries";
    }
    leaf vni-node-cnt {
      type uint32;
      description
        "Specifies the number of VNI nodes in VxLAN static routes";
    }
    leaf next-hop-cnt {
      type uint32;
      description
        "Specifies the number of next-hop entries in VxLAN static routes";
    }
    leaf auto-tunnel-cnt {
      type uint32;
      description
        "Specifies the number of auto tunnels in VxLAN static routes";
    }
    leaf vni-vrf-node-cnt {
      type uint32;
      description
        "Specifies the number of VNI and VRF node combinations in VxLAN static routes";
    }
    leaf default-dst-mac {
      type yang:mac-address;
      description
        "VxLAN static route destination MAC address";
    }
    leaf auto-tunnel-start {
      type uint32;
      description
        "Starting value for the auto-tunnel range used by VxLAN static routes";
    }
    leaf auto-tunnel-end {
      type uint32;
      description
        "Ending value for the auto-tunnel range used by VxLAN static routes";
    }
    leaf p2p-accounting-policing {
      type boolean;
      description
        "Indicates whether accounting and policing are enabled for VxLAN point-to-point tunnels";
    }
  }

  container sd-vxlan-oper-data {
    config false;
    description
      "VXLAN operational data";
    list per-vni-vrf-stats {
      key "vrf-name vni";
      description
        "List of VxLAN statistics by Virtual Network Interface (VNI) and VRF. Each entry includes ingress and egress packet and byte counts for the VNI and VRF.";
      uses sd-vxlan-ios-xe-oper:per-vni-vrf-key;
      uses sd-vxlan-ios-xe-oper:per-vni-vrf-stats;
    }
    list per-vni-vrf-policer {
      key "vrf-name vni";
      description
        "List of policer statistics by VNI and VRF. Each entry includes the committed information rate (CIR), burst size, and confirmed and exceeded packet and byte counts for the VNI and VRF.";
      uses sd-vxlan-ios-xe-oper:per-vni-vrf-key;
      uses sd-vxlan-ios-xe-oper:per-vni-vrf-policer;
    }
    list per-vni-stats {
      key "vni";
      description
        "List of VxLAN statistics by VNI. Each entry includes the packet and byte count for the VNI.";
      uses sd-vxlan-ios-xe-oper:per-vni-stats;
    }
    list per-vrf-pfx-stats {
      key "vrf-name";
      description
        "List of VxLAN statistics by VRF. Each entry includes total IPv4 and IPv6 packet and byte counts for the VRF, along with IPv4 and IPv6 prefix statistics.";
      uses sd-vxlan-ios-xe-oper:per-vrf-pfx-entries;
    }
    list static-route {
      key "vrf-name prefix";
      description
        "List of VxLAN static routes by VRF and prefix. Each entry includes the next-hop data associated with the VRF and prefix.";
      uses sd-vxlan-ios-xe-oper:vxlan-sr-entry-key;
      uses sd-vxlan-ios-xe-oper:vxlan-sr-entry;
    }
    list route-profile {
      key "name";
      description
        "List of VxLAN route profiles. Each entry includes the associated VRF and tunnel data.";
      uses sd-vxlan-ios-xe-oper:vxlan-rp-entry;
    }
    list rp-auto-tunnel {
      key "name";
      description
        "List of VxLAN route profile auto tunnels. Each entry includes IPv4 and IPv6 auto-tunnel information.";
      uses sd-vxlan-ios-xe-oper:vxlan-rp-auto-tunnel-entry;
    }
    list rp-tunnel-symmetric {
      key "name vrf-name";
      description
        "List of VxLAN route profile auto-tunnel symmetric entries. Each entry includes IPv4 and IPv6 auto-tunnels for the route profile and VRF.";
      uses sd-vxlan-ios-xe-oper:vxlan-rp-auto-tunnel-symmetric-entry-key;
      uses sd-vxlan-ios-xe-oper:vxlan-rp-auto-tunnel-symmetric-entry;
    }
    list bind-label-data {
      key "bind-label";
      description
        "List of VxLAN static route next-hop entries by bind label. Each entry includes next-hop information for the bind label.";
      uses sd-vxlan-ios-xe-oper:vxlan-sr-nh-data;
    }
    list conn-id-data {
      key "conn-id";
      description
        "List of VxLAN static route next-hop entries by connection ID. Each entry includes next-hop information for the connection ID.";
      uses sd-vxlan-ios-xe-oper:vxlan-sr-nh-data;
    }
    list sr-summary-data {
      key "entry-key";
      description
        "List of VxLAN static route summary entries. Each entry includes summary counts and attributes for VxLAN static routes.";
      uses sd-vxlan-ios-xe-oper:vxlan-sr-summary-entry-key;
      uses sd-vxlan-ios-xe-oper:vxlan-sr-summary-entry;
    }
  }
}
