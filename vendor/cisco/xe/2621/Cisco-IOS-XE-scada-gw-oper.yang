module Cisco-IOS-XE-scada-gw-oper {
  yang-version 1.1;
  namespace "http://cisco.com/ns/yang/Cisco-IOS-XE-scada-gw-oper";
  prefix scada-gw-ios-xe-oper;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Scada Gateway operational data.
     Copyright (c) 2019, 2022, 2026 by Cisco Systems, Inc.
     All rights reserved.";

  revision 2026-08-01 {
    description
      "Updated descriptions for several model elements to clarify their meaning and purpose";
    reference
      "1.1.1";
    cisco-semver:module-version "1.1.1";
  }
  revision 2022-11-01 {
    description
      "Update yang-version to 1.1";
    reference
      "1.1.0";
    cisco-semver:module-version "1.1.0";
  }
  revision 2019-05-01 {
    description
      "Cleaned up spelling errors in descriptions.";
    reference
      "1.0.1";
    cisco-semver:module-version "1.0.1";
  }
  revision 2019-03-19 {
    description
      "Initial revision";
    reference
      "1.0.0";
    cisco-semver:module-version "1.0.0";
  }

  grouping line-stats {
    description
      "Line statistics for channel";
    leaf channel-name {
      type string;
      description
        "Name of the channel";
    }
    leaf messages-sent {
      type uint32;
      description
        "Total messages sent on the channel";
    }
    leaf messages-received {
      type uint32;
      description
        "Total messages received on the channel";
    }
    leaf timeouts {
      type uint32;
      description
        "Total number of requests that received no response on the channel";
    }
    leaf aborts {
      type uint32;
      description
        "Total number of aborts";
    }
    leaf rejections {
      type uint32;
      description
        "Total number of requests rejected by the remote device on the channel";
    }
    leaf protocol-errors {
      type uint32;
      description
        "Total number of protocol-level errors detected on the channel";
    }
    leaf link-errors {
      type uint32;
      description
        "Total number of data link layer errors on the channel";
    }
    leaf addr-errors {
      type uint32;
      description
        "Total number of invalid or unrecognized address errors on the channel";
    }
  }

  grouping scada-gw-stats {
    description
      "Scada Gateway statistics";
    list t104-stats {
      key "channel-name";
      description
        "T104 statistics list";
      uses scada-gw-ios-xe-oper:line-stats;
    }
    list t101-stats {
      key "channel-name";
      description
        "T101 statistics list";
      uses scada-gw-ios-xe-oper:line-stats;
    }
    list dnp3n-stats {
      key "channel-name";
      description
        "DNP3 Network statistics list";
      uses scada-gw-ios-xe-oper:line-stats;
    }
    list dnp3s-stats {
      key "channel-name";
      description
        "DNP3 Serial statistics list";
      uses scada-gw-ios-xe-oper:line-stats;
    }
  }

  grouping scada-tcp-conn-info {
    description
      "Scada Gateway statistics";
    leaf local-ip {
      type inet:ip-address;
      description
        "Local IP used by the TCP connection";
    }
    leaf local-port {
      type uint16;
      description
        "Local port used by the TCP connection";
    }
    leaf remote-ip {
      type inet:ip-address;
      description
        "Remote IP of the TCP connection";
    }
    leaf data-socket {
      type uint32;
      description
        "Data socket associated with the TCP connection";
    }
  }

  grouping tcp-connection {
    description
      "TCP connection data for T104 channel";
    leaf channel-name {
      type string;
      description
        "Name of the channel";
    }
    list conn {
      description
        "List of TCP connections on the channel";
      uses scada-gw-ios-xe-oper:scada-tcp-conn-info;
    }
  }

  grouping scada-gw-conns {
    description
      "Scada Gateway connections";
    list t104-tcp-conns {
      key "channel-name";
      description
        "Scada Gateway T104 TCP Connections";
      uses scada-gw-ios-xe-oper:tcp-connection;
    }
    list dnp3n-tcp-conns {
      key "channel-name";
      description
        "SCADA Gateway DNP3 Network TCP connections";
      uses scada-gw-ios-xe-oper:tcp-connection;
    }
  }

  container scada-gw-oper-data {
    config false;
    description
      "Operational state of Scada Gateway";
    container scada-gw-stats {
      presence "scada-gw-stats";
      description
        "Scada Gateway operation statistics";
      uses scada-gw-ios-xe-oper:scada-gw-stats;
    }
    container scada-gw-conns {
      presence "scada-gw-conns";
      description
        "SCADA Gateway TCP connections, including T104 and DNP3 Network connections";
      uses scada-gw-ios-xe-oper:scada-gw-conns;
    }
  }
}
