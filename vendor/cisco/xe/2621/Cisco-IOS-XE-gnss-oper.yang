module Cisco-IOS-XE-gnss-oper {
  yang-version 1.1;
  namespace "http://cisco.com/ns/yang/Cisco-IOS-XE-gnss-oper";
  prefix gnss-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for IOS-XE GNSS (Global Navigation Satellite System)
     operational data.
     Copyright (c) 2021-2022 by Cisco Systems, Inc.
     All rights reserved.";

  revision 2026-08-01 {
    description
      "- Added optional GNSS device information grouping with version details and constellation type
       - Added Dilution of Precision metrics, major and minor alarm status leaves
       - Added satellite health, quality leaves
       - Updated descriptions for several model elements to clarify their meaning and purpose";
    reference
      "1.4.0";
    cisco-semver:module-version "1.4.0";
  }
  revision 2023-03-01 {
    description
      "Increased maximum satellite number from 32 to 100";
    reference
      "1.3.0";
    cisco-semver:module-version "1.3.0";
  }
  revision 2022-11-01 {
    description
      "Update yang-version to 1.1";
    reference
      "1.2.0";
    cisco-semver:module-version "1.2.0";
  }
  revision 2022-03-01 {
    description
      "Added support for optional GNSS location and timestamp";
    reference
      "1.1.0";
    cisco-semver:module-version "1.1.0";
  }
  revision 2020-03-01 {
    description
      "Initial revision";
    reference
      "1.0.0";
    cisco-semver:module-version "1.0.0";
  }

  typedef gnss-module-status {
    type enumeration {
      enum gnss-module-status-unknown {
        value 0;
        description
          "Module presence status unknown";
      }
      enum gnss-module-status-absent {
        value 1;
        description
          "Module presence status absent";
      }
      enum gnss-module-status-present {
        value 2;
        description
          "Module presence status present";
      }
      enum gnss-module-status-invalid {
        value 3;
        description
          "Module presence status invalid";
      }
    }
    description
      "GNSS (Global Navigation Satellite System) module presence status";
  }

  typedef gnss-module-lock-status {
    type enumeration {
      enum gnss-module-lock-status-unknown {
        value 0;
        description
          "Module lock status unknown";
      }
      enum gnss-module-lock-status-down {
        value 1;
        description
          "Module lock status down";
      }
      enum gnss-module-lock-status-up {
        value 2;
        description
          "Module lock status up";
      }
      enum gnss-module-lock-status-invalid {
        value 3;
        description
          "Module lock status invalid";
      }
    }
    description
      "GNSS (Global Navigation Satellite System) module lock status";
  }

  typedef gnss-sv-type {
    type enumeration {
      enum gnss-sv-type-gps {
        value 0;
        description
          "Satellite type 0";
      }
      enum gnss-sv-type-sbas {
        value 1;
        description
          "Satellite type 1";
      }
      enum gnss-sv-type-galileo {
        value 2;
        description
          "Satellite type 2";
      }
      enum gnss-sv-type-beidou {
        value 3;
        description
          "Satellite type 3";
      }
      enum gnss-sv-type-imes {
        value 4;
        description
          "Satellite type 4";
      }
      enum gnss-sv-type-qzss {
        value 5;
        description
          "Satellite type 5";
      }
      enum gnss-sv-type-glonass {
        value 6;
        description
          "Satellite type 6";
      }
      enum gnss-sv-type-unknown {
        value 7;
        description
          "Satellite type 7";
      }
    }
    description
      "GNSS (Global Navigation Satellite System) satellite types";
  }

  typedef gnss-module-sv-tracking-status {
    type enumeration {
      enum satellite-tracking-status-bad {
        value 0;
        description
          "Satellite tracking status bad";
      }
      enum satellite-tracking-status-good {
        value 1;
        description
          "Satellite tracking status good";
      }
      enum satellite-tracking-status-unknown {
        value 2;
        description
          "Satellite tracking status cannot be determined or signal quality assessment is unavailable";
      }
    }
    description
      "GNSS (Global Navigation Satellite System) module satellite
       tracking status. If tracking minimum 3 satellites with more
       than 30 decibel milliwatts then good, if not bad";
  }

  typedef gnss-sv-health {
    type enumeration {
      enum gnss-sv-health-healthy {
        value 0;
        description
          "Satellite is healthy and operational";
      }
      enum gnss-sv-health-unhealthy {
        value 1;
        description
          "Satellite is unhealthy and should not be used";
      }
      enum gnss-sv-health-unknown {
        value 2;
        description
          "Satellite health status is unknown";
      }
      enum gnss-sv-health-reserved {
        value 3;
        description
          "Reserved health status value";
      }
    }
    description
      "GNSS satellite health status";
  }

  typedef gnss-module-alarm-status {
    type enumeration {
      enum alarm-disable {
        value 0;
        description
          "Alarm disable";
      }
      enum alarm-enable {
        value 1;
        description
          "Alarm enable";
      }
      enum alarm-unused {
        value 2;
        description
          "Alarm unused";
      }
    }
    description
      "GNSS (Global Navigation Satellite System) module alarm status";
  }

  typedef rsp-slot-state {
    type enumeration {
      enum active-rsp {
        value 0;
        description
          "Active RSP (Route Switch Processor)";
      }
      enum standby-rsp {
        value 1;
        description
          "Standby RSP (Route Switch Processor)";
      }
    }
    description
      "Slot state";
  }

  typedef satellite-acq-flag-type {
    type enumeration {
      enum never-acquired {
        value 0;
        description
          "Never acquired";
      }
      enum acquired {
        value 1;
        description
          "Acquired";
      }
      enum reopened-search {
        value 2;
        description
          "Reopened search";
      }
    }
    description
      "GNSS (Global Navigation Satellite System) satellite acquisition flag types";
  }

  typedef maj-alrm {
    type enumeration {
      enum maj-alrm-unknown {
        value 0;
        description
          "Major alarm status unknown";
      }
      enum maj-alrm-false {
        value 1;
        description
          "No major alarm";
      }
      enum maj-alrm-ant-open {
        value 2;
        description
          "Antenna open circuit detected";
      }
      enum maj-alrm-ant-short {
        value 3;
        description
          "Antenna short circuit detected";
      }
    }
    description
      "GNSS major alarm status";
  }

  typedef gnss-fix-type {
    type enumeration {
      enum fix-no-fix {
        value 0;
        description
          "The receiver has no valid position or timing solution";
      }
      enum fix-dr-only {
        value 1;
        description
          "The solution is derived only from dead reckoning without an active GNSS fix.";
      }
      enum fix-2d {
        value 2;
        description
          "The receiver has a valid two-dimensional position fix.";
      }
      enum fix-3d {
        value 3;
        description
          "The receiver has a valid three-dimensional position fix.";
      }
      enum fix-gnss-dr-both {
        value 4;
        description
          "The solution combines GNSS measurements with dead reckoning data.";
      }
      enum fix-time-only {
        value 5;
        description
          "The receiver has a valid timing solution but no usable position fix.";
      }
    }
    description
      "Defines the GNSS position solution state reported by the receiver.";
  }

  typedef min-alrm {
    type bits {
      bit min-alrm-unknown {
        position 0;
        description
          "Minor alarm status unknown";
      }
      bit min-alrm-false {
        position 1;
        description
          "No minor alarm";
      }
      bit min-alrm-survy-in-prog {
        position 2;
        description
          "Survey in progress";
      }
      bit min-alrm-low-curr-det {
        position 3;
        description
          "Low current detected on antenna";
      }
    }
    description
      "GNSS minor alarm status as flags";
  }

  typedef gnss-constellation-type {
    type bits {
      bit const-gps {
        position 0;
        description
          "Indicates that Global Positioning System by the U.S. government is enabled";
      }
      bit const-glonass {
        position 1;
        description
          "Indicates that Global Navigation Satellite System by Russia is enabled";
      }
      bit const-galileo {
        position 2;
        description
          "Indicates that Galileo, the global navigation satellite system by the European Union, is enabled";
      }
      bit const-bds {
        position 3;
        description
          "Indicates that Global navigation satellite system by China is enabled";
      }
      bit const-auto {
        position 4;
        description
          "Indicates that constellation selection is automatic";
      }
    }
    description
      "GNSS constellation types as flags";
  }

  grouping gnss-satellite-info {
    description
      "Satellite information data";
    leaf sv-prn {
      type int32;
      description
        "Pseudo-random noise (PRN) number of the satellite";
    }
    leaf channel {
      type uint8;
      description
        "Channel number assigned to the tracked satellite";
    }
    leaf acq-flag {
      type gnss-ios-xe-oper:satellite-acq-flag-type;
      description
        "Indicates the acquisition state of the satellite signal";
    }
    leaf eph-flag {
      type uint8;
      description
        "Indicates whether ephemeris data is available for the satellite";
    }
    leaf signal-level {
      type int64;
      description
        "Signal strength SNR in decibel Hertz ";
    }
    leaf sv-type {
      type gnss-ios-xe-oper:gnss-sv-type;
      description
        "Type of satellite constellation";
    }
    leaf elevation {
      type int64;
      description
        "Satellite elevation angle";
    }
    leaf azimuth {
      type int64;
      description
        "Satellite azimuth angle";
    }
    leaf health {
      type gnss-ios-xe-oper:gnss-sv-health;
      description
        "Satellite health status indicating operational state, helps in deciding whether to use a specific satellite for navigation";
    }
    leaf quality {
      type uint8;
      description
        "Signal quality indicator is a discrete quality metric on scale of 0-7, the most common interpretation is: 0 indicates no signal and 7 indicates excellent signal quality";
    }
  }

  grouping gnss-device {
    description
      "GNSS (Global Navigation Satellite System) device information";
    leaf sw-ver {
      type string;
      description
        "Software version of the GNSS receiver module";
    }
    leaf hw-ver {
      type string;
      description
        "Hardware version of the GNSS receiver module";
    }
    leaf proto-ver {
      type string;
      description
        "Communication protocol version supported by the GNSS receiver module";
    }
    leaf fw-ver {
      type string;
      description
        "Firmware version of the GNSS receiver module";
    }
    leaf model {
      type string;
      description
        "Model identifier of the GNSS receiver module";
    }
    leaf major-const {
      type gnss-ios-xe-oper:gnss-constellation-type;
      description
        "Primary GNSS constellation system used";
    }
    leaf unique-chip-id {
      type string;
      description
        "Unique identifier of the GNSS receiver chip";
    }
  }

  grouping gnss-location {
    description
      "Device location";
    leaf latitude {
      type decimal64 {
        fraction-digits 2;
      }
      units "decimal degrees";
      description
        "Geographic latitude coordinate in decimal degrees (positive for North, negative for South)";
    }
    leaf longitude {
      type decimal64 {
        fraction-digits 2;
      }
      units "decimal degrees";
      description
        "Geographic longitude coordinate in decimal degrees (positive for East, negative for West)";
    }
    leaf height {
      type decimal64 {
        fraction-digits 2;
      }
      units "meters";
      description
        "Altitude above mean sea level in meters";
    }
  }

  grouping gnss-data {
    description
      "Operational data for GNSS (Global Navigation Satellite System) modules";
    leaf slot {
      type uint16;
      description
        "Router slot number where
         GNSS (Global Navigation Satellite System) module is inserted";
    }
    leaf slot-state {
      type gnss-ios-xe-oper:rsp-slot-state;
      description
        "Router slot state (active or standby) where
         GNSS (Global Navigation Satellite System) module is inserted";
    }
    leaf presence-status {
      type gnss-ios-xe-oper:gnss-module-status;
      description
        "GNSS (Global Navigation Satellite System)
         card presence status";
    }
    leaf lock-status {
      type gnss-ios-xe-oper:gnss-module-lock-status;
      description
        "GNSS (Global Navigation Satellite System)
         card lock status";
    }
    leaf survey-progress-status {
      type uint8;
      description
        "GNSS (Global Navigation Satellite System)
         card survey progress status";
    }
    leaf satellite-tracking-status {
      type gnss-ios-xe-oper:gnss-module-sv-tracking-status;
      description
        "GNSS (Global Navigation Satellite System)
         satellite tracking status";
    }
    leaf gnss-antenna-open-alarm-status {
      type gnss-ios-xe-oper:gnss-module-alarm-status;
      description
        "GNSS (Global Navigation Satellite System)
         module antenna open alarm status";
    }
    leaf gnss-antenna-short-alarm-status {
      type gnss-ios-xe-oper:gnss-module-alarm-status;
      description
        "GNSS (Global Navigation Satellite System)
         module antenna short alarm status";
    }
    leaf satellite-cnt {
      type uint8;
      description
        "Number of satellites visible at a particular time";
    }
    list satellite-info {
      max-elements 100;
      description
        "List of information for tracked satellites";
      uses gnss-ios-xe-oper:gnss-satellite-info;
    }
    leaf gnss-location-supported {
      type empty;
      description
        "When present, GNSS location is valid";
    }
    container location {
      when 'boolean(../gnss-location-supported)';
      description
        "Container for GNSS location information";
      uses gnss-ios-xe-oper:gnss-location;
    }
    leaf gnss-time-supported {
      type empty;
      description
        "When present, GNSS time is valid";
    }
    leaf timestamp {
      when 'boolean(../gnss-time-supported)';
      type yang:date-and-time;
      description
        "Timestamp of the valid GNSS time";
    }
    leaf min-alarm {
      type gnss-ios-xe-oper:min-alrm;
      description
        "Non-critical alarm conditions detected by the GNSS receiver";
    }
    leaf maj-alarm {
      type gnss-ios-xe-oper:maj-alrm;
      description
        "Critical alarm conditions affecting GNSS receiver functionality";
    }
    leaf pdop {
      type decimal64 {
        fraction-digits 2;
      }
      description
        "Position Dilution of Precision indicating the geometric quality of satellite positioning (lower values indicate better accuracy)";
    }
    leaf hdop {
      type decimal64 {
        fraction-digits 2;
      }
      description
        "Horizontal Dilution of Precision indicating horizontal positioning accuracy (lower values indicate better accuracy)";
    }
    leaf tdop {
      type decimal64 {
        fraction-digits 2;
      }
      description
        "Time Dilution of Precision indicating time synchronization accuracy (lower values indicate better accuracy)";
    }
    leaf vdop {
      type decimal64 {
        fraction-digits 2;
      }
      description
        "Vertical Dilution of Precision indicating vertical positioning accuracy (lower values indicate better accuracy)";
    }
    leaf is-dev-sup {
      type empty;
      description
        "When present, GNSS device information is valid";
    }
    container device {
      when 'boolean(../is-dev-sup)';
      description
        "GNSS device information";
      uses gnss-ios-xe-oper:gnss-device;
    }
    leaf const-type {
      type gnss-ios-xe-oper:gnss-constellation-type;
      description
        "Indicates the active GNSS constellation selection mode configured on the receiver.";
    }
    leaf cable-delay {
      type uint16;
      units "nanoseconds";
      description
        "Configured cable delay value, in nanoseconds, used to compensate for signal propagation latency in the antenna cable.";
    }
    leaf fix-type {
      type gnss-ios-xe-oper:gnss-fix-type;
      description
        "Indicates the current GNSS position solution state reported by the receiver.";
    }
  }

  container gnss-oper-data {
    config false;
    description
      "GNSS (Global Navigation Satellite System) operational data";
    list gnss-data {
      key "slot";
      description
        "Operational data for GNSS (Global Navigation Satellite System) modules";
      uses gnss-ios-xe-oper:gnss-data;
    }
  }
}
