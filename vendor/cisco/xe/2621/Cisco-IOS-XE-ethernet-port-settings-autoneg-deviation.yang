module Cisco-IOS-XE-ethernet-port-settings-autoneg-deviation {
  yang-version 1.1;
  namespace "http://cisco.com/ns/yang/Cisco-IOS-XE-ethernet-port-settings-autoneg-deviation";
  prefix ios-ethernet-port-settings-autoneg-d;

  import Cisco-IOS-XE-native {
    prefix ios;
  }
  import Cisco-IOS-XE-ethernet {
    prefix ios-eth;
  }
  import cisco-semver {
    prefix cisco-semver;
  }

  organization
    "Cisco Systems";
  description
    "Cisco XE Native Ethernet Deviation YANG module for platforms whose IOS
     auto-negotiation default is platform or media dependent. This removes the
     fixed YANG default so explicit port-settings auto-negotiation is preserved.
     Copyright (c) 2026 by Cisco Systems, Inc.
     All rights reserved.";

  revision 2026-08-01 {
    description
      "Remove fixed auto-negotiation default for ethernet port settings.";
    cisco-semver:module-version "1.0.0";
  }

  deviation "/ios:native/ios:interface/ios:FastEthernet/ios-eth:port-settings/ios-eth:auto-negotiation" {
    deviate delete {
      default "enable";
    }
  }

  deviation "/ios:native/ios:interface/ios:GigabitEthernet/ios-eth:port-settings/ios-eth:auto-negotiation" {
    deviate delete {
      default "enable";
    }
  }

  deviation "/ios:native/ios:interface/ios:TwoGigabitEthernet/ios-eth:port-settings/ios-eth:auto-negotiation" {
    deviate delete {
      default "enable";
    }
  }

  deviation "/ios:native/ios:interface/ios:FiveGigabitEthernet/ios-eth:port-settings/ios-eth:auto-negotiation" {
    deviate delete {
      default "enable";
    }
  }

  deviation "/ios:native/ios:interface/ios:AppGigabitEthernet/ios-eth:port-settings/ios-eth:auto-negotiation" {
    deviate delete {
      default "enable";
    }
  }

  deviation "/ios:native/ios:interface/ios:TenGigabitEthernet/ios-eth:port-settings/ios-eth:auto-negotiation" {
    deviate delete {
      default "enable";
    }
  }

  deviation "/ios:native/ios:interface/ios:TwentyFiveGigE/ios-eth:port-settings/ios-eth:auto-negotiation" {
    deviate delete {
      default "enable";
    }
  }

  deviation "/ios:native/ios:interface/ios:FortyGigabitEthernet/ios-eth:port-settings/ios-eth:auto-negotiation" {
    deviate delete {
      default "enable";
    }
  }

  deviation "/ios:native/ios:interface/ios:FiftyGigabitEthernet/ios-eth:port-settings/ios-eth:auto-negotiation" {
    deviate delete {
      default "enable";
    }
  }

  deviation "/ios:native/ios:interface/ios:HundredGigE/ios-eth:port-settings/ios-eth:auto-negotiation" {
    deviate delete {
      default "enable";
    }
  }

  deviation "/ios:native/ios:interface/ios:TwoHundredGigE/ios-eth:port-settings/ios-eth:auto-negotiation" {
    deviate delete {
      default "enable";
    }
  }

  deviation "/ios:native/ios:interface/ios:FourHundredGigE/ios-eth:port-settings/ios-eth:auto-negotiation" {
    deviate delete {
      default "enable";
    }
  }

  deviation "/ios:native/ios:interface/ios:Port-channel/ios-eth:port-settings/ios-eth:auto-negotiation" {
    deviate delete {
      default "enable";
    }
  }

  deviation "/ios:native/ios:interface/ios:Port-channel-subinterface/ios:Port-channel/ios-eth:port-settings/ios-eth:auto-negotiation" {
    deviate delete {
      default "enable";
    }
  }

  deviation "/ios:native/ios:interface/ios:VirtualPortGroup/ios-eth:port-settings/ios-eth:auto-negotiation" {
    deviate delete {
      default "enable";
    }
  }

  deviation "/ios:native/ios:interface/ios:Virtual-Template/ios-eth:port-settings/ios-eth:auto-negotiation" {
    deviate delete {
      default "enable";
    }
  }

  deviation "/ios:native/ios:interface/ios:BDI/ios-eth:port-settings/ios-eth:auto-negotiation" {
    deviate delete {
      default "enable";
    }
  }

  deviation "/ios:native/ios:interface/ios:Vlan/ios-eth:port-settings/ios-eth:auto-negotiation" {
    deviate delete {
      default "enable";
    }
  }

  deviation "/ios:native/ios:interface/ios:BD-VIF/ios-eth:port-settings/ios-eth:auto-negotiation" {
    deviate delete {
      default "enable";
    }
  }

  deviation "/ios:native/ios:interface/ios:ucse/ios-eth:port-settings/ios-eth:auto-negotiation" {
    deviate delete {
      default "enable";
    }
  }
}
