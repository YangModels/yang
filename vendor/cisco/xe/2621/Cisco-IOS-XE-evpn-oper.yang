module Cisco-IOS-XE-evpn-oper {
  yang-version 1.1;
  namespace "http://cisco.com/ns/yang/Cisco-IOS-XE-evpn-oper";
  prefix evpn-ios-xe-oper;

  import Cisco-IOS-XE-common-types {
    prefix common-types-ios-xe;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for EVPN operational data.
     Copyright (c) 2024-2026 by Cisco Systems, Inc.
     All rights reserved.";

  revision 2026-08-01 {
    description
      "- Updated descriptions for several leaves to better explain their meaning and purpose
       - Added EVPN statistics list with per-VNI route counters for telemetry support";
    reference
      "1.1.0";
    cisco-semver:module-version "1.1.0";
  }
  revision 2025-03-01 {
    description
      "Initial revision";
    reference
      "1.0.0";
    cisco-semver:module-version "1.0.0";
  }

  typedef evpn-type {
    type enumeration {
      enum evpn-unknown {
        value 0;
        description
          "EVPN Type unknown";
      }
      enum evpn-vpws {
        value 1;
        description
          "EVPN point-to-point";
      }
      enum evpn-vlan-based {
        value 2;
        description
          "VLAN Based EVPN";
      }
      enum evpn-vlan-bundle {
        value 3;
        description
          "VLAN Bundle EVPN";
      }
      enum evpn-vlan-aware {
        value 4;
        description
          "VLAN Aware EVPN";
      }
    }
    description
      "EVPN Type";
  }

  typedef evpn-encapsulation-type {
    type enumeration {
      enum evpn-encap-type-none {
        value 0;
        description
          "EVPN encapsulation unknown";
      }
      enum evpn-encap-type-mpls {
        value 1;
        description
          "EVPN MPLS encapsulation";
      }
      enum evpn-encap-type-vxlan {
        value 2;
        description
          "EVPN VxLAN encapsulation";
      }
      enum evpn-encap-type-max {
        value 3;
        description
          "EVPN encapsulation maximum value";
      }
    }
    description
      "EVPN Encapsulation Type";
  }

  typedef evpn-replication-type {
    type enumeration {
      enum evpn-replication-undefined {
        value 0;
        description
          "EVPN replication type unknown";
      }
      enum evpn-replication-ingress {
        value 1;
        description
          "EVPN Ingress replication";
      }
      enum evpn-replication-p2mp {
        value 2;
        description
          "EVPN Point to multipoint replication";
      }
      enum evpn-replication-mp2mp {
        value 3;
        description
          "EVPN Multipoint to multipoint replication";
      }
      enum evpn-replication-static {
        value 4;
        description
          "EVPN Static replication";
      }
      enum evpn-replication-none {
        value 5;
        description
          "No EVPN replication";
      }
    }
    description
      "EVPN Replication Type";
  }

  typedef evpn-ip-local-learn {
    type enumeration {
      enum evpn-ip-local-learn-undefined {
        value 0;
        description
          "EVPN IP local learn undefined";
      }
      enum evpn-ip-local-learn-enabled {
        value 1;
        description
          "EVPN IP local learn enabled";
      }
      enum evpn-ip-local-learn-disabled {
        value 2;
        description
          "EVPN IP local learn disabled";
      }
    }
    description
      "EVPN IP local learn";
  }

  typedef evpn-dg-type {
    type enumeration {
      enum evpn-dg-advertise-undefined {
        value 0;
        description
          "undefined";
      }
      enum evpn-dg-advertise-enabled {
        value 1;
        description
          "EVPN Distributed Gateway Advertising Enabled";
      }
      enum evpn-dg-advertise-disabled {
        value 2;
        description
          "EVPN Distributed Gateway Advertising Disabled";
      }
    }
    description
      "EVPN Distributed Gateway Advertising";
  }

  typedef evpn-route-re-originate {
    type enumeration {
      enum evpn-re-orig-route-undefined {
        value 0;
        description
          "EVPN Route Re-Originate Undefined";
      }
      enum evpn-re-orig-route-enabled {
        value 1;
        description
          "EVPN Route Re-Originate Enabled";
      }
      enum evpn-re-orig-route-disabled {
        value 2;
        description
          "EVPN Route Re-Originate Disabled";
      }
    }
    description
      "EVPN Route Re-Originate";
  }

  typedef evpn-mcast-adv {
    type enumeration {
      enum evpn-multicast-advertise-undefined {
        value 0;
        description
          "EVPN Multicast Advertising Undefined";
      }
      enum evpn-multicast-advertise-enabled {
        value 1;
        description
          "EVPN Multicast Advertising Enabled";
      }
      enum evpn-multicast-advertise-disabled {
        value 2;
        description
          "EVPN Multicast Advertising Disabled";
      }
    }
    description
      "EVPN Multicast Advertising";
  }

  typedef evpn-flooding-suppression-flag {
    type enumeration {
      enum evpn-flood-suppress-undefined {
        value 0;
        description
          "EVPN Flood Suppression not defined";
      }
      enum evpn-flood-suppress-enabled {
        value 1;
        description
          "EVPN Flood Suppression Enabled";
      }
      enum evpn-flood-suppress-disabled {
        value 2;
        description
          "EVPN Flood Suppression Disabled";
      }
    }
    description
      "EVPN Flood Suppression Flag";
  }

  typedef evpn-irb-type {
    type enumeration {
      enum evpn-irb-asymmetric {
        value 0;
        description
          "EVPN Integrated Routing and Bridging Asymmetric";
      }
      enum evpn-irb-local-routing {
        value 1;
        description
          "EVPN Integrated Routing and Bridging Local Routing";
      }
    }
    description
      "EVPN Integrated Routing and Bridging Type";
  }

  typedef evpn-evi-state {
    type enumeration {
      enum evi-state-no-bgp-incomplete {
        value 0;
        description
          "No BGP, Incomplete";
      }
      enum evi-state-no-bgp-complete {
        value 1;
        description
          "No BGP, Complete";
      }
      enum evi-state-incomplete {
        value 2;
        description
          "Incomplete";
      }
      enum evi-state-delete-pending {
        value 3;
        description
          "Delete Pending";
      }
      enum evi-state-incomplete-pending {
        value 4;
        description
          "Incomplete Pending";
      }
      enum evi-state-complete-pending {
        value 5;
        description
          "Complete Pending";
      }
      enum evi-state-established {
        value 6;
        description
          "Established";
      }
    }
    description
      "EVPN Instance State";
  }

  typedef evpn-efi-state {
    type enumeration {
      enum efi-state-evi-down-bd-adown {
        value 0;
        description
          "EVPN Instance Down, BD Admin Down";
      }
      enum efi-state-evi-up-bd-adown {
        value 1;
        description
          "EVPN Instance Up, BD Admin Down";
      }
      enum efi-state-evi-down-bd-down {
        value 2;
        description
          "EVPN Instance Down, BD Oper Down";
      }
      enum efi-state-evi-up-bd-down {
        value 3;
        description
          "EVPN Instance Up, BD Oper Down";
      }
      enum efi-state-evi-down-bd-up {
        value 4;
        description
          "EVPN Instance Down, BD Up";
      }
      enum efi-state-established {
        value 5;
        description
          "Established";
      }
      enum efi-state-evi-down-bd-adown-delpend {
        value 6;
        description
          "EVPN Instance Down, BD Admin Down, Delete Pending";
      }
      enum efi-state-evi-up-bd-adown-delpend {
        value 7;
        description
          "EVPN Instance Up, BD Admin Down, Delete Pending";
      }
      enum efi-state-evi-down-bd-down-delpend {
        value 8;
        description
          "EVPN Instance Down, BD Oper Down, Delete Pending";
      }
      enum efi-state-evi-up-bd-down-delpend {
        value 9;
        description
          "EVPN Instance Up, BD Oper Down, Delete Pending";
      }
      enum efi-state-evi-down-bd-up-delpend {
        value 10;
        description
          "EVPN Instance Down, BD Up, Delete Pending";
      }
      enum efi-state-evi-up-bd-up-delpend {
        value 11;
        description
          "EVPN Instance Up, BD Up, Delete Pending";
      }
      enum efi-state-evi-down-bd-adown-crepend {
        value 12;
        description
          "EVPN Instance Down, BD Admin Down, Create Pending";
      }
      enum efi-state-evi-up-bd-adown-crepend {
        value 13;
        description
          "EVPN Instance Up, BD Admin Down, Create Pending";
      }
      enum efi-state-evi-down-bd-down-crepend {
        value 14;
        description
          "EVPN Instance Down, BD Oper Down, Create Pending";
      }
      enum efi-state-evi-up-bd-down-crepend {
        value 15;
        description
          "EVPN Instance Up, BD Oper Down, Create Pending";
      }
      enum efi-state-evi-down-bd-up-crepend {
        value 16;
        description
          "EVPN Instance Down, BD Up, Create Pending";
      }
      enum efi-state-evi-up-bd-up-crepend {
        value 17;
        description
          "Established Pending";
      }
    }
    description
      "EVPN Ethernet State";
  }

  typedef evpn-efp-state {
    type enumeration {
      enum evpn-efp-state-up {
        value 1;
        description
          "EVPN EFP State Up";
      }
      enum evpn-efp-state-admindown {
        value 2;
        description
          "EVPN EFP Admin Down State";
      }
      enum evpn-efp-state-efp-admindown {
        value 3;
        description
          "EVPN EFP Admin Down EFP State";
      }
      enum evpn-efp-state-down {
        value 4;
        description
          "EVPN EFP Down State";
      }
      enum evpn-efp-state-errdisabled {
        value 5;
        description
          "EVPN EFP Error Disabled State";
      }
      enum evpn-efp-state-unknown {
        value 6;
        description
          "EVPN EFP Unknown State";
      }
      enum evpn-efp-state-deleted {
        value 7;
        description
          "EVPN EFP Deleted State";
      }
      enum evpn-efp-state-bd-admindown {
        value 8;
        description
          "EVPN EFP BD Admin Down State";
      }
      enum evpn-efp-red-state-active {
        value 99;
        description
          "EVPN EFP Redundancy Active State";
      }
      enum evpn-efp-red-state-standby {
        value 100;
        description
          "EVPN EFP Redundancy Standby State";
      }
    }
    description
      "EVPN EFP State";
  }

  typedef network-instance-type {
    type enumeration {
      enum default-instance {
        value 0;
        description
          "Default Network Instance";
      }
      enum l3vrf {
        value 1;
        description
          "Layer 3 only routing instance";
      }
      enum l2vsi {
        value 2;
        description
          "Layer 2 only forwarding instance";
      }
      enum l2p2p {
        value 3;
        description
          "Layer 2 point to point forwarding instance";
      }
      enum l2l3 {
        value 4;
        description
          "Layer 2 and Layer 3 forwarding instance";
      }
    }
    description
      "Network Instance Type";
  }

  grouping evpn-pseudo-port-table-key {
    description
      "EVPN Port key";
    leaf if-id {
      type uint64;
      description
        "Interface index";
    }
    leaf svc-inst {
      type uint32;
      description
        "Identifier for the service instance associated with the EVPN pseudo-port";
    }
  }

  grouping evpn-pseudo-port {
    description
      "EVPN Port operational data";
    leaf if-name {
      type string;
      description
        "Specifies the name of the interface associated with this EVPN pseudo-port";
    }
    leaf efp-state {
      type evpn-ios-xe-oper:evpn-efp-state;
      description
        "Indicates the current state of the Ethernet Forwarding Port (EFP)
         for this EVPN pseudo-port (e.g., up, down, admin down, error disabled)";
    }
  }

  grouping evpn-peer-table-key {
    description
      "EVPN Peer key";
    leaf peer-ip-addr {
      type inet:ip-address;
      description
        "Peer IP address";
    }
  }

  grouping evpn-peer {
    description
      "EVPN Peer operational data";
    leaf peer-up-time {
      type yang:date-and-time;
      description
        "Represents the time when the EVPN peer became operationally active";
    }
    leaf local-vni-id {
      when "../../../evpn-encap-type = 'evpn-encap-type-vxlan'";
      type uint32;
      description
        "Local VXLAN Network Identifier (VNI) used for this EVPN peer";
    }
    leaf remote-vni-id {
      when "../../../evpn-encap-type = 'evpn-encap-type-vxlan'";
      type uint32;
      description
        "Remote VXLAN Network Identifier (VNI) used for this EVPN peer";
    }
  }

  grouping evpn-vlan-table-key {
    description
      "EVPN VLAN key";
    leaf vlan-id {
      type uint16;
      description
        "VLAN identifier associated with the bridge domain (BD) for this EVPN instance";
    }
  }

  grouping evpn-vlan {
    description
      "EVPN VLAN operational data";
    leaf evpn-inst-id {
      type uint16;
      description
        "EVPN Instance Id";
    }
    leaf vlan-if {
      type string;
      description
        "VLAN interface name";
    }
    leaf vlan-protected {
      type boolean;
      description
        "Indicates whether this VLAN is configured as protected, which may affect redundancy or failover behavior";
    }
    leaf efi-state {
      type evpn-ios-xe-oper:evpn-efi-state;
      description
        "Operational state of EVPN Forwarding instance, indicating the current status such as up, down, or pending";
    }
    leaf flood-suppr-attached {
      type boolean;
      description
        "Flood suppression status";
    }
    leaf core-if {
      when "../../evpn-encap-type = 'evpn-encap-type-vxlan'";
      type string;
      description
        "Specifies the name of the core-facing interface associated with this EVPN VLAN
         when VxLAN encapsulation is used";
    }
    leaf access-if {
      type string;
      description
        "Specifies the name of the access-facing interface associated with this EVPN VLAN";
    }
    leaf nve-if {
      when "../../evpn-encap-type = 'evpn-encap-type-vxlan'";
      type string;
      description
        "Network Virtual Endpoint Interface";
    }
    leaf host-reach-bgp {
      when "../../evpn-encap-type = 'evpn-encap-type-vxlan'";
      type boolean;
      description
        "Indicates whether host reachability information for this EVPN VLAN is advertised via BGP";
    }
    leaf rmac {
      when "../../evpn-encap-type = 'evpn-encap-type-vxlan'";
      type yang:mac-address;
      description
        "Specifies the router MAC address (RMAC) used for integrated routing and bridging (IRB)
         in this EVPN VLAN when VxLAN encapsulation is enabled";
    }
    leaf core-vlan {
      when "../../evpn-encap-type = 'evpn-encap-type-vxlan'";
      type uint32;
      description
        "Specifies the VLAN ID used on the core-facing side for this EVPN VLAN when VxLAN encapsulation is enabled";
    }
    leaf l2-vni {
      when "../../evpn-encap-type = 'evpn-encap-type-vxlan'";
      type uint32;
      description
        "Specifies the Layer 2 VXLAN Network Identifier (VNI) associated with this EVPN VLAN
         when VxLAN encapsulation is used";
    }
    leaf l3-vni {
      when "../../evpn-encap-type = 'evpn-encap-type-vxlan'";
      type uint32;
      description
        "Specifies the Layer 3 VXLAN Network Identifier (VNI) used for routed traffic in this EVPN VLAN
         when VxLAN encapsulation is enabled";
    }
    leaf vtep-ip {
      when "../../evpn-encap-type = 'evpn-encap-type-vxlan'";
      type inet:ip-address;
      description
        "VTEP IP Address";
    }
    leaf sec-vtep-ip {
      when "../../evpn-encap-type = 'evpn-encap-type-vxlan'";
      type inet:ip-address;
      description
        "Secondary VTEP IP Address";
    }
    leaf mcast-ip {
      type inet:ip-address;
      description
        "Specifies the multicast IP address associated with this EVPN VLAN,
         used for multicast traffic distribution within the VLAN";
    }
    leaf ni-type {
      type common-types-ios-xe:net-inst-type;
      description
        "Network instance type. Differentiates between the
         default routing instance and VRFs";
    }
    leaf ni-name {
      type string;
      description
        "Network Instance or VRF name. If the type is
         net-inst-default, the name is not meaningful";
    }
    leaf irb-type {
      when "../../evpn-encap-type = 'evpn-encap-type-vxlan'";
      type evpn-ios-xe-oper:evpn-irb-type;
      description
        "Specifies the type of Integrated Routing and Bridging (IRB) configured for this EVPN VLAN,
         indicating the IRB operational mode (e.g., asymmetric or local routing)";
    }
    leaf ipv4-irb {
      type boolean;
      description
        "IPv4 IRB enabled";
    }
    leaf ipv6-irb {
      type boolean;
      description
        "IPv6 IRB enabled";
    }
    list evpn-pseudo-port {
      key "if-id svc-inst";
      description
        "List of EVPN pseudo-ports associated with this VLAN, representing logical
         or physical interfaces participating in the EVPN instance";
      uses evpn-ios-xe-oper:evpn-pseudo-port;
      uses evpn-ios-xe-oper:evpn-pseudo-port-table-key;
    }
    list evpn-peer {
      key "peer-ip-addr";
      description
        "Table EVPN Peers";
      uses evpn-ios-xe-oper:evpn-peer;
      uses evpn-ios-xe-oper:evpn-peer-table-key;
    }
  }

  grouping evpn-inst-table-key {
    description
      "EVPN Table key";
    leaf evpn-inst-id {
      type uint16;
      description
        "EVPN Instance Id";
    }
  }

  grouping evpn-inst {
    description
      "EVPN Instance operational data";
    leaf evpn-type {
      type evpn-ios-xe-oper:evpn-type;
      description
        "EVPN Type";
    }
    leaf evi-state {
      type evpn-ios-xe-oper:evpn-evi-state;
      description
        "EVPN Instance State";
    }
    leaf evpn-repl-type {
      type evpn-ios-xe-oper:evpn-replication-type;
      description
        "EVPN Replication Type";
    }
    leaf evpn-encap-type {
      type evpn-ios-xe-oper:evpn-encapsulation-type;
      description
        "EVPN Encapsulation Type";
    }
    leaf evpn-ip-local-learn {
      type evpn-ios-xe-oper:evpn-ip-local-learn;
      description
        "EVPN IP Local learn";
    }
    leaf evpn-dg-adv {
      type evpn-ios-xe-oper:evpn-dg-type;
      description
        "EVPN Distributed Gateway Advertising";
    }
    leaf evi-re-orig-rt5 {
      type evpn-ios-xe-oper:evpn-route-re-originate;
      description
        "EVPN Route Re-origination";
    }
    leaf evpn-ip-mcast-adv {
      type evpn-ios-xe-oper:evpn-mcast-adv;
      description
        "EVPN Multicast Advertising";
    }
    leaf evpn-ar-flood-suppr {
      type evpn-ios-xe-oper:evpn-flooding-suppression-flag;
      description
        "Indicates the status of EVPN flood suppression for this instance. Specifies whether unknown unicast,
         broadcast, and multicast traffic flooding is suppressed within the EVPN instance";
    }
    leaf rd {
      type string;
      description
        "Specifies the Route Distinguisher (RD) used to uniquely identify routes within the EVPN instance,
         enabling support for overlapping address spaces across different VPNs";
    }
    leaf-list import-rts {
      type string;
      ordered-by user;
      description
        "List of import route targets (RTs) for the EVPN instance.
         These RTs determine which routes are imported into this EVPN instance from other VPNs";
    }
    leaf-list export-rts {
      type string;
      ordered-by user;
      description
        "List of export route targets (RTs) for the EVPN instance.
         These RTs are attached to routes exported from this EVPN instance to control their distribution to other VPNs";
    }
    list evpn-vlan {
      key "vlan-id";
      description
        "List of VLANs associated with this EVPN instance, providing operational data
         for each VLAN configured under the instance";
      uses evpn-ios-xe-oper:evpn-vlan;
      uses evpn-ios-xe-oper:evpn-vlan-table-key;
    }
  }

  grouping evpn-id-map-info {
    description
      "VLAN EVPN Mapping";
    leaf evpn-inst-id {
      type uint16;
      description
        "EVPN Instance Id";
    }
  }

  grouping ni-evpn-map {
    description
      "Network Instance EVPN Mapping";
    leaf ni-name {
      type string;
      description
        "Network Instance Name";
    }
    leaf oc-ni-type {
      type evpn-ios-xe-oper:network-instance-type;
      description
        "Specifies the type of network instance, such as default, Layer 3 VRF, Layer 2 VSI,
         or Layer 2/3 instance, associated with the EVPN mapping";
    }
    list evpn-id-map-info {
      key "evpn-inst-id";
      description
        "List of EVPN instance identifiers associated with the network instance";
      uses evpn-ios-xe-oper:evpn-id-map-info;
    }
  }

  grouping evpn-vni-rt-cnt-table-key {
    description
      "EVPN Virtual Network Identifier Route Counters key";
    leaf vni {
      type uint32;
      description
        "VXLAN Network Identifier";
    }
  }

  grouping evpn-rt-cnt {
    description
      "Per-route-type counters";
    leaf ead-evi-cnt {
      type uint64;
      description
        "Number of Ethernet Auto-Discovery per EVPN instance routes";
    }
    leaf ead-es-cnt {
      type uint64;
      description
        "Number of Ethernet Auto-Discovery per Ethernet Segment routes";
    }
    leaf mac-cnt {
      type uint64;
      description
        "Number of MAC-only routes";
    }
    leaf mac-ip-cnt {
      type uint64;
      description
        "Number of MAC/IP routes";
    }
    leaf imet-cnt {
      type uint64;
      description
        "Number of Inclusive Multicast Ethernet Tag routes";
    }
    leaf es-cnt {
      type uint64;
      description
        "Number of Ethernet Segment routes";
    }
    leaf ip-prefix-cnt {
      type uint64;
      description
        "Number of IP Prefix routes";
    }
  }

  grouping evpn-vni-rt-cnt {
    description
      "EVPN Virtual Network Identifier Route Statistics";
    container local-add {
      description
        "Local route add counters";
      uses evpn-ios-xe-oper:evpn-rt-cnt;
    }
    container local-del {
      description
        "Local route delete counters";
      uses evpn-ios-xe-oper:evpn-rt-cnt;
    }
    container remote-add {
      description
        "Remote route add counters";
      uses evpn-ios-xe-oper:evpn-rt-cnt;
    }
    container remote-del {
      description
        "Remote route delete counters";
      uses evpn-ios-xe-oper:evpn-rt-cnt;
    }
    leaf last-update {
      type yang:date-and-time;
      description
        "Timestamp of last counter update";
    }
  }

  grouping evpn-stats {
    description
      "EVPN Telemetry Statistics";
    leaf evpn-stats-id {
      type uint32;
      description
        "EVPN Statistics identifier (always 0 for singleton)";
    }
    list evpn-vni-rt-cnt {
      key "vni";
      description
        "Per-Virtual Network Identifier route statistics";
      uses evpn-ios-xe-oper:evpn-vni-rt-cnt;
      uses evpn-ios-xe-oper:evpn-vni-rt-cnt-table-key;
    }
  }

  container evpn-oper-data {
    config false;
    description
      "Container for all operational data related to Ethernet VPN (EVPN) instances,
       including status, configuration, and runtime information";
    list evpn-inst {
      key "evpn-inst-id";
      description
        "List of operational data entries for each EVPN instance configured on the device";
      uses evpn-ios-xe-oper:evpn-inst;
      uses evpn-ios-xe-oper:evpn-inst-table-key;
    }
    list ni-evpn-map {
      key "ni-name";
      description
        "Network Instance EVPN Mapping";
      uses evpn-ios-xe-oper:ni-evpn-map;
    }
    list evpn-stats {
      key "evpn-stats-id";
      description
        "EVPN Statistics";
      uses evpn-ios-xe-oper:evpn-stats;
    }
  }
}
