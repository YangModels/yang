module Cisco-IOS-XE-banner-internal {
  yang-version 1.1;
  namespace "http://cisco.com/ns/yang/Cisco-IOS-XE-banner-internal";
  prefix ios-banner-internal;

  import Cisco-IOS-XE-native {
    prefix ios;
  }
  import cisco-semver {
    prefix cisco-semver;
  }
  import Cisco-IOS-XE-aaa {
    prefix ios-aaa;
  }

  organization
    "Cisco Systems, Inc.";
  contact
    "Cisco Systems, Inc.
     Customer Service

     Postal: 170 W Tasman Drive
     San Jose, CA 95134

     Tel: +1 1800 553-NETS

     E-mail: cs-yang@cisco.com";
  description
    "NED YANG module for IOS-XE.
     Copyright (c) 2019-2022 by Cisco Systems, Inc.
     All rights reserved.";

  revision 2024-07-01 {
    description
      "- Augmented aaa fail-message";
    cisco-semver:module-version "1.3.0";
  }
  revision 2024-03-01 {
    description
      "- Imported and augmented aaa banner";
    cisco-semver:module-version "1.2.0";
  }
  revision 2022-11-01 {
    description
      "- Update yang-version to 1.1";
    cisco-semver:module-version "1.1.0";
  }
  revision 2020-07-01 {
    description
      "Initial revision";
    cisco-semver:module-version "1.0.0";
  }

  grouping config-internal-banner-grouping {
    leaf internal-banner {
      description
        "Banner message";
      type string;
    }
  }

  augment "/ios:native/ios:banner/ios:exec" {
    uses config-internal-banner-grouping;
  }

  augment "/ios:native/ios:banner/ios:login" {
    uses config-internal-banner-grouping;
  }

  augment "/ios:native/ios:banner/ios:prompt-timeout" {
    uses config-internal-banner-grouping;
  }

  augment "/ios:native/ios:banner/ios:motd" {
    uses config-internal-banner-grouping;
  }

  augment "/ios:native/ios:aaa/ios-aaa:authentication/ios-aaa:banner" {
    uses config-internal-banner-grouping;
  }

  augment "/ios:native/ios:aaa/ios-aaa:authentication/ios-aaa:fail-message" {
    uses config-internal-banner-grouping;
  }
}
