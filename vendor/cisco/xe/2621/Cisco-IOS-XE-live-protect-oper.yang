module Cisco-IOS-XE-live-protect-oper {
  yang-version 1.1;
  namespace "http://cisco.com/ns/yang/Cisco-IOS-XE-live-protect-oper";
  prefix live-protect-ios-xe-oper;

  import Cisco-IOS-XE-common-types {
    prefix common-types-ios-xe;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Live Protect operational data.
     Copyright (c) 2025-2026 by Cisco Systems, Inc.
     All rights reserved.";

  revision 2026-08-01 {
    description
      "Initial revision";
    reference
      "1.0.0";
    cisco-semver:module-version "1.0.0";
  }

  typedef lp-shield-enum {
    type enumeration {
      enum mode-disabled {
        value 0;
        description
          "Indicates the shield is neither detecting nor blocking exploits";
      }
      enum mode-mon {
        value 1;
        description
          "Indicates the shield is actively detecting exploits but not blocking them";
      }
      enum mode-enf {
        value 2;
        description
          "Indicates the shield is actively detecting and blocking exploits";
      }
    }
    description
      "Shield operational mode enumeration: Disabled/Monitoring/Enforcing";
  }

  grouping lp-shield-oper {
    description
      "Shield operational data";
    leaf id {
      type string;
      description
        "Unique shield identifier";
    }
    leaf mode {
      type live-protect-ios-xe-oper:lp-shield-enum;
      description
        "Shield operational mode";
    }
    leaf total-hits {
      type uint64;
      description
        "Number of times the shield has monitored or prevented an exploit";
    }
    leaf enf-hits {
      type uint64;
      description
        "Number of times the shield has prevented an exploit";
    }
    leaf mon-hits {
      type uint64;
      description
        "Number of times the shield has detected an exploit";
    }
  }

  grouping fru-lp-shield-oper {
    description
      "Active shields and shield data for a given FRU";
    list fru-member-lp-shield {
      key "id";
      description
        "Per FRU shield operational data";
      uses live-protect-ios-xe-oper:lp-shield-oper;
    }
  }

  container live-protect-oper-data {
    config false;
    description
      "Live Protect operational data";
    list fru-lp-shield {
      key "fru slot bay chassis node";
      description
        "List of active shields and shield data for a given FRU";
      uses common-types-ios-xe:extended-location;
      uses live-protect-ios-xe-oper:fru-lp-shield-oper;
    }
    list lp-shield {
      key "id";
      description
        "Aggregate list of active shields and shield data across every FRU";
      uses live-protect-ios-xe-oper:lp-shield-oper;
    }
  }
}
