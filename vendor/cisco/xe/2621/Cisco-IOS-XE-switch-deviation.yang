module Cisco-IOS-XE-switch-deviation {
  yang-version 1.1;
  namespace "http://cisco.com/ns/yang/Cisco-IOS-XE-switch-deviation";
  prefix ios-sw-d;

  import cisco-semver {
    prefix cisco-semver;
  }
  import Cisco-IOS-XE-native {
    prefix ios;
  }
  import Cisco-IOS-XE-policy {
    prefix ios-policy;
  }
  import Cisco-IOS-XE-switch {
    prefix ios-sw;
  }
  import Cisco-IOS-XE-igmp {
    prefix ios-igmp;
  }

  organization
    "Cisco Systems";
  description
    "Cisco XE Native Deviation YANG module for IOS
     Copyright (c) 2016-2025 by Cisco Systems, Inc.
     All rights reserved.";

  revision 2026-02-01 {
    description
      "- Update version for igmp to <1-3>";
    cisco-semver:module-version "1.9.0";
  }
  revision 2025-07-01 {
    description
      "- Added NVE interface range deviation";
    cisco-semver:module-version "1.7.0";
  }
  revision 2024-07-01 {
    description
      "- Remove deviations for deprecated port-security maxcount
       - Added deviations for boot-start-marker and boot-end-marker";
    cisco-semver:module-version "1.6.0";
  }
  revision 2023-11-01 {
    description
      " - Move line vty range to quake/switch deviation files";
    cisco-semver:module-version "1.5.0";
  }
  revision 2023-07-01 {
    description
      "- Add deviation for autohangup";
  }
  revision 2022-11-01 {
    description
      "- Update yang-version to 1.1";
    cisco-semver:module-version "1.4.0";
  }
  revision 2021-07-01 {
    description
      "- Updated range for priority to <8-100000000> kbps";
    cisco-semver:module-version "1.3.0";
  }
  revision 2019-11-01 {
    description
      "- Added IP routing default value deviation";
    cisco-semver:module-version "1.2.0";
  }
  revision 2019-07-01 {
    description
      "Establish semantic version baseline";
    cisco-semver:module-version "1.0.0";
  }
  revision 2016-12-01 {
    description
      "Added interface switchport deviation";
  }

  deviation "/ios:native/ios:ip/ios-igmp:igmp/ios-igmp:snooping-entry/ios-igmp:snooping/ios-sw:vlan/ios-sw:range/ios-sw:querier/ios-sw:version" {
    deviate replace {
      type uint8 {
        range "1..3";
      }
    }
  }

  deviation "/ios:native/ios:policy/ios-policy:class-map/ios-policy:match/ios-policy:access-group/ios-policy:index" {
    deviate replace {
      type uint32 {
        range "1..2799";
      }
    }
  }

  deviation "/ios:native/ios:policy/ios-policy:policy-map/ios-policy:class/ios-policy:action-list/ios-policy:action-param/ios-policy:bandwidth-case/ios-policy:bandwidth/ios-policy:bits" {
    deviate replace {
      type uint32 {
        range "100..40000000";
      }
    }
  }

  deviation "/ios:native/ios:policy/ios-policy:policy-map/ios-policy:class/ios-policy:action-list/ios-policy:action-param/ios-policy:priority-case/ios-policy:priority/ios-policy:priority-type/ios-policy:kilo-bits/ios-policy:kilo-bits" {
    deviate replace {
      type uint32 {
        range "8..100000000";
      }
    }
  }

  deviation "/ios:native/ios:ip/ios:routing-conf/ios:routing" {
    deviate replace {
      default "false";
    }
  }

  deviation "/ios:native/ios:line/ios:console/ios:autohangup_only" {
    deviate not-supported;
  }

  deviation "/ios:native/ios:line/ios:aux/ios:autohangup_only" {
    deviate not-supported;
  }

  deviation "/ios:native/ios:line/ios:vty/ios:autohangup_only" {
    deviate not-supported;
  }

  deviation "/ios:native/ios:line/ios:line-list/ios:autohangup_only" {
    deviate not-supported;
  }

  deviation "/ios:native/ios:line/ios:async-line-single/ios:autohangup_only" {
    deviate not-supported;
  }

  deviation "/ios:native/ios:line/ios:async-line-range/ios:autohangup_only" {
    deviate not-supported;
  }

  deviation "/ios:native/ios:line/ios:console/ios:autohangup" {
    deviate not-supported;
  }

  deviation "/ios:native/ios:line/ios:aux/ios:autohangup" {
    deviate not-supported;
  }

  deviation "/ios:native/ios:line/ios:vty/ios:autohangup" {
    deviate not-supported;
  }

  deviation "/ios:native/ios:line/ios:line-list/ios:autohangup" {
    deviate not-supported;
  }

  deviation "/ios:native/ios:line/ios:async-line-single/ios:autohangup" {
    deviate not-supported;
  }

  deviation "/ios:native/ios:line/ios:async-line-range/ios:autohangup" {
    deviate not-supported;
  }

  deviation "/ios:native/ios:line/ios:console/ios:logout-warning" {
    deviate not-supported;
  }

  deviation "/ios:native/ios:line/ios:aux/ios:logout-warning" {
    deviate not-supported;
  }

  deviation "/ios:native/ios:line/ios:vty/ios:logout-warning" {
    deviate not-supported;
  }

  deviation "/ios:native/ios:line/ios:line-list/ios:logout-warning" {
    deviate not-supported;
  }

  deviation "/ios:native/ios:line/ios:async-line-single/ios:logout-warning" {
    deviate not-supported;
  }

  deviation "/ios:native/ios:line/ios:async-line-range/ios:logout-warning" {
    deviate not-supported;
  }

  deviation "/ios:native/ios:interface/ios:GigabitEthernet/ios:switchport-wrapper/ios:switchport/ios:trunk/ios:allowed/ios:vlan" {
    deviate not-supported;
  }

  deviation "/ios:native/ios:interface/ios:AppGigabitEthernet/ios:switchport-wrapper/ios:switchport/ios:trunk/ios:allowed/ios:vlan" {
    deviate not-supported;
  }

  deviation "/ios:native/ios:interface/ios:ucse/ios:switchport-wrapper/ios:switchport/ios:trunk/ios:allowed/ios:vlan" {
    deviate not-supported;
  }

  deviation "/ios:native/ios:interface/ios:Ethernet-Internal/ios:switchport-wrapper/ios:switchport/ios:trunk/ios:allowed/ios:vlan" {
    deviate not-supported;
  }

  deviation "/ios:native/ios:interface/ios:Wlan-GigabitEthernet/ios:switchport-wrapper/ios:switchport/ios:trunk/ios:allowed/ios:vlan" {
    deviate not-supported;
  }

  deviation "/ios:native/ios:boot-start-marker" {
    deviate not-supported;
  }

  deviation "/ios:native/ios:boot-end-marker" {
    deviate not-supported;
  }

  deviation "/ios:native/ios:interface/ios:nve/ios:name" {
    deviate replace {
      type uint16 {
        range "1..32";
      }
    }
  }

  deviation "/ios:native/ios-sw:device/ios-sw:classifier-with-condition/ios-sw:classifier/ios-sw:condition" {
    deviate add {
      must '(count(../condition) <= 1600)' {
        error-message "Condition exceeds the maximum supported value";
      }
      must '((count(../condition/CDP/tlv-type/value/Integer) + count(../condition/CDP/tlv-type/value/Hexstr) + count(../condition/CDP/tlv-type/value/Regex) + count(../condition/CDP/tlv-type/value/String) + count(../condition/LLDP/tlv-type/value/Integer) + count(../condition/LLDP/tlv-type/value/Hexstr) + count(../condition/LLDP/tlv-type/value/Regex) + count(../condition/LLDP/tlv-type/value/String) + count(../condition/DHCP/tlv-type/value/Integer) + count(../condition/DHCP/tlv-type/value/Hexstr) + count(../condition/DHCP/tlv-type/value/Regex) + count(../condition/DHCP/tlv-type/value/String) + count(../condition/MAC/Regex) + count(../condition/condition)) <= 3200)' {
        error-message "Check exceeds the maximum supported value";
      }
    }
  }

  deviation "/ios:native/ios-sw:device/ios-sw:classifier-with-condition/ios-sw:classifier/ios-sw:device-type" {
    deviate add {
      must '(count(../device-type) <= 800)' {
        error-message "Device-type exceeds the maximum supported value";
      }
    }
  }
}
