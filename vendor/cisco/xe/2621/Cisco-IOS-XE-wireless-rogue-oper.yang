module Cisco-IOS-XE-wireless-rogue-oper {
  yang-version 1.1;
  namespace "http://cisco.com/ns/yang/Cisco-IOS-XE-wireless-rogue-oper";
  prefix wireless-rogue-oper;

  import Cisco-IOS-XE-event-history-types {
    prefix event-history-types;
  }
  import Cisco-IOS-XE-wireless-enum-types {
    prefix wireless-enum-types;
  }
  import Cisco-IOS-XE-wireless-types {
    prefix wireless-types;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for wireless rogue operational data.
     Copyright (c) 2016-2026 by Cisco Systems, Inc.
     All rights reserved.";

  revision 2026-08-01 {
    description
      "Updated descriptions for several model elements to clarify their meaning and purpose";
    reference
      "5.15.0";
    cisco-semver:module-version "5.15.0";
  }
  revision 2025-07-01 {
    description
      "- Added RSSI and SNR data for unconnected client
       - Added Security violation bitmap for rogue authz
       - Added URWB link address stats for rogue AP";
    reference
      "5.14.0";
    cisco-semver:module-version "5.14.0";
  }
  revision 2025-03-01 {
    description
      "- Added off channel PMF Rogue Containment.
       - Unconnected client data and stats";
    reference
      "5.13.0";
    cisco-semver:module-version "5.13.0";
  }
  revision 2024-07-01 {
    description
      "- Support for WIFI 7 rogue AP and rogue client handling";
    reference
      "5.12.0";
    cisco-semver:module-version "5.12.0";
  }
  revision 2023-11-01 {
    description
      "- enabled a new containment strategy";
    reference
      "5.11.0";
    cisco-semver:module-version "5.11.0";
  }
  revision 2023-07-01 {
    description
      "- Rogue PMF-Denial Containment.
       - Additional error code for PMF-Denial containment.";
    reference
      "5.10.0";
    cisco-semver:module-version "5.10.0";
  }
  revision 2022-11-01 {
    description
      "Update yang-version to 1.1";
    reference
      "5.9.0";
    cisco-semver:module-version "5.9.0";
  }
  revision 2022-07-01 {
    description
      "- Added Rogue AP per-band channel width to the global rogue AP table.
       - Added rogue scale quota and priority statistics.";
    reference
      "5.8.0";
    cisco-semver:module-version "5.8.0";
  }
  revision 2021-11-01 {
    description
      "- Added Rogue AP properties: rogue wrong channel.";
    reference
      "5.7.0";
    cisco-semver:module-version "5.7.0";
  }
  revision 2021-07-01 {
    description
      "- Maximum-RSSI LRAD data for channel, encryption and WPA support.
       - Added statistics counter of dropped false-positive rogue reports.";
    reference
      "5.6.0";
    cisco-semver:module-version "5.6.0";
  }
  revision 2021-03-01 {
    description
      "Removal of: parent-rogue-data-rogue-address-key, parent-rogue-client-data-rogue-client-address-key, parent-containment-lrad-key.";
    reference
      "5.5.0";
    cisco-semver:module-version "5.5.0";
  }
  revision 2020-11-01 {
    description
      "- Added representation for Rogue Beacon DS Attack.
       - Added when statement to hide BSSID in containment parameters when containment does not involve clients or adhoc devices.
       - Deprecated Rogue RLDP operational model.";
    reference
      "5.4.0";
    cisco-semver:module-version "5.4.0";
  }
  revision 2020-03-01 {
    description
      "- Added statistics for AP channel change events.
       - Added Protected Management Frames (PMF) flag.
       - Added statistics for Beacon DS attack events.
       - Added impersonation flag.
       - Added new statistics.";
    reference
      "5.3.0";
    cisco-semver:module-version "5.3.0";
  }
  revision 2019-08-13 {
    description
      "- Added last heard SSID.";
    reference
      "5.2.0";
    cisco-semver:module-version "5.2.0";
  }
  revision 2019-05-01 {
    description
      "- Added statistics for Rogue WSA events.
       - Renamed statistics for Rogue WSA events.
       - Added semantic version";
    reference
      "5.1.0";
    cisco-semver:module-version "5.1.0";
  }
  revision 2019-01-10 {
    description
      "- Removal of unused leaves
       - Cleaned up spelling errors in descriptions.
       - Cleanup of the data model
       - Removed internal only leaves";
    reference
      "5.0.0";
    cisco-semver:module-version "5.0.0";
  }
  revision 2018-08-16 {
    description
      "- Update rogue client IP address types.
       - Statistics for mobilityd interaction.
       - Reformat descriptions.";
    reference
      "4.0.0";
    cisco-semver:module-version "4.0.0";
  }
  revision 2018-05-18 {
    description
      "Statistics for dropped updates for scale.";
    reference
      "3.1.0";
    cisco-semver:module-version "3.1.0";
  }
  revision 2018-03-22 {
    description
      "Add support for Prime initiated Auto Containment.
       Move event grouping out from module";
    reference
      "3.0.0";
    cisco-semver:module-version "3.0.0";
  }
  revision 2018-01-24 {
    description
      "The first generally available version";
    reference
      "2.0.0";
    cisco-semver:module-version "2.0.0";
  }
  revision 2017-05-05 {
    description
      "Initial revision";
    reference
      "1.0.0";
    cisco-semver:module-version "1.0.0";
  }

  typedef enm-rogue-class-type-change {
    type enumeration {
      enum default-class-type {
        value 0;
        description
          "Default Classification Type Change";
      }
      enum manual-changed-class-type {
        value 1;
        description
          "Manual Classification Type Change";
      }
      enum auto-changed-class-type {
        value 2;
        description
          "Automatic Classification Type Change";
      }
      enum rogue-rule-changed-class-type {
        value 3;
        description
          "Rule-based Classification Type Change";
      }
      enum awips-changed-class-type {
        value 4;
        description
          "AWIPS Classification Type Change";
      }
      enum aaa-changed-class-type {
        value 5;
        description
          "AAA Classification Type Change";
      }
    }
    description
      "Classification type change reason";
  }

  typedef enm-rogue-state-type-change {
    type enumeration {
      enum default-state-type {
        value 0;
        description
          "Default State Type Change";
      }
      enum manual-changed-state-type {
        value 1;
        description
          "Manual State Type Change";
      }
      enum auto-changed-state-type {
        value 2;
        description
          "Automatic State Type Change";
      }
      enum rogue-rule-changed-state-type {
        value 3;
        description
          "Rule-Based State Type Change";
      }
      enum awips-changed-state-type {
        value 4;
        description
          "AWIPS State Type Change";
      }
      enum aaa-changed-state-type {
        value 5;
        description
          "AAA State Type Change";
      }
    }
    description
      "State type change reason";
  }

  typedef enm-rogue-radio-type {
    type enumeration {
      enum 802-11-bg-radio-type {
        value 1;
        description
          "802.11bg";
      }
      enum 802-11a-radio-type {
        value 2;
        description
          "802.11a";
      }
      enum 802-11-abgn-radio-type {
        value 3;
        description
          "802.11abgn";
      }
      enum 802-11ac-radio-type {
        value 4;
        description
          "802.11ac";
      }
      enum 802-11-n-5g-radio-type {
        value 5;
        description
          "802.11n 5 Ghz";
      }
      enum 802-11-n-24g-radio-type {
        value 6;
        description
          "802.11n 2.4 Ghz";
      }
      enum 802-11g-radio-type {
        value 7;
        description
          "802.11g";
      }
      enum 802-11ax-24g-radio-type {
        value 8;
        description
          "802.11ax 2.4GHz";
      }
      enum 802-11ax-5g-radio-type {
        value 9;
        description
          "802.11ax 5GHz";
      }
      enum 802-11ax-6g-radio-type {
        value 10;
        description
          "802.11ax 6GHz";
      }
      enum 802-11be-radio-type {
        value 11;
        description
          "802.11be";
      }
    }
    description
      "Radio Type";
  }

  typedef enm-rogue-containment-type {
    type enumeration {
      enum invalid {
        value 0;
        description
          "Invalid Containment Type";
      }
      enum deauth-bcast {
        value 1;
        description
          "Deauthentication Broadcast Containment";
      }
      enum cfp {
        value 2;
        description
          "CFP Containment";
      }
      enum client-deauth {
        value 3;
        description
          "Client Deauthentication Containment";
      }
      enum adhoc-deauth {
        value 4;
        description
          "AdHoc Deauthentication Containment";
      }
      enum clear-all {
        value 5;
        description
          "Clear all Existing Containment";
      }
      enum rogue-ap-pmf-deauth {
        value 6;
        description
          "Deauthentication PMF Containment";
      }
      enum rogue-ap-pmf-off-channel {
        value 7;
        description
          "Off-channel PMF Containment";
      }
    }
    description
      "Rogue Containment Type";
  }

  typedef enm-rogue-validation-result {
    type enumeration {
      enum rogue-val-none {
        value 0;
        description
          "Not Evaluated/Not Containing";
      }
      enum rogue-contain-success {
        value 1;
        description
          "Success.";
      }
      enum skipped-not-monitor-ap {
        value 2;
        description
          "Skipped: Not Monitor-AP.";
      }
      enum failure-no-managed-ap-info-in-cache {
        value 3;
        description
          "Failure: No Managed AP info in cache.";
      }
      enum failure-no-radio-type-info {
        value 4;
        description
          "Failure: No Radio Type info";
      }
      enum failure-no-radio-oper-info {
        value 5;
        description
          "Failure: No Radio Oper info";
      }
      enum skipped-radio-is-down {
        value 6;
        description
          "Skipped: Radio is Down";
      }
      enum failure-no-country-string {
        value 7;
        description
          "Failure: No Country String";
      }
      enum skipped-invalid-channel-for-country {
        value 8;
        description
          "Skipped: Invalid Channel for Country";
      }
      enum failure-no-radar-mode-info {
        value 9;
        description
          "Failure: No Radar mode info";
      }
      enum skipped-dfs-channel {
        value 10;
        description
          "Skipped: DFS Channel";
      }
      enum failure-generic-db-error {
        value 11;
        description
          "Failure: Generic DB Error";
      }
      enum failure-error-sending-containment-message {
        value 12;
        description
          "Failure: Error sending Containment message";
      }
      enum skipped-max-scale-containment-reached-on {
        value 13;
        description
          "Skipped: Max Scale Containment reached on AP";
      }
      enum waiting-for-post-sso-cleanup-to-complete {
        value 14;
        description
          "Waiting for post-SSO Cleanup to complete";
      }
      enum failure-ap-in-wrong-mode {
        value 15;
        description
          "Failure: AP in wrong mode";
      }
      enum rogue-val-encr-enabled {
        value 16;
        description
          "Encryption is enabled";
      }
      enum rogue-val-ssid-too-long {
        value 17;
        description
          "SSID is too long";
      }
      enum rogue-val-hidden-ssid {
        value 18;
        description
          "SSID is hidden";
      }
      enum rogue-val-ap-in-use {
        value 19;
        description
          "AP is in use";
      }
      enum rogue-val-rldp-in-progress {
        value 20;
        status deprecated;
        description
          "RLDP is in progress";
      }
      enum rogue-val-mfp-required {
        value 21;
        description
          "802.11w Protected Management Frames (PMF) is required";
      }
      enum rogue-val-no-tx-radio-on-band {
        value 22;
        description
          "The AP has not TX-enabled radio on this band";
      }
      enum rogue-val-mfp-required-not-on-chan {
        value 23;
        description
          "Rogue AP requires PMF-denial containment but is not on client-serving channel";
      }
      enum rogue-val-mfp-required-ap-disable {
        value 24;
        description
          "Rogue AP requires PMF-denial containment which is disabled on the Managed AP";
      }
      enum rogue-val-mfp-required-no-ds-channel {
        value 25;
        description
          "Rogue AP requires PMF-denial containment but No Beacon-DS IE channel information found";
      }
      enum rogue-val-mfp-required-monitor-mode {
        value 26;
        description
          "Rogue AP requires PMF-denial containment but this is a radio or AP in monitor mode";
      }
      enum rogue-val-pmf-required-aux-radio {
        value 27;
        description
          "Rogue AP requires PMF-off-channel containment but this is not an AUX radio";
      }
    }
    description
      "Validation result";
  }

  typedef enm-rogue-mfp {
    type enumeration {
      enum rogue-mfp-required {
        value 0;
        description
          "802.11w PMF is required";
      }
      enum rogue-mfp-capable {
        value 1;
        description
          "802.11w PMF capability exists, but it is not required";
      }
      enum rogue-mfp-none {
        value 2;
        description
          "802.11w PMF capability does not exist and is not required";
      }
    }
    description
      "Status of 802.11w Protected Management Frames (PMF)";
  }

  typedef enm-rogue-override-src {
    type enumeration {
      enum rogue-override-none {
        value 0;
        description
          "no override of classification or containment";
      }
      enum rogue-override-config-ap {
        value 1;
        description
          "override by rogue AP configuration";
      }
      enum rogue-override-config-client {
        value 2;
        description
          "override by rogue client configuration";
      }
      enum rogue-override-snmp {
        value 3;
        description
          "override by rogue AP SNMP setting";
      }
    }
    description
      "Classification and/or containment override reason";
  }

  typedef enm-rogue-mld-rec-type {
    type enumeration {
      enum rogue-mld-rec-none {
        value 0;
        description
          "A non-MLD rogue AP/rogue client record";
      }
      enum rogue-mld-rec {
        value 1;
        description
          "A MLD rogue AP/rogue client record";
      }
      enum rogue-mld-lik-rec {
        value 2;
        description
          "A MLD-Link rogue AP/rogue client record";
      }
    }
    description
      "Rogue AP/rogue Client MLD record type";
  }

  typedef enm-lrad-impersonation {
    type enumeration {
      enum rogue-impersonation-none {
        value 0;
        description
          "No impersonation detected by this LRAD";
      }
      enum rogue-impersonation-direct-detection {
        value 1;
        description
          "A managed AP reported a rogue AP BSSID or MLD-Link MAC that belongs to the pool of the reporting managed AP";
      }
      enum rogue-impersonation-auth-fail-count {
        value 2;
        description
          "A managed AP reported a rogue AP which fails the check of Authentication IE or Cisco PMF MIC";
      }
    }
    description
      "Rogue AP Impersonation type detected by LRAD";
  }

  typedef rogue-wpa-support-flag {
    type bits {
      bit wpa-support-wpa {
        position 0;
        description
          "WiFi Protected Access";
      }
      bit wpa-support-wpa2 {
        position 1;
        description
          "WiFi Protected Access 2";
      }
      bit wpa-support-ft {
        position 2;
        description
          "WiFi Fast Transition";
      }
      bit wpa-support-security-dot1x {
        position 3;
        description
          "802.1X authentication";
      }
      bit wpa-support-psk {
        position 4;
        description
          "WiFi WPA Pre-Shared Key";
      }
      bit wpa-support-security-owe {
        position 5;
        description
          "WiFi Protected Access 3 Opportunistic Wireless Encryption";
      }
      bit wpa-support-security-sae {
        position 6;
        description
          "WiFi Protected Access 3 Simultaneous Authentication of Equals";
      }
      bit wpa-support-security-suite-b {
        position 7;
        description
          "WiFi Protected Access Suite B";
      }
      bit wpa-support-security-suite-b-192 {
        position 8;
        description
          "WiFi Protected Access Suite B 192";
      }
      bit wpa-support-security-ex-key {
        position 9;
        description
          "WiFi Protected Access Ext Key";
      }
      bit wpa-support-wpa3 {
        position 10;
        description
          "WiFi Protected Access 3";
      }
      bit wpa-support-security-cckm {
        position 11;
        description
          "WiFi Protected Access CCKM";
      }
      bit wpa-support-security-fils {
        position 12;
        description
          "WiFi Protected Access Fast Initial Link Setup";
      }
      bit wpa-support-security-sha384 {
        position 13;
        description
          "WiFi Protected Access SHA384";
      }
      bit wpa-support-security-pasn {
        position 14;
        description
          "WiFi Protected Access PASN";
      }
    }
    description
      "WPA and Security Support of the Rogue AP";
  }

  typedef rogue-encrypted-flag {
    type bits {
      bit rogue-encrypted-wep-mode {
        position 0;
        description
          "Rogue AP supports WiFi Wired Equivalent Privacy";
      }
    }
    description
      "Encrypted flag of Rogue AP report";
  }

  typedef rogue-properties-flag {
    type bits {
      bit beacon-wrong-channel {
        position 0;
        description
          "Impersonator Rogue AP transmits on wrong channel";
      }
    }
    description
      "Rogue properties";
  }

  typedef ucon-clnt-sec-vio {
    type bits {
      bit sec-vio-clnt-probe {
        position 0;
        description
          "Active probing client security violation";
      }
      bit sec-vio-clnt-actv-wlan-scan {
        position 1;
        description
          "Active WLAN scanner client security violation";
      }
      bit sec-vio-ucon-clnt {
        position 2;
        description
          "Unconnected client security violation";
      }
    }
    description
      "Unconnected client security violation options flag";
  }

  grouping st-rogue-ap-remote-override {
    description
      "Containment override manipulated remotely via a manageability interface";
    leaf remote-override-class-type {
      type wireless-enum-types:rogue-class-type;
      description
        "Specifies the classification type used for remote override of containment actions for this rogue access point";
    }
    leaf remote-override-mode {
      type wireless-enum-types:rogue-state;
      description
        "Specifies the mode used for remote containment override of a rogue access point, indicating the current override state applied remotely";
    }
    leaf remote-override-containment-level {
      type uint32;
      description
        "Indicates the level of containment applied to a rogue access point through remote override, representing the intensity or type of containment action";
    }
  }

  grouping st-rogue-lrad-key {
    description
      "Local Radio Key";
    leaf lrad-mac-addr {
      type yang:mac-address;
      description
        "MAC Address of AP Interface that Detected the Rogue.";
    }
    leaf slot-id {
      type uint8;
      description
        "The slot ID of the AP Interface that detected the Rogue.";
    }
  }

  grouping st-rogue-data-per-band {
    description
      "Per-band data for the BSSID-reuse case";
    leaf chan-width {
      type uint16;
      units "MHz";
      description
        "Channel width (in MHz) used by the rogue access point in this band";
    }
    leaf actual-containment {
      type uint32;
      description
        "Indicates the number of containment actions currently being performed against the rogue access point in this band";
    }
    leaf mld-link-mac {
      type yang:mac-address;
      description
        "Specifies the MAC address used by the Multi-Link Device (MLD) for its link in this band";
    }
  }

  grouping st-rogue-data {
    description
      "Rogue AP data";
    leaf rogue-address {
      type yang:mac-address;
      description
        "MAC Address of a rogue AP.";
    }
    leaf rogue-class-type {
      type wireless-enum-types:rogue-class-type;
      description
        "This object specifies the type of a rogue AP.
         friendly     - existing known, acknowledged, and trusted APs
         malicious    - unknown AP that could be a threat.
         unclassified - an unknown or rogue AP is identified
           but it does not belong to Friendly or
           Malicious rogue types.
         custom       - AP that matches user defined custom rules.";
    }
    leaf rogue-mode {
      type wireless-enum-types:rogue-state;
      description
        "This objects specifies the state in which the rogue AP is.
         pending          - a read-only value indicates that rogue AP
         is under classification process
         alert            - rogue AP that can be a potential threat.
         Trap will be sent out to trap recipients.
         detectedLrad     - a read-only value indicates that a LRAD
         that got detected as rogue.
         known            - a read-only value indicates that an internal
         AP which is not on the same switch.
         acknowledge      - a read-only value indicates that an external
         AP whose existence is acceptable and not a
         threat (probably from vendor other than cisco).
         contained        - containment is initiated and ongoing.
         threat           - rogue AP is found on wired network.
         containedPending - a read-only value indicates that no AP
         resources are available for containment.
         knownContained   - a read-only value - no longer used.
         trustedMissing   - rogue AP is friendly but there is no slot
         for friendly AP.
         initializing     - a read-only value indicates that rogue
         AP is being initialized.
         For a friendly rogue AP, only two states are valid:
         'known' and 'acknowledge'.
         'known', 'knownContained' and 'trustedMissing'
         can appear in known rogue list.
         Known rogues can be pre-provisioned and known rogues
         state can be changed to 'alert'.";
    }
    leaf rogue-containment-level {
      type uint32;
      description
        "Indicates the configured containment level for the rogue access point";
    }
    leaf actual-containment {
      type uint32;
      description
        "Number of Containing APs.";
    }
    leaf manual-contained {
      type boolean;
      description
        "Indicates whether the rogue AP is manually contained (true) or not (false)";
    }
    leaf class-override-src {
      type wireless-rogue-oper:enm-rogue-override-src;
      description
        "Source of the classification/containment override";
    }
    leaf containment-type {
      type wireless-rogue-oper:enm-rogue-containment-type;
      description
        "Indicates the containment mode applied to this rogue AP
         if it is in 'contained' state.
          A value of '0' indicates invalid containment mode.
          A value of '1' indicates deauthentication broadcast used for containment.
          A value of '2' indicates CFP containment.
          A value of '3' indicates client containment.
          A value of '4' indicates adhoc containment.
          A value of '5' indicates max value i.e invalid.
          A value of '99' indicates unknown containment type.";
    }
    leaf contained {
      type boolean;
      description
        "Indicates whether this rogue AP is currently contained by the wireless network";
    }
    leaf severity-score {
      type uint32;
      description
        "This object specifies the custom classification
         severity score of the rules.
         This object is applicable when cLRuleRogueType is configured as 'custom'.";
    }
    leaf class-type-custom-name {
      type string;
      description
        "Specifies the name of the custom classification rule applied to this rogue access point";
    }
    leaf rogue-first-timestamp {
      type yang:date-and-time;
      description
        "Time Stamp when this Rogue was First Detected.";
    }
    leaf rogue-last-timestamp {
      type yang:date-and-time;
      description
        "Time Stamp when this Rogue was Last Detected.";
    }
    leaf rogue-is-on-my-network {
      type boolean;
      description
        "Indicates whether the rogue AP is connected to the wired network (true) or not (false)";
    }
    leaf ad-hoc {
      type boolean;
      description
        "Indicates whether the rogue device is an ad-hoc network (true) or an access point (false)";
    }
    leaf ad-hoc-bssid {
      type yang:mac-address;
      description
        "Specifies the BSSID (MAC address) of the rogue device if it is operating as an ad-hoc network";
    }
    leaf rogue-rule-name {
      type string;
      description
        "Specifies the name of the rule used to classify this rogue AP";
    }
    leaf rogue-radio-type-last-seen {
      type wireless-rogue-oper:enm-rogue-radio-type;
      description
        "Specifies the type of radio on which the rogue access point was last detected";
    }
    leaf rldp-retries {
      type uint32;
      status deprecated;
      description
        "Indicates the number of Rogue Location Discovery Protocol (RLDP) attempts made to locate the rogue access point";
    }
    leaf rogue-class-type-change {
      type wireless-rogue-oper:enm-rogue-class-type-change;
      description
        "Indicates the type of classification change detected for the rogue access point, such as a change from friendly to malicious";
    }
    leaf rogue-state-change {
      type wireless-rogue-oper:enm-rogue-state-type-change;
      description
        "Indicates the type of state change event detected for the rogue access point, such as a transition from active to contained";
    }
    leaf rogue-if-num {
      type uint32;
      description
        "Specifies the interface number associated with the rogue access point detection event";
    }
    leaf managed-ap {
      type boolean;
      description
        "There is a managed AP locally or via AP list with the same MAC";
    }
    leaf autocontain-adhoc-trap {
      type boolean;
      description
        "Trap for AdHoc Auto-Containment has been sent";
    }
    leaf autocontain-trap {
      type boolean;
      description
        "Trap for Auto-Containment has been sent";
    }
    leaf potential-honeypot-trap {
      type boolean;
      description
        "Trap for Potential Honeypot has been sent";
    }
    container history {
      description
        "Contains the history of events related to the rogue access point, such as detection, classification, and containment actions";
      uses event-history-types:event-history;
    }
    container rldp-history {
      status deprecated;
      description
        "History of events related to Rogue Location Discovery Protocol (RLDP) operations for the rogue access point";
      uses event-history-types:event-history;
    }
    leaf rldp-last-result {
      type wireless-enum-types:rogue-rldp-result;
      status deprecated;
      description
        "Result of the most recent RLDP (Rogue Location Discovery Protocol) operation performed on the rogue access point";
    }
    leaf rldp-in-progress {
      type boolean;
      status deprecated;
      description
        "Indicates whether the Rogue Location Discovery Protocol (RLDP) operation is currently in progress for this rogue access point";
    }
    leaf max-detected-rssi {
      type int8;
      description
        "This is the max RSSI value of all the detecting APs,
          which have detected this rogue.";
    }
    leaf ssid-max-rssi {
      type string;
      description
        "This is the SSID of the rogue detected by Access Point,
          which has max RSSI value of all the detecting APs of this rogue.";
    }
    leaf ap-name-max-rssi {
      type string;
      description
        "The name of the access point that detected this rogue access point with the maximum received signal strength indicator (RSSI) value";
    }
    leaf detecting-radio-type-802-11bg {
      type empty;
      description
        "Indicates whether any detecting access point used an 802.11b/g radio to detect this rogue access point";
    }
    leaf detecting-radio-type-802-11a {
      type empty;
      description
        "Indicates whether any detecting access point used an 802.11a radio to detect this rogue access point";
    }
    leaf detecting-radio-type-802-11abgn {
      type empty;
      description
        "Indicates whether any detecting access point used an 802.11a/b/g/n radio to detect this rogue access point";
    }
    leaf detecting-radio-type-80211ac {
      type empty;
      description
        "Indicates whether any detecting access point used an 802.11ac radio to detect this rogue access point";
    }
    leaf detecting-radio-type-80211n-5g {
      type empty;
      description
        "Indicates whether any detecting access point used an 802.11n 5 GHz radio to detect this rogue access point";
    }
    leaf detecting-radio-type-80211n-24g {
      type empty;
      description
        "Indicates whether any detecting access point used an 802.11n 2.4 GHz radio to detect this rogue access point";
    }
    leaf detecting-radio-type-80211g {
      type empty;
      description
        "Indicates whether the rogue access point was detected by an AP operating in 802.11g radio mode";
    }
    leaf lrad-mac-max-rssi {
      type yang:mac-address;
      description
        "MAC address of the detecting AP that received the maximum RSSI value from the rogue access point";
    }
    leaf rogue-radio-type-max-rssi {
      type wireless-rogue-oper:enm-rogue-radio-type;
      description
        "The radio type of detecting AP which received max  RSSI value.";
    }
    leaf last-channel {
      type uint32;
      description
        "Channel number used by the last AP that detected this rogue access point";
    }
    leaf-list radio-type-count {
      type uint8;
      ordered-by user;
      description
        "Specifies the count of each radio type that detected the rogue access point";
    }
    container last-heard-lrad-key {
      description
        "Specifies the key identifying the last local radio access device (AP interface) that detected this rogue";
      uses wireless-rogue-oper:st-rogue-lrad-key;
    }
    leaf n-lrads {
      type uint32;
      description
        "Total number of APs that detected this rogue.";
    }
    list rogue-lrad {
      key "lrad-mac-addr slot-id";
      description
        "List of local radios (AP interfaces) that detected this rogue access point, including identifying information for each radio";
      uses wireless-rogue-oper:st-rogue-lrad;
      uses wireless-rogue-oper:st-rogue-lrad-key;
    }
    leaf n-clients {
      type uint32;
      description
        "Total number of Clients detected on this rogue.";
    }
    list rogue-client {
      key "rogue-client-address";
      description
        "List of MAC addresses for clients detected as associated with this rogue access point";
      uses wireless-rogue-oper:st-rogue-client;
    }
    container remote-override {
      description
        "Container for settings that override default remote containment actions for this rogue access point";
      uses wireless-rogue-oper:st-rogue-ap-remote-override;
    }
    leaf last-heard-ssid {
      type string;
      description
        "Last detected SSID advertised by Rogue station.";
    }
    leaf mfp-required {
      type boolean;
      description
        "This rogue requires 802.11w PMF.";
    }
    leaf is-impersonation {
      type empty;
      description
        "Indicates whether this rogue access point is impersonating a managed access point";
    }
    leaf beacon-ds-attack {
      type empty;
      description
        "This rogue performs Beacon DS DoS attack.";
    }
    leaf d-radio-type-802-11ax24g {
      type empty;
      description
        "Indicates whether any managed access point used an 802.11ax 2.4 GHz radio to detect this rogue access point";
    }
    leaf d-radio-type-802-11ax5g {
      type empty;
      description
        "Indicates whether any managed access point used an 802.11ax 5 GHz radio to detect this rogue access point";
    }
    leaf d-radio-type-802-11ax6g {
      type empty;
      description
        "Indicates whether any managed access point used an 802.11ax 6 GHz radio to detect this rogue access point";
    }
    leaf channel-max-rssi {
      type uint8;
      description
        "Specifies the channel on which the rogue access point was detected with the maximum received signal strength indicator (RSSI) by the local radio (LRAD)";
    }
    leaf wpa-support-max-rssi {
      type wireless-rogue-oper:rogue-wpa-support-flag;
      description
        "Indicates whether WPA encryption is supported by the rogue access point as detected by the local radio (LRAD) with the highest received signal strength (RSSI)";
    }
    leaf encrypted-max-rssi {
      type wireless-rogue-oper:rogue-encrypted-flag;
      description
        "Indicates the type of encryption detected on the rogue access point by the local radio (LRAD) with the highest received signal strength (RSSI)";
    }
    leaf snr-max-rssi {
      type int8;
      description
        "Signal-to-noise ratio of the maximum RSSI LRAD";
    }
    leaf properties {
      type wireless-rogue-oper:rogue-properties-flag;
      description
        "Bitmask value encoding specific properties or characteristics of the rogue access point, such as its operational status or detected behaviors";
    }
    container band-data-2dot4g {
      description
        "Rogue AP 2.4GHz band-specific data";
      uses wireless-rogue-oper:st-rogue-data-per-band;
    }
    container band-data-5g {
      description
        "Rogue AP 5GHz band-specific data";
      uses wireless-rogue-oper:st-rogue-data-per-band;
    }
    container band-data-6g {
      description
        "Rogue AP 6GHz band-specific data";
      uses wireless-rogue-oper:st-rogue-data-per-band;
    }
    leaf mld-record {
      type wireless-rogue-oper:enm-rogue-mld-rec-type;
      description
        "Indicates the type of Multi-Link Device (MLD) record associated with the rogue access point";
    }
    leaf mld-mac {
      type yang:mac-address;
      description
        "Specifies the MAC address assigned to the Multi-Link Device (MLD) associated with the rogue access point";
    }
    leaf d-radio-type-802-11be {
      type empty;
      description
        "Radio type of detecting APs. If the radio type is
         detected by 802.11be";
    }
    leaf band-max-rssi {
      type wireless-types:enm-ewlc-dot11-radio-band;
      description
        "Radio Band reported by the maximum RSSI LRAD";
    }
  }

  grouping st-rogue-signal {
    description
      "Signal Level";
    leaf val {
      type int8;
      description
        "Most recent signal measurement value for this rogue signal sample";
    }
    leaf num {
      type int16;
      description
        "Numerator used to represent the signal measurement value";
    }
    leaf den {
      type int16;
      description
        "Denominator used to represent the signal measurement value";
    }
  }

  grouping st-rogue-unconnected-lrad {
    description
      "Local Radio that detected this unconnected client";
    leaf lrad-mac-addr {
      type yang:mac-address;
      description
        "MAC Address of AP interface that detected the unconnected client";
    }
    leaf last-heard {
      type yang:date-and-time;
      description
        "Timestamp indicating when this unconnected client was last heard by this AP";
    }
    container rssi {
      description
        "RSSI of unconnected client in dBm";
      uses wireless-rogue-oper:st-rogue-signal;
    }
    container snr {
      description
        "SNR of unconnected client in dB";
      uses wireless-rogue-oper:st-rogue-signal;
    }
    leaf clnt-syslog {
      type wireless-rogue-oper:ucon-clnt-sec-vio;
      description
        "Unconnected client security violation syslog bitmap";
    }
  }

  grouping st-rogue-unconnected-data {
    description
      "Rogue unconnected client data";
    leaf client-mac {
      type yang:mac-address;
      description
        "MAC address of the unconnected client";
    }
    leaf n-lrads {
      type uint32;
      description
        "Total number of APs that detected this unconnected client";
    }
    leaf first-timestamp {
      type yang:date-and-time;
      description
        "Timestamp when this unconnected client was first detected.";
    }
    leaf last-timestamp {
      type yang:date-and-time;
      description
        "Timestamp when this unconnected client was last detected.";
    }
    list rogue-unconnected-lrad {
      key "lrad-mac-addr";
      description
        "Local radio that detected this rogue";
      uses wireless-rogue-oper:st-rogue-unconnected-lrad;
    }
  }

  grouping st-rogue-akm {
    description
      "Rogue AKM";
    leaf-list wpa-support {
      type wireless-enum-types:enm-rogue-akm;
      ordered-by user;
      description
        "Indicates the types of WiFi Protected Access (WPA) Authentication and Key Management (AKM) protocols supported by the detected rogue AP";
    }
  }

  grouping st-rogue-cipher {
    description
      "Rogue Cipher";
    leaf-list wpa-cipher {
      type wireless-enum-types:enm-rogue-cipher;
      ordered-by user;
      description
        "List of WPA cipher suites supported by the detected rogue access point";
    }
  }

  grouping st-rogue-lrad {
    description
      "Local Radio";
    leaf ssid {
      type string;
      description
        "Specifies the SSID advertised by the rogue station";
    }
    leaf hidden-ssid {
      type boolean;
      description
        "Indicates whether the SSID advertised by the rogue access point is hidden, as detected by this AP";
    }
    leaf name {
      type string;
      description
        "Specifies the name of the detecting AP interface that detected the rogue";
    }
    container rssi {
      description
        "Container for the rogue RSSI as seen by the detecting access point interface";
      uses wireless-rogue-oper:st-rogue-signal;
    }
    container snr {
      description
        "Container for the SNR seen by the detecting AP interface from the rogue";
      uses wireless-rogue-oper:st-rogue-signal;
    }
    leaf short-preamble {
      type uint8;
      description
        "Specifies the preamble used on this detecting access point.";
    }
    leaf channel {
      type uint32;
      description
        "Specifies the advertised channel number of the detecting access point interface picked up from the rogue";
    }
    leaf-list channels {
      type uint32;
      ordered-by user;
      description
        "List of channel numbers on which the rogue device was observed by the detecting AP interface";
    }
    leaf encrypted {
      type uint32;
      description
        "Specifies the encryption mode on this detecting access point";
    }
    leaf wpa-support {
      type uint32;
      description
        "Specifies the WPA mode on this detecting access point";
    }
    leaf dot11-phy-support {
      type uint32;
      description
        "Specifies the IEEE 802.11 physical layer (PHY) type supported by the rogue radio as detected by the AP";
    }
    leaf last-heard {
      type yang:date-and-time;
      description
        "Specifies the date and time when this rogue device was last detected by the AP";
    }
    leaf chan-width {
      type uint16;
      description
        "Specifies the channel width using the rogue monitor-specific representation, as observed by the detecting AP interface for the rogue device. The value ranges from 0 to 34";
    }
    leaf chan-width-label {
      type uint16;
      description
        "Specifies the channel width using the Radio Resource Management (RRM)-specific representation, as observed by the detecting AP interface for the rogue device. The value ranges from 1 to 35";
    }
    leaf ext-chan {
      type uint32;
      description
        "Specifies the extension channel number used by the local radio that detected the rogue access point";
    }
    leaf band-id {
      type uint8;
      description
        "Indicates the frequency band (such as 2.4 GHz, 5 GHz, or 6 GHz) used by the local radio that detected the rogue access point";
    }
    leaf num-slots {
      type uint32;
      description
        "Number of slots in this AP";
    }
    leaf report-radio-type {
      type uint32;
      description
        "Indicates the type of radio interface reported by the local radio that detected the rogue access point";
    }
    leaf contain-result {
      type wireless-rogue-oper:enm-rogue-validation-result;
      description
        "Last containment result";
    }
    leaf contain-slot-id {
      type wireless-enum-types:slot-id-type;
      description
        "Slot performing containment ";
    }
    leaf contain-radio-type {
      type uint32;
      description
        "Radio type for containment";
    }
    leaf radio-type {
      type wireless-rogue-oper:enm-rogue-radio-type;
      description
        "Indicates the detecting access point interface type that detected the rogue";
    }
    leaf containment-type {
      type wireless-rogue-oper:enm-rogue-containment-type;
      description
        "Indicates the containment mode used by the AP
         if the rogue is in 'contained' state.
          A value of '0' indicates invalid containment mode.
          A value of '1' indicates deauthentication broadcast used for containment.
          A value of '2' indicates CFP containment.
          A value of '3' indicates client containment.
          A value of '4' indicates adhoc containment.
          A value of '5' indicates max value i.e invalid.
          A value of '99' indicates unknown containment type.";
    }
    leaf containment-channel-count {
      type uint8;
      description
        "Specifies the number of channels used for rogue containment";
    }
    leaf rogue-containment-chans {
      type string;
      description
        "Specifies the comma-separated string of channels used for rogue containment";
    }
    leaf auth-fail-count {
      type uint8;
      description
        "Number of authentication failures detected by this local radio (LRAD) for the rogue access point";
    }
    leaf mfp-status {
      type wireless-rogue-oper:enm-rogue-mfp;
      description
        "802.11w Protected Management Frames (PMF) status.";
    }
    leaf channel-from-ds {
      type boolean;
      description
        "Channel information is detected from DS Parameter Set.";
    }
    leaf phy-ap-slot {
      type uint8;
      description
        "Manageability AP slot of the reporting LRAD";
    }
    leaf mld-link-mac {
      type yang:mac-address;
      description
        "Multi-Link Device link address";
    }
    leaf lrad-impersonation {
      type wireless-rogue-oper:enm-lrad-impersonation;
      description
        "Rogue AP impersonation indicated by this LRAD";
    }
    container rogue-cipher {
      description
        "Container for the WPA cipher on this detecting access point";
      uses wireless-rogue-oper:st-rogue-cipher;
    }
    leaf beacon-interval {
      type uint16;
      units "milliseconds";
      description
        "Specifies the beacon interval on this detecting access point";
    }
    leaf hotspot-type {
      type wireless-enum-types:enm-rogue-hotspot;
      description
        "Specifies the type of hotspot on this detecting access point";
    }
    container rogue-akm {
      description
        "Container for the type of security AKM on this detecting access point";
      uses wireless-rogue-oper:st-rogue-akm;
    }
  }

  grouping st-rogue-client {
    description
      "Rogue Client connected to a Rogue AP";
    leaf rogue-client-address {
      type yang:mac-address;
      description
        "MAC Address of the Rogue Client.";
    }
  }

  grouping st-rogue-client-data-per-band {
    description
      "Per-band data for a rogue client";
    leaf n-lrads {
      type uint16;
      description
        "Number of radios detecting this rogue client on this band";
    }
    leaf actual-containment {
      type uint32;
      description
        "Number of radios containing this rogue client on this band";
    }
    leaf mld-link-mac {
      type yang:mac-address;
      description
        "Multi-Link Device link address";
    }
  }

  grouping st-rogue-client-data {
    description
      "Operational data fields for a detected rogue wireless client";
    leaf rogue-client-address {
      type yang:mac-address;
      description
        "Mac Address of Rogue Station";
    }
    leaf rogue-client-bssid {
      type yang:mac-address;
      description
        "BSSID (Basic Service Set Identifier) of the rogue access point to which the rogue client is associated";
    }
    leaf rogue-client-gateway {
      type yang:mac-address;
      description
        "Indicates the MAC address of the rogue access point client gateway";
    }
    leaf rogue-client-state {
      type wireless-enum-types:rogue-state;
      description
        "Indicates the current state of the rogue client";
    }
    leaf rogue-client-containment-level {
      type uint32;
      description
        "If the state of the rogue is contained, this specifies
         the level of containment.  Higher the level, more the
         number of detecting APs that are used to contain it.
         The value must be between 1 to 4 for 'contained'
         state.";
    }
    leaf actual-containment {
      type uint32;
      description
        "Actual number of access points currently containing the rogue client";
    }
    leaf containment-type {
      type wireless-rogue-oper:enm-rogue-containment-type;
      description
        "Indicates the containment mode applied to this rogue client
         if it is in 'contained' state.
          A value of '0' indicates invalid containment mode.
          A value of '1' indicates deauthentication broadcast used for containment.
          A value of '2' indicates CFP containment.
          A value of '3' indicates client containment.
          A value of '4' indicates adhoc containment.
          A value of '5' indicates max value i.e invalid.
          A value of '99' indicates unknown containment type.";
    }
    leaf rogue-client-if-num {
      type uint32;
      description
        "Interface number associated with the rogue client";
    }
    leaf rogue-client-ipv4-addr {
      type inet:ipv4-address;
      description
        "Rogue Client IPv4 address.";
    }
    leaf rogue-client-ipv6-addr {
      type inet:ipv6-address;
      description
        "Specifies the IPv6 address assigned to the detected rogue client device";
    }
    leaf manual-contained {
      type boolean;
      description
        "Indicates whether this rogue client has been manually contained by an administrator (true) or not (false)";
    }
    leaf contained {
      type boolean;
      description
        "Indicates whether this rogue client is currently contained (true) or not (false) by the wireless network security system";
    }
    leaf aaa-check {
      type boolean;
      description
        "AAA Validation Status of this rogue client";
    }
    leaf cmx-check {
      type boolean;
      description
        "CMX Validation Status of this rogue client";
    }
    leaf rogue-client-first-timestamp {
      type yang:date-and-time;
      description
        "Time Stamp when this Rogue was First Detected.";
    }
    leaf rogue-client-last-timestamp {
      type yang:date-and-time;
      description
        "Time Stamp when this Rogue was Last Detected.";
    }
    leaf n-lrads {
      type uint32;
      description
        "Total number of Airespace APs that detected this rogue.";
    }
    container last-heard-lrad-key {
      description
        "Specifies the key identifying the last local radio access device (AP interface) that detected this rogue client";
      uses wireless-rogue-oper:st-rogue-lrad-key;
    }
    container history {
      description
        "Event history for this rogue client";
      uses event-history-types:event-history;
    }
    leaf parent-rogue-data-address {
      type yang:mac-address;
      description
        "Mac Address of the rogue AP address this client is connected to";
    }
    list rogue-client-lrad {
      key "lrad-mac-addr slot-id";
      description
        "Local Radio that detected this rogue";
      uses wireless-rogue-oper:st-rogue-client-lrad;
      uses wireless-rogue-oper:st-rogue-lrad-key;
    }
    container band-data-2dot4g {
      description
        "Rogue AP 2.4GHz band-specific data";
      uses wireless-rogue-oper:st-rogue-client-data-per-band;
    }
    container band-data-5g {
      description
        "Rogue AP 5GHz band-specific data";
      uses wireless-rogue-oper:st-rogue-client-data-per-band;
    }
    container band-data-6g {
      description
        "Rogue AP 6GHz band-specific data";
      uses wireless-rogue-oper:st-rogue-client-data-per-band;
    }
    leaf mld-record {
      type wireless-rogue-oper:enm-rogue-mld-rec-type;
      description
        "Type of Multi-Link Device (MLD) record associated with the rogue client, indicating the MLD status or role";
    }
    leaf mld-mac {
      type yang:mac-address;
      description
        "MAC address of the Multi-Link Device (MLD) associated with this rogue client";
    }
    leaf rogue-ap-mld-mac {
      type yang:mac-address;
      description
        "Multi-Link Device MAC of Rogue AP of Rogue Client";
    }
  }

  grouping st-rogue-client-lrad {
    description
      "Local Radio that detected this rogue";
    leaf last-heard {
      type yang:date-and-time;
      description
        "Timestamp indicating when this rogue client was last detected by this AP";
    }
    leaf name {
      type string;
      description
        "Name of Airespace AP Interface that detected the Rogue.";
    }
    container rssi {
      description
        "RSSI seen by Airespace AP Interface from the Rogue";
      uses wireless-rogue-oper:st-rogue-signal;
    }
    container snr {
      description
        "SNR seen by Airespace AP Interface from Rogue";
      uses wireless-rogue-oper:st-rogue-signal;
    }
    leaf channel {
      type uint32;
      description
        "The advertised Channel Number of that the
         Airespace AP Interface picked up from the Rogue.";
    }
    leaf band-id {
      type uint8;
      description
        "Identifier for the frequency band (such as 2.4 GHz, 5 GHz, or 6 GHz) used by the local radio that detected the rogue client";
    }
    leaf num-slots {
      type uint32;
      description
        "Number of slots in this AP";
    }
    leaf contain-slot-id {
      type wireless-enum-types:slot-id-type;
      description
        "Slot performing containment ";
    }
    leaf contain-radio-type {
      type uint32;
      description
        "Radio type for containment";
    }
    leaf contain-result {
      type wireless-rogue-oper:enm-rogue-validation-result;
      description
        "Last containment result.";
    }
    leaf phy-ap-slot {
      type uint8;
      description
        "Manageability AP slot of the reporting LRAD";
    }
    leaf mld-link-mac {
      type yang:mac-address;
      description
        "MLD-Link Device MAC of MLD Rogue Client";
    }
    leaf rogue-ap-mld-link-mac {
      type yang:mac-address;
      description
        "MLD-Link Device MAC of Rogue AP this MLD Rogue Client is associated with";
    }
  }

  grouping st-rogue-containment-params {
    description
      "Parameters of ongoing containments";
    leaf rogue-mac-address {
      type yang:mac-address;
      description
        "Mac Address of the Rogue";
    }
    leaf bssid {
      when "(../containment-type='client-deauth') or (../containment-type='adhoc-deauth')";
      type yang:mac-address;
      description
        "BSSID of the rogue";
    }
    leaf containment-type {
      type wireless-rogue-oper:enm-rogue-containment-type;
      description
        "Type of containment action being applied to the rogue device (e.g., client deauthentication, ad-hoc deauthentication)";
    }
    leaf-list chans {
      type uint8;
      ordered-by user;
      description
        "List of wireless channels on which containment actions are performed against the rogue device";
    }
    leaf detecting-slot-id {
      type wireless-enum-types:slot-id-type;
      description
        "The slot that detected the Rogue";
    }
    leaf band-id {
      type uint8;
      description
        "Band for this containment";
    }
    leaf mld-link {
      type boolean;
      description
        "BSSID and Rogue MAC fields are MLD-Link MAC addresses";
    }
  }

  grouping st-rogue-containment-lrad {
    description
      "Local Radio performing containment";
    leaf n-contained {
      type uint32;
      description
        "Number of active containments on this Local Radio";
    }
    list params {
      key "rogue-mac-address";
      description
        "List of parameters used for rogue containment, including details such as rogue MAC address, BSSID, containment type, channels, and detection information";
      uses wireless-rogue-oper:st-rogue-containment-params;
    }
  }

  grouping st-rogue-stats {
    description
      "Rogue feature statistics";
    leaf restart-count {
      type uint32;
      description
        "Number of process restarts";
    }
    leaf pending-count {
      type uint32;
      description
        "Number of rogue AP in pending state.";
    }
    leaf lrad-count {
      type uint32;
      description
        "Number of rogue AP in LRAD state.";
    }
    leaf on-my-network-count {
      type uint32;
      description
        "Number of rogue AP in my network.";
    }
    leaf adhoc-count {
      type uint32;
      description
        "Number of ad-hoc rogue APs.";
    }
    leaf unknown-count {
      type uint32;
      description
        "Number of unknown rogue APs.";
    }
    leaf unclassified-count {
      type uint32;
      description
        "Number of unclassified rogue APs.";
    }
    leaf malicious-count {
      type uint32;
      description
        "Number of malicious rogue APs.";
    }
    leaf friendly-count {
      type uint32;
      description
        "Specifies the number of detected rogue access points that are classified as friendly (known or authorized APs operating in the environment but not managed by the controller)";
    }
    leaf custom-count {
      type uint32;
      description
        "Specifies the number of rogue access points that have been classified as custom based on user-defined criteria or policies";
    }
    leaf not-adhoc-count {
      type uint32;
      description
        "Specifies the number of detected rogue access points that are not operating in ad-hoc mode (infrastructure mode only)";
    }
    leaf total-count {
      type uint32;
      description
        "Number of rogue APs in total";
    }
    leaf contained-count {
      type uint32;
      description
        "Number of contained rogue APs";
    }
    leaf contained-client-count {
      type uint32;
      description
        "Number of contained rogue clients";
    }
    leaf contained-pending-count {
      type uint32;
      description
        "Number of containment-pending rogue APs";
    }
    leaf contained-pending-client-count {
      type uint32;
      description
        "Number of containment-pending rogue clients";
    }
    leaf total-client-count {
      type uint32;
      description
        "Number of rogue clients in total.";
    }
    leaf max-count {
      type uint32;
      description
        "Number of rogue APs that system can support.";
    }
    leaf max-client-count {
      type uint32;
      description
        "Number of rogue clients that system can support.";
    }
    leaf report-count {
      type uint64;
      description
        "Number of IAPP AP reports received.";
    }
    leaf client-report-count {
      type uint64;
      description
        "Number of IAPP Client reports received.";
    }
    leaf rate-report-count {
      type uint32;
      description
        "Number of IAPP AP reports received in last minute.";
    }
    leaf rate-client-report-count {
      type uint32;
      description
        "Number of IAPP Client reports received in last minute.";
    }
    leaf iapp-ap-pkt {
      type uint64;
      description
        "Number of IAPP AP packets received";
    }
    leaf iapp-client-pkt {
      type uint64;
      description
        "Number of IAPP Client packets received";
    }
    leaf rate-iapp-ap-pkt {
      type uint32;
      description
        "Number of IAPP AP packets received in last minute";
    }
    leaf rate-iapp-client-pkt {
      type uint32;
      description
        "Number of IAPP Client packets received in last minute";
    }
    leaf rldp-count {
      type uint64;
      status deprecated;
      description
        "Number of RLDP (Rogue Location Discovery Protocol) procedures started";
    }
    leaf aaa-msg-rx-count {
      type uint64;
      description
        "Number of AAA messages received";
    }
    leaf aaa-msg-tx-count {
      type uint64;
      description
        "Number of AAA messages sent";
    }
    leaf snmp-traps-tx-count {
      type uint64;
      description
        "Number of SNMP traps sent";
    }
    leaf lrad-off-count {
      type uint64;
      description
        "Number of events where a local radio (LRAD) was turned off";
    }
    leaf ap-create-count {
      type uint64;
      description
        "Number of AP create events.";
    }
    leaf ap-delete-count {
      type uint64;
      description
        "Number of AP delete events.";
    }
    leaf ap-radio-up-count {
      type uint64;
      description
        "Number of AP Radio Up events.";
    }
    leaf ap-radio-down-count {
      type uint64;
      description
        "Number of AP Radio Down events.";
    }
    leaf ap-name-change-count {
      type uint32;
      description
        "Number of AP Name Change events.";
    }
    leaf wncd-ipc-tx-count {
      type uint64;
      description
        "Number of inter-process communication (IPC) messages sent to Wireless Network Control Daemons (WNCDs) by the rogue detection subsystem";
    }
    leaf wncd-ipc-rx-count {
      type uint64;
      description
        "Number of IPCs from WNCDs received.";
    }
    leaf wncmgr-ipc-rx-count {
      type uint64;
      description
        "Number of IPCs from WNCMGR received.";
    }
    leaf ios-ipc-tx-count {
      type uint64;
      description
        "Number of IPCs to IOS sent.";
    }
    leaf ios-ipc-rx-count {
      type uint64;
      description
        "Number of IPCs from IOS received.";
    }
    leaf nmspd-ipc-tx-count {
      type uint64;
      description
        "Number of IPCs to NMSPD sent.";
    }
    leaf nmspd-ipc-rx-count {
      type uint64;
      description
        "Number of IPCs from NMSPD received.";
    }
    leaf contain-msg-count {
      type uint64;
      description
        "Number of containment messages sent to Access Points (APs) as part of rogue device mitigation";
    }
    leaf fsm-errors {
      type uint32;
      description
        "Number of finite state machine (FSM) errors encountered during rogue detection or mitigation processes";
    }
    leaf trap-errors {
      type uint32;
      description
        "Number of SNMP TRAP errors encountered during rogue device monitoring or reporting";
    }
    container enq-count {
      description
        "Container for counters tracking the number of objects enqueued for processing in the rogue detection or mitigation workflow";
      uses event-history-types:dynamic-counter;
    }
    leaf similar-ap-report-count {
      type uint64;
      description
        "Number of very-similar AP reports.";
    }
    leaf similar-client-report-count {
      type uint64;
      description
        "Number of very-similar client reports";
    }
    container snmp-traps-per-type {
      description
        "Container for counters tracking the number of SNMP traps sent per trap type for rogue operational events";
      uses event-history-types:dynamic-counter;
    }
    leaf iapp-report-messages-load-shedded {
      type uint32;
      description
        "Number of IAPP report messages not processed due to rx IPC too-high occupancy.";
    }
    leaf managed-client-message-count {
      type uint32;
      description
        "Number of client join/leave messages.";
    }
    leaf managed-client-join-count {
      type uint32;
      description
        "Number of join events for managed clients";
    }
    leaf managed-client-leave-count {
      type uint32;
      description
        "Number of client leaving the run state events.";
    }
    leaf managed-rogue-client-count {
      type uint32;
      description
        "Number of managed clients matching rogue clients.";
    }
    container proc-time {
      description
        "Per-processing-type average processing time statistics";
      uses event-history-types:dynamic-counter;
    }
    container global-history {
      description
        "Global Event History";
      uses event-history-types:event-history;
    }
    leaf tbl-apf-vap-cache-reload-count {
      type uint32;
      description
        "Count of APF VAP SSID cache reloads.";
    }
    leaf new-lrad-count {
      type uint64;
      description
        "Number of times a new LRAD has been added";
    }
    leaf lrad-purge-count {
      type uint64;
      description
        "Specifies the total number of local radio (LRAD) purge events that have occurred";
    }
    leaf rssi-change-count {
      type uint64;
      description
        "Indicates the number of events where the Received Signal Strength Indicator (RSSI) value for a rogue device has changed";
    }
    leaf final-state-change-count {
      type uint64;
      description
        "Specifies the number of times the final classification state of a rogue device has changed during monitoring";
    }
    leaf contain-level-change-count {
      type uint64;
      description
        "Indicates the number of times the containment level for a rogue device has changed, reflecting adjustments in the mitigation actions applied";
    }
    leaf class-change-count {
      type uint64;
      description
        "Specifies the number of times the classification type of a rogue device (such as friendly, malicious, or unknown) has changed";
    }
    leaf adhoc-change-count {
      type uint64;
      description
        "Indicates the number of times the status of a rogue device being identified as an ad-hoc network has changed";
    }
    leaf on-my-network-change-count {
      type uint64;
      description
        "Specifies the number of times the status indicating whether a rogue device is detected on the local network has changed";
    }
    leaf n-clients-changed-count {
      type uint64;
      description
        "Number of times the client-number has changed";
    }
    leaf client-new-lrad-count {
      type uint64;
      description
        "Specifies the number of times a new rogue client has been detected by a local radio (LRAD)";
    }
    leaf client-lrad-purge-count {
      type uint64;
      description
        "Indicates the number of times rogue client entries have been purged from local radios (LRADs)";
    }
    leaf client-rssi-change-count {
      type uint64;
      description
        "Number of client RSSI change events";
    }
    leaf client-final-state-change-count {
      type uint64;
      description
        "Number of times the final client state has changed";
    }
    leaf client-contain-level-change-count {
      type uint64;
      description
        "Number of times the client containment level has changed";
    }
    leaf client-channel-change-count {
      type uint64;
      description
        "Number of events where a rogue client has changed its operating wireless channel";
    }
    leaf client-ip-change-count {
      type uint64;
      description
        "Number of events where a rogue client has changed its IP address";
    }
    leaf client-roam-count {
      type uint64;
      description
        "Number of rogue-client-roam events";
    }
    leaf rogue-ap-reports-dropped-scale {
      type uint64;
      description
        "Number of rogue AP reports dropped due to max. scale reached";
    }
    leaf rogue-client-reports-dropped-scale {
      type uint64;
      description
        "Number of rogue client reports dropped due to max. scale reached";
    }
    leaf rogue-client-reports-dropped-no-parent {
      type uint64;
      description
        "Number of rogue client reports dropped due to missing parent rogue AP";
    }
    leaf rogue-enabled {
      type boolean;
      description
        "Indicates whether the rogue detection feature is enabled and actively listening on port 5247";
    }
    leaf mm-ipc-rx-count {
      type uint64;
      description
        "Number of IPCs from Mobilityd received.";
    }
    leaf rogue-wsa-events-triggered-counter {
      type uint64;
      description
        "Number of Rogue WSA events triggered";
    }
    leaf rogue-wsa-events-enqueued-counter {
      type uint64;
      description
        "Number of Rogue WSA events enqueued";
    }
    container rogue-wsa-events-triggered-per-type {
      description
        "Container for counters representing the number of Wireless Assurance (WSA) events triggered per rogue event type";
      uses event-history-types:dynamic-counter;
    }
    container rogue-wsa-events-enqueued-per-type {
      description
        "Container for counters representing the number of Wireless Assurance (WSA) events enqueued for each rogue event type";
      uses event-history-types:dynamic-counter;
    }
    leaf bssid-ipc-count {
      type uint64;
      description
        "Number of BSSID cache update events.";
    }
    leaf ap-channel-change-count {
      type uint64;
      description
        "Number of AP channel change events.";
    }
    leaf beacon-ds-attack-count {
      type uint64;
      description
        "Number of Beacon DS attacks detected.";
    }
    leaf internal-count {
      type uint32;
      description
        "Number of rogue APs in internal state.";
    }
    leaf external-count {
      type uint32;
      description
        "Number of rogue APs in external state.";
    }
    leaf alert-count {
      type uint32;
      description
        "Number of rogue APs in alert state.";
    }
    leaf threat-count {
      type uint32;
      description
        "Number of rogue APs in threat state.";
    }
    leaf rogue-ap-report-false-drop {
      type uint64;
      description
        "Number of rogue AP reports dropped because they might be falsely reported neighbor APs.";
    }
    leaf adhoc-unknown-count {
      type uint32;
      description
        "Number of unknown ad-hoc rogue APs";
    }
    leaf adhoc-unclassified-count {
      type uint32;
      description
        "Number of unclassified ad-hoc rogue APs";
    }
    leaf adhoc-malicious-count {
      type uint32;
      description
        "Number of malicious ad-hoc rogue APs";
    }
    leaf adhoc-friendly-count {
      type uint32;
      description
        "Number of friendly ad-hoc rogue APs";
    }
    leaf adhoc-custom-count {
      type uint32;
      description
        "Number of custom ad-hoc rogue APs";
    }
    leaf malicious-init-count {
      type uint32;
      description
        "Number of malicious rogue APs in init state";
    }
    leaf custom-init-count {
      type uint32;
      description
        "Number of custom rogue APs in init state";
    }
    leaf unclassified-init-count {
      type uint32;
      description
        "Number of unclassified rogue APs in init state";
    }
    leaf friendly-init-count {
      type uint32;
      description
        "Number of friendly rogue APs in init state";
    }
    leaf unknown-init-count {
      type uint32;
      description
        "Number of unknown rogue APs in init state";
    }
    leaf init-count {
      type uint32;
      description
        "Total number of rogue APs in init state";
    }
    leaf post-init-count {
      type uint32;
      description
        "Total number of rogue APs in post init state";
    }
    leaf max-init-count {
      type uint32;
      description
        "Maximum number of rogue APs in init state";
    }
    leaf total-malicious-count {
      type uint32;
      description
        "Total number of rogue access points (APs) that have been classified as malicious";
    }
    leaf total-custom-count {
      type uint32;
      description
        "Total number of rogue access points (APs) that have been classified as custom";
    }
    leaf total-unclassified-count {
      type uint32;
      description
        "Total number of rogue access points (APs) that have not been classified";
    }
    leaf total-friendly-count {
      type uint32;
      description
        "Total number of rogue access points (APs) that have been classified as friendly";
    }
    leaf total-unknown-count {
      type uint32;
      description
        "Total number of rogue access points (APs) that have been classified as unknown";
    }
    leaf rogue-ap-mld-link-count {
      type uint32;
      description
        "Total number of Rogue AP backward compatible MLD-Link records";
    }
    leaf rogue-client-mld-link-cnt {
      type uint32;
      description
        "Total number of Rogue Client backward compatible MLD-Link records";
    }
    leaf ap-drop-mld-mismatch {
      type uint64;
      description
        "Total number of rogue AP reports dropped due to MLD / Non-MLD type mismatch";
    }
    leaf client-drop-mld-mismatch {
      type uint64;
      description
        "Total number of rogue AP reports dropped due to MLD / Non-MLD type mismatch";
    }
    leaf iapp-unconnected-client {
      type uint64;
      description
        "Number of IAPP Unconnected Client packets received";
    }
    leaf unconnected-client-report {
      type uint64;
      description
        "Number of IAPP (Inter-Access Point Protocol) reports received regarding unconnected clients detected as potential rogues";
    }
    leaf unconnected-client-count {
      type uint64;
      description
        "Total number of unconnected clients detected by the rogue detection system";
    }
    leaf unconnected-reports-drop {
      type uint64;
      description
        "Number of unconnected clients dropped due to max. scale reached";
    }
    leaf ap-drop-urwb-link {
      type uint64;
      description
        "Total number of rogue AP reports dropped due to URWB link address reported as rogue AP";
    }
  }

  grouping st-rogue-link2mld {
    description
      "Multi-Link Device Rogue AP - mapping of link address to MLD address";
    leaf link {
      type yang:mac-address;
      description
        "Link Address of Multi-Link Device Rogue AP";
    }
    leaf mld {
      type yang:mac-address;
      description
        "Multi-Link Device address of Rogue AP";
    }
  }

  grouping st-rogue-client-link2mld {
    description
      "Multi-Link Device Rogue client - mapping of link address to MLD address";
    leaf link {
      type yang:mac-address;
      description
        "Link Address of Multi-Link Device Rogue client";
    }
    leaf mld {
      type yang:mac-address;
      description
        "Multi-Link Device address of Rogue client";
    }
  }

  grouping st-rldp-stats {
    description
      "Rogue Location Discovery Protocol (RLDP) feature statistics";
    leaf num-in-progress {
      type uint32;
      description
        "Total number of in-progress Rogue Location Discovery Protocol requests";
    }
    leaf num-rldp-started {
      type uint32;
      description
        "Total number of Rogue Location Discovery Protocol requests";
    }
    leaf auth-timeout {
      type uint32;
      units "seconds";
      description
        "Specifies the timeout period, in seconds, for authentication attempts during RLDP (Rogue Location Discovery Protocol) operations";
    }
    leaf assoc-timeout {
      type uint32;
      units "seconds";
      description
        "Specifies the timeout period, in seconds, for association attempts during RLDP (Rogue Location Discovery Protocol) operations";
    }
    leaf dhcp-timeout {
      type uint32;
      units "seconds";
      description
        "Specifies the timeout period, in seconds, for DHCP or ARP operations during RLDP (Rogue Location Discovery Protocol) processing";
    }
    leaf not-connected {
      type uint32;
      description
        "Number of RLDP (Rogue Location Discovery Protocol) attempts where the client was not connected to the network";
    }
    leaf connected {
      type uint32;
      description
        "Number of RLDP (Rogue Location Discovery Protocol) attempts where the client was successfully connected to the network";
    }
    leaf rldp-socket-enabled {
      type boolean;
      description
        "Rogue Location Discovery Protocol socket on port 6352 is enabled";
    }
  }

  grouping st-rldp-ap {
    description
      "Access point that is performing Rogue Location Discovery Protocol (RLDP)";
    leaf ap-mac {
      type yang:mac-address;
      description
        "MAC address of the access point (AP) performing Rogue Location Discovery Protocol (RLDP)";
    }
    leaf slot-id {
      type wireless-enum-types:slot-id-type;
      description
        "Slot ID of the managed AP";
    }
    leaf rogue-ap-mac {
      type yang:mac-address;
      description
        "Rogue mac address against which RLDP is executed";
    }
    leaf rogue-channel {
      type uint32;
      description
        "Channel used to run RLDP";
    }
    leaf rogue-chan-width-label {
      type uint16;
      description
        "Label indicating the channel width used by the rogue access point (AP) during Rogue Location Discovery Protocol (RLDP) operation";
    }
  }

  container rogue-oper-data {
    config false;
    description
      "Container for operational data related to rogue access points detected and managed by the wireless controller";
    container rogue-stats {
      presence "rogue-stats";
      description
        "Statistics related to the detection and classification of rogue access points in the wireless network";
      uses wireless-rogue-oper:st-rogue-stats;
    }
    list rogue-link2mld {
      key "link";
      description
        "Rogue AP link address to Multi-Link Device Address map";
      uses wireless-rogue-oper:st-rogue-link2mld;
    }
    list rogue-client-link2mld {
      key "link";
      description
        "Rogue client link address to Multi-Link Device Address map";
      uses wireless-rogue-oper:st-rogue-client-link2mld;
    }
    list rogue-data {
      key "rogue-address";
      description
        "List of detected rogue access points and their associated operational data";
      uses wireless-rogue-oper:st-rogue-data;
    }
    list rogue-client-data {
      key "rogue-client-address";
      description
        "List of rogue wireless clients detected by the system, containing operational data for each rogue client";
      uses wireless-rogue-oper:st-rogue-client-data;
    }
    list rogue-containment-lrad {
      key "lrad-mac-addr slot-id";
      description
        "Local Radio Performing Containment";
      uses wireless-rogue-oper:st-rogue-containment-lrad;
      uses wireless-rogue-oper:st-rogue-lrad-key;
    }
    list rldp-ap {
      key "ap-mac";
      status deprecated;
      description
        "List of access points (APs) that are currently performing Rogue Location Discovery Protocol (RLDP) operations";
      uses wireless-rogue-oper:st-rldp-ap;
    }
    container rldp-stats {
      presence "rldp-stats";
      status deprecated;
      description
        "Statistics related to the operation and performance of the Rogue Location Discovery Protocol (RLDP) feature";
      uses wireless-rogue-oper:st-rldp-stats;
    }
    list rogue-unconnected-data {
      key "client-mac";
      description
        "List of rogue wireless clients detected by the system that are not currently connected to the network";
      uses wireless-rogue-oper:st-rogue-unconnected-data;
    }
  }
}
