module Cisco-IOS-XE-bgp-nbr-oper {
  yang-version 1.1;
  namespace "http://cisco.com/ns/yang/Cisco-IOS-XE-bgp-nbr-oper";
  prefix bgp-nbr-ios-xe-oper;

  import Cisco-IOS-XE-common-types {
    prefix common-types-ios-xe;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for bgp neighbor operational data and Counters.
     Copyright (c) 2024-2026 by Cisco Systems, Inc.
     All rights reserved.";

  revision 2026-08-01 {
    description
      "Updated descriptions of several model elements to clarify their meaning and purpose";
    reference
      "1.0.1";
    cisco-semver:module-version "1.0.1";
  }
  revision 2025-07-01 {
    description
      "Initial revision";
    reference
      "1.0.0";
    cisco-semver:module-version "1.0.0";
  }

  typedef bgp-conn-mode {
    type enumeration {
      enum mode-active {
        value 0;
        description
          "Active connection";
      }
      enum mode-passive {
        value 1;
        description
          "Passive connection";
      }
    }
    description
      "BGP mode";
  }

  typedef tcp-fsm-state-neighbor {
    type enumeration {
      enum bgp-tcp-closed {
        value 0;
        description
          "No connection";
      }
      enum bgp-tcp-listen {
        value 1;
        description
          "Waiting for a connection request from any remote TCP";
      }
      enum bgp-tcp-synsent {
        value 2;
        description
          "Waiting for a matching connection request after having sent a connection request";
      }
      enum bgp-tcp-synrcvd {
        value 3;
        description
          "Waiting for a confirming connection request acknowledgment after having both received and sent a connection request";
      }
      enum bgp-tcp-est {
        value 4;
        description
          "connection established";
      }
      enum bgp-tcp-finwait1 {
        value 5;
        description
          "Waiting for a connection termination request from the remote TCP, or an acknowledgment of the connection termination request previously sent";
      }
      enum bgp-tcp-finwait2 {
        value 6;
        description
          "Waiting for a connection termination request from the remote TCP";
      }
      enum bgp-tcp-closewait {
        value 7;
        description
          "Waiting for a connection termination request from the local use";
      }
      enum bgp-tcp-lastack {
        value 8;
        description
          "Waiting for an acknowledgment of the connection termination request previously sent to the remote TCP";
      }
      enum bgp-tcp-closing {
        value 9;
        description
          "Waiting for a connection termination request acknowledgment from the remote";
      }
      enum bgp-tcp-timewait {
        value 10;
        description
          "Waiting for enough time to pass to be sure the remote TCP received the acknowledgment of its connection termination request";
      }
    }
    description
      "TCP FSM State";
  }

  typedef neighbor-afi-safi {
    type enumeration {
      enum af-ipv4-mdt {
        value 0;
        description
          "ipv4-mdt";
      }
      enum af-ipv4-multicast {
        value 1;
        description
          "ipv4-multicast";
      }
      enum af-ipv4-unicast {
        value 2;
        description
          "ipv4-unicast";
      }
      enum af-ipv4-mvpn {
        value 3;
        description
          "ipv4-mvpn";
      }
      enum af-ipv4-flowspec {
        value 4;
        description
          "ipv4-flowspec";
      }
      enum af-ipv6-multicast {
        value 5;
        description
          "ipv6-multicast";
      }
      enum af-ipv6-unicast {
        value 6;
        description
          "ipv6-unicast";
      }
      enum af-ipv6-mpvn {
        value 7;
        description
          "ipv6-mpvn";
      }
      enum af-ipv6-flowspec {
        value 8;
        description
          "ipv6-flowspec";
      }
      enum af-l2vpn-vpls {
        value 9;
        description
          "l2vpn-vpls";
      }
      enum af-l2vpn-evpn {
        value 10;
        description
          "l2vpn-evpn";
      }
      enum af-nsap-unicast {
        value 11;
        description
          "nsap-unicast";
      }
      enum af-rtfilter-unicast {
        value 12;
        description
          "rtfilter-unicast";
      }
      enum af-vpnv4-multicast {
        value 13;
        description
          "vpnv4-multicast";
      }
      enum af-vpnv4-unicast {
        value 14;
        description
          "vpnv4-unicast";
      }
      enum af-vpnv6-unicast {
        value 15;
        description
          "vpnv6-unicast";
      }
      enum af-vpnv6-multicast {
        value 16;
        description
          "vpnv6-multicast";
      }
      enum af-vpnv4-flowspec {
        value 17;
        description
          "vpnv4-flowspec";
      }
      enum af-vpnv6-flowspec {
        value 18;
        description
          "vpnv6-flowspec";
      }
    }
    description
      "Address family under which the neighbor is activated";
  }

  typedef bgp-link-neighbor {
    type enumeration {
      enum link-int {
        value 0;
        description
          "iBGP neighbors";
      }
      enum link-ext {
        value 1;
        description
          "eBGP neighbors";
      }
    }
    description
      "Operational state relevant to bgp global neighbor";
  }

  typedef bgp-neighbor-state {
    type enumeration {
      enum fsm-idle {
        value 0;
        description
          "Neighbor is in idle state";
      }
      enum fsm-connect {
        value 1;
        description
          "Neighbor is in connect state";
      }
      enum fsm-active {
        value 2;
        description
          "Neighbor is in active state";
      }
      enum fsm-opensent {
        value 3;
        description
          "Neighbor is in openSent state";
      }
      enum fsm-openconfirm {
        value 4;
        description
          "Neighbor is in openConfirm state";
      }
      enum fsm-est {
        value 5;
        description
          "Neighbor is in established state";
      }
      enum fsm-nonnego {
        value 6;
        description
          "Neighbor is non negotiated state";
      }
    }
    description
      "BGP FSM State";
  }

  typedef bgp-reset-reason {
    type enumeration {
      enum brs-prot-init {
        value 0;
        description
          "BGP protocol initialization";
      }
      enum brs-no-memory {
        value 1;
        description
          "No memory";
      }
      enum brs-notif-received {
        value 2;
        description
          "BGP Notification received";
      }
      enum brs-notif-sent {
        value 3;
        description
          "BGP Notification sent";
      }
      enum brs-user-reset {
        value 4;
        description
          "User reset";
      }
      enum brs-peer-timeout {
        value 5;
        description
          "Peer timeout";
      }
      enum brs-conn-collision-err {
        value 6;
        description
          "Error during connection collision";
      }
      enum brs-closed-sess {
        value 7;
        description
          "Peer closed the session";
      }
      enum brs-over-prfx-limit {
        value 8;
        description
          "Peer over prefix limit";
      }
      enum brs-max-prfx-rstrt-timeout {
        value 9;
        description
          "Maximum-Prefix restart timeout";
      }
      enum brs-interface-flap {
        value 10;
        description
          "Interface flap";
      }
      enum brs-router-id-chng {
        value 11;
        description
          "Router ID changed";
      }
      enum brs-nbr-deleted {
        value 12;
        description
          "Neighbor deleted";
      }
      enum brs-nbr-reset {
        value 13;
        description
          "Neighbor reset";
      }
      enum brs-active-open-failed {
        value 14;
        description
          "Active open failed";
      }
      enum brs-remote-conn-failed {
        value 15;
        description
          "Remote connection failed";
      }
      enum brs-member-added-to-pg {
        value 16;
        description
          "Member added to peer-group";
      }
      enum brs-admin-shutdown {
        value 17;
        description
          "Admin. shutdown";
      }
      enum brs-remote-as-chng {
        value 18;
        description
          "Remote AS changed";
      }
      enum brs-cap-chng {
        value 19;
        description
          "Capability changed";
      }
      enum brs-rr-config-chng {
        value 20;
        description
          "Route-reflector client config changed";
      }
      enum brs-aigp-config-chng {
        value 21;
        description
          "AIGP config change";
      }
      enum brs-soft-reconfig-chng {
        value 22;
        description
          "Soft re-config change";
      }
      enum brs-local-as-chng {
        value 23;
        description
          "Local AS change";
      }
      enum brs-address-family-activated {
        value 24;
        description
          "Address family activated";
      }
      enum brs-vrf-config-chng {
        value 25;
        description
          "VRF config change";
      }
      enum brs-allowas-in-chng {
        value 26;
        description
          "Allow-as in change";
      }
      enum brs-as-override-chng {
        value 27;
        description
          "AS-override change";
      }
      enum brs-nsf-sess-rstrt-timeout {
        value 28;
        description
          "NSF session restart timeout";
      }
      enum brs-nsf-closed-session {
        value 29;
        description
          "NSF peer closed the session";
      }
      enum brs-nsf-switch {
        value 30;
        description
          "NSF Switchover";
      }
      enum brs-nsf-gr-reload {
        value 31;
        description
          "NSF GR RELOAD";
      }
      enum brs-cluster-id-chng {
        value 32;
        description
          "Cluster ID changed";
      }
      enum brs-route-to-peer-lost {
        value 33;
        description
          "Route to peer lost";
      }
      enum brs-bfd-adjacency-down {
        value 34;
        description
          "BFD adjacency down";
      }
      enum brs-max-path-limit {
        value 35;
        description
          "Maximum path limit is reached";
      }
      enum brs-sso-disabled {
        value 36;
        description
          "SSO Disabled";
      }
      enum brs-pass-send-open-failed {
        value 37;
        description
          "Passive send open failed";
      }
      enum brs-afi-safi-not-supported {
        value 38;
        description
          "AFI/SAFI not supported";
      }
      enum brs-upd-src-chng {
        value 39;
        description
          "Update source changed";
      }
      enum brs-sso-connection-coll-on-standby {
        value 40;
        description
          "SSO connection collision on standby";
      }
      enum brs-unknown-path-error {
        value 41;
        description
          "Unknown path error";
      }
      enum brs-prefix-storage-size-chng {
        value 42;
        description
          "Prefix Storage Size changed";
      }
      enum brs-route-server-context-chng {
        value 43;
        description
          "Route server context changed";
      }
      enum brs-int-vpn-client-chng {
        value 44;
        description
          "Internal VPN Client changed";
      }
      enum brs-legacy-rt-config-chng {
        value 45;
        description
          "Legacy RT config change";
      }
      enum brs-tcp-ao-config-chng {
        value 46;
        description
          "TCP AO config change";
      }
      enum brs-split-horizon-config-chng {
        value 47;
        description
          "split-horizon config change";
      }
      enum brs-l-unicast-config-chng {
        value 48;
        description
          "labeled-unicast configuration changed";
      }
      enum brs-never-reset {
        value 49;
        description
          "This neighbor was never reset";
      }
    }
    description
      "BGP Neighbor reset reasons";
  }

  typedef bgp-encaps-pref-neighbor {
    type enumeration {
      enum encaps-unset {
        value 0;
        description
          "Encapsulation preference is not set";
      }
      enum encaps-any {
        value 1;
        description
          "No encapsulation is preferred";
      }
      enum encaps-vxlan-if-vtep-up {
        value 2;
        description
          "Use VxLAN if VTEP is UP else use MPLS";
      }
      enum encaps-vxlan {
        value 3;
        description
          "Prefer VxLAN encapsulation";
      }
      enum encaps-mpls {
        value 4;
        description
          "Prefer MPLS encapsulation";
      }
    }
    description
      "BGP encapsulation preferences";
  }

  grouping bgp-transport-neighbor {
    description
      "BGP transport information";
    leaf path-mtu-dis {
      type boolean;
      description
        "Indication whether path MTU discovery is enabled";
    }
    leaf local-port {
      type uint16;
      description
        "Local TCP port used for TCP session";
    }
    leaf local-host {
      type inet:ip-address;
      description
        "Local address used for the TCP session";
    }
    leaf foreign-port {
      type uint16;
      description
        "Remote port used by the peer for the TCP session";
    }
    leaf foreign-host {
      type inet:ip-address;
      description
        "Remote address of the BGP session";
    }
    leaf mss {
      type uint16;
      units "bytes";
      description
        "Maximum data segment size for this tcp session in bytes";
    }
    leaf ao-key {
      type string;
      description
        "Name of the key chain for TCP Authentication Option (AO)";
    }
    leaf ao-key-id {
      type int32;
      description
        "ID of the AO key chain";
    }
    leaf ao-incl-tcp-opts {
      type boolean;
      description
        "Indicates whether TCP options are included in the TCP Authentication Option (AO) calculation";
    }
    leaf ao-acc-mis-conn {
      type boolean;
      description
        "Indicates whether TCP Authentication Option (AO) will accept connections with mismatched parameters";
    }
  }

  grouping bgp-connection-neighbor {
    description
      "Data for current BGP connection state";
    leaf state {
      type bgp-nbr-ios-xe-oper:tcp-fsm-state-neighbor;
      description
        "TCP FSM state";
    }
    leaf mode {
      type bgp-nbr-ios-xe-oper:bgp-conn-mode;
      description
        "BGP transport connection mode";
    }
  }

  grouping bgp-connection-counters {
    description
      "Data for current BGP connection counters";
    leaf total-est {
      type uint32;
      description
        "Number of times a TCP and BGP
         connection has been successfully established";
    }
    leaf total-dropped {
      type uint32;
      description
        "Number of times that a valid
         session has failed or been taken down";
    }
    leaf last-reset {
      type yang:date-and-time;
      description
        "Timestamp indicating when the peering session was last reset";
    }
    leaf reset-reason {
      type bgp-nbr-ios-xe-oper:bgp-reset-reason;
      description
        "Reason for the last reset of the BGP neighbor session";
    }
  }

  grouping bgp-message-counters {
    description
      "BGP messages counters";
    leaf opens {
      type uint32;
      description
        "Number of open messages";
    }
    leaf updates {
      type uint32;
      description
        "Number of update messages";
    }
    leaf notifs {
      type uint32;
      description
        "Number of notification messages";
    }
    leaf keepalives {
      type uint32;
      description
        "Number of keepalive messages";
    }
    leaf route-refreshes {
      type uint32;
      description
        "Number of route refresh messages";
    }
  }

  grouping bgp-prefix-counters-neighbor {
    description
      "Grouping for various prefix counters";
    leaf cur-prfx {
      type uint64;
      description
        "Current number of accepted prefixes";
    }
    leaf acc-prfx {
      type uint64;
      description
        "Total number of accepted prefixes";
    }
    leaf imp-with {
      type uint64;
      description
        "Number of times a prefix has been
         withdrawn and readvertised";
    }
    leaf exp-with {
      type uint64;
      description
        "Number of times a prefix has been
         withdrawn because it is no longer feasible";
    }
    leaf bpath {
      type uint64;
      description
        "Number of received prefixes installed as best paths";
    }
    leaf mpath {
      type uint64;
      description
        "Number of received prefixes installed as multipaths";
    }
  }

  grouping negotiated-timers-neighbor {
    description
      "Negotiated timers details";
    leaf hold-time {
      type uint16;
      units "seconds";
      description
        "Negotiated hold time with the neighbor, in seconds";
    }
    leaf keepalive-time {
      type uint16;
      units "seconds";
      description
        "Negotiated keepalive interval with the neighbor, in seconds";
    }
  }

  grouping bgp-af-prefix-activity-neighbor {
    description
      "Address family prefix statistics";
    container sent {
      description
        "Number of prefixes sent";
      uses bgp-nbr-ios-xe-oper:bgp-prefix-counters-neighbor;
    }
    container rcvd {
      description
        "Counts and statistics for prefixes received from the BGP neighbor";
      uses bgp-nbr-ios-xe-oper:bgp-prefix-counters-neighbor;
    }
  }

  grouping bgp-neighbor-counters {
    description
      "Neighbor counters Info";
    leaf inst-prfx {
      type uint32;
      description
        "Number of prefixes received from this neighbor that are currently installed in the local routing table";
    }
    container prfx-act {
      description
        "Statistics and counters related to BGP prefix activity for the neighbor";
      uses bgp-nbr-ios-xe-oper:bgp-af-prefix-activity-neighbor;
    }
    container sent {
      description
        "Counters for BGP protocol messages sent to the neighbor";
      uses bgp-nbr-ios-xe-oper:bgp-message-counters;
    }
    container rcvd {
      description
        "Counters for BGP protocol messages received from the neighbor";
      uses bgp-nbr-ios-xe-oper:bgp-message-counters;
    }
    leaf inq-dep {
      type uint32;
      description
        "Number of messages in the input queue for the BGP neighbor session";
    }
    leaf outq-dep {
      type uint32;
      description
        "Number of messages in the output queue for the BGP neighbor session";
    }
    leaf up-time {
      type yang:date-and-time;
      description
        "When was the session established with the neighbor";
    }
    leaf last-write {
      type yang:date-and-time;
      description
        "Time when the last message was sent to the BGP neighbor";
    }
    leaf last-read {
      type yang:date-and-time;
      description
        "Time when the last message was received from the BGP neighbor";
    }
    container conn-cntrs {
      description
        "TCP connection counters for the neighbor";
      uses bgp-nbr-ios-xe-oper:bgp-connection-counters;
    }
  }

  grouping bgp-neighbor-key {
    description
      "Grouping for neighbor key";
    leaf ip {
      type inet:ip-address;
      description
        "Identifier for the BGP neighbor, typically the neighbor's IP address or router ID";
    }
    leaf if-name {
      type string;
      description
        "Contains interface name if this neighbor is a link-local address, empty otherwise";
    }
    leaf af {
      type bgp-nbr-ios-xe-oper:neighbor-afi-safi;
      description
        "Address family under which the neighbor is activated";
    }
    leaf ni-name {
      type string;
      description
        "Network instance name. If the type is net-inst-default,
         the name is not meaningful";
    }
    leaf ni-type {
      type common-types-ios-xe:net-inst-type;
      description
        "Network instance type. Differentiates between the
         default routing instance and VRFs";
    }
  }

  grouping bgp-neighbor-info {
    description
      "BGP neighbor state information";
    leaf desc {
      type string;
      description
        "User-configured text description assigned to the BGP neighbor";
    }
    leaf as {
      type uint32;
      description
        "BGP neighbor AS number";
    }
    leaf ver {
      type uint16;
      description
        "BGP version being used to communicate
         with the remote router";
    }
    leaf dyn-conf {
      type boolean;
      description
        "Indicates whether this neighbor is dynamically configured";
    }
    leaf link {
      type bgp-nbr-ios-xe-oper:bgp-link-neighbor;
      description
        "Type of BGP neighbor link, indicating whether the peer relationship is internal (iBGP) or external (eBGP)";
    }
    leaf session {
      type bgp-nbr-ios-xe-oper:bgp-neighbor-state;
      description
        "Current BGP finite state machine (FSM) state of the neighbor session (e.g., Idle, Connect, Active, OpenSent, OpenConfirm, Established)";
    }
    container timers {
      description
        "Negotiated timers status of BGP neighbor";
      uses bgp-nbr-ios-xe-oper:negotiated-timers-neighbor;
    }
    container conn {
      description
        "Information about the current BGP neighbor connection, including TCP state and connection mode";
      uses bgp-nbr-ios-xe-oper:bgp-connection-neighbor;
    }
    container transp {
      description
        "Transport-related information for the BGP neighbor, including TCP session parameters and connection details";
      uses bgp-nbr-ios-xe-oper:bgp-transport-neighbor;
    }
    leaf encaps-pref {
      type bgp-nbr-ios-xe-oper:bgp-encaps-pref-neighbor;
      description
        "Preferred tunnel encapsulation type";
    }
  }

  container bgp-nbr-oper-data {
    config false;
    description
      "All BGP Neighbor Operational Information";
    list bgp-nbr-data {
      key "ip if-name af ni-name ni-type";
      description
        "BGP Neighbor State Information";
      uses bgp-nbr-ios-xe-oper:bgp-neighbor-key;
      uses bgp-nbr-ios-xe-oper:bgp-neighbor-info;
    }
    list bgp-nbr-cntrs {
      key "ip if-name af ni-name ni-type";
      description
        "BGP Neighbor Counters Information";
      uses bgp-nbr-ios-xe-oper:bgp-neighbor-key;
      uses bgp-nbr-ios-xe-oper:bgp-neighbor-counters;
    }
  }
}
