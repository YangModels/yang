module Cisco-IOS-XE-loop-detect-events {
  yang-version 1.1;
  namespace "http://cisco.com/ns/yang/Cisco-IOS-XE-loop-detect-events";
  prefix loop-detect-ios-xe-events;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for loop-detect events notification.
     Copyright (c) 2023 by Cisco Systems, Inc.
     All rights reserved.";

  revision 2024-03-01 {
    description
      "Initial revision";
    reference
      "1.0.0";
    cisco-semver:module-version "1.0.0";
  }

  typedef loopdetect-event-type {
    type enumeration {
      enum loopdet-unknown {
        value 0;
        description
          "Event type is unknown.";
      }
      enum loopdet-loop-det {
        value 1;
        description
          "Event type is loop detected.";
      }
      enum loopdet-loop-det-err-dis {
        value 2;
        description
          "Event type is loop detected with error disabled.";
      }
    }
    description
      "Event type for loop detect.";
  }

  grouping loop-detect-interface-event {
    description
      "Loop detection in the topology.";
    leaf if-name {
      type string;
      description
        "Reference to the device's interface where a loop is detected.";
    }
    leaf recvr-if-name {
      type string;
      description
        "Receiver interface where loop detect frame is received.";
    }
    leaf event-type {
      type loop-detect-ios-xe-events:loopdetect-event-type;
      description
        "Loop detect event type.";
    }
  }

  notification loopdetect-intf-event {
    description
      "Loop detection event notification.";
    uses loop-detect-ios-xe-events:loop-detect-interface-event;
  }
}
