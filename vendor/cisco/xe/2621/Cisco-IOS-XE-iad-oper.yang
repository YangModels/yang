module Cisco-IOS-XE-iad-oper {
  yang-version 1.1;
  namespace "http://cisco.com/ns/yang/Cisco-IOS-XE-iad-oper";
  prefix iad-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Industrial Asset Discovery (IAD) operational data.
     IAD feature enables users to view details of directly connected end devices
     through different protocols (CDP, LLDP, PROFINET, IPDT, CIP etc.)
     This is implemented for learning devices in industrial networks which include end devices
     such as programmable logic controllers (PLCs) and Intelligent Electronic Devices (IED).

     Copyright (c) 2025-2026 by Cisco Systems, Inc.

     All rights reserved.";

  revision 2026-08-01 {
    description
      "Improve YANG descriptions for IAD container, asset list, and port-proto leaf";
    reference
      "1.0.1";
    cisco-semver:module-version "1.0.1";
  }
  revision 2026-02-01 {
    description
      "Initial revision";
    reference
      "1.0.0";
    cisco-semver:module-version "1.0.0";
  }

  typedef iad-port-state {
    type enumeration {
      enum iadp-port-up {
        value 0;
        description
          "Port is up";
      }
      enum iadp-port-down {
        value 1;
        description
          "Port is down";
      }
      enum iadp-port-unknown {
        value 2;
        description
          "Port state is unknown";
      }
    }
    description
      "State of the port belonging to IAD asset";
  }

  typedef iad-port-mode {
    type enumeration {
      enum iadpm-access {
        value 0;
        description
          "Port is in access mode";
      }
      enum iadpm-trunk {
        value 1;
        description
          "Port is in trunk mode";
      }
      enum iadpm-unknown {
        value 2;
        description
          "Port mode is unknown";
      }
    }
    description
      "Mode of the port belonging to IAD asset";
  }

  typedef iad-port-proto-flag {
    type bits {
      bit iadppf-cdp {
        position 0;
        description
          "Protocol is CDP";
      }
      bit iadppf-cip {
        position 1;
        description
          "Protocol is CIP";
      }
      bit iadppf-ipdt {
        position 2;
        description
          "Protocol is IPDT";
      }
      bit iadppf-lldp {
        position 3;
        description
          "Protocol is LLDP";
      }
      bit iadppf-profinet {
        position 4;
        description
          "Protocol is PROFINET";
      }
    }
    description
      "Protocol used to discover the IAD asset";
  }

  typedef iad-dev-type-flag {
    type bits {
      bit iaddtf-router {
        position 0;
        description
          "Type is router";
      }
      bit iaddtf-trans-bridge {
        position 1;
        description
          "Type is trans bridge";
      }
      bit iaddtf-src-route-bridge {
        position 2;
        description
          "Type is source route bridge";
      }
      bit iaddtf-switch {
        position 3;
        description
          "Type is switch";
      }
      bit iaddtf-host {
        position 4;
        description
          "Type is host";
      }
      bit iaddtf-igmp {
        position 5;
        description
          "Type is IGMP";
      }
      bit iaddtf-repeater {
        position 6;
        description
          "Type is repeater";
      }
      bit iaddtf-phone {
        position 7;
        description
          "Type is phone";
      }
      bit iaddtf-remote {
        position 8;
        description
          "Type is remote";
      }
      bit iaddtf-cvta {
        position 9;
        description
          "Type is cisco video transmission advantage (CVTA)";
      }
      bit iaddtf-two-port-mac-relay {
        position 10;
        description
          "Type is two port mac relay";
      }
      bit iaddtf-cable-device {
        position 11;
        description
          "Type is cable device";
      }
      bit iaddtf-station {
        position 12;
        description
          "Type is station";
      }
      bit iaddtf-wlan-access-bridge {
        position 13;
        description
          "Type is wlan access bridge";
      }
      bit iaddtf-other {
        position 14;
        description
          "Type is other";
      }
    }
    description
      "Device type of the IAD asset";
  }

  grouping iad-asset {
    description
      "Asset information from IAD";
    leaf index {
      type uint32;
      description
        "Index number of the device";
    }
    leaf if-name {
      type string;
      description
        "Name of the network interface associated with the device.
         (for example, 'GigabitEthernet1/0/1').";
    }
    leaf port-state {
      type iad-ios-xe-oper:iad-port-state;
      description
        "State of the port belonging to the IAD interface";
    }
    leaf port-mode {
      type iad-ios-xe-oper:iad-port-mode;
      description
        "Mode of the port belonging to the IAD interface";
    }
    leaf mac-addr {
      type yang:mac-address;
      description
        "Mac address of the interface";
    }
    leaf ip-addr {
      type inet:ip-address;
      description
        "IP Address of the device";
    }
    leaf vlan {
      type uint16;
      description
        "Vlan assigned to the port";
    }
    leaf port-proto {
      type iad-ios-xe-oper:iad-port-proto-flag;
      description
        "Protocol used to discover the IAD device.
          Can be: CDP, LLDP, PROFINET, CIP, IPDT or a combination,
          as one or more protocols can discover the device";
    }
    leaf serial-no {
      type string;
      description
        "Serial number of the discovered device";
    }
    leaf sw-version {
      type string;
      description
        "Software version the device is running";
    }
    leaf vendor {
      type string;
      description
        "Vendor of the discovered device";
    }
    leaf dev-type {
      type iad-ios-xe-oper:iad-dev-type-flag;
      description
        "Type of the discovered device";
    }
    leaf dev-pid {
      type string;
      description
        "Product name of the discovered device";
    }
    leaf last-rep-time {
      type yang:date-and-time;
      description
        "Timestamp of the most recent report received for the device.";
    }
  }

  container iad-oper-data {
    config false;
    description
      "Container for Industrial Asset Discovery (IAD) operational data,
       providing information about discovered assets and their network
       connectivity";
    list iad-asset {
      key "index";
      description
        "List of assets discovered by the Industrial Asset Discovery (IAD) feature,
         including details such as device type, interface, and protocol information";
      uses iad-ios-xe-oper:iad-asset;
    }
  }
}
