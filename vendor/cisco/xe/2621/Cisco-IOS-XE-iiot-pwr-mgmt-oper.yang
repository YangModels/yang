module Cisco-IOS-XE-iiot-pwr-mgmt-oper {
  yang-version 1.1;
  namespace "http://cisco.com/ns/yang/Cisco-IOS-XE-iiot-pwr-mgmt-oper";
  prefix iiot-pwr-mgmt-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module provides YANG operational data definitions for
     Power Management. It is platform-specific and supported only on Cisco IOS-XE Industrial IoT
     rugged routers which supports other power management features (sense, low power mode, etc.),
     not supported on other Industrial IoT Routers.
     Copyright (c) 2025-2026 by Cisco Systems, Inc.
     All rights reserved.";

  revision 2026-08-01 {
    description
      "Initial revision";
    reference
      "1.0.0";
    cisco-semver:module-version "1.0.0";
  }

  typedef pwr-mgmt-state {
    type enumeration {
      enum pwr-hw-boot-loader {
        value 0;
        description
          "Indicates that the device is in the boot loader stage of power management.";
      }
      enum pwr-hw-power-on {
        value 1;
        description
          "Power management is at power on state.";
      }
      enum pwr-hw-shut-low-volt {
        value 2;
        description
          "Indicates that the device has been shut down due to a low-voltage condition.";
      }
      enum pwr-hw-shut-off {
        value 3;
        description
          "Indicates that the device has been shut down because the power management state is off.";
      }
      enum pwr-hw-shut-high-volt {
        value 4;
        description
          "Indicates that the device has been shut down due to a high-voltage condition.";
      }
      enum pwr-hw-powering-up {
        value 5;
        description
          "Indicates that the device is in the process of powering up.";
      }
      enum pwr-hw-monitor {
        value 6;
        description
          "Indicates that the device is in the power management monitor state.";
      }
      enum pwr-hw-sleep {
        value 7;
        description
          "Indicates that the device is in the power management sleep state.";
      }
      enum pwr-hw-unknown {
        value 8;
        description
          "Indicates that the power management hardware state is unknown.";
      }
    }
    description
      "Represents possible hardware-level power management states of the device.";
  }

  typedef pwr-mgmt-sw-state {
    type enumeration {
      enum pwr-sw-power-on {
        value 0;
        description
          "Indicates that the software power management is in the on state.";
      }
      enum pwr-sw-sense-off {
        value 1;
        description
          "Indicates that the software power management is in the voltage sensing off state.";
      }
      enum pwr-sw-low-voltage {
        value 2;
        description
          "Indicates that the software power management has detected a low-voltage condition.";
      }
      enum pwr-sw-high-voltage {
        value 3;
        description
          "Indicates that the software power management has detected a high-voltage condition.";
      }
      enum pwr-sw-shutdown {
        value 4;
        description
          "Indicates that the software power management has initiated a shutdown.";
      }
    }
    description
      "Represents possible software-level power management states of the device.";
  }

  typedef pwr-mgmt-pwr-mode {
    type enumeration {
      enum pwr-mode-low {
        value 0;
        description
          "Indicates that the software power management is in the low power state.";
      }
      enum pwr-mode-high {
        value 1;
        description
          "Indicates that the software power management is in the high power state.";
      }
    }
    description
      "Represents possible software-level power management states of the device.";
  }

  typedef pwr-mode-status {
    type enumeration {
      enum pwr-stat-reload-pend {
        value 0;
        description
          "Indicates that a reload is pending.";
      }
      enum pwr-stat-run {
        value 1;
        description
          "Indicates that the power management is running with no pending configuration changes.";
      }
    }
    description
      "Represents the pending status of a software-level power mode change, indicating whether a configuration save, a reload, or both are outstanding.";
  }

  typedef pwr-mgmt-tb {
    type enumeration {
      enum pm-tb-on-dur {
        value 0;
        description
          "Indicates that the device is configured with time-based on-duration setting and ready to go to sleep after the specified duration.";
      }
      enum pm-tb-start-time {
        value 1;
        description
          "Indicates that the device is configured with time-based start-time setting and ready to go to sleep after the specified start time.";
      }
      enum pm-tb-none {
        value 2;
        description
          "Indicates that the device is not configured with any time-based sleep settings.";
      }
    }
    description
      "Represents the time-based sleep scheduling mode configured on the device.";
  }

  grouping power-hist {
    description
      "Represents the power consumption history for a single day, including the date, maximum, minimum, and average power values recorded during that day.";
    leaf day {
      type uint8;
      description
        "Specifies the relative day position for which the power consumption history is recorded within the last 31 days of available runtime data. This value is displayed only for days when the device has been running.";
    }
    leaf max-val {
      type decimal64 {
        fraction-digits 3;
      }
      units "watts";
      description
        "Represents the highest power consumption value observed during the specified day, measured in watts. This value is shown only for days when the router has been running.";
    }
    leaf min-val {
      type decimal64 {
        fraction-digits 3;
      }
      units "watts";
      description
        "Represents the lowest power consumption value observed during the specified day, measured in watts. This value is shown only for days when the router has been running.";
    }
    leaf avg-val {
      type decimal64 {
        fraction-digits 3;
      }
      units "watts";
      description
        "Represents the average power consumption value calculated over the entire specified day, measured in watts. This value is shown only for days when the router has been running.";
    }
  }

  grouping pwr-mgmt-history {
    description
      "Power management history details.";
    leaf-list hist-hourly-avg {
      type decimal64 {
        fraction-digits 3;
      }
      units "watts";
      ordered-by user;
      description
        "Lists the average power consumption values for each hour for last 24 hours, Entries are ordered from the most recent hour to the oldest hour.";
    }
    list hist-last-31-day {
      description
        "Contains per-day power statistics for up to the last 31 days of available runtime data. Each list entry represents one day and includes the date, maximum, minimum, and average power values, ordered from newest day to oldest day.";
      uses iiot-pwr-mgmt-ios-xe-oper:power-hist;
    }
  }

  grouping pwr-mgmt-reg {
    description
      "Represents the operational status and configuration parameters for power management, including power state, voltage readings, sensing thresholds, and low-power mode settings.";
    leaf pwr-mgmt {
      type boolean;
      description
        "Indicates whether power management is enabled or disabled";
    }
    leaf input-volt {
      type decimal64 {
        fraction-digits 3;
      }
      units "volts";
      description
        "Measured input voltage in volts";
    }
    leaf pwr-state {
      type iiot-pwr-mgmt-ios-xe-oper:pwr-mgmt-state;
      description
        "Indicates the current hardware-level power management state of the device.";
    }
    leaf pwr-sw-state {
      type iiot-pwr-mgmt-ios-xe-oper:pwr-mgmt-sw-state;
      description
        "Indicates the current software-managed power state of the device.";
    }
    leaf sense {
      type boolean;
      description
        "Indicates whether voltage sensing is enabled or disabled";
    }
    leaf time-based {
      type iiot-pwr-mgmt-ios-xe-oper:pwr-mgmt-tb;
      description
        "Indicates the time-based sleep scheduling mode configured on the device.";
    }
    leaf tb-sleep-time {
      when "(../time-based = 'pm-tb-on-dur' or ../time-based = 'pm-tb-start-time')";
      type yang:date-and-time;
      description
        "Indicates the absolute time at which the device is going to sleep.";
    }
    leaf off-dur {
      type uint32;
      units "seconds";
      description
        "Indicates the configured timer-based off-duration in seconds.";
    }
    leaf shdn-sleep-time {
      when "(../sense = 'true')";
      type yang:date-and-time;
      description
        "Indicates the absolute scheduled shutdown sleep time for the software-managed power state; applicable when voltage sensing is enabled.";
    }
    leaf pwr-mode {
      type iiot-pwr-mgmt-ios-xe-oper:pwr-mgmt-pwr-mode;
      description
        "Indicates the current power operating mode of the device, either high power or low power.";
    }
    leaf pwr-status {
      type iiot-pwr-mgmt-ios-xe-oper:pwr-mode-status;
      description
        "Indicates the pending status of power mode changes.";
    }
    leaf under-volt {
      type decimal64 {
        fraction-digits 3;
      }
      units "volts";
      description
        "Under-voltage threshold in volts at which a low-voltage condition is triggered.";
    }
    leaf over-volt {
      type decimal64 {
        fraction-digits 3;
      }
      units "volts";
      description
        "Over-voltage threshold in volts at which a high-voltage condition is triggered.";
    }
    leaf sense-on-thresh {
      type decimal64 {
        fraction-digits 3;
      }
      units "volts";
      description
        "Voltage threshold in volts at which voltage sensing is activated";
    }
    leaf sense-off-thresh {
      type decimal64 {
        fraction-digits 3;
      }
      units "volts";
      description
        "Voltage threshold in volts at which voltage sensing is deactivated";
    }
  }

  container iiot-pwr-mgmt-oper-data {
    config false;
    description
      "The top level container for power management module";
    container pwr-mgmt-history {
      presence "pwr-mgmt-history";
      description
        "Contains power management history data, including hourly average power consumption values and per-day statistics for the last 31 days.";
      uses iiot-pwr-mgmt-ios-xe-oper:pwr-mgmt-history;
    }
    container pwr-mgmt-reg {
      presence "pwr-mgmt-reg";
      description
        "Contains power management operational status and configuration data, including hardware and software power states, voltage readings, sensing thresholds, and low-power mode.";
      uses iiot-pwr-mgmt-ios-xe-oper:pwr-mgmt-reg;
    }
  }
}
