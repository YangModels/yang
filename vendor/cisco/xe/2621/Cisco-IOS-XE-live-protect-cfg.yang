module Cisco-IOS-XE-live-protect-cfg {
  yang-version 1.1;
  namespace "http://cisco.com/ns/yang/Cisco-IOS-XE-live-protect-cfg";
  prefix live-protect-ios-xe-cfg;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Live Protect shield configuration.
     Copyright (c) 2026 by Cisco Systems, Inc.
     All rights reserved.";

  revision 2026-08-01 {
    description
      "Initial revision";
    reference
      "1.0.0";
    cisco-semver:module-version "1.0.0";
  }

  grouping lp-shield-cfg {
    description
      "Live Protect shield configuration parameters";
    leaf shield-id {
      type string {
        length "1..64";
        pattern '[0-9a-zA-Z\-_]+';
      }
      description
        "Unique shield identifier. Configuration can be
         pre-provisioned independently of shield installation.";
    }
    leaf is-enf {
      type boolean;
      default "false";
      description
        "Shield enforcement mode. When true, the shield actively
         blocks policy violations. When false, the shield operates
         in monitoring mode and only logs violations without blocking.";
    }
  }

  container live-protect-cfg-data {
    description
      "Live Protect configuration data";
    container lp-shield-configs {
      description
        "Live Protect shield configurations";
      list lp-shield-cfg {
        key "shield-id";
        description
          "Live Protect shield configuration entry";
        uses live-protect-ios-xe-cfg:lp-shield-cfg;
      }
    }
  }
}
