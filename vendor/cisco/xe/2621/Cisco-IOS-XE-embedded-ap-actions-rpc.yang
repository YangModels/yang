module Cisco-IOS-XE-embedded-ap-actions-rpc {
  yang-version 1.1;
  namespace "http://cisco.com/ns/yang/Cisco-IOS-XE-embedded-ap-actions-rpc";
  prefix embedded-ap-actions-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     embedded AP RPC.
     Copyright (c) 2023 by Cisco Systems, Inc.
     All rights reserved.";

  revision 2024-03-01 {
    description
      "Initial revision";
    reference
      "1.0.0";
    cisco-semver:module-version "1.0.0";
  }

  typedef enm-reset-actions {
    type enumeration {
      enum factory-reset-config {
        value 0;
        description
          "Reset wireless-bridge with config settings.
           This action is available only when embedded AP
           is configured as wireless-bridge with boot mode set as WGB";
      }
      enum factory-reset-default {
        value 1;
        description
          "Reset wireless-bridge with default settings.
           This action is available only when embedded AP
           is configured as wireless-bridge with boot mode set as WGB";
      }
    }
    description
      "Wireless-bridge factory reset options.";
  }

  typedef enm-wireless-bridge-actions {
    type enumeration {
      enum config-erase {
        value 10;
        description
          "Erase wireless-bridge configuration.
           This action is available only when embedded AP
           is configured as wireless-bridge with boot mode set as WGB";
      }
    }
    description
      "Wireless-bridge actions.";
  }

  typedef enm-boot-mode {
    type enumeration {
      enum mode-wgb {
        value 20;
        description
          "Boot embedded AP with WGB (WorkGroup Bridge) mode.
           Wireless embedded AP is configured as a wireless-bridge in this mode.
           It supports wired as well as wireless traffic bridging.";
      }
      enum mode-capwap {
        value 21;
        description
          "Boot embedded AP with CAPWAP (Control and Provisioning of Wireless
           Access Points) mode.
           Embedded AP works as a wireless access point in this mode.";
      }
    }
    description
      "Embedded AP boot modes.";
  }

  grouping reset-actions-type {
    description
      "Grouping of factory reset options on wireless-bridge.";
    leaf reset-actions {
      type embedded-ap-actions-rpc:enm-reset-actions;
      mandatory true;
      description
        "Factory reset options available when embedded AP
         is configured as wireless-bridge with boot mode set as WGB.";
    }
  }

  grouping wireless-bridge-actions-type {
    description
      "Grouping of executable actions on wireless-bridge.";
    leaf wireless-bridge-actions {
      type embedded-ap-actions-rpc:enm-wireless-bridge-actions;
      mandatory true;
      description
        "Executable actions available when embedded AP is configured
         as wireless-bridge with boot mode set as WGB.";
    }
  }

  grouping boot-mode-type {
    description
      "Grouping of available boot mode options on embedded AP.";
    leaf boot-mode {
      type embedded-ap-actions-rpc:enm-boot-mode;
      mandatory true;
      description
        "Boot mode options available for embedded AP.";
    }
  }

  rpc wireless-bridge-reset {
    description
      "This RPC is used to execute factory reset on embedded AP
       configured as wireless-bridge with boot mode set as WGB.";
    input {
      uses embedded-ap-actions-rpc:reset-actions-type;
    }
  }

  rpc wireless-bridge {
    description
      "This RPC is used to execute actions on embedded AP configured as
       wireless-bridge with boot mode set as WGB.";
    input {
      uses embedded-ap-actions-rpc:wireless-bridge-actions-type;
    }
  }

  rpc switch-boot-mode {
    description
      "This RPC is used to boot embedded AP with requested mode.";
    input {
      uses embedded-ap-actions-rpc:boot-mode-type;
    }
  }
}
