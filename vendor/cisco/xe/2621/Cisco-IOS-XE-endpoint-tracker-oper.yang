module Cisco-IOS-XE-endpoint-tracker-oper {
  yang-version 1.1;
  namespace "http://cisco.com/ns/yang/Cisco-IOS-XE-endpoint-tracker-oper";
  prefix endpoint-tracker-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG
     definitions for endpoint tracker operational data.
     The endpoint tracker allows users to periodically
     check if an endpoint identified by IP or Domain or
     an API URL is reachable.
     Copyright (c) 2020-2026 by Cisco Systems, Inc.
     All rights reserved.";

  revision 2026-08-01 {
    description
      "Updated descriptions of several model elements to clarify their meaning and purpose";
    reference
      "1.2.2";
    cisco-semver:module-version "1.2.2";
  }
  revision 2023-11-01 {
    description
      "Document the interpretation of values for actual latency";
    reference
      "1.2.1";
    cisco-semver:module-version "1.2.1";
  }
  revision 2022-11-01 {
    description
      "Update yang-version to 1.1";
    reference
      "1.2.0";
    cisco-semver:module-version "1.2.0";
  }
  revision 2021-11-01 {
    description
      "Added tracker group status";
    reference
      "1.1.0";
    cisco-semver:module-version "1.1.0";
  }
  revision 2020-07-01 {
    description
      "Initial revision";
    reference
      "1.0.0";
    cisco-semver:module-version "1.0.0";
  }

  typedef endpoint-tracker-if-state {
    type enumeration {
      enum tracker-if-state-na {
        value 0;
        description
          "Tracker Interface State NA";
      }
      enum tracker-if-state-up {
        value 1;
        description
          "Tracker Interface State UP";
      }
      enum tracker-if-state-down {
        value 2;
        description
          "Tracker Interface State DOWN";
      }
    }
    description
      "Endpoint tracker interface state";
  }

  typedef endpoint-tracker-group-oper {
    type enumeration {
      enum tracker-group-oper-na {
        value 0;
        description
          "Tracker group operation is not applicable";
      }
      enum tracker-group-oper-or {
        value 1;
        description
          "Tracker group operation is logical OR";
      }
      enum tracker-group-oper-and {
        value 2;
        description
          "Tracker group operation is logical AND";
      }
    }
    description
      "Logical operation to be performed on tracker status for tracker elements [or/and]";
  }

  grouping endpoint-tracker-record {
    description
      "List of Trackers on an interface";
    leaf record-name {
      type string;
      description
        "Tracker record name associated with this interface";
    }
    leaf actual-delay {
      type uint32;
      units "milliseconds";
      description
        "Measured latency, in milliseconds, from the device to the endpoint.
         A value of 0 indicates unknown or invalid latency. A timeout is
         indicated by the maximum 32-bit unsigned integer value.";
    }
  }

  grouping endpoint-tracker-status {
    description
      "Endpoint Tracker Attach Point status";
    leaf if-name {
      type string;
      description
        "Interface name used to send tracker probes";
    }
    leaf state {
      type endpoint-tracker-ios-xe-oper:endpoint-tracker-if-state;
      description
        "Operational state of the tracker on this interface";
    }
    list tracker-record {
      description
        "List of Trackers on an interface";
      uses endpoint-tracker-ios-xe-oper:endpoint-tracker-record;
    }
  }

  grouping endpoint-tracker-element {
    description
      "Tracker elements of a tracker group";
    leaf name {
      type string;
      description
        "Tracker element name within the group";
    }
    leaf actual-delay {
      type uint32;
      units "milliseconds";
      description
        "Measured latency, in milliseconds, from the device to the element endpoint";
    }
    leaf state {
      type endpoint-tracker-ios-xe-oper:endpoint-tracker-if-state;
      description
        "Operational state of the tracker element";
    }
  }

  grouping endpoint-tracker-group-status {
    description
      "Endpoint Tracker Group Attach Point status";
    leaf attach-point-name {
      type string;
      description
        "Attach point name for the tracker group";
    }
    leaf group-name {
      type string;
      description
        "Tracker group name";
    }
    leaf oper {
      type endpoint-tracker-ios-xe-oper:endpoint-tracker-group-oper;
      description
        "Logical operation applied to tracker element states (and/or)";
    }
    leaf state {
      type endpoint-tracker-ios-xe-oper:endpoint-tracker-if-state;
      description
        "Operational state of the tracker group";
    }
    list tk-elem {
      description
        "Tracker elements of a tracker group";
      uses endpoint-tracker-ios-xe-oper:endpoint-tracker-element;
    }
  }

  container endpoint-tracker-oper {
    config false;
    description
      "Endpoint tracker operational data";
    list endpoint-tracker {
      key "if-name";
      description
        "The endpoint tracker status provides
         information about a trackers on an interface.";
      uses endpoint-tracker-ios-xe-oper:endpoint-tracker-status;
    }
    list tracker-group {
      key "attach-point-name";
      description
        "The endpoint tracker group status provides
         information about a trackers group on an attach point.";
      uses endpoint-tracker-ios-xe-oper:endpoint-tracker-group-status;
    }
  }
}
