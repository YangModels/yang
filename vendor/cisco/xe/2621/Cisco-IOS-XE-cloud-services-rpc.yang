module Cisco-IOS-XE-cloud-services-rpc {
  yang-version 1.1;
  namespace "http://cisco.com/ns/yang/Cisco-IOS-XE-cloud-services-rpc";
  prefix cloud-services-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     cloud services RPC operations including OTP token import.
     Copyright (c) 2022, 2024, 2026 by Cisco Systems, Inc.
     All rights reserved.";

  revision 2026-08-01 {
    description
      "- Updated descriptions for guidelines compliance.";
    reference
      "1.2.1";
    cisco-semver:module-version "1.2.1";
  }
  revision 2026-02-01 {
    description
      "- Import public key for spaces cloud services";
    reference
      "1.2.0";
    cisco-semver:module-version "1.2.0";
  }
  revision 2024-07-01 {
    description
      "Added spaces OTP token";
    reference
      "1.1.0";
    cisco-semver:module-version "1.1.0";
  }
  revision 2023-03-01 {
    description
      "Initial revision";
    reference
      "1.0.0";
    cisco-semver:module-version "1.0.0";
  }

  grouping clear-token {
    description
      "Parameters for clearing cloud service tokens";
    leaf service {
      type string;
      mandatory true;
      description
        "Name of the cloud service for which tokens are cleared";
    }
  }

  grouping otp-token-import {
    description
      "Parameters for importing a one-time password upgrade token for cloud services";
    leaf otp-token {
      type string {
        length "1..4095";
      }
      mandatory true;
      description
        "One-time password upgrade token";
    }
  }

  grouping otp-pkey-import {
    description
      "Public key used to validate OTP authorization codes";
    leaf otp-pkey {
      type string {
        length "1..4095";
        pattern '[A-Za-z0-9/+-_=.]+';
      }
      mandatory true;
      description
        "Public key used to validate the OTP authorization code";
    }
  }

  rpc cloudm-otp-token-import {
    description
      "Import an OTP upgrade token for cloud services";
    input {
      uses cloud-services-rpc:otp-token-import;
    }
  }

  rpc cloudm-spaces-otp-token-import {
    description
      "Import an OTP authorization code for Cisco Spaces cloud services";
    input {
      uses cloud-services-rpc:otp-token-import;
    }
  }

  rpc cloudm-spaces-tokens-clear {
    description
      "Clear all persistent and temporary tokens for Cisco Spaces cloud services";
    input {
      uses cloud-services-rpc:clear-token;
    }
  }

  rpc cloudm-spaces-pkey-import {
    description
      "Import a public key for Cisco Spaces cloud services";
    input {
      uses cloud-services-rpc:otp-pkey-import;
    }
  }
}
