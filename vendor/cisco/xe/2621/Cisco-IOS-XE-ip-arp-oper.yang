module Cisco-IOS-XE-ip-arp-oper {
  yang-version 1.1;
  namespace "http://cisco.com/ns/yang/Cisco-IOS-XE-ip-arp-oper";
  prefix ip-arp-ios-xe-oper;

  import Cisco-IOS-XE-common-types {
    prefix common-types-ios-xe;
  }
  import Cisco-IOS-XE-ios-common-oper {
    prefix ios-common-ios-xe-oper;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for IOS-XE ARP operational data. Compared to other model
     Cisco-IOS-XE-arp-oper, this model supports high scale queries
     and on-change telemetry subscriptions.
     Copyright (c) 2025-2026 by Cisco Systems, Inc.
     All rights reserved.";

  revision 2026-08-01 {
    description
      "Updated descriptions of several model elements to clarify their meaning and purpose.";
    reference
      "1.0.1";
    cisco-semver:module-version "1.0.1";
  }
  revision 2025-07-01 {
    description
      "Initial revision";
    reference
      "1.0.0";
    cisco-semver:module-version "1.0.0";
  }

  typedef ip-arp-mode {
    type enumeration {
      enum ip-arp-mode-undef {
        value 0;
        description
          "Entry created with undefined error";
      }
      enum ip-arp-mode-dyn {
        value 1;
        description
          "Entry has been learned dynamically";
      }
      enum ip-arp-mode-incomplete {
        value 2;
        description
          "ARP request has been sent but have not received
           reply yet from peer";
      }
      enum ip-arp-mode-if {
        value 3;
        description
          "Entry associated with interface";
      }
      enum ip-arp-mode-static {
        value 4;
        description
          "Statically configured entry";
      }
      enum ip-arp-mode-alias {
        value 5;
        description
          "ARP requests have been responded as if it were the owner
           of both the specified IP address and hardware address,
           whether proxy ARP is enabled or not";
      }
      enum ip-arp-mode-app-simple {
        value 6;
        description
          "Simple application ARP";
      }
      enum ip-arp-mode-app-alias {
        value 7;
        description
          "Entry created with application alias";
      }
      enum ip-arp-mode-app-timer {
        value 8;
        description
          "Entry created with application timer";
      }
    }
    description
      "The mode that this entry is running in";
  }

  grouping ip-arp-entry-key {
    description
      "Key for ARP entry";
    leaf addr {
      type inet:ipv4-address;
      description
        "IPv4 address of ARP entry";
    }
    leaf if-name {
      type string;
      description
        "Interface associated with this ARP entry";
    }
  }

  grouping ip-arp-entry {
    description
      "ARP operational data entry";
    leaf enc-type {
      type ios-common-ios-xe-oper:ios-encaps-type;
      description
        "Encapsulation type of protocol that produced the entry";
    }
    leaf type {
      type ios-common-ios-xe-oper:ios-linktype;
      description
        "Protocol type of the ARP entry";
    }
    leaf mode {
      type ip-arp-ios-xe-oper:ip-arp-mode;
      description
        "Mode of the ARP entry";
    }
    leaf hw-type {
      type ios-common-ios-xe-oper:ios-snpa-type;
      description
        "Specifies the type of hardware address (such as Ethernet, Frame Relay, etc.) associated with this ARP entry.";
    }
    leaf hw-addr {
      type yang:mac-address;
      description
        "Hardware (data link layer) address that the IPv4
         address is linked to";
    }
    leaf update-time {
      type yang:date-and-time;
      description
        "Timestamp of the last entry update";
    }
  }

  grouping ni-ip-arp {
    description
      "ARP Table parent network instance";
    leaf ni-type {
      type common-types-ios-xe:net-inst-type;
      description
        "Network instance type that the ARP table entries are tied to";
    }
    leaf ni-name {
      type string;
      description
        "Network instance name that the ARP table entries are tied to";
    }
    list ip-arp-entry {
      key "addr if-name";
      description
        "List of ARP entries associated with this network instance";
      uses ip-arp-ios-xe-oper:ip-arp-entry-key;
      uses ip-arp-ios-xe-oper:ip-arp-entry;
    }
  }

  container ip-arp-oper-data {
    config false;
    description
      "IOS XE ARP Operational data.";
    list ni-ip-arp {
      key "ni-name";
      description
        "List of network instances with ARP table entries";
      uses ip-arp-ios-xe-oper:ni-ip-arp;
    }
  }
}
