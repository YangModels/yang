module Cisco-IOS-XE-lorawan {
  yang-version 1.1;
  namespace "http://cisco.com/ns/yang/Cisco-IOS-XE-lorawan";
  prefix ios-lorawan;

  import cisco-semver {
    prefix cisco-semver;
  }
  import ietf-inet-types {
    prefix inet;
  }
  import Cisco-IOS-XE-native {
    prefix ios;
  }
  import Cisco-IOS-XE-features {
    prefix ios-features;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE LORAWAN yang model";

  revision 2022-11-01 {
    description
      "Initially created";
    cisco-semver:module-version "1.0.0";
  }

  grouping config-cpf-grouping {
    container profile {
      description
        "Common Packet Forwarder(cpf) configuration";
      presence "true";
      container antenna-values {
        description
          "configures antenna properties";
        leaf antenna {
          description
            "antenna ID";
          type enumeration {
            enum 1;
          }
        }
        leaf type {
          description
            "antenna type";
          type enumeration {
            enum omni {
              description
                "antenna type omni";
            }
            enum sector {
              description
                "antenna type sector";
            }
          }
        }
        leaf gain {
          description
            "antenna gain value";
          type uint8 {
            range "0..10";
          }
        }
        leaf cable-loss {
          description
            "cable loss value";
          type uint8 {
            range "0..10";
          }
        }
      }
      leaf auth-mode {
        description
          "configure authentication mode";
        type enumeration {
          enum client-server {
            description
              "client and server authentication mode";
          }
          enum server {
            description
              "server authentication mode";
          }
          enum sudi {
            description
              "cisco sudi authentication mode";
          }
        }
      }
      leaf board-bw {
        description
          "board rx bandwidth in HZ";
        type uint32 {
          range "0..20000000";
        }
      }
      leaf board-freq {
        description
          "board center frequency in HZ";
        type uint32 {
          range "400000000..950000000";
        }
      }
      leaf country {
        description
          "country code name";
        type string {
          length "1..20";
        }
      }
      container cpf {
        description
          "enable or disable common packet forwarder (cpf)";
        leaf enable {
          description
            "enable cpf";
          must '../../lns-ip and ../../lns-port' {
            error-message "cpf enable depends on lns-ip and lns-port";
          }
          type empty;
        }
      }
      leaf gateway-id {
        description
          "Gateway ID used for CPF";
        type string {
          length "1..32";
        }
      }
      container gps {
        description
          "configure gps for CPF";
        leaf enable {
          description
            "enables CPF to utilize GPS signal";
          type empty;
        }
      }
      leaf lns-ip {
        description
          "lora network server IP Address";
        type inet:ipv4-address;
      }
      leaf lns-name {
        description
          "lora network server FQDN name";
        type string {
          length "1..50";
        }
      }
      leaf lns-port {
        description
          "lora network server port number";
        type uint16 {
          range "1..65535";
        }
      }
      container log-level-values {
        description
          "configure cpf log level";
        leaf log-level {
          description
            "log level";
          type enumeration {
            enum debug {
              description
                "log level debug";
            }
            enum info {
              description
                "log level info";
            }
            enum xdebug {
              description
                "log level xdebug";
            }
          }
        }
        leaf lines {
          description
            "lines";
          type uint8 {
            range "1..255";
          }
        }
      }
      leaf region-channel-plan {
        description
          "region channel plan code";
        type string {
          length "1..10";
        }
      }
      container tls-sni {
        description
          "configure TLS SNI feature";
        leaf enable {
          description
            "use TLS_SNI to connect to LNS";
          type empty;
        }
      }
    }
  }

  grouping config-interface-lorawan-grouping {
    container common-packet-forwarder {
      description
        "Common Packet Forwarder(cpf)";
      uses config-cpf-grouping;
    }
  }

  augment "/ios:native/ios:interface/ios:LORAWAN" {
    uses config-interface-lorawan-grouping {
      if-feature "ios-features:lorawan";
    }
  }
}
