module Cisco-IOS-XE-group-policy-oper {
  yang-version 1.1;
  namespace "http://cisco.com/ns/yang/Cisco-IOS-XE-group-policy-oper";
  prefix group-policy-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for monitoring of Cisco group-policy steering
     information on Group-Policy traffic-steering contracts.
     Copyright (c) 2024-2025, 2026 by Cisco Systems, Inc.
     All rights reserved.";

  revision 2026-08-01 {
    description
      "- Revised the descriptions of several model elements to better clarify their meaning and purpose.";
    reference
      "1.0.1";
    cisco-semver:module-version "1.0.1";
  }
  revision 2025-03-01 {
    description
      "Initial revision";
    reference
      "1.0.0";
    cisco-semver:module-version "1.0.0";
  }

  typedef grp-policy-prov-status {
    type enumeration {
      enum provision-failed {
        value 0;
        description
          "Policy failed to provision";
      }
      enum provision-success {
        value 1;
        description
          "Policy successfully provisioned";
      }
    }
    description
      "Platform provision state of policy";
  }

  typedef grp-policy-src-type {
    type enumeration {
      enum grp-src-cfgrd {
        value 0;
        description
          "Group policy contract source is configured manually";
      }
      enum grp-src-dwnld {
        value 1;
        description
          "Group policy contract source is downloaded from policy server";
      }
    }
    description
      "Source type of group policy contract";
  }

  grouping grp-steer-permissions-entry {
    description
      "The contract name and source type of the corresponding destination SGT";
    leaf dst-sgt {
      type uint32;
      description
        "Destination Security Group Tag number.
         This value must be in the inclusive range of 2 to 65519";
    }
    leaf contract-name {
      type string;
      description
        "Name of the group policy traffic steering contract applied between the source and destination Security Group Tags (SGTs).";
    }
    leaf policy-src {
      type group-policy-ios-xe-oper:grp-policy-src-type;
      description
        "Source type of group policy contract";
    }
  }

  grouping grp-steer-permissions-record {
    description
      "Permission details of the Security Group Access Control List applied between
       Source Security Group Tag and Destination Security Group Tag";
    leaf src-sgt {
      type uint32;
      description
        "Source Security Group Tag number.
         This value must be in the inclusive range of 2 to 65519";
    }
    leaf status {
      type group-policy-ios-xe-oper:grp-policy-prov-status;
      description
        "Shows the data path policy provisioning status of the traffic steering contract for the designated Security Group Tag (SGT)";
    }
    list policy-cell-details {
      description
        "Details of the policy corresponding to each destination SGT";
      uses group-policy-ios-xe-oper:grp-steer-permissions-entry;
    }
  }

  grouping grp-steer-key {
    description
      "Source Security Group Tag (SGT) and Destination Security
       Group Tag(DGT) information to find the list of Security
       Group Access Control List that are currently
       applied between two security groups in the device";
    leaf src-sgt {
      type uint32;
      description
        "Source Security Group Tag number.
         This value must be in the inclusive range of 2 to 65519";
    }
    leaf dst-sgt {
      type uint32;
      description
        "Destination Security Group Tag number.
         This value must be in the inclusive range of 2 to 65519";
    }
  }

  grouping grp-steer-stats {
    description
      "Group-Policy traffic-steering counters between a Source
       Security Group and the Destination Security Group";
    leaf contract-name {
      type string;
      description
        "Name of the group policy traffic steering contract applied between the source and destination Security Group Tags (SGTs).";
    }
    leaf num-of-steer-contract {
      type uint32;
      description
        "Number of Steering contracts that
         are currently applied between
         the Source Security Group and the Destination
         Security Group. This should match
         the number of Steering contracts
         names in a contract";
    }
    leaf policy-life-time {
      type uint64;
      units "seconds";
      description
        "Duration of the Group-Policy traffic-steering contracts that are
         applied between a Source Security Group
         and a Destination Security Group. The duration
         is represented in seconds";
    }
    leaf last-upd-time {
      type yang:date-and-time;
      description
        "Indicates the time when the Group-Policy traffic-steering contracts
         between a Source Security Group and a Destination
         Security Group was modified or updated last. The
         value will be represented as date and time
         corresponding to the UTC time of the
         Identify Services Engine when the Role based
         permissions was modified or updated last";
    }
    leaf total-fwd-pkt-cnt {
      type uint64;
      description
        "Total number of packets that have been denied by
         the Group-Policy traffic-steering contracts
         between a Source Security Group and a Destination
         Security Group. This corresponds to
         total packets denied in both hardware and software
         forwarding paths of the device";
    }
    leaf total-steer-pkt-cnt {
      type uint64;
      description
        "Total number of packets that have been permitted
         by the Group-Policy traffic-steering contracts
         between a Source Security Group and a Destination
         Security Group. This corresponds to
         total packets allowed in both hardware and software
         forwarding paths of the device";
    }
    leaf sw-fwd-pkt-cnt {
      type uint64;
      description
        "Number of packets that have been denied in the
         software forwarding path of the device
         by the Group-Policy traffic-steering contracts between a Source
         Security Group and a Destination
         Security Group";
    }
    leaf sw-steer-pkt-cnt {
      type uint64;
      description
        "Number of packets that have been permitted in the
         software forwarding path of the device
         by the Group-Policy traffic-steering contracts between a Source
         Security Group and a Destination Security Group";
    }
    leaf hw-fwd-pkt-cnt {
      type uint64;
      description
        "Number of packets that have been denied in the
         hardware forwarding path of the device by
         the Group-Policy traffic-steering contracts between a Source
         Security Group and a Destination Security Group";
    }
    leaf hw-steer-pkt-cnt {
      type uint64;
      description
        "Number of packets that have been permitted in the
         hardware forwarding path of the device
         by the Group-Policy traffic-steering contracts between a Source
         Security Group and a Destination Security Group.";
    }
  }

  grouping grp-steer-policy-info {
    description
      "Group-Policy traffic-steering policy SGT between a Source
       Security Group and the Destination Security Group";
    leaf src-sgt-gen-id {
      type int32;
      description
        "Source Security Group Tag Generation ID. It is a version identification number.
         For every change under Security Group Tag the Generation ID will increment by one.";
    }
    leaf dst-sgt-gen-id {
      type int32;
      description
        "Destination Security Group Tag Generation ID. It is a version identification number.
         For every change under Security Group Tag the Generation ID will increment by one.";
    }
    leaf contract-name {
      type string;
      description
        "Name of the traffic steering contract applied between the source and destination Security Group Tags (SGTs).";
    }
    leaf stale {
      type boolean;
      description
        "State to represent if the policy is invalid or not";
    }
    leaf status {
      type group-policy-ios-xe-oper:grp-policy-prov-status;
      description
        "Displays the data path policy provisioning status of the group policy traffic steering contract (e.g., successfully provisioned or failed)";
    }
  }

  container group-policy-oper-data {
    config false;
    description
      "Represents the operational data of group policy traffic steering
       information from permissions, statistics and policy of respective SGTs";
    list grp-steer-perm-info {
      key "src-sgt";
      description
        "Operational data showing the traffic redirect actions applied between source and destination Security Group Tags (SGTs) for a specific protocol & transport layer port.";
      uses group-policy-ios-xe-oper:grp-steer-permissions-record;
    }
    list grp-steer-stats {
      key "src-sgt dst-sgt";
      description
        "Operational data containing counters and statistics for group policy traffic steering between source and destination Security Group Tags (SGTs).";
      uses group-policy-ios-xe-oper:grp-steer-key;
      uses group-policy-ios-xe-oper:grp-steer-stats;
    }
    list grp-steer-policy-info {
      key "src-sgt dst-sgt";
      description
        "Operational data for group policy traffic steering policies, including Security Group Tags (SGTs), associated contracts, and policy status between source and destination SGTs.";
      uses group-policy-ios-xe-oper:grp-steer-key;
      uses group-policy-ios-xe-oper:grp-steer-policy-info;
    }
  }
}
