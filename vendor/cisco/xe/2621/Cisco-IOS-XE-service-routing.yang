module Cisco-IOS-XE-service-routing {
  yang-version 1.1;
  namespace "http://cisco.com/ns/yang/Cisco-IOS-XE-service-routing";
  prefix ios-sr;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Service Routing Yang model.
     Copyright (c) 2016 by Cisco Systems, Inc.
     All rights reserved.";

  revision 2022-11-01 {
    description
      "- Update yang-version to 1.1";
    cisco-semver:module-version "1.1.0";
  }
  revision 2019-07-01 {
    description
      "- Establish semantic version baseline
       - Add service-routing capabilities-manager default value";
    cisco-semver:module-version "1.0.0";
  }
  revision 2017-07-24 {
    description
      "fix service-routing mdns-sd deleting issue";
  }
  revision 2017-06-28 {
    description
      "add service-policy under service routing mdns-sd";
  }
  revision 2017-05-09 {
    description
      "add service-routing mdns-sd support";
  }
  revision 2017-02-07 {
    description
      "Initial revision";
  }

  grouping config-service-routing-grouping {
    container service-routing {
      description
        "Configure service-routing";
      leaf capabilities-manager {
        description
          "Service-Routing Capabilities Manager configuration";
        type boolean;
        default "true";
      }
      container mdns-sd {
        description
          "Service-Routing MDNS configuration";
        presence "true";
        list service-policy {
          key "direction";
          leaf direction {
            type enumeration {
              enum IN;
              enum OUT;
            }
          }
          leaf policy-name {
            type string;
          }
        }
      }
    }
  }

  augment "/ios:native" {
    uses config-service-routing-grouping;
  }
}
