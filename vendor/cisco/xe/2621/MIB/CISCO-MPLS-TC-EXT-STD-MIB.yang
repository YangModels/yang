/*
 * Generated by confdc --mib2yang-std
 * Source: mgmt/dmi/model/mib/src/CISCO-MPLS-TC-EXT-STD-MIB.mib
 */
/*
 * This YANG module has been generated by smidump 0.5.0:
 *
 *      smidump -f yang CISCO-MPLS-TC-EXT-STD-MIB
 *
 * Do not edit. Edit the source file instead!
 */

module CISCO-MPLS-TC-EXT-STD-MIB {

  namespace "urn:ietf:params:xml:ns:yang:smiv2:CISCO-MPLS-TC-EXT-STD-MIB";
  prefix CISCO-MPLS-TC-EXT-STD-MIB;

  import ietf-yang-smiv2 {
    prefix "smiv2";
  }

  organization
   "Multiprotocol Label Switching (MPLS) Working Group";

  contact
   "Venkatesan Mahalingam
    Dell Inc,
    350 Holger way, San Jose, CA, USA
    Email: venkat.mahalingams@gmail.com
    
    Kannan KV Sampath
    Aricent,
    India
    Email: Kannan.Sampath@aricent.com
    
    Sam Aldrin
    Huawei Technologies
    2330 Central Express Way,
    Santa Clara, CA 95051, USA
    Email:  aldrin.ietf@gmail.com
    
    Thomas D. Nadeau
    CA Technologies
    273 Corporate Drive, Portsmouth, NH, USA
    Email: thomas.nadeau@ca.com";

  description
   "Copyright (c) 2012 IETF Trust and the persons identified
    as the document authors.  All rights reserved.
    
    This MIB module contains Textual Conventions for
    MPLS based transport networks.";

  revision 2012-02-22 {
    description
     "MPLS Textual Convention Extensions";
  }

  typedef CMplsGlobalId {
    type binary {
      length "4";
    }
    description
     "This object contains the Textual Convention of IP based
      operator unique identifier (Global_ID), the Global_ID can
      contain the 2-octet or 4-octet value of the operator's
      Autonomous System Number (ASN).
      
      It is expected that the Global_ID will be derived from
      the globally unique ASN of the autonomous system hosting
      the PEs containing the actual AIIs.
      The presence of a Global_ID based on the operator's
      ASN ensures that the AII will be globally unique.
      
      When the Global_ID is derived from a 2-octet AS number,
      
      
      
      the two high-order octets of this 4-octet identifier
      MUST be set to zero.
      Further ASN 0 is reserved.  A Global_ID of zero means
      that no Global_ID is present.  Note that a Global_ID of
      zero is limited to entities contained within a single
      operator and MUST NOT be used across an NNI.
      A non-zero Global_ID MUST be derived from an ASN owned by
      the operator.";
  }

  typedef CMplsNodeId {
    type uint32;
    description
     "The Node_ID is assigned within the scope of the Global_ID.
      The value 0(or 0.0.0.0 in dotted decimal notation) is
      reserved and MUST NOT be used.
      
      When IPv4 addresses are in use, the value of this object
      can be derived from the LSR's /32 IPv4 loop back address.
      When IPv6 addresses are in use, the value of this object
      can be a 32-bit value unique within the scope of
      a Global_ID.
      
      Note that, when IP reach ability is not needed, the 32-bit
      Node_ID is not required to have any association
      with the IPv4 address space.";
    smiv2:display-hint "d";
  }

  typedef CMplsIccId {
    type binary {
      length "1..6";
    }
    description
     "The ICC is a string of one to six characters, each
      character being either alphabetic (i.e.  A-Z) or
      numeric (i.e. 0-9) characters.
      Alphabetic characters in the ICC SHOULD be represented
      
      with upper case letters.";
  }

  typedef CMplsLocalId {
    type uint32 {
      range "1..16777215";
    }
    description
     "This textual convention is used in accommodating the bigger
      size Global_Node_ID and/or ICC with lower size LSR
      identifier in order to index the mplsTunnelTable.
      
      The Local Identifier is configured between 1 and 16777215,
      as valid IP address range starts from 16777216(01.00.00.00).
      This range is chosen to identify the mplsTunnelTable's
      Ingress/Egress LSR-id is IP address or Local identifier,
      if the configured range is not IP address, administrator is
      expected to retrieve the complete information
      (Global_Node_ID or ICC) from mplsNodeConfigTable. This way,
      existing mplsTunnelTable is reused for bidirectional tunnel
      extensions for MPLS based transport networks.
      
      This Local Identifier allows the administrator to assign
      a unique identifier to map Global_Node_ID and/or ICC.";
    smiv2:display-hint "d";
  }

  smiv2:alias "cmplsTcExtStdMIB" {
    smiv2:oid "1.3.6.1.4.1.9.10.144";
  }

}
