module Cisco-IOS-XE-wireless-afc-types {
  yang-version 1.1;
  namespace "http://cisco.com/ns/yang/Cisco-IOS-XE-wireless-afc-types";
  prefix wireless-afc-types;

  import Cisco-IOS-XE-wireless-enum-types {
    prefix wireless-enum-types;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Model for managing AFC
     Copyright (c) 2022-2026 by Cisco Systems, Inc.
     All rights reserved.";

  revision 2026-08-01 {
    description
      "- Updated descriptions for clarity and accuracy";
    reference
      "1.2.0";
    cisco-semver:module-version "1.2.0";
  }
  revision 2024-07-01 {
    description
      "- Added support for new operating class";
    reference
      "1.1.0";
    cisco-semver:module-version "1.1.0";
  }
  revision 2023-11-01 {
    description
      "Initial revision";
    reference
      "1.0.0";
    cisco-semver:module-version "1.0.0";
  }

  grouping afc-point {
    description
      "Geographic point location of the AFC device";
    leaf longitude {
      type decimal64 {
        fraction-digits 2;
      }
      units "degrees";
      description
        "Longitude of the AFC device location in decimal degrees";
    }
    leaf latitude {
      type decimal64 {
        fraction-digits 2;
      }
      units "degrees";
      description
        "Latitude of the AFC device location in decimal degrees";
    }
  }

  grouping afc-ellipse {
    description
      "Elliptical area describing the AFC device location";
    container center {
      description
        "Geographic center point of the location ellipse";
      uses wireless-afc-types:afc-point;
    }
    leaf major-axis {
      type uint16;
      units "meters";
      description
        "Length of the major axis of the location ellipse in meters";
    }
    leaf minor-axis {
      type uint16;
      units "meters";
      description
        "Length of the minor axis of the location ellipse in meters";
    }
    leaf orientation {
      type decimal64 {
        fraction-digits 2;
      }
      units "degrees";
      description
        "Orientation of the major axis of the location ellipse in degrees from true north";
    }
  }

  grouping afc-linear-polygon {
    description
      "Linear polygon area describing the AFC device location";
    list points {
      description
        "Vertices of the linear polygon as latitude and longitude coordinates";
      uses wireless-afc-types:afc-point;
    }
  }

  grouping afc-elevation {
    description
      "Elevation of the AFC device above a reference point";
    leaf height {
      type int16;
      units "meters";
      description
        "Height of the AFC device above a reference point";
    }
    leaf height-type {
      type wireless-enum-types:afc-height-type;
      description
        "Reference point type used for the height measurement";
    }
    leaf uncertainty {
      type uint16;
      units "meters";
      description
        "Uncertainty of the elevation measurement";
    }
  }

  grouping afc-location {
    description
      "Geographic location of the AFC device";
    leaf loc-type {
      type wireless-enum-types:afc-location-type;
      description
        "Type of geographic location used for the AFC device";
    }
    container ellipse {
      description
        "Elliptical area representing the geographic location of the AFC device";
      uses wireless-afc-types:afc-ellipse;
    }
    container linear-pol {
      description
        "Linear polygon representing the geographic location of the AFC device";
      uses wireless-afc-types:afc-linear-polygon;
    }
    container elevation {
      description
        "Elevation information for the AFC device location";
      uses wireless-afc-types:afc-elevation;
    }
    leaf deployment {
      type wireless-enum-types:afc-deployment-type;
      description
        "Deployment type of the AFC device, such as indoor or outdoor";
    }
    leaf area-of-uncertainty {
      when "../loc-type='afc-loc-ellipse'";
      type uint32;
      units "square meters";
      description
        "Area of uncertainty for the access point geolocation";
    }
  }

  grouping afc-cert-id {
    description
      "Certification identifier for the AFC device";
    leaf id {
      type string;
      description
        "Certification identifier used for AFC registration";
    }
    leaf ruleset-id {
      type string;
      description
        "Identifier of the regulatory ruleset associated with this certification";
    }
  }

  grouping afc-device-descriptor {
    description
      "Descriptor information identifying the AFC device";
    leaf serial-number {
      type string;
      description
        "Serial number of the AFC device";
    }
    list cert-id {
      description
        "Certification identifiers associated with the AFC device";
      uses wireless-afc-types:afc-cert-id;
    }
  }

  grouping afc-band-req {
    description
      "Band-specific channel request parameters for the AFC request";
    leaf global-oper-class {
      type uint16;
      description
        "Global operating class for the requested band";
    }
    leaf-list channel-cfi {
      type uint16;
      ordered-by user;
      description
        "Channel center frequency indices (CFI) requested for this band";
    }
    leaf enabled {
      type boolean;
      description
        "Indicates whether this band is included in the AFC request";
    }
  }

  grouping afc-request-data {
    description
      "AFC request parameters for the access point";
    container device {
      description
        "Device descriptor identifying the access point for the AFC request";
      uses wireless-afc-types:afc-device-descriptor;
    }
    container location {
      description
        "Geographic location of the access point for the AFC request";
      uses wireless-afc-types:afc-location;
    }
    container band20 {
      description
        "AFC request information for 20 MHz channels";
      uses wireless-afc-types:afc-band-req;
    }
    container band40 {
      description
        "AFC request information for 40 MHz channels";
      uses wireless-afc-types:afc-band-req;
    }
    container band80 {
      description
        "AFC request information for 80 MHz channels";
      uses wireless-afc-types:afc-band-req;
    }
    container band160 {
      description
        "AFC request information for 160 MHz channels";
      uses wireless-afc-types:afc-band-req;
    }
    container band80plus {
      description
        "AFC request information for 80+80 MHz channels";
      uses wireless-afc-types:afc-band-req;
    }
    leaf min-desired-power {
      type decimal64 {
        fraction-digits 2;
      }
      units "dBm";
      description
        "Minimum desired transmit power in dBm for the AFC request";
    }
    container band320 {
      description
        "AFC request information for 320 MHz channels";
      uses wireless-afc-types:afc-band-req;
    }
  }

  grouping afc-resp-code {
    description
      "Response code and description returned by the AFC server";
    leaf code {
      type int16;
      description
        "Numeric code indicating the result of the AFC response";
    }
    leaf description {
      type string;
      description
        "Human-readable description of the AFC response code";
    }
    leaf supplemental-info {
      type string;
      description
        "Supplemental information associated with the AFC response code";
    }
  }

  grouping afc-chan-resp {
    description
      "Channel availability and power information from the AFC response";
    leaf avail-channel-cfi {
      type uint16;
      description
        "Channel center frequency index (CFI) of the available channel";
    }
    leaf max-eirp {
      type decimal64 {
        fraction-digits 2;
      }
      units "dBm";
      description
        "Maximum effective isotropic radiated power (EIRP) allowed on this channel";
    }
  }

  grouping afc-band-resp {
    description
      "Band-specific channel availability from the AFC response";
    leaf global-oper-class {
      type uint16;
      description
        "Global operating class for this band in the AFC response";
    }
    list channels {
      description
        "Available channels in this AFC response band";
      uses wireless-afc-types:afc-chan-resp;
    }
  }

  grouping afc-response-data {
    description
      "AFC response parameters received for the access point";
    leaf request-id {
      type uint64;
      description
        "Identifier of the AFC request associated with this response";
    }
    leaf ruleset-id {
      type string;
      description
        "Identifier of the regulatory ruleset applied in the AFC response";
    }
    container resp-code {
      description
        "Response code information returned by the AFC service";
      uses wireless-afc-types:afc-resp-code;
    }
    container band20 {
      description
        "AFC response information for 20 MHz channels";
      uses wireless-afc-types:afc-band-resp;
    }
    container band40 {
      description
        "AFC response information for 40 MHz channels";
      uses wireless-afc-types:afc-band-resp;
    }
    container band80 {
      description
        "AFC response information for 80 MHz channels";
      uses wireless-afc-types:afc-band-resp;
    }
    container band160 {
      description
        "AFC response information for 160 MHz channels";
      uses wireless-afc-types:afc-band-resp;
    }
    container band80plus {
      description
        "AFC response information for 80+80 MHz channels";
      uses wireless-afc-types:afc-band-resp;
    }
    leaf expire-time {
      type yang:date-and-time;
      description
        "Time at which the AFC response expires";
    }
    leaf resp-rcvd-timestamp {
      type yang:date-and-time;
      description
        "Timestamp when the AFC response was received";
    }
    container band320 {
      description
        "AFC response information for 320 MHz channels";
      uses wireless-afc-types:afc-band-resp;
    }
  }

  grouping afc-httpcon-error {
    description
      "AFC health check HTTP error codes";
    leaf http-error-code {
      type uint32;
      description
        "HTTP status error code returned during the health check";
    }
    leaf httpcon-error-code {
      type uint32;
      description
        "HTTP connection error code returned during the health check";
    }
  }

  grouping afc-hc-error-status {
    description
      "AFC health check error status";
    choice hc-error-choice {
      description
        "Type of health check error";
      case afc-hc-err-http-con {
        container httpcon-error {
          description
            "HTTP connection error codes";
          uses wireless-afc-types:afc-httpcon-error;
        }
      }
      case afc-hc-err-prov {
        leaf fw-status {
          type wireless-enum-types:afc-provider-status;
          description
            "Status returned by the AFC provider during the health check";
        }
      }
      case afc-hc-err-token {
        leaf no-valid-token {
          type boolean;
          description
            "Device does not have a valid token to communicate with cloud services";
        }
      }
      case afc-hc-err-otp {
        leaf not-otp-upgraded {
          type boolean;
          description
            "Device is not OTP upgraded";
        }
      }
      case afc-hc-err-onboard {
        leaf device-not-onboarded {
          type boolean;
          description
            "Device is not onboarded";
        }
      }
      case afc-hc-err-unknown {
        leaf error-unknown {
          type boolean;
          description
            "Error status is unknown";
        }
      }
    }
  }

  grouping afc-healthcheck {
    description
      "AFC health check status";
    leaf hc-timestamp {
      type yang:date-and-time;
      description
        "Timestamp of the last AFC cloud health check";
    }
    leaf query-in-progress {
      type boolean;
      description
        "Indicates whether an AFC cloud health check query is in progress";
    }
    leaf country-not-supported {
      type boolean;
      description
        "Country not supported by AFC, cloud health check not applicable";
    }
    leaf num-hc-down {
      type uint32;
      description
        "Number of times cloud health check failed";
    }
    choice cloud-status-choice {
      description
        "Type of health check status";
      case afc-cloud-error {
        container hc-error-status {
          description
            "Error details from the AFC cloud health check";
          uses wireless-afc-types:afc-hc-error-status;
        }
      }
      case afc-cloud-ok {
        leaf cloud-hc-ok {
          type boolean;
          description
            "Indicates that the AFC cloud health check completed successfully";
        }
      }
      case afc-cloud-unknown {
        leaf cloud-hc-unknown {
          type boolean;
          description
            "Indicates that the AFC cloud health check status is unknown";
        }
      }
    }
  }
}
