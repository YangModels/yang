module Cisco-IOS-XE-install-oper-types {
  yang-version 1.1;
  namespace "http://cisco.com/ns/yang/Cisco-IOS-XE-install-oper-types";
  prefix install-oper-types-ios-xe;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for install status notification for image install events.
     Copyright (c) 2021-2022 by Cisco Systems, Inc.
     All rights reserved.";

  revision 2022-11-01 {
    description
      "- Added schedule transaction for install operations
       - Add support for notify install transaction
       - Add support for commit post check install transaction
       - Added support for install download operation.";
    reference
      "1.2.0";
    cisco-semver:module-version "1.2.0";
  }
  revision 2022-07-01 {
    description
      "- Added support fot set default controller mode install operation";
    reference
      "1.1.0";
    cisco-semver:module-version "1.1.0";
  }
  revision 2022-03-01 {
    description
      "Initial revision";
    reference
      "1.0.0";
    cisco-semver:module-version "1.0.0";
  }

  typedef install-op-cmd {
    type enumeration {
      enum install-op-unknown {
        value 0;
        description
          "Install operation type is not known";
      }
      enum install-op-add {
        value 1;
        description
          "Install operation to add new package";
      }
      enum install-op-activate {
        value 2;
        description
          "Install operation to activate installed package";
      }
      enum install-op-commit {
        value 3;
        description
          "Install operation to commit activated package";
      }
      enum install-op-rollback {
        value 4;
        description
          "Install operation to rollback to recorded commit states for device";
      }
      enum install-op-deactivate {
        value 5;
        description
          "Install operation to deactivate activate supported packages";
      }
      enum install-op-remove {
        value 6;
        description
          "Install operation to remove polaris packages from device";
      }
      enum install-op-auto-cancel-timer {
        value 7;
        description
          "Install operation to update auto cancel timer running for commit confirmation after activation";
      }
      enum install-op-cancel {
        value 8;
        description
          "Install operation to cancel operations pending commit confirmation";
      }
      enum install-op-set-default {
        value 9;
        description
          "Install operation to set defaults for device in controller mode";
      }
      enum install-op-download {
        value 10;
        description
          "Install operation to download package to the device";
      }
    }
    description
      "Install operation Command type to be executed on device";
  }

  typedef install-op-sts {
    type enumeration {
      enum install-op-not-started {
        value 0;
        description
          "Install operation has not started yet";
      }
      enum install-op-succ {
        value 1;
        description
          "Install operation finished successfully";
      }
      enum install-op-fail {
        value 2;
        description
          "Install operation failed";
      }
      enum install-op-fail-revert {
        value 3;
        description
          "Install operation failed and followed with cleanup of install state";
      }
      enum install-op-in-progress {
        value 4;
        description
          "Install operation execution is in progress";
      }
      enum install-op-dep-fail {
        value 5;
        description
          "Install operation failed because of dependencies";
      }
      enum install-op-timeout {
        value 6;
        description
          "Install operation timed out";
      }
      enum install-op-sts-cancel {
        value 7;
        description
          "Install operation cancelled";
      }
      enum install-op-marked-succ {
        value 8;
        description
          "Install operation does not change system state. Marked successful";
      }
      enum install-op-pend-usr-cnfrm {
        value 9;
        description
          "Install operation is pending for user confirmation";
      }
    }
    description
      "Install operation status";
  }

  typedef install-op-finish-sts {
    type enumeration {
      enum op-not-complete {
        value 0;
        description
          "Install operation is not complete yet and possibly in execution";
      }
      enum op-complete {
        value 1;
        description
          "Install operation completed its execution with either success or failure. Refer operation state for granular update";
      }
      enum op-reverted {
        value 2;
        description
          "Install operation is reverted as a result of failures detected in later states";
      }
    }
    description
      "Confirms if install operation reached to final state";
  }

  typedef install-txn-cmd {
    type enumeration {
      enum install-txn-unknown {
        value 0;
        description
          "Install transaction type is not known";
      }
      enum install-txn-download {
        value 1;
        description
          "Install transaction download to get package file on active FRU";
      }
      enum install-txn-copy {
        value 2;
        description
          "Install transaction copy to move file within device";
      }
      enum install-txn-verify {
        value 3;
        description
          "Install transaction verify to confirm validity of the package";
      }
      enum install-txn-extract {
        value 4;
        description
          "Install transaction extract to expand internal files from package";
      }
      enum install-txn-smu-add {
        value 5;
        description
          "Install transaction to add SMU package";
      }
      enum install-txn-pkg-add {
        value 6;
        description
          "Install transaction to add optional package";
      }
      enum install-txn-copy-setup {
        value 7;
        description
          "Install transaction copy setup to trigger copy within device";
      }
      enum install-txn-add-prechk {
        value 8;
        description
          "Install transaction to perform checks before add operation is started";
      }
      enum install-txn-remove {
        value 9;
        description
          "Install transaction remove to trigger remove of package files";
      }
      enum install-txn-add-clnup {
        value 10;
        description
          "Install transaction to cleanup install state after img add operation fails";
      }
      enum install-txn-add-postchk {
        value 11;
        description
          "Install transaction to perform checks or notifications after add operation is complete";
      }
      enum install-txn-smu-add-clnup {
        value 12;
        description
          "Install transaction to cleanup install state after smu add operation fails";
      }
      enum install-txn-rollback {
        value 13;
        description
          "Install transaction to trigger rollback of install state";
      }
      enum install-txn-act-prechk {
        value 14;
        description
          "Install transaction to perform checks before activate";
      }
      enum install-txn-pkg-act {
        value 15;
        description
          "Install transactions to perform sub-package activation";
      }
      enum install-txn-smu-act {
        value 16;
        description
          "Install transaction to perform smu activation";
      }
      enum install-txn-act-postchk {
        value 17;
        description
          "Install transaction to perform checks after activate";
      }
      enum install-txn-act-fail-clnup {
        value 18;
        description
          "Install transaction to perform cleanup after activate failure";
      }
      enum install-txn-reload {
        value 19;
        description
          "Install transaction to reload device";
      }
      enum install-txn-commit {
        value 20;
        description
          "Install transaction to commit current install state";
      }
      enum install-txn-chk-rbk-sanity {
        value 21;
        description
          "Install transaction to check rollback state sanity on device";
      }
      enum install-txn-rbk-prechk {
        value 22;
        description
          "Install transaction to perform checks after rollback";
      }
      enum install-txn-rbk-postchk {
        value 23;
        description
          "Install transaction to perform checks after rollback";
      }
      enum install-txn-reload-all {
        value 24;
        description
          "Install transaction to trigger reload of complete device";
      }
      enum install-txn-cancel-prechk {
        value 25;
        description
          "Install transaction to perform checks before cancel operation";
      }
      enum install-txn-cancel {
        value 26;
        description
          "Install transaction to perform cancel currently pending commit operation";
      }
      enum install-txn-cancel-postchk {
        value 27;
        description
          "Install transaction to perform checks after cancelling pending commit operation";
      }
      enum install-txn-remove-prechk {
        value 28;
        description
          "Install transaction to perform checks before remove operation";
      }
      enum install-txn-commit-prechk {
        value 29;
        description
          "Install transaction to perform checks before commit operation";
      }
      enum install-txn-deact-prechk {
        value 30;
        description
          "Install transaction to perform checks before deactivate operation";
      }
      enum install-txn-pkg-deact {
        value 31;
        description
          "Install transaction to perform sub-package deactivate";
      }
      enum install-txn-smu-deact {
        value 32;
        description
          "Install transaction to perform SMU deactivate";
      }
      enum install-txn-deact-postchk {
        value 33;
        description
          "Install transaction to perform checks after deactivate operation";
      }
      enum install-txn-img-act {
        value 34;
        description
          "Install transaction to perform image activation";
      }
      enum install-txn-remove-postchk {
        value 35;
        description
          "Install transaction to perform post checks after successful remove operation";
      }
      enum install-txn-set-default {
        value 36;
        description
          "Install transaction to set defaults";
      }
      enum install-txn-sched {
        value 37;
        description
          "Install transaction to schedule operation execution";
      }
      enum install-txn-notify {
        value 38;
        description
          "Install transaction to notify";
      }
      enum install-txn-commit-postchk {
        value 39;
        description
          "Install transaction to perform checks after commit operation";
      }
      enum install-txn-dwnld-precheck {
        value 40;
        description
          "Install transaction download pre check";
      }
    }
    description
      "Install transaction type";
  }

  typedef install-txn-sts {
    type enumeration {
      enum install-txn-sts-unknown {
        value 0;
        description
          "Install transaction status  not known";
      }
      enum install-txn-sts-succ {
        value 1;
        description
          "Install transaction finished execution with success";
      }
      enum install-txn-sts-in-progress {
        value 2;
        description
          "Install transaction is executing";
      }
      enum install-txn-sts-fail {
        value 3;
        description
          "Install transaction finished with failure";
      }
      enum install-txn-sts-dep-fail {
        value 4;
        description
          "Install transaction failed as dependent steps failed";
      }
      enum install-txn-sts-timeout {
        value 5;
        description
          "Install transaction timed out during execution";
      }
      enum install-txn-sts-cancel {
        value 6;
        description
          "Install transaction was cancelled";
      }
      enum install-txn-sts-op-timeout {
        value 7;
        description
          "Install transaction cancelled as top level operation timed out";
      }
      enum install-txn-sts-disconnect {
        value 8;
        description
          "Install transaction cancelled as peer disconnect detected";
      }
      enum install-txn-sts-marked-succ {
        value 9;
        description
          "Install transaction marked success as expecting no change in install state";
      }
      enum install-txn-sts-pend-usr-cnfrm {
        value 10;
        description
          "Install transaction is pending user confirmation to proceed. Valid for cli triggered operations";
      }
    }
    description
      "Install transaction Status";
  }

  typedef install-op-intf {
    type enumeration {
      enum op-intf-cli {
        value 0;
        description
          "Install operation is triggered via cli on device";
      }
      enum op-intf-ipc {
        value 1;
        description
          "Install operation is triggered via ipc interface";
      }
    }
    description
      "Indicates interface used to trigger install operation";
  }
}
