module Cisco-IOS-XE-eigrp-oper {
  yang-version 1.1;
  namespace "http://cisco.com/ns/yang/Cisco-IOS-XE-eigrp-oper";
  prefix eigrp-ios-xe-oper;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for EIGRP operational data.
     Copyright (c) 2019, 2022, 2026 by Cisco Systems, Inc.
     All rights reserved.";

  revision 2026-08-01 {
    description
      "Updated descriptions of several model elements to help clarify their meaning and purpose";
    reference
      "1.3.0";
    cisco-semver:module-version "1.3.0";
  }
  revision 2022-11-01 {
    description
      "Update yang-version to 1.1";
    reference
      "1.2.0";
    cisco-semver:module-version "1.2.0";
  }
  revision 2019-05-01 {
    description
      "Added semantic version";
    reference
      "1.1.0";
    cisco-semver:module-version "1.1.0";
  }
  revision 2019-01-11 {
    description
      "Initial revision";
    reference
      "1.0.0";
    cisco-semver:module-version "1.0.0";
  }

  typedef eigrp-ios-oper-afi {
    type enumeration {
      enum eigrp-af-illegal {
        value 0;
        description
          "Unsupported Address Family";
      }
      enum eigrp-af-ipv4 {
        value 1;
        description
          "Address Family IPv4";
      }
      enum eigrp-af-ipv6 {
        value 2;
        description
          "Address Family IPv6";
      }
      enum eigrp-af-sf-ipv4 {
        value 3;
        description
          "Service Family IPv4";
      }
      enum eigrp-af-sf-ipv6 {
        value 4;
        description
          "Service Family IPv6";
      }
    }
    description
      "Address Family";
  }

  typedef eigrp-ios-oper-authentication-mode {
    type enumeration {
      enum eigrp-auth-none {
        value 0;
        description
          "No Authentication";
      }
      enum eigrp-auth-md5 {
        value 1;
        description
          "MD5 Authentication";
      }
      enum eigrp-auth-hmac-sha-256 {
        value 2;
        description
          "HMAC SHA256 Authentication";
      }
    }
    description
      "EIGRP authentication mode";
  }

  typedef eigrp-ios-oper-origin-type {
    type enumeration {
      enum eigrp-origin-connected {
        value 0;
        description
          "Origin - Connected";
      }
      enum eigrp-origin-rediststatic {
        value 1;
        description
          "Origin - Redistributed Static";
      }
      enum eigrp-origin-redistconnect {
        value 2;
        description
          "Origin - Redistributed Connected";
      }
      enum eigrp-origin-redistributed {
        value 3;
        description
          "Origin - Redistributed";
      }
      enum eigrp-origin-vpnv4 {
        value 4;
        description
          "Origin - VPNv4";
      }
      enum eigrp-origin-summary {
        value 5;
        description
          "Origin - Summary";
      }
      enum eigrp-origin-dummy {
        value 6;
        description
          "Origin - Dummy";
      }
      enum eigrp-origin-igrp2 {
        value 7;
        description
          "Origin - EIGRP";
      }
      enum eigrp-origin-vpnv6 {
        value 8;
        description
          "Origin - VPNv6";
      }
      enum eigrp-origin-count {
        value 9;
        description
          "Count of Origins";
      }
    }
    description
      "EIGRP origin type";
  }

  grouping eigrp-ios-oper-instance-key {
    description
      "Key to uniquely identify a EIGRP instance";
    leaf afi {
      type eigrp-ios-xe-oper:eigrp-ios-oper-afi;
      description
        "Address Family";
    }
    leaf vrf-name {
      type string;
      description
        "VRF Name";
    }
    leaf as-num {
      type uint16;
      description
        "Autonomous System Number";
    }
  }

  grouping eigrp-ios-oper-instance {
    description
      "EIGRP Instance";
    leaf router-id {
      type uint32;
      description
        "Router-ID";
    }
    leaf named-mode {
      type empty;
      description
        "Indicates that the EIGRP instance is operating in named mode; when absent, the instance is operating in classic mode.";
    }
    leaf name {
      type string;
      description
        "EIGRP Virtual-Instance Name";
    }
    list eigrp-interface {
      key "name";
      description
        "EIGRP Interface";
      uses eigrp-ios-xe-oper:eigrp-ios-oper-intf;
    }
    list eigrp-topo {
      key "topo-id";
      description
        "List of EIGRP topologies associated with the EIGRP instance, representing different routing topologies maintained by EIGRP.";
      uses eigrp-ios-xe-oper:eigrp-ios-oper-topo;
    }
  }

  grouping eigrp-ios-oper-auth-key {
    description
      "EIGRP Authentication Key";
    leaf key-chain {
      type string;
      description
        "Key-Chain";
    }
    leaf sha256-password {
      type string;
      description
        "HMAC-SHA-256 Password";
    }
  }

  grouping eigrp-ios-oper-auth {
    description
      "EIGRP Authentication";
    leaf auth-mode {
      type eigrp-ios-xe-oper:eigrp-ios-oper-authentication-mode;
      description
        "Authentication Mode";
    }
    container auth-key {
      description
        "Authentication Key";
      uses eigrp-ios-xe-oper:eigrp-ios-oper-auth-key;
    }
  }

  grouping eigrp-ios-oper-intf {
    description
      "EIGRP Interface";
    leaf name {
      type string;
      description
        "Interface Name";
    }
    leaf passive {
      type empty;
      description
        "Indicates that the EIGRP interface is configured as passive; when present, the interface will not send or receive EIGRP hello packets but will continue to advertise the connected network.";
    }
    leaf hello-interval {
      type uint16;
      units "seconds";
      description
        "Hello Interval in Seconds";
    }
    leaf hold-timer {
      type uint16;
      units "seconds";
      description
        "Hold Timer in Seconds";
    }
    container auth-val {
      description
        "Contains EIGRP authentication configuration and state for the interface.";
      uses eigrp-ios-xe-oper:eigrp-ios-oper-auth;
    }
    list eigrp-nbr {
      key "afi nbr-address";
      description
        "EIGRP Neighbor";
      uses eigrp-ios-xe-oper:eigrp-ios-oper-nbr-key;
      uses eigrp-ios-xe-oper:eigrp-ios-oper-nbr;
    }
  }

  grouping eigrp-ios-oper-nbr-sw-version {
    description
      "EIGRP Neighbor Software Version";
    leaf os-majorver {
      type uint8;
      description
        "EIGRP OS Major Version";
    }
    leaf os-minorver {
      type uint8;
      description
        "EIGRP OS Minor Version";
    }
    leaf tlv-majorrev {
      type uint8;
      description
        "EIGRP TLV Major Version";
    }
    leaf tlv-minorrev {
      type uint8;
      description
        "EIGRP TLV Minor Version";
    }
  }

  grouping eigrp-ios-oper-nbr-stubinfo {
    description
      "EIGRP Neighbor Stub Information";
    leaf stubbed {
      type empty;
      description
        "Stub Enabled/Disabled";
    }
    leaf receive-only {
      type empty;
      description
        "Receive-Only mode Enabled/Disabled";
    }
    leaf allow-connected {
      type empty;
      description
        "Allow Connected Routes";
    }
    leaf allow-static {
      type empty;
      description
        "Indicates that the EIGRP neighbor is permitted to advertise static routes as part of its stub configuration; when absent, static routes are not permitted.";
    }
    leaf allow-summary {
      type empty;
      description
        "Indicates that the EIGRP neighbor is permitted to advertise summary routes as part of its stub configuration; when absent, summary routes are not permitted.";
    }
    leaf static-nbr {
      type empty;
      description
        "Indicates that this EIGRP neighbor is configured as a static neighbor in the stub configuration; when absent, the neighbor is not configured as a static neighbor.";
    }
    leaf allow-redist {
      type empty;
      description
        "Indicates that the EIGRP neighbor is permitted to advertise redistributed routes as part of its stub configuration; when absent, redistributed routes are not permitted.";
    }
    leaf allow-leaking {
      type empty;
      description
        "Indicates that the EIGRP neighbor is permitted to leak routes (i.e., advertise routes not typically allowed by stub configuration); when absent, route leaking is not permitted.";
    }
  }

  grouping eigrp-ios-oper-nbr-key {
    description
      "Key to Uniquely Identify a EIGRP Neighbor";
    leaf afi {
      type eigrp-ios-xe-oper:eigrp-ios-oper-afi;
      description
        "Address Family";
    }
    leaf nbr-address {
      type inet:ip-address;
      description
        "IP address of the EIGRP neighbor.";
    }
  }

  grouping eigrp-ios-oper-nbr {
    description
      "EIGRP Neighbor";
    container nbr-sw-ver {
      description
        "Neighbor Software Version";
      uses eigrp-ios-xe-oper:eigrp-ios-oper-nbr-sw-version;
    }
    container nbr-stubinfo {
      description
        "Neighbor Stub Information";
      uses eigrp-ios-xe-oper:eigrp-ios-oper-nbr-stubinfo;
    }
    leaf retransmit-count {
      type uint32;
      description
        "The number of EIGRP packets retransmitted to this neighbor due to lack of acknowledgment.";
    }
    leaf retry-count {
      type uint16;
      description
        "The number of times EIGRP has retried sending a packet to this neighbor without receiving an acknowledgment.";
    }
    leaf last-seq-number {
      type uint32;
      description
        "The sequence number of the last EIGRP packet sent to or received from this neighbor.";
    }
    leaf srtt {
      type uint32;
      description
        "Smooth Round Trip Time";
    }
    leaf rto {
      type uint32;
      description
        "Retransmission Time Out";
    }
  }

  grouping eigrp-ios-oper-topo {
    description
      "List of EIGRP topologies associated with the EIGRP instance, representing different routing topologies maintained by EIGRP.";
    leaf topo-id {
      type uint32;
      description
        "Unique identifier for the EIGRP topology within the EIGRP instance.";
    }
    list eigrp-network {
      key "afi ip-prefix";
      description
        "List of networks included in the EIGRP topology, each representing a network prefix being advertised or learned by EIGRP.";
      uses eigrp-ios-xe-oper:eigrp-ios-oper-network-key;
      uses eigrp-ios-xe-oper:eigrp-ios-oper-network;
    }
  }

  grouping eigrp-ios-oper-network-key {
    description
      "Key to Uniquely Identify a EIGRP Network";
    leaf afi {
      type eigrp-ios-xe-oper:eigrp-ios-oper-afi;
      description
        "Address Family";
    }
    leaf ip-prefix {
      type inet:ip-prefix;
      description
        "IP Prefix";
    }
  }

  grouping eigrp-ios-oper-metric {
    description
      "EIGRP Vector Metric";
    leaf bandwidth {
      type uint64;
      units "Kbps";
      description
        "Minimum bandwidth (in Kbps) along the path for this EIGRP route, used in metric calculation.";
    }
    leaf delay {
      type uint64;
      units "tens of microseconds";
      description
        "Cumulative delay (in tens of microseconds) along the path for this EIGRP route, used in metric calculation.";
    }
    leaf tag {
      type uint32;
      description
        "Route Tag";
    }
    leaf routerid {
      type uint32;
      description
        "Specifies the Router-ID associated with the reported distance vector metric for this EIGRP network.";
    }
    leaf mtu {
      type uint16;
      units "bytes";
      description
        "Specifies the IP Maximum Transmission Unit (MTU), in bytes, used in the reported distance vector metric for this EIGRP network.";
    }
    leaf hopcount {
      type uint8;
      description
        "Specifies the number of hops (routers traversed) for the EIGRP route metric.";
    }
    leaf reliability {
      type uint8;
      description
        "Specifies the reliability value used in the EIGRP route metric, representing the likelihood of successful packet transmission on the route.";
    }
    leaf load {
      type uint8;
      description
        "Indicates the link load metric value in the reported distance vector metric for this EIGRP network.";
    }
  }

  grouping eigrp-ios-oper-network {
    description
      "EIGRP Network";
    leaf rd-metric {
      type uint64;
      description
        "Reported Distance Metric";
    }
    container rd-vecmetric {
      description
        "Reported Distance Vector Metric";
      uses eigrp-ios-xe-oper:eigrp-ios-oper-metric;
    }
    leaf fd-metric {
      type uint64;
      description
        "Feasible Distance Metric";
    }
    leaf successor-count {
      type uint16;
      description
        "Successor Count";
    }
    leaf active {
      type empty;
      description
        "Active State of the Network";
    }
    list eigrp-route {
      key "afi infosource";
      description
        "EIGRP Route";
      uses eigrp-ios-xe-oper:eigrp-ios-oper-route-key;
      uses eigrp-ios-xe-oper:eigrp-ios-oper-route;
    }
  }

  grouping eigrp-ios-oper-extdatatype {
    description
      "EIGRP External Data";
    leaf routerid {
      type uint32;
      description
        "Router-ID";
    }
    leaf asystem {
      type uint32;
      description
        "Autonomous System";
    }
    leaf tag {
      type uint32;
      description
        "Tag value associated with the EIGRP external route, typically used for route identification or policy routing.";
    }
    leaf ext-metric {
      type uint32;
      description
        "Metric value assigned to the route by the external routing protocol before being redistributed into EIGRP.";
    }
    leaf protocol {
      type uint8;
      description
        "Indicates the routing protocol from which the route was redistributed into EIGRP. Values: 0=Unknown, 1=IGRP, 2=EIGRP, 3=Static, 4=RIP, 5=HELLO, 6=OSPF, 7=IS-IS, 8=EGP, 9=BGP, 10=IDRP, 11=Connected, 12=OSPFv3, 13=Mobile IP, 14=App Route, 15=LISP, 16=NHRP, 17=OMP, 18=NAT.";
    }
    leaf flag {
      type uint8;
      description
        "Numeric bitmask encoding route property flags associated with the EIGRP external route. Bit 0: Route Source WithDraw. Bit 1: Candidate Default (CD) - indicates if this route is a candidate default route. Bit 2: Route is currently in active state. Bit 3: Route is replicated from another VRF. Bit 4: Route imported from OMP at remote node.";
    }
  }

  grouping eigrp-ios-oper-route-key {
    description
      "Key to Uniquely Identify a EIGRP Route";
    leaf afi {
      type eigrp-ios-xe-oper:eigrp-ios-oper-afi;
      description
        "Address Family";
    }
    leaf infosource {
      type inet:ip-address;
      description
        "IP address of the source from which the EIGRP route information was learned.";
    }
  }

  grouping eigrp-ios-oper-route {
    description
      "EIGRP Route";
    leaf nexthop {
      type inet:ip-address;
      description
        "IP address of the next hop for this EIGRP route.";
    }
    leaf originating-interface {
      type string;
      description
        "Name of the interface from which this EIGRP route originated.";
    }
    leaf metric {
      type uint64;
      description
        "Route Metric";
    }
    container vecmetric {
      description
        "Route Vector Metric";
      uses eigrp-ios-xe-oper:eigrp-ios-oper-metric;
    }
    leaf succ-metric {
      type uint64;
      description
        "Successor Metric";
    }
    container succ-vecmetric {
      description
        "Successor Vector Metric";
      uses eigrp-ios-xe-oper:eigrp-ios-oper-metric;
    }
    leaf origin {
      type eigrp-ios-xe-oper:eigrp-ios-oper-origin-type;
      description
        "Route Origin";
    }
    leaf omp-tag {
      type uint32;
      description
        "Overlay Management Protocol (OMP) tag associated with the EIGRP route.";
    }
    leaf in-rib {
      type empty;
      description
        "Route in RIB";
    }
    leaf external {
      type empty;
      description
        "External Route";
    }
    container ext-data {
      description
        "Container for additional data associated with EIGRP external routes.";
      uses eigrp-ios-xe-oper:eigrp-ios-oper-extdatatype;
    }
  }

  container eigrp-oper-data {
    config false;
    description
      "EIGRP operational data";
    list eigrp-instance {
      key "afi vrf-name as-num";
      description
        "The EIGRP Instance";
      uses eigrp-ios-xe-oper:eigrp-ios-oper-instance-key;
      uses eigrp-ios-xe-oper:eigrp-ios-oper-instance;
    }
  }
}
