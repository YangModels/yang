module openconfig-route-summary {
  yang-version "1";

  namespace "http://openconfig.net/yang/route-summary";

  prefix "oc-rtsummary";

  import openconfig-extensions { prefix "oc-ext"; }
  import openconfig-yang-types { prefix "oc-yang-types"; }
  import openconfig-policy-types { prefix "oc-pol-types"; }
  import openconfig-network-instance { prefix "oc-ni"; }

  organization
    "OpenConfig working group";

  contact
    "OpenConfig working group
    www.openconfig.net";

  description
    "This module provides summary of route counts per route type for each network
    instance.";

  oc-ext:openconfig-version "1.0.0";

  revision "2022-12-21" {
    description
      "Initial version.";
    reference "1.0.0";
  }

  grouping route-counter {
    description
      "Route type counter item.";

    leaf origin-protocol {
      description
        "Route type that keys the route count list.";

      type identityref {
        base "oc-pol-types:INSTALL_PROTOCOL_TYPE";
      }
    }

    container total-count {
      description
        "A collection of route counts.";
      uses total-count;
    }
  }

  grouping total-count {
    description
      "A collection of route counts.";

    leaf fib-count {
      description
        "Total number of routes in the FIB.";
      type oc-yang-types:counter64;
    }
  }

  grouping route-summary {
    description
      "A summary of route count by route type.";

    list route-count {
      key "origin-protocol";

      description
        "Route types that keys the route count list.";

      leaf origin-protocol {
        type leafref {
          path "../state/origin-protocol";
        }
        description
          "Reference to the source of the route.";
      }

      container state {
        description
          "State parameters for the route summary list entry.";
        uses route-counter;
      }
    }
  }

  augment "/oc-ni:network-instances/oc-ni:network-instance/oc-ni:afts/oc-ni:ipv6-unicast" {
    description
      "Augment the network-instance model with the route summary container for
      IPv4.";

    container summary {
      uses route-summary;
      description
        "IPv4 route summary for the network instance.";
    }
  }

  augment "/oc-ni:network-instances/oc-ni:network-instance/oc-ni:afts/oc-ni:ipv4-unicast" {
    description
      "Augment the network-instance model with the route summary container for
      IPv6.";

    container summary {
      uses route-summary;
      description
        "IPv6 route summary for the network instance.";
    }
  }
}
