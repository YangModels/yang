module Cisco-IOS-XE-webauth-banner-internal {
  yang-version 1.1;
  namespace "http://cisco.com/ns/yang/Cisco-IOS-XE-webauth-banner-internal";
  prefix ios-webauth-banner-internal;

  import Cisco-IOS-XE-native {
    prefix ios;
  }
  import Cisco-IOS-XE-policy {
    prefix ios-policy;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "NED YANG module for IOS-XE.
     Copyright (c) 2019-2022 by Cisco Systems, Inc.
     All rights reserved.";

  revision 2025-03-01 {
    description
      "- Added tailf to handle ordering between banner text , banner file and banner node";
    cisco-semver:module-version "1.1.0";
  }
  revision 2023-03-01 {
    description
      "Initial revision
       - Added support for banner text/title for named webauth parameter-map
       - Removed length restriction of banner title";
    cisco-semver:module-version "1.0.0";
  }

  grouping config-internal-webauth-banner-grouping {
    leaf webauth-internal-banner-text {
      description
        "Banner message";
      type string;
    }
    leaf webauth-internal-banner-title {
      description
        "Banner message";
      type string;
    }
  }

  augment "/ios:native/ios:parameter-map/ios:type/ios-policy:webauth-global/ios-policy:webauth/ios-policy:global/ios-policy:banner-conf" {
    uses config-internal-webauth-banner-grouping {
      refine "webauth-internal-banner-text";
    }
  }

  augment "/ios:native/ios:parameter-map/ios:type/ios-policy:webauth/ios-policy:banner" {
    uses config-internal-webauth-banner-grouping {
      refine "webauth-internal-banner-text";
    }
  }
}
