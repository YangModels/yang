module Cisco-IOS-XE-udld-oper {
  yang-version 1.1;
  namespace "http://cisco.com/ns/yang/Cisco-IOS-XE-udld-oper";
  prefix udld-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for monitoring of unidirectional neighbors.
     Copyright (c) 2023, 2026 by Cisco Systems, Inc.
     All rights reserved.";

  revision 2026-08-01 {
    description
      "Updated descriptions of several model elements to clarify their meaning and purpose";
    reference
      "1.0.1";
    cisco-semver:module-version "1.0.1";
  }
  revision 2024-03-01 {
    description
      "Initial revision";
    reference
      "1.0.0";
    cisco-semver:module-version "1.0.0";
  }

  typedef e-udld-neighbor-state {
    type enumeration {
      enum udld-nbr-state-unidir {
        value 0;
        description
          "Link is broken and the state of the link is unidirectional.";
      }
      enum udld-nbr-state-bidir {
        value 1;
        description
          "Link is active and bidirectional.
           Connected devices are allowed to send packets specific to unidirectional link detection.";
      }
      enum udld-nbr-state-tx-rx-loop {
        value 2;
        description
          "Neighbor state is Transmit-Receive-Loop.";
      }
      enum udld-nbr-state-mismatch {
        value 3;
        description
          "Neighbor state is in Mismatched state.";
      }
      enum udld-nbr-state-nbr-ech-empty {
        value 4;
        description
          "Neighbor state is described as Neighbor Echo Empty.";
      }
      enum udld-nbr-state-unknown {
        value 5;
        description
          "Neighbor state is Unknown.";
      }
    }
    description
      "Unidirectional link neighbor states";
  }

  grouping neighbor-info {
    description
      "Connected neighbor information.";
    leaf device-name {
      type string;
      description
        "The human-readable device name of the connected neighbor.";
    }
    leaf device-id {
      type uint32;
      description
        "Device identifier of the connected neighbor.";
    }
    leaf port-id {
      type string;
      description
        "The unique port identifier corresponding to the connected neighbor's interface.";
    }
    leaf nbr-state {
      type udld-ios-xe-oper:e-udld-neighbor-state;
      description
        "The current unidirectional link detection state of the neighbor.";
    }
  }

  grouping udld-info {
    description
      "Unidirectional link information";
    leaf if-name {
      type string;
      description
        "The name of the local interface on which unidirectional link detection is being performed.";
    }
    container nbr-info {
      description
        "Contains identification and state information for the connected neighbor.";
      uses udld-ios-xe-oper:neighbor-info;
    }
  }

  container udld-oper-data {
    config false;
    description
      "Neighbor information associated with the device's port.";
    list udld-info {
      key "if-name";
      description
        "List of per-interface Unidirectional Link detection neighbor information.";
      uses udld-ios-xe-oper:udld-info;
    }
  }
}
