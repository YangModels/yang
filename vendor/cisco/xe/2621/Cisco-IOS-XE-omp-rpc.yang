module Cisco-IOS-XE-omp-rpc {
  yang-version 1.1;
  namespace "http://cisco.com/ns/yang/Cisco-IOS-XE-omp-rpc";
  prefix omp-ios-xe-rpc;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Copyright (c) 2024 by Cisco Systems, Inc.
     All rights reserved.";

  revision 2024-07-01 {
    description
      "Initial revision";
    reference
      "1.0.0";
    cisco-semver:module-version "1.0.0";
  }

  typedef clear-omp-choice-enum {
    type enumeration {
      enum clear-omp-choice-peer {
        value 0;
        description
          "The choice to clear OMP's peer";
      }
      enum clear-omp-choice-routes {
        value 1;
        description
          "The choice to clear OMP's routes";
      }
      enum clear-omp-choice-multicast {
        value 2;
        description
          "The choice to clear OMP's multicast";
      }
      enum clear-omp-choice-tlocs {
        value 3;
        description
          "The choice to clear OMP's transport locators";
      }
      enum clear-omp-choice-identity {
        value 4;
        description
          "The choice to clear OMP's identity";
      }
      enum clear-omp-choice-all {
        value 5;
        description
          "The choice to clear OMP's all RIB";
      }
      enum clear-omp-choice-l2-routes {
        value 6;
        description
          "The choice to clear OMP's layer2 routes";
      }
    }
    description
      "The choice definition to clear OMP's RIB";
  }

  typedef clear-omp-peer-soft-enum {
    type enumeration {
      enum clear-omp-peer-soft-in {
        value 0;
        description
          "Re-evaluate received RIB from a peer";
      }
      enum clear-omp-peer-soft-out {
        value 1;
        description
          "Force to advertise RIB to a peer";
      }
    }
    description
      "The enumeration definition of a soft reset";
  }

  grouping clear-omp-peer {
    description
      "Clear OMP's specific peer";
    leaf tenant-id {
      type uint32 {
        range "0..65534";
      }
      description
        "Tenant ID";
    }
    leaf address {
      type inet:ip-address;
      mandatory true;
      description
        "IPv4 address of a peer";
    }
    leaf soft {
      type omp-ios-xe-rpc:clear-omp-peer-soft-enum;
      description
        "Re-evaluate the peer's information with a soft reset.
         If not specify this value, it will take a hard reset.";
    }
  }

  grouping clear-omp-routes {
    description
      "Re-install routes into the route table";
    leaf tenant-id {
      type uint32 {
        range "0..65534";
      }
      default "0";
      description
        "Tenant ID, default 0";
    }
  }

  grouping clear-omp-multicast {
    description
      "Re-install multicast routes into the route table";
    leaf vpn {
      type uint32 {
        range "0..65531";
      }
      mandatory true;
      description
        "VPN ID";
    }
  }

  grouping clear-omp-l2-routes {
    description
      "Re-install layer2 routes into the SDWAN L2VPN table";
    leaf clear-all-vpn {
      type empty;
      description
        "Clear OMP's layer2 routes with all configured L2VPN";
    }
    leaf vpn {
      type uint32 {
        range "1..65531";
      }
      must 'not(../clear-all-vpn)' {
        error-message "%Error: vpn cannot coexist with clear-all-vpn.";
        error-app-tag "must-violation";
      }
      description
        "Layer2 VPN ID";
    }
    leaf vc-id {
      type uint32 {
        range "1..4294967295";
      }
      must '../vpn' {
        error-message "%Error: vpn is mandatory when clear with vc-id.";
        error-app-tag "must-violation";
      }
      description
        "Virtual circuit ID";
    }
  }

  grouping sdwan-clear-omp {
    description
      "Clear omp";
    choice type-choice {
      mandatory true;
      description
        "The type choice to clear OMP";
      case clear-omp-choice-peer {
        container peer {
          description
            "Clear OMP's peer";
          uses omp-ios-xe-rpc:clear-omp-peer;
        }
      }
      case clear-omp-choice-routes {
        container routes {
          description
            "Clear OMP's routes";
          uses omp-ios-xe-rpc:clear-omp-routes;
        }
      }
      case clear-omp-choice-multicast {
        container multicast {
          description
            "Clear OMP's multicast";
          uses omp-ios-xe-rpc:clear-omp-multicast;
        }
      }
      case clear-omp-choice-tlocs {
        leaf tlocs {
          type empty;
          mandatory true;
          description
            "Clear OMP's transport locators";
        }
      }
      case clear-omp-choice-identity {
        leaf identity {
          type empty;
          mandatory true;
          description
            "Clear OMP's identity";
        }
      }
      case clear-omp-choice-all {
        leaf all {
          type empty;
          mandatory true;
          description
            "Clear OMP's all RIB";
        }
      }
      case clear-omp-choice-l2-routes {
        container l2-routes {
          description
            "Clear OMP's layer2 routes";
          uses omp-ios-xe-rpc:clear-omp-l2-routes;
        }
      }
    }
  }

  rpc sdwan-clear-omp {
    description
      "A SDWAN specific RPC action to clear the routing information base (RIB)
       of overlay management protocol (OMP)";
    input {
      uses omp-ios-xe-rpc:sdwan-clear-omp;
    }
  }
}
