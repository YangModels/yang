module Cisco-IOS-XE-power {
  yang-version 1.1;
  namespace "http://cisco.com/ns/yang/Cisco-IOS-XE-power";
  prefix ios-power;

  import cisco-semver {
    prefix cisco-semver;
  }
  import Cisco-IOS-XE-native {
    prefix ios;
  }
  import Cisco-IOS-XE-features {
    prefix ios-features;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Power over Ethernet Yang (PoE) model.
     Copyright (c) 2016-2019 by Cisco Systems, Inc.
     All rights reserved.";

  revision 2026-08-01 {
    description
      "- Added model support for 2-event
       - Removed presence for power inline
       - Added FiftyGigabitEthernet, TwoHundredGigE and FourHundredGigE interface support";
    cisco-semver:module-version "3.0.0";
  }
  revision 2026-02-01 {
    description
      "- Added maximum wattage support for power inline
       - Added  flexible poe support for power inline";
    cisco-semver:module-version "2.1.0";
  }
  revision 2025-07-01 {
    description
      "-Obsolete leaves never, auto-max, static-max, redundancy mode
       -Added switch number support for power supply";
    cisco-semver:module-version "2.0.0";
  }
  revision 2024-11-01 {
    description
      "Added 1-event support for power inline";
    cisco-semver:module-version "1.5.0";
  }
  revision 2022-11-01 {
    description
      "- Update yang-version to 1.1";
    cisco-semver:module-version "1.4.0";
  }
  revision 2021-11-01 {
    description
      "- Added port priority options
       - Added switch number for redundancy mode config";
    cisco-semver:module-version "1.3.0";
  }
  revision 2021-07-01 {
    description
      "Modify Maximum power allowed on interface";
    cisco-semver:module-version "1.2.0";
  }
  revision 2019-11-01 {
    description
      "Added redundancy mode config";
    cisco-semver:module-version "1.1.0";
  }
  revision 2019-07-01 {
    description
      "Establish semantic version baseline";
    cisco-semver:module-version "1.0.0";
  }
  revision 2019-01-22 {
    description
      "Added leaf for App-hosting Gigabit Ethernet interface";
  }
  revision 2017-11-27 {
    description
      "Added Change 25GE name";
  }
  revision 2017-11-14 {
    description
      "This revision has changes for new 40 and 100GE interface addition";
  }
  revision 2017-09-15 {
    description
      "This revision has changes for new 2gig interface addition";
  }
  revision 2017-08-16 {
    description
      "This revision has changes for new 5gig and 25gig interfaces addition";
  }
  revision 2017-02-07 {
    description
      "Initial revision";
  }

  grouping power-config-mode {
    leaf combined {
      description
        "Enable global inline power logging messages";
      type empty;
    }
    container redundant {
      description
        "Either power supply can operate system";
      leaf n-plus-one {
        description
          "Redundant N+1";
        type uint8 {
          range "1..8";
        }
      }
      leaf-list n-plus-n {
        description
          "Redundant N+N";
        max-elements 8;
        type uint8 {
          range "1..8";
        }
      }
    }
  }

  grouping config-power-grouping {
    container power {
      description
        "Power configure";
      container inline {
        description
          "Inline power configuration";
        container wattage {
          if-feature "ios-features:wattage";
          description
            "Modify power supply total PoE watts available";
          leaf max {
            description
              "maximum wattage as per input power supply rating
               Device-specific max values:
               - IE 3500     : up to 360 Watts
               - IE 3505     : up to 480 Watts
               - IE 3500 10G : up to 480 Watts
               - IE 3500-H   : up to 240 Watts";
            type uint16 {
              range "4..480";
            }
            units "watts";
            default "125";
          }
        }
        container consumption {
          description
            "Inline device power consumption";
          leaf default {
            description
              "Inline device power consumption";
            type uint16 {
              range "4000..15400";
            }
          }
        }
        container logging {
          description
            "Inline power logging messages";
          leaf global {
            description
              "Enable global inline power logging messages";
            type empty;
          }
        }
        leaf flexible-poe {
          if-feature "ios-features:power-inline-flexible-poe";
          description
            "Enable global inline power flexible poe";
          type empty;
        }
        leaf two-event {
          description
            "POE Global 2-event Configuration";
          type empty;
        }
      }
      container redundancy-mode-config {
        description
          "Configure redundancy-mode of power supply";
        list switch {
          description
            "Configure power redundancy mode on selected switch";
          key "number";
          leaf number {
            description
              "switch number";
            type uint8 {
              range "1..8";
            }
          }
          uses power-config-mode;
        }
        uses power-config-mode;
      }
      leaf redundancy-mode {
        status obsolete;
        description
          "This node is obsolete and replace by redundancy-mode-config";
        type enumeration {
          enum combined;
          enum redundant;
        }
      }
      container supply {
        description
          "Power supply configuration";
        list switch {
          description
            "Configure power supply on selected switch";
          key "number";
          leaf number {
            description
              "switch number";
            type uint8 {
              range "1..8";
            }
          }
          container autoLC {
            description
              "Automatic linecard power configuration";
            leaf-list priority {
              description
                "Set priority (highest to lowest) of auto linecard shutdown";
              max-elements 8;
              ordered-by user;
              type uint8 {
                range "1..10";
              }
            }
            leaf shutdown {
              description
                "Linecard auto shutdown control";
              type empty;
            }
          }
        }
        container autoLC {
          description
            "Automatic linecard power configuration";
          leaf-list priority {
            description
              "Set priority (highest to lowest) of auto linecard shutdown";
            max-elements 8;
            ordered-by user;
            type uint8 {
              range "1..10";
            }
          }
          leaf shutdown {
            description
              "Linecard auto shutdown control";
            type empty;
          }
        }
      }
      leaf max-min {
        type enumeration {
          enum max;
        }
      }
      leaf inputs {
        type uint8;
      }
    }
  }

  grouping config-interface-power-grouping {
    container power {
      container efficient-ethernet {
        description
          "Energy efficient ethernet Configuration";
        leaf auto {
          description
            "Enable automatic efficient ethernet on this interface";
          type empty;
        }
      }
      container inline {
        leaf consumption {
          type uint16 {
            range "4000..15400";
          }
        }
        choice auto-static-never {
          leaf never-choice {
            type empty;
          }
          container auto-choice {
            description
              "Automatically detect and power inline devices";
            presence "true";
            leaf max {
              description
                "Maximum power allowed on this interface";
              type int32 {
                range "4000..90000";
              }
            }
          }
          container static-choice {
            description
              "High priority inline power interface";
            presence "true";
            leaf max {
              description
                "Maximum power allowed on this interface";
              type int32 {
                range "4000..90000";
              }
            }
          }
        }
        leaf never {
          status obsolete;
          description
            "OBSOLETE, use auto-static-never";
          type empty;
        }
        container auto {
          status obsolete;
          description
            "OBSOLETE, Automatically detect power inline devices";
          presence "true";
          leaf max {
            status obsolete;
            description
              "Maximum power allowed on this interface";
            type int32 {
              range "4000..90000";
            }
          }
        }
        container four-pair {
          description
            "Four-pair PoE power";
          leaf forced {
            description
              "Enable Four-pair PoE without L2 negotiation";
            type empty;
          }
        }
        container police {
          description
            "Police the power drawn on the port";
          presence "true";
          container action {
            description
              "Action to be taken when power is overdrawn on the port";
            leaf errdisable {
              description
                "Error-disable the port when power is overdrawn on the port";
              type empty;
            }
            leaf log {
              description
                "Log a message when power is overdrawn on the port";
              type empty;
            }
          }
        }
        container port {
          description
            "Configure Port Power Level";
          leaf poe-ha {
            description
              "Apply poe-ha to the port";
            type empty;
          }
          leaf perpetual-poe-ha {
            description
              "Apply perpetual-poe-ha to the port";
            type empty;
          }
          leaf one-event {
            description
              "Enable 1-event classification";
            type empty;
          }
          leaf two-event {
            description
              "Enable 2-event classification";
            type empty;
          }
          leaf twox-mode {
            description
              "Apply 2X power level to the port";
            type empty;
          }
          leaf no-xtalk-wa {
            description
              "Disable MagJack XTalk workaround";
            type empty;
          }
          leaf priority {
            description
              "set power priority of the port";
            type enumeration {
              enum high;
              enum low;
              enum 0;
              enum 1;
              enum 2;
              enum 3;
              enum 4;
              enum 5;
              enum 6;
              enum 7;
            }
            default "low";
          }
        }
        container static {
          status obsolete;
          description
            "OBSOLETE, High priority inline power interface, use static-choice";
          presence "true";
          leaf max {
            status obsolete;
            description
              "Maximum power allowed on this interface";
            type int32 {
              range "4000..90000";
            }
          }
        }
      }
    }
  }

  augment "/ios:native" {
    uses config-power-grouping;
  }

  augment "/ios:native/ios:interface/ios:FastEthernet" {
    uses config-interface-power-grouping;
  }

  augment "/ios:native/ios:interface/ios:GigabitEthernet" {
    uses config-interface-power-grouping;
  }

  augment "/ios:native/ios:interface/ios:TenGigabitEthernet" {
    uses config-interface-power-grouping;
  }

  augment "/ios:native/ios:interface/ios:FiveGigabitEthernet" {
    uses config-interface-power-grouping;
  }

  augment "/ios:native/ios:interface/ios:AppGigabitEthernet" {
    uses config-interface-power-grouping;
  }

  augment "/ios:native/ios:interface/ios:TwentyFiveGigE" {
    uses config-interface-power-grouping;
  }

  augment "/ios:native/ios:interface/ios:TwoGigabitEthernet" {
    uses config-interface-power-grouping;
  }

  augment "/ios:native/ios:interface/ios:FortyGigabitEthernet" {
    uses config-interface-power-grouping;
  }

  augment "/ios:native/ios:interface/ios:FiftyGigabitEthernet" {
    uses config-interface-power-grouping;
  }

  augment "/ios:native/ios:interface/ios:HundredGigE" {
    uses config-interface-power-grouping;
  }

  augment "/ios:native/ios:interface/ios:TwoHundredGigE" {
    uses config-interface-power-grouping;
  }

  augment "/ios:native/ios:interface/ios:FourHundredGigE" {
    uses config-interface-power-grouping;
  }
}
