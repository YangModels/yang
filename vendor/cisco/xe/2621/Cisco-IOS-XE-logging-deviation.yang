module Cisco-IOS-XE-logging-deviation {
  yang-version 1.1;
  namespace "http://cisco.com/ns/yang/Cisco-IOS-XE-logging-deviation";
  prefix ios-logging-d;

  import Cisco-IOS-XE-native {
    prefix ios;
  }

  organization
    "Cisco Systems";
  description
    "Cisco XE Native Deviation YANG module for IOS
     Copyright (c) 2024 by Cisco Systems, Inc.
     All rights reserved.";

  revision 2024-07-01 {
    description
      "- Update yang-version to 1.1";
  }

  deviation "/ios:native/ios:logging/ios:queue-limit/ios:esm" {
    deviate replace {
      default "8192";
    }
  }

  deviation "/ios:native/ios:logging/ios:discriminator/ios:name" {
    deviate replace {
      type string;
    }
  }

  deviation "/ios:native/ios:logging/ios:buffered-config/ios:config-options/ios:common-case/ios:common-config/ios:buffered/ios:log-options/ios:discriminator-config/ios:discriminator-config" {
    deviate replace {
      type string;
    }
  }

  deviation "/ios:native/ios:logging/ios:monitor-config/ios:config-options/ios:common-case/ios:common-config/ios:monitor/ios:log-options/ios:discriminatior-case/ios:discriminator/ios:name" {
    deviate replace {
      type string;
    }
  }

  deviation "/ios:native/ios:logging/ios:console-config/ios:config-options/ios:common-case/ios:common-config/ios:console/ios:log-options/ios:discriminatior-case/ios:discriminator/ios:name" {
    deviate replace {
      type string;
    }
  }
}
