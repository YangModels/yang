module Cisco-IOS-XE-mld {
  yang-version 1.1;
  namespace "http://cisco.com/ns/yang/Cisco-IOS-XE-mld";
  prefix ios-mld;

  import cisco-semver {
    prefix cisco-semver;
  }
  import Cisco-IOS-XE-native {
    prefix ios;
  }
  import ietf-inet-types {
    prefix inet;
  }
  import Cisco-IOS-XE-types {
    prefix ios-types;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Multicast Listener Discovery (MLD) Yang model.
     Copyright (c) 2017-2019 by Cisco Systems, Inc.
     All rights reserved.";

  revision 2026-08-01 {
    description
      "- Added Vif interface support
       - Added vlan dependency for MLD Snooping vlan list
       - Added TwoHundredGigE and FourHundredGigE interface support";
    cisco-semver:module-version "1.9.0";
  }
  revision 2026-02-01 {
    description
      "- Update leaf interface to list interface under mrouter";
    cisco-semver:module-version "1.8.0";
  }
  revision 2025-07-01 {
    description
      "- Added FiftyGigabitEthernet interface support
       - Removed catalyst from Global MLD Snooping enable for Vlans";
    cisco-semver:module-version "1.7.0";
  }
  revision 2024-07-01 {
    description
      "- Added a new leaf to support MLD explicit-tracking configuration
       - Added default values for ipv6 mld querier commands";
    cisco-semver:module-version "1.6.0";
  }
  revision 2023-07-01 {
    description
      "- Added MLD robustness-variable config";
    cisco-semver:module-version "1.5.0";
  }
  revision 2022-11-01 {
    description
      "- Update yang-version to 1.1";
    cisco-semver:module-version "1.4.0";
  }
  revision 2022-03-01 {
    description
      "- Added MLD snooping querier";
    cisco-semver:module-version "1.3.0";
  }
  revision 2020-03-01 {
    description
      "- Added status obsolete for dns leaf";
    cisco-semver:module-version "1.2.0";
  }
  revision 2019-11-01 {
    description
      "- Changes leaf to container";
    cisco-semver:module-version "1.1.0";
  }
  revision 2019-07-01 {
    description
      "- Establish semantic version baseline
       - Moved MLD snooping sub commands to snooping-container
       - Added MLD snooping, static-group model gaps";
    cisco-semver:module-version "1.0.0";
  }
  revision 2018-02-12 {
    description
      "Add mld snooping";
  }
  revision 2017-02-07 {
    description
      "Initial revision";
  }

  grouping config-mld-static-group-source {
    choice source-or-source-list {
      description
        "Select between a single source or a source-list";
      case case-source {
        leaf source {
          description
            "Source address";
          type inet:ipv6-address;
        }
      }
      case case-source-list {
        leaf source-list {
          description
            "Specify a source-list";
          type ios-types:ext-acl-type;
        }
      }
    }
  }

  grouping config-ipv6-mld-static-group {
    list static-group {
      description
        "List of MLD static group entries";
      key "gaddr";
      leaf gaddr {
        description
          "IP group address";
        type inet:ipv6-address;
      }
      choice choice-source {
        case case-source {
          uses config-mld-static-group-source;
        }
        case include-source {
          container include {
            description
              "Switch to include mode";
            uses config-mld-static-group-source;
          }
        }
        case exclude-source {
          container exclude {
            description
              "Switch to exclude mode";
            uses config-mld-static-group-source;
          }
        }
      }
    }
  }

  grouping config-mld-grouping {
    container mld {
      description
        "Global mld commands";
      container snooping-conf {
        leaf snooping {
          description
            "Global MLD Snooping enable for Vlans";
          type empty;
        }
      }
      container snooping-container {
        container snooping {
          leaf last-listener-query-count {
            description
              "Last listener query count";
            default "2";
            type uint8 {
              range "1..7";
            }
          }
          leaf last-listener-query-interval {
            description
              "Last listener query interval";
            default "1000";
            type uint16 {
              range "100..32768";
            }
          }
          container querier-conf {
            leaf querier {
              description
                "MLD querier disable/enable";
              type empty;
            }
          }
          container querier-entry {
            description
              "MLD querier configuration";
            leaf address {
              description
                "MLD querier source IP address";
              type inet:ipv6-address;
            }
            leaf max-response-time {
              description
                "MLD querier maximum response time (sec)";
              type uint8 {
                range "1..25";
              }
              default "10";
            }
            leaf query-interval {
              description
                "MLD querier query interval (sec)";
              type uint16 {
                range "1..18000";
              }
              default "125";
            }
            container tcn {
              description
                "MLD querier TCN related parameters";
              container query {
                leaf count {
                  description
                    "MLD querier TCN query count";
                  type uint8 {
                    range "1..10";
                  }
                  default "2";
                }
                leaf interval {
                  description
                    "MLD querier TCN query interval (sec)";
                  type uint8 {
                    range "1..255";
                  }
                  default "10";
                }
              }
            }
            container timer {
              description
                "MLD other querier timer";
              leaf expiry {
                description
                  "MLD querier other querier time out (sec)";
                type uint16 {
                  range "60..300";
                }
                default "250";
              }
            }
            leaf version {
              description
                "MLD version";
              type uint8 {
                range "1..2";
              }
              default "1";
            }
          }
          leaf listener-message-suppression {
            description
              "Listener Message Suppression";
            default "true";
            type boolean;
          }
          leaf robustness-variable {
            description
              "MLD Robustness Variable configuration";
            default "2";
            type uint8 {
              range "1..3";
            }
          }
          container tcn {
            description
              "Topology change notification configuration";
            container flood {
              description
                "TCN flooding configuration";
              container query {
                description
                  "TCN query configuration";
                leaf count {
                  description
                    "Configure query flooding duration";
                  default "2";
                  type uint8 {
                    range "1..10";
                  }
                }
              }
            }
            container query {
              description
                "TCN query configuration";
              leaf solicit {
                description
                  "Solicit an MLD general query";
                type boolean;
                default "false";
              }
            }
          }
          list mld-snooping-vlans {
            description
              "MLD Snooping enable on VLAN";
            key "vlan";
            leaf vlan {
              description
                "Vlan ID";
              type uint16 {
                range "1..4094";
              }
            }
            leaf immediate-leave {
              description
                "Enable MLD version-1 immediate leave processing";
              type empty;
            }
            leaf last-listener-query-interval {
              description
                "Last listener query interval";
              type uint16 {
                range "100..32768";
              }
            }
            leaf last-listener-query-count {
              description
                "Last listener query count";
              type uint8 {
                range "1..7";
              }
            }
            container querier-conf {
              leaf querier {
                description
                  "MLD querier disable/enable";
                type empty;
              }
            }
            container querier-entry {
              description
                "Enable MLD querier for this Vlan";
              leaf address {
                description
                  "MLD querier source IP address";
                type inet:ipv6-address;
              }
              leaf max-response-time {
                description
                  "MLD querier maximum response time (sec)";
                type uint8 {
                  range "1..25";
                }
              }
              leaf query-interval {
                description
                  "MLD querier query interval (sec)";
                type uint16 {
                  range "1..18000";
                }
              }
              container tcn {
                description
                  "MLD querier TCN related parameters";
                container query {
                  leaf count {
                    description
                      "MLD querier TCN query count";
                    type uint8 {
                      range "1..10";
                    }
                  }
                  leaf interval {
                    description
                      "MLD querier TCN query interval (sec)";
                    type uint8 {
                      range "1..255";
                    }
                  }
                }
              }
              container timer {
                description
                  "MLD other querier timer";
                leaf expiry {
                  description
                    "MLD querier other querier time out (sec)";
                  type uint16 {
                    range "60..300";
                  }
                }
              }
              leaf version {
                description
                  "MLD version";
                type uint8 {
                  range "1..2";
                }
              }
            }
            container mrouter {
              description
                "Configure an L2 port as a multicast router port";
              leaf-list interfaces {
                description
                  "next-hop interface to mrouter";
                type string {
                  pattern '[FfGgTtPp][OoIiEeWw].*';
                }
              }
              leaf interface {
                description
                  "next-hop interface to mrouter";
                status deprecated;
                type string {
                  pattern '[FfGgTtPp][OoIiEeWw].*';
                }
              }
            }
            leaf robustness-variable {
              description
                "MLD Robustness Variable configuration";
              type uint8 {
                range "1..3";
              }
            }
            list static {
              description
                "Configure an L2 port as a member of a group";
              key "gaddr interface";
              leaf gaddr {
                description
                  "IPv6 address of the group";
                type inet:ipv6-address;
              }
              leaf interface {
                description
                  "Specify an interface statically configured";
                type string {
                  pattern '[FfGgTtPp][OoIiEeWw].*';
                }
              }
            }
          }
        }
      }
      container ssm-map {
        description
          "SSM mapping commands";
        leaf enable {
          description
            "Enable SSM mapping";
          type empty;
        }
        container query {
          description
            "Which database should we query for the source";
          leaf dns-leaf {
            description
              "Use DNS for source lookup";
            type boolean;
            default "true";
          }
          leaf dns {
            status obsolete;
            description
              "Use DNS for source lookup";
            type empty;
          }
        }
        container static {
          description
            "SSM static group to source mapping";
          leaf acl {
            type string;
          }
          leaf source-ip {
            type inet:ipv6-address;
          }
        }
      }
    }
  }

  grouping config-interface-ipv6-mld-group {
    container mld {
      description
        "MLD interface commands";
      uses config-ipv6-mld-static-group;
      leaf robustness-variable {
        description
          "MLD Query Robustness Variable";
        type uint8 {
          range "1..7";
        }
        default "2";
      }
      container explicit-tracking {
        description
          "Enables MLD explicit tracking of the hosts within its IPv6 network";
        presence "true";
        leaf acl {
          description
            "Explicit tracking access list";
          type ios-types:ext-acl-type;
        }
      }
    }
  }

  augment "/ios:native/ios:ipv6" {
    uses config-mld-grouping;
  }

  augment "/ios:native/ios:interface/ios:FastEthernet/ios:ipv6" {
    uses config-interface-ipv6-mld-group;
  }

  augment "/ios:native/ios:interface/ios:GigabitEthernet/ios:ipv6" {
    uses config-interface-ipv6-mld-group;
  }

  augment "/ios:native/ios:interface/ios:TwoGigabitEthernet/ios:ipv6" {
    uses config-interface-ipv6-mld-group;
  }

  augment "/ios:native/ios:interface/ios:FiveGigabitEthernet/ios:ipv6" {
    uses config-interface-ipv6-mld-group;
  }

  augment "/ios:native/ios:interface/ios:TenGigabitEthernet/ios:ipv6" {
    uses config-interface-ipv6-mld-group;
  }

  augment "/ios:native/ios:interface/ios:TwentyFiveGigE/ios:ipv6" {
    uses config-interface-ipv6-mld-group;
  }

  augment "/ios:native/ios:interface/ios:FortyGigabitEthernet/ios:ipv6" {
    uses config-interface-ipv6-mld-group;
  }

  augment "/ios:native/ios:interface/ios:FiftyGigabitEthernet/ios:ipv6" {
    uses config-interface-ipv6-mld-group;
  }

  augment "/ios:native/ios:interface/ios:HundredGigE/ios:ipv6" {
    uses config-interface-ipv6-mld-group;
  }

  augment "/ios:native/ios:interface/ios:TwoHundredGigE/ios:ipv6" {
    uses config-interface-ipv6-mld-group;
  }

  augment "/ios:native/ios:interface/ios:FourHundredGigE/ios:ipv6" {
    uses config-interface-ipv6-mld-group;
  }

  augment "/ios:native/ios:interface/ios:Port-channel/ios:ipv6" {
    uses config-interface-ipv6-mld-group;
  }

  augment "/ios:native/ios:interface/ios:Loopback/ios:ipv6" {
    uses config-interface-ipv6-mld-group;
  }

  augment "/ios:native/ios:interface/ios:Tunnel/ios:ipv6" {
    uses config-interface-ipv6-mld-group;
  }

  augment "/ios:native/ios:interface/ios:Vlan/ios:ipv6" {
    uses config-interface-ipv6-mld-group;
  }

  augment "/ios:native/ios:interface/ios:LISP/ios:ipv6" {
    uses config-interface-ipv6-mld-group;
  }

  augment "/ios:native/ios:interface/ios:Multilink/ios:ipv6" {
    uses config-interface-ipv6-mld-group;
  }

  augment "/ios:native/ios:interface/ios:Cellular/ios:ipv6" {
    uses config-interface-ipv6-mld-group;
  }

  augment "/ios:native/ios:interface/ios:Port-channel-subinterface/ios:Port-channel/ios:ipv6" {
    uses config-interface-ipv6-mld-group;
  }

  augment "/ios:native/ios:interface/ios:BDI/ios:ipv6" {
    uses config-interface-ipv6-mld-group;
  }

  augment "/ios:native/ios:interface/ios:VirtualPortGroup/ios:ipv6" {
    uses config-interface-ipv6-mld-group;
  }

  augment "/ios:native/ios:interface/ios:Vif/ios:ipv6" {
    uses config-interface-ipv6-mld-group;
  }
}
