module Cisco-IOS-XE-vdsp-oper {
  yang-version 1.1;
  namespace "http://cisco.com/ns/yang/Cisco-IOS-XE-vdsp-oper";
  prefix vdsp-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for vDSP (Virtual Digital Signal Processing) operational data.
     Copyright (c) 2024, 2026 by Cisco Systems, Inc.
     All rights reserved.";

  revision 2026-08-01 {
    description
      "Updated descriptions of model elements to provide clearer vDSP operational context.";
    reference
      "1.0.1";
    cisco-semver:module-version "1.0.1";
  }
  revision 2024-11-01 {
    description
      "Initial revision";
    reference
      "1.0.0";
    cisco-semver:module-version "1.0.0";
  }

  grouping vdsp-status {
    description
      "Grouping for current vDSP subsystem status and version compatibility information.";
    leaf supported-regex {
      type string;
      description
        "This regular expression represents all supported vDSP firmware versions";
    }
    leaf installed-version {
      type string;
      description
        "vDSP version currently installed";
    }
    leaf version-supported {
      type boolean;
      description
        "vDSP version supported flag - indicates installed vDSP version compatibility with IOS-XE version";
    }
  }

  container vdsp-oper-data {
    config false;
    description
      "Container for operational data related to the vDSP subsystem.";
    container vdsp-status {
      presence "vdsp-status";
      description
        "Container for current vDSP subsystem status and version compatibility information.";
      uses vdsp-xe-oper:vdsp-status;
    }
  }
}
