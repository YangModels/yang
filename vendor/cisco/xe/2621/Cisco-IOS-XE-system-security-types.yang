module Cisco-IOS-XE-system-security-types {
  yang-version 1.1;
  namespace "http://cisco.com/ns/yang/Cisco-IOS-XE-system-security-types";
  prefix system-security-types-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for operational data related to system security types.
     Copyright (c) 2026 by Cisco Systems, Inc.
     All rights reserved.";

  revision 2026-08-01 {
    description
      "- Added an enumeration value for TFTP server configuration command
       - Added enum for Tool Command Line module.
       - Added reason, remedy and description enums for Tool Command Language and Logging.
       - Added description enums for Parser module.
       - Added reason, remedy and description enums for SNMP File transfer.
       - Added enum value for Device Sensor module.
       - Added submode enum value for Device Sensor DHCP filter list configuration.
       - Added an enumeration for SSH EC weak host key
       - Added reason, remedy, description, and submode enums for AAA weak password/key
       - Added description enum for boot system insecure file transfer protocol
       - Added module enum for IFS module
       - Added module enum for Crypto PKI Trustpoint module
       - Added description enum for Crypto PKI insecure file transfer protocol
       - Added submode enum for crypto-ca-trustpoint
       - Added dedicated remedy enum for generic secure protocol usage
       - Added module enum for DHCP snooping module
       - Added enum for DHCP module
       - Added remedy and description enums for DHCP
       - Added module enums for voice configuration contexts
       - Added remedy enum for insecure real-time streaming transport usage
       - Added description enums for insecure voice URL and transport configurations
       - Added submode enums for voice configuration contexts
       - Added reason, remediation and description enums for service password-encryption.
       - Added module enum for macro command and description enum for macro auto execute CLI.
       - Added reason, remedy, and description enums for RADIUS Message Authenticator warnings
       - Added description enums for RADIUS, TACACS, and LDAP without TLS warnings
       - Added description enum for Tool Command Language encoding directory
       - Added reason for SNMP group and remediation for SNMP group and cipher AES
       - Added module enums for IVR, gateway accounting, call leg, application monitor, and web service
       - Added description enums for IVR voice prompts, gateway accounting, call leg, event log, and web service configurations
       - Added submode enums for gateway accounting and application monitor configurations
       - Added reason, remedy and description enums for NTP allow mode control
       - Added description enum for NTP without authentication
       - Added module, description, and submode enums for IP SLA insecure protocol
       - Added submode enums for IP SLA LSR path echo and jitter configuration
       - Added module, reason, remediation and description enums for the insecure gNxI server
       - Updated SNMP no ACL reason and remedy descriptions
       - Added module and description enums for Crimson Function Tracking (CRFT) collect-on-reload insecure protocol";
    reference
      "1.1.0";
    cisco-semver:module-version "1.1.0";
  }
  revision 2026-02-01 {
    description
      "Initial revision";
    reference
      "1.0.0";
    cisco-semver:module-version "1.0.0";
  }

  typedef insec-conf-module {
    type enumeration {
      enum module-unknown {
        value 0;
        description
          "Unknown module";
      }
      enum module-aaa {
        value 1;
        description
          "AAA module";
      }
      enum module-bootp {
        value 2;
        description
          "BOOTP module";
      }
      enum module-http {
        value 3;
        description
          "HTTP module";
      }
      enum module-cdp {
        value 4;
        description
          "CDP module";
      }
      enum module-ip {
        value 5;
        description
          "IP module";
      }
      enum module-transport {
        value 6;
        description
          "TRANSPORT module";
      }
      enum module-tftp {
        value 7;
        description
          "TFTP module";
      }
      enum module-telnet {
        value 8;
        description
          "TELNET module";
      }
      enum module-rcmd {
        value 9;
        description
          "Route Convergence Monitoring and Diagnostics module";
      }
      enum module-line {
        value 10;
        description
          "LINE module";
      }
      enum module-ftp {
        value 11;
        description
          "FTP module";
      }
      enum module-ntp {
        value 12;
        description
          "NTP module";
      }
      enum module-snmp {
        value 13;
        description
          "SNMP module";
      }
      enum module-sanet {
        value 14;
        description
          "SANET module";
      }
      enum module-cts {
        value 15;
        description
          "CTS module";
      }
      enum module-parser {
        value 16;
        description
          "PARSER module";
      }
      enum module-logging {
        value 17;
        description
          "LOGGING module";
      }
      enum module-dspfarm-profile {
        value 18;
        description
          "DSPFARM PROFILE module";
      }
      enum module-stcapp {
        value 19;
        description
          "SCCP Telephony Control Application module";
      }
      enum module-ssh {
        value 20;
        description
          "SSH module";
      }
      enum module-capwap {
        value 21;
        description
          "CAPWAP module";
      }
      enum module-voice {
        value 22;
        description
          "Indicates that the insecure configuration was detected in the Voice module.";
      }
      enum module-http-client {
        value 23;
        description
          "Indicates that the insecure configuration was detected in the HTTP client module.";
      }
      enum module-call-mgr {
        value 24;
        description
          "Indicates that the insecure configuration was detected in the Call manager module.";
      }
      enum module-sipua {
        value 25;
        description
          "Indicates that the insecure configuration was detected in the SIP user agent module.";
      }
      enum module-tls-tunnel {
        value 26;
        description
          "Indicates that the insecure configuration was detected in the TLS tunnel module.";
      }
      enum module-nmsp {
        value 27;
        description
          "Indicates that the insecure configuration was detected in the NMSP module.";
      }
      enum module-tcl-bleed {
        value 28;
        description
          "Indicates that the insecure configuration was detected in the Tool Command Line module.";
      }
      enum module-device-sensor {
        value 29;
        description
          "Indicates that the insecure configuration was detected in the DEVICE SENSOR module.";
      }
      enum module-ifs {
        value 30;
        description
          "Indicates that the insecure configuration was detected in the IFS module.";
      }
      enum module-cryptopki-tp {
        value 31;
        description
          "Indicates that the insecure configuration was detected in the Crypto PKI Trustpoint module.";
      }
      enum module-dhcp-snoop {
        value 32;
        description
          "Indicates that the insecure configuration was detected in the DHCP snooping module.";
      }
      enum module-dhcp {
        value 33;
        description
          "Indicates that the insecure configuration was detected in the DHCP module.";
      }
      enum module-config-voice-default {
        value 34;
        description
          "Indicates that the insecure configuration was detected in default voice configuration mode.";
      }
      enum module-config-voice {
        value 35;
        description
          "Indicates that the insecure configuration was detected in voice configuration mode.";
      }
      enum module-config-voice-app {
        value 36;
        description
          "Indicates that the insecure configuration was detected in voice application configuration mode.";
      }
      enum module-config-voice-reg-global {
        value 37;
        description
          "Indicates that the insecure configuration was detected in global voice registration mode.";
      }
      enum module-config-voice-dnismaps {
        value 38;
        description
          "Indicates that the insecure configuration was detected in voice DNIS map configuration mode.";
      }
      enum module-macro {
        value 39;
        description
          "Indicates that the insecure configuration was detected in the macro command module.";
      }
      enum module-ivr {
        value 40;
        description
          "Indicates that the insecure configuration was detected in the IVR module.";
      }
      enum module-gw-acct {
        value 41;
        description
          "Indicates that the insecure configuration belongs to the gateway accounting module.";
      }
      enum module-call-leg {
        value 42;
        description
          "Indicates that the insecure configuration was detected in the call leg module.";
      }
      enum module-app-mon {
        value 43;
        description
          "Indicates that the insecure configuration was detected in the application monitor module.";
      }
      enum module-web-svc {
        value 44;
        description
          "Indicates that the insecure configuration was detected in the web service module.";
      }
      enum module-ipsla {
        value 45;
        description
          "Indicates that the insecure configuration was detected in the IP SLA module.";
      }
      enum module-gnxi {
        value 46;
        description
          "Indicates that insecure configuration was detected in the gNxI (gNMI/gNOI) module";
      }
      enum module-crft {
        value 47;
        description
          "Indicates that insecure configuration was detected in the CRFT collect-on-reload module.";
      }
    }
    description
      "IOS-XE software module owning insecure configuration CLI";
  }

  typedef insec-conf-reason {
    type enumeration {
      enum reason-unknown {
        value 0;
        description
          "Not specified";
      }
      enum reason-weak-encr-for-pwd {
        value 1;
        description
          "Configuration employs an insecure method for password storage";
      }
      enum reason-no-sec-login {
        value 2;
        description
          "The secure login-block feature is un-configured";
      }
      enum reason-legacy-proto {
        value 3;
        description
          "Legacy protocol poses data confidentiality and integrity risks
           due to lack of encryption and authentication";
      }
      enum reason-tls-ver {
        value 4;
        description
          "Weak TLS version";
      }
      enum reason-cipher {
        value 5;
        description
          "Weak cipher(s) are present in the command";
      }
      enum reason-on-demand-routing {
        value 6;
        description
          "On demand routing need to be disabled as in conjunction
           with cdp protocol static default routes will be added";
      }
      enum reason-ip-finger-insec {
        value 7;
        description
          "IP finger service can potentially expose system information to
           unauthorized users";
      }
      enum reason-ip-src-insec {
        value 8;
        description
          "IP source routing allows attackers to bypass network security
           controls and routing policies";
      }
      enum reason-tcp-small-srvr {
        value 9;
        description
          "TCP small servers expose unnecessary network services and
           potential attack vectors";
      }
      enum reason-udp-small-srvr {
        value 10;
        description
          "UDP small servers expose unnecessary network services and
           potential attack vectors";
      }
      enum reason-no-auth {
        value 11;
        description
          "SNMP host with auth/no-auth security level";
      }
      enum reason-insec-hash {
        value 12;
        description
          "Insecure hash digest";
      }
      enum reason-no-acl {
        value 13;
        description
          "Indicates that an SNMP user is configured without an ACL.";
      }
      enum reason-weak-auth-meth {
        value 14;
        description
          "A weak authentication method is being configured
           as part of EAP profile";
      }
      enum reason-no-sec-webauth {
        value 15;
        description
          "Secure web authentication is disabled, forcing insecure web-based
           authentication via HTTP";
      }
      enum reason-without-tls {
        value 16;
        description
          "TLS is not configured, exposing traffic to potential eavesdropping";
      }
      enum reason-ntp-lack-auth {
        value 17;
        description
          "NTP configuration lacks authentication, allowing potential time
           manipulation attacks";
      }
      enum reason-ssh-insuff-key-len {
        value 18;
        description
          "SSH host key uses insufficient key length";
      }
      enum reason-no-encr {
        value 19;
        description
          "No encryption is configured";
      }
      enum reason-zero-idle {
        value 20;
        description
          "Telnet sessions are not configured with an idle timeout";
      }
      enum reason-ip-no-encr {
        value 21;
        description
          "IP traffic is not encrypted";
      }
      enum reason-snmp-user-no-auth-no-priv {
        value 22;
        description
          "SNMP user without authentication
           and privacy security level";
      }
      enum reason-test-reason {
        value 23;
        description
          "Test reason";
      }
      enum reason-weak-file-trans-proto {
        value 24;
        description
          "It indicates that a weak file transfer protocol (FTP, TFTP, RCP, or HTTP)
           is in use";
      }
      enum reason-use-of-weak-pwd-or-key {
        value 25;
        description
          "Password or key does not meet security requirements due to
           insufficient complexity or use of default keywords";
      }
      enum reason-srv-pwd-enc {
        value 26;
        description
          "Indicates that passwords and keys are encrypted with weak Type 7 encryption.";
      }
      enum reason-nosrv-pwd-enc {
        value 27;
        description
          "Indicates that passwords and keys are stored in plaintext";
      }
      enum reason-send-ma-not-enabled {
        value 28;
        description
          "RADIUS Message-Authenticator send is not enabled on this
           server or client configuration";
      }
      enum reason-vali-ma-not-enabled {
        value 29;
        description
          "RADIUS Message-Authenticator validation is not enabled on this
           server or client configuration";
      }
      enum reason-group-no-auth {
        value 30;
        description
          "Indicates an SNMP group configured with no-auth security level.";
      }
      enum reason-ntp-allow-mode-ctrl-ddos {
        value 31;
        description
          "NTP allow mode control renders device susceptible to
           Distributed Denial of Service (DDoS) attacks";
      }
      enum reason-gnxi-no-tls-no-auth {
        value 32;
        description
          "The insecure gNxI (gNMI/gNOI) gRPC server is unencrypted and does not support authentication";
      }
    }
    description
      "Reason enum for configuration CLI being marked insecure";
  }

  typedef insec-conf-remedy {
    type enumeration {
      enum remedy-unknown {
        value 0;
        description
          "Not specified";
      }
      enum remedy-sec-opt-type6 {
        value 1;
        description
          "Consider migrating to a secure alternative such as type-6";
      }
      enum remedy-sec-opt-sha-aes {
        value 2;
        description
          "Transition to more secure algorithms like SHA and AES";
      }
      enum remedy-cfg-sec-login {
        value 3;
        description
          "Consider re-configuring it for protecting against DoS attacks";
      }
      enum remedy-use-dhcp {
        value 4;
        description
          "Use DHCP to automatically configure network settings";
      }
      enum remedy-use-http-sec-srvr {
        value 5;
        description
          "Use http secure server to ensure secure web access";
      }
      enum remedy-use-stronger-tls-ver {
        value 6;
        description
          "Use stronger tls version to enhance security";
      }
      enum remedy-use-stronger-cipher {
        value 7;
        description
          "Use stronger cipher(s) to enhance security";
      }
      enum remedy-obsolete {
        value 8;
        description
          "This is a legacy feature, need to disable the feature";
      }
      enum remedy-ssh-show-cmds {
        value 9;
        description
          "Disable finger service and use secure SSH-based
           show commands for system information retrieval";
      }
      enum remedy-disable-ping-tr-ssh {
        value 10;
        description
          "Disable TCP small servers and use modern network diagnostic tools
           like ping, traceroute, or SSH-based commands";
      }
      enum remedy-use-scp-sftp {
        value 11;
        description
          "Transition to secure file transfer methods
           using SCP, SFTP, HTTPS protocols";
      }
      enum remedy-use-ssh {
        value 12;
        description
          "Migrate to secure SSH-based remote access";
      }
      enum remedy-snmpv3 {
        value 13;
        description
          "Configure snmp version 3 user";
      }
      enum remedy-snmp-priv-sec {
        value 14;
        description
          "Use SNMP host with Private security level";
      }
      enum remedy-snmp-sha-sha2 {
        value 15;
        description
          "Use secure hash digest such as sha and sha-2";
      }
      enum remedy-snmp-3des {
        value 16;
        description
          "Use secure cipher such as 3des";
      }
      enum remedy-snmp-with-acl {
        value 17;
        description
          "Indicates that the remedy is to configure an ACL for the SNMP user.";
      }
      enum remedy-strong-auth-meth {
        value 18;
        description
          "Please consider configuring a stronger method
           such as EAP-FAST, EAP-PEAP or EAP-TLS";
      }
      enum remedy-webauth-https {
        value 19;
        description
          "Remove secure-webauth-disable configuration to ensure secure
           web-based authentication via HTTPS";
      }
      enum remedy-use-sec-encr {
        value 20;
        description
          "Use secure encryption methods to protect sensitive data";
      }
      enum remedy-conf-sec-opts-under-srvr {
        value 21;
        description
          "Configure secure options under server to enhance security";
      }
      enum remedy-ntp-make-authkey-trusted {
        value 22;
        description
          "Please make the configured auth key trusted using the
           command - ntp trusted-key";
      }
      enum remedy-ntp-conf-authkey-trusted {
        value 23;
        description
          "Configure a valid auth key and make it trusted using the
           command - ntp trusted-key";
      }
      enum remedy-ntp-auth {
        value 24;
        description
          "Configure ntp authenticate command to enable NTP authentication";
      }
      enum remedy-ssh-rsa-3072-key-len {
        value 25;
        description
          "Use SSH RSA host key with a minimum length of 3072 bits for
           enhanced security";
      }
      enum remedy-ssh-ec-384-key-len {
        value 26;
        description
          "Use SSH EC host key with a minimum length of 384 bits for
           enhanced security";
      }
      enum remedy-sec-opt-type6-9 {
        value 27;
        description
          "Please consider migrating to a secure alternative
           such as type-6 or type-9";
      }
      enum remedy-snmp-auth-priv {
        value 28;
        description
          "Use SNMP user with authentication and privacy";
      }
      enum remedy-test {
        value 29;
        description
          "Test remediation";
      }
      enum remedy-ssh-ec-256-key-len {
        value 30;
        description
          "Use SSH EC host key with a minimum length of 256 bits for
           enhanced security";
      }
      enum remedy-use-sec-file-trans-proto {
        value 31;
        description
          "It indicates that the remediation is to use a secure file transfer
           protocol (SFTP, HTTPS, or SCP)";
      }
      enum remedy-use-strong-pwd-or-key {
        value 32;
        description
          "Configure a password or key that meets the AAA common-criteria
           default policy requirements";
      }
      enum remedy-use-sec-proto {
        value 33;
        description
          "It indicates that the remediation is to use a crypto secure protocol
           instead of an insecure one";
      }
      enum remedy-dhcp-bootp-ignore-enable {
        value 34;
        description
          "Keep 'ip dhcp bootp ignore' enabled to block legacy BOOTP clients and prevent security vulnerabilities";
      }
      enum remedy-use-sec-proto-generic {
        value 35;
        description
          "Use secure protocols such as HTTPS, SFTP, or SCP instead of
           insecure HTTP, FTP, or TFTP";
      }
      enum remedy-use-sec-proto-srtp {
        value 36;
        description
          "Use secure real-time streaming protocols instead of plain
           real-time streaming transport";
      }
      enum remedy-use-secure-pwd-enc {
        value 37;
        description
          "Indicates that stronger encryption methods such as Type 6/8/9
           should be used where supported, and that this command should not be relied upon alone";
      }
      enum remedy-enable-send-ma {
        value 38;
        description
          "Enable send-ma on the RADIUS server or client configuration
           to protect against Blast Radius attacks";
      }
      enum remedy-enable-vali-ma {
        value 39;
        description
          "Enable validate-ma on the RADIUS server or client configuration
           to protect against Blast Radius attacks";
      }
      enum remedy-snmp-group-priv-sec {
        value 40;
        description
          "Indicates that the SNMP group uses the Private security level.";
      }
      enum remedy-snmp-aes {
        value 41;
        description
          "Indicates that a secure cipher such as AES is used.";
      }
      enum remedy-ntp-rate-limit-ctrl-mode {
        value 42;
        description
          "If NTP control mode needs to be enabled, configure a higher
           rate-limit delay and monitor the flow";
      }
      enum remedy-use-gnxi-sec-srvr {
        value 43;
        description
          "Configure the TLS-encrypted gNxI secure-server
           along with an authentication method such as password authentication
           or client certificate authentication.";
      }
      enum remedy-use-gnxi-tunnel-sec {
        value 44;
        description
          "Configure the secure gRPC tunnel target type.";
      }
    }
    description
      "Remedy enum for insecure configuration CLI";
  }

  typedef insec-conf-desc {
    type enumeration {
      enum unknown {
        value 0;
        description
          "Not specified";
      }
      enum username-pwd-0-5-7 {
        value 1;
        description
          "Username password configured with weak encryption
           (type 0, 7, or plain text) instead of secure type 6 encryption";
      }
      enum rad-srvr-key-weak-encr {
        value 2;
        description
          "RADIUS server key configured with weak encryption
           (type 0, 7, or plain text) instead of secure type 6 encryption";
      }
      enum rad-srvr-pac-key-weak-encr {
        value 3;
        description
          "RADIUS server PAC key configured with weak encryption
           (type 0, 7, or plain text) instead of secure type 6 encryption";
      }
      enum rad-srvr-key-wrap-weak-encr {
        value 4;
        description
          "RADIUS server key-wrap encryption or message auth code key
           configured with weak encryption instead of secure type 6";
      }
      enum tacacs-srvr-key-weak-encr {
        value 5;
        description
          "TACACS server key configured with weak encryption
           (type 0, 7, or plain text) instead of secure type 6 encryption";
      }
      enum rad-grp-srvr-priv-key-weak-encr {
        value 6;
        description
          "RADIUS group server private key configured with weak encryption
           instead of secure type 6 encryption";
      }
      enum rad-da-cient-srvr-key-weak-encr {
        value 7;
        description
          "RADIUS dynamic authorization client server-key configured with
           weak encryption instead of secure type 6";
      }
      enum ldap-srvr-key-weak-encr {
        value 8;
        description
          "LDAP server key configured with weak encryption
           (type 0, 7, or plain text) instead of secure type 6 encryption";
      }
      enum aaa-auth-pwd-weak-encr {
        value 9;
        description
          "AAA authentication password configured with weak encryption
           instead of secure type 6 encryption";
      }
      enum global-rad-srvr-key-weak-encr {
        value 10;
        description
          "Global RADIUS server key configured with weak encryption
           instead of secure type 6 encryption";
      }
      enum rad-sesm-srvr-key-weak-encr {
        value 11;
        description
          "RADIUS SES Manager server key configured with weak encryption
           instead of secure type 6 encryption";
      }
      enum rad-sesm-client-key-weak-encr {
        value 12;
        description
          "RADIUS SES Manager client key configured with weak encryption
           instead of secure type 6 encryption";
      }
      enum rad-proxy-srvr-key-weak-encr {
        value 13;
        description
          "RADIUS proxy server key configured with weak encryption
           instead of secure type 6 encryption";
      }
      enum en-pwd-weak-encr {
        value 14;
        description
          "Enable password configured with weak encryption
           instead of secure type 6 or 9 encryption";
      }
      enum rad-pol-dev-srvr-key-weak-encr {
        value 15;
        description
          "RADIUS policy device server key configured with weak encryption
           instead of secure type 6 encryption";
      }
      enum rad-pol-dev-client-key-weak-encr {
        value 16;
        description
          "RADIUS policy device client key configured with weak encryption
           instead of secure type 6 encryption";
      }
      enum global-tacacs-srvr-key-weak-encr {
        value 17;
        description
          "Global TACACS server key configured with weak encryption
           instead of secure type 6 encryption";
      }
      enum tacacs-grp-srvr-priv-key-weak-encr {
        value 18;
        description
          "TACACS group server private key configured with weak encryption
           instead of secure type 6 encryption";
      }
      enum login-blocking-disabled {
        value 19;
        description
          "Login blocking disabled - removes protection against
           brute force attacks";
      }
      enum bootp-srvr-legacy-proto {
        value 20;
        description
          "BOOTP server enabled - legacy protocol vulnerable to
           man-in-the-middle attacks and lacks security features";
      }
      enum http-srvr-unencr-proto {
        value 21;
        description
          "HTTP server enabled - unencrypted protocol vulnerable to
           eavesdropping and man-in-the-middle attacks";
      }
      enum http-client-weak-tls-ver {
        value 22;
        description
          "HTTP client configured with weak TLS version 1.0 or
           1.1 - vulnerable to various cryptographic attacks";
      }
      enum http-client-weak-cipher {
        value 23;
        description
          "HTTP client using weak cipher suite with CBC mode and
           SHA-1 - vulnerable to padding oracle and collision attacks";
      }
      enum odr-obs-routing-proto {
        value 24;
        description
          "On-Demand Routing enabled - obsolete routing protocol
           with security vulnerabilities";
      }
      enum ip-finger-svc-en {
        value 25;
        description
          "IP finger service enabled - provides system information that
           can be used for reconnaissance attacks";
      }
      enum finger-svc-en {
        value 26;
        description
          "Finger service enabled - provides detailed user information
           that can be exploited for social engineering";
      }
      enum ip-src-routing-en {
        value 27;
        description
          "IP source routing enabled - allows attackers to specify packet
           routing and bypass security controls";
      }
      enum tcp-small-srvr-en {
        value 28;
        description
          "TCP small servers enabled - provides unnecessary services like
           echo, discard, and daytime that can be exploited";
      }
      enum udp-small-srvr-en {
        value 29;
        description
          "UDP small servers enabled - provides unnecessary services that
           can be used for Distributed Denial of Service amplification attacks";
      }
      enum tcp-key-chain-weak-encr {
        value 30;
        description
          "TCP Key chain weak encryption";
      }
      enum tftp-svc-en {
        value 31;
        description
          "TFTP service enabled - unencrypted file transfer protocol
           vulnerable to eavesdropping and tampering";
      }
      enum telnet-zero-idle-svc-en {
        value 32;
        description
          "Telnet zero-idle service enabled - unencrypted remote access
           protocol vulnerable to credential theft";
      }
      enum ip-telnet-svc-en {
        value 33;
        description
          "IP telnet service enabled - transmits credentials and data
           in plain text over the network";
      }
      enum rcmd-svc-en {
        value 34;
        description
          "Remote command service enabled - allows unencrypted remote
           command execution without proper authentication";
      }
      enum line-transport-unencr-protos {
        value 35;
        description
          "Line transport configured with unencrypted protocols - allows
           plain text transmission of sensitive data";
      }
      enum telnet-line-opt-config {
        value 36;
        description
          "Telnet line options configured - enables unencrypted remote access
           vulnerable to session hijacking";
      }
      enum ftp-svc-en {
        value 37;
        description
          "FTP service enabled - transmits credentials and data in plain text,
           vulnerable to interception";
      }
      enum ntp-auth-using-md5 {
        value 38;
        description
          "NTP authentication using MD5 - vulnerable to collision attacks
           and should use stronger algorithms";
      }
      enum snmp-comm-str-config {
        value 39;
        description
          "SNMP community string configured - uses insecure SNMP v1 or v2 c
           protocol vulnerable to eavesdropping";
      }
      enum snmp-mib-comm-map-config {
        value 40;
        description
          "SNMP MIB community map configured - exposes community strings in
           insecure SNMP v1 or v2 c";
      }
      enum snmp-grp-insec-ver {
        value 41;
        description
          "SNMP group configured with insecure version 1 or 2 c - lacks
           encryption and authentication";
      }
      enum snmp-host-insec-ver {
        value 42;
        description
          "SNMP host configured with insecure version 1 or 2 c - transmits
           data without encryption";
      }
      enum snmp-host-insuff-auth {
        value 43;
        description
          "SNMP host configured with insufficient authentication - missing
           privacy encryption";
      }
      enum snmp-host-no-explicit-ver {
        value 44;
        description
          "SNMP host configured without explicit version - defaults to
           insecure SNMP v1 or v2 c";
      }
      enum snmp-user-insec-ver {
        value 45;
        description
          "SNMP user configured with insecure version 1 or 2 c - uses
           plain text community strings";
      }
      enum snmp-context-comm-str {
        value 46;
        description
          "SNMP context using community string - vulnerable to packet
           sniffing and replay attacks";
      }
      enum snmp-user-md5-auth {
        value 47;
        description
          "SNMP user configured with MD5 authentication - vulnerable to
           collision attacks";
      }
      enum snmp-user-weak-priv-encr {
        value 48;
        description
          "SNMP user configured with weak privacy encryption
           DES/3DES - vulnerable to cryptographic attacks";
      }
      enum snmp-user-sha2-auth-weak-priv {
        value 49;
        description
          "SNMP user configured with SHA-2 authentication but weak DES/3DES
           privacy encryption - vulnerable to cryptographic attacks";
      }
      enum snmp-context-user-weak-priv {
        value 50;
        description
          "SNMP context user configured with weak DES/3DES/DES-56 privacy
           encryption - vulnerable to cryptographic attacks";
      }
      enum snmp-context-user-md5-auth {
        value 51;
        description
          "SNMP context user configured with MD5 authentication - vulnerable
           to collision attacks";
      }
      enum snmp-grp-insuff-auth-lvl {
        value 52;
        description
          "SNMP group configured with insufficient authentication
           level - missing privacy encryption";
      }
      enum snmp-user-sha-auth-no-priv {
        value 53;
        description
          "SNMP user configured with SHA authentication but no privacy
           encryption - data transmitted in plain text";
      }
      enum snmp-user-sha2-auth-no-priv {
        value 54;
        description
          "SNMP user configured with SHA-2 authentication but no privacy
           encryption - data transmitted in plain text";
      }
      enum snmp-context-user-sha-auth-no-priv {
        value 55;
        description
          "SNMP context user configured with SHA authentication but no
           privacy encryption - data transmitted in plain text";
      }
      enum snmp-context-user-min-sec {
        value 56;
        description
          "SNMP context user configured with minimal security
           settings - missing proper authentication and privacy";
      }
      enum snmp-grp-no-acl {
        value 57;
        description
          "SNMP group configured with privacy but without proper access
           control lists - allows unrestricted SNMP access";
      }
      enum snmp-user-no-acl {
        value 58;
        description
          "SNMP user configured without proper access control lists - allows
           unrestricted SNMP access";
      }
      enum snmp-user-aes-priv-no-acl {
        value 59;
        description
          "SNMP user configured with AES privacy encryption but without
           access control lists - allows unrestricted SNMP access";
      }
      enum snmp-user-sha2-aes-priv-no-acl {
        value 60;
        description
          "SNMP user configured with SHA-2 authentication and AES privacy but
           without access control lists - allows unrestricted SNMP access";
      }
      enum snmp-context-user-aes-priv-no-acl {
        value 61;
        description
          "SNMP context user configured with AES privacy encryption but
           without access control lists - allows unrestricted SNMP access";
      }
      enum eap-fast-profile-local-key-weak-encr {
        value 62;
        description
          "EAP FAST profile local key configured with weak encryption
           (type 0 or 7) instead of secure type 6 or 9";
      }
      enum eap-fast-profile-pac-pwd-weak-encr {
        value 63;
        description
          "EAP FAST profile PAC password configured with weak encryption
           instead of secure type 6 or 9";
      }
      enum dot1x-cred-pwd-weak-encr {
        value 64;
        description
          "Dot1x credentials password configured with weak encryption
           instead of secure type 6 or 9";
      }
      enum mab-req-format-pwd-weak-encr {
        value 65;
        description
          "MAB request format password configured with weak encryption
           instead of secure type 6 or 9";
      }
      enum eap-profile-weak-cipher {
        value 66;
        description
          "EAP profile configured with weak cipher suite using
           SHA-1 - vulnerable to collision attacks";
      }
      enum eap-profile-weak-auth-meth {
        value 67;
        description
          "EAP profile configured with weak authentication method MD5 or
           LEAP - vulnerable to dictionary attacks";
      }
      enum access-sess-tls-ver-1-0 {
        value 68;
        description
          "Access session configured with TLS version 1.0 - deprecated and
           vulnerable to various attacks";
      }
      enum access-sess-all-tls-vers {
        value 69;
        description
          "Access session allowing all TLS
           versions - includes deprecated and vulnerable versions";
      }
      enum sec-weoauth-disabled {
        value 70;
        description
          "Secure web authentication disabled - allows unencrypted HTTP
           authentication vulnerable to credential theft";
      }
      enum cts-policy-srvr-pwd-weak-encr {
        value 71;
        description
          "CTS policy server password configured with weak encryption
           instead of secure type 6 or 9";
      }
      enum cts-cred-pwd-weak-encr {
        value 72;
        description
          "CTS credentials password configured with weak encryption
           instead of secure type 6 or 9";
      }
      enum cts-sxp-default-pwd-weak-encr {
        value 73;
        description
          "CTS SXP default password configured with weak encryption
           instead of secure type 6 or 9";
      }
      enum grp-policy-srvr-pwd-weak-encr {
        value 74;
        description
          "Group policy server password configured with weak encryption
           instead of secure type 6 or 9";
      }
      enum svc-pwd-encr-en {
        value 75;
        description
          "Service password-encryption enabled - uses weak type 7 encryption
           instead of secure type 6 or 9";
      }
      enum svc-pwd-encr-disabled {
        value 76;
        description
          "Service password-encryption disabled - passwords stored in
           plain text configuration";
      }
      enum parser-view-secret-type-5-encr {
        value 77;
        description
          "Parser view secret configured with type 5 (MD5)
           encryption - vulnerable to collision attacks";
      }
      enum logging-tls-profile-weak-cipher {
        value 78;
        description
          "Logging TLS profile configured with weak cipher suite
           using CBC mode and SHA-1";
      }
      enum logging-tls-profile-tls-ver-1-1 {
        value 79;
        description
          "Logging TLS profile configured with TLS
           version 1.1 - deprecated and vulnerable to attacks";
      }
      enum dsp-farm-profile-weak-tls-ver {
        value 80;
        description
          "DSP farm profile configured with TLS version 1.0 or
           1.1 - deprecated and vulnerable to attacks";
      }
      enum stcapp-sec-weak-tls-ver {
        value 81;
        description
          "SCCP Telephony Control Application security configured with TLS
           version 1.0 or 1.1 - deprecated and vulnerable to attacks";
      }
      enum access-point-dtls-ver-1-0 {
        value 82;
        description
          "Access Point DTLS version configured with DTLS 1.0 - deprecated
           and vulnerable to various attacks";
      }
      enum access-point-dtls-weak-cipher {
        value 83;
        description
          "Access Point DTLS cipher suite configured with weak ciphers
           using SHA-1 - vulnerable to collision attacks";
      }
      enum msdp-peer-pwd-weak-encr {
        value 84;
        description
          "MSDP peer password configured with weak encryption instead of
           secure type 6";
      }
      enum key-chain-key-str-weak-encr {
        value 85;
        description
          "key-string in key-chain configured with weak encryption
           (type 0, 7, or plain text) instead of secure type 6 encryption";
      }
      enum macsec-key-chain-key-str-weak-encr {
        value 86;
        description
          "key-string in macsec key-chain configured with weak encryption
           (type 0, 7, or plain text) instead of secure type 6 encryption";
      }
      enum voice-class-weak-cipher {
        value 87;
        description
          "Voice class configured with weak cipher suite - vulnerable
           to cryptographic attacks";
      }
      enum voice-class-strict-cipher-weak {
        value 88;
        description
          "Voice class strict-cipher configured with weak
           ciphers - includes vulnerable algorithms";
      }
      enum http-client-sec-cipher-weak {
        value 89;
        description
          "HTTP client secure ciphersuite configured with weak
           algorithms - vulnerable to cryptographic attacks";
      }
      enum http-client-no-sec-cipher {
        value 90;
        description
          "HTTP client secure ciphersuite disabled - allows weak
           cipher negotiations";
      }
      enum callmanager-fallback-weak-tls-ver {
        value 91;
        description
          "Call manager fallback configured with weak TLS version 1.0 or
           1.1 - deprecated and vulnerable";
      }
      enum callmanager-fallback-no-tls {
        value 92;
        description
          "Call manager fallback TLS disabled - allows unencrypted communication";
      }
      enum callmanager-fallback-default-tls {
        value 93;
        description
          "Call manager fallback TLS default configuration includes
           TLS 1.1 fallback - deprecated from 17.14+";
      }
      enum sip-crypto-signaling-strict-cipher {
        value 94;
        description
          "SIP crypto signaling configured with strict-cipher - includes
           weak cipher algorithms";
      }
      enum sip-no-crypto-signaling-default {
        value 95;
        description
          "SIP crypto signaling default disabled - removes encryption protection";
      }
      enum sip-ua-transport-weak-tls-ver {
        value 96;
        description
          "SIP-UA transport configured with weak TLS version 1.0 or
           1.1 - deprecated and vulnerable";
      }
      enum sip-ua-transport-default-tls {
        value 97;
        description
          "SIP-UA transport TLS default configuration includes TLS 1.1
           fallback - deprecated from 17.14+";
      }
      enum pmipv6-domain-auth-weak-encr {
        value 98;
        description
          "Proxy Mobile IPv6 domain authentication configured with weak
           encryption (type 0 or 7) instead of secure type 6";
      }
      enum pmipv6-lma-mag-auth-weak-encr {
        value 99;
        description
          "Proxy Mobile IPv6 Local Mobility Anchor - Mobile Access Gateway
           authentication configured with weak encryption (type 0 or 7)
           instead of secure type 6";
      }
      enum pmipv6-mag-lma-auth-weak-encr {
        value 100;
        description
          "Proxy Mobile IPv6 Mobile Access Gateway - Local Mobility Anchor
           authentication configured with weak encryption (type 0 or 7)
           instead of secure type 6";
      }
      enum pmipv6-lma-cust-auth-weak-encr {
        value 101;
        description
          "Proxy Mobile IPv6 Local Mobility Anchor - customer authentication
           configured with weak encryption (type 0 or 7) instead of
           secure type 6";
      }
      enum pmipv6-domain-mn-auth-weak-encr {
        value 102;
        description
          "Proxy Mobile IPv6 domain MN authentication configured with weak
           encryption (type 0 or 7) instead of secure type 6";
      }
      enum tls-tunnel-weak-cipher {
        value 103;
        description
          "tls tunnel using weak cipher suite RSA-AES256-CBC-SHA1";
      }
      enum device-sensor-dhcp-tftp-srvr-opt {
        value 104;
        description
          "Device sensor DHCP filter-list configured for TFTP server
           option - TFTP is an insecure protocol";
      }
      enum mon-capt-cont-insec-url {
        value 105;
        description
          "Monitor capture with continuous-capture option is using insecure URL";
      }
      enum mon-capt-export-insec-url {
        value 106;
        description
          "Monitor capture buffer is exporting using insecure URL";
      }
      enum ntp-auth-md5-vulnerable {
        value 107;
        description
          "NTP authentication using MD5 - vulnerable to collision attacks
           and should use stronger algorithms";
      }
      enum ntp-auth-key-weak-encr {
        value 108;
        description
          "NTP authentication key configured with weak encryption
           (type 0 or 7) instead of secure type 6 encryption";
      }
      enum ip-scp-sftp-pwd-weak-encr {
        value 109;
        description
          "IP SCP/SFTP password configured with weak encryption
           (type 0, 7 or plain text) instead of secure type 6 encryption";
      }
      enum http-client-pwd-weak-encr {
        value 110;
        description
          "HTTP client password configured with weak encryption
           (type 0, 5, or 7) instead of secure type 6 or 9 encryption";
      }
      enum dhcp-auth-shared-pwd-weak-encr {
        value 111;
        description
          "DHCP authorization shared-password configured with weak encryption
           (type 0, 5, or 7) instead of secure type 6 or 9";
      }
      enum ip-fwd-proto-udp-tftp-en {
        value 112;
        description
          "IP forward protocol for UDP TFTP enabled - can be exploited for
           unauthorized file transfers";
      }
      enum tftp-srvr-service-en {
        value 113;
        description
          "Provide TFTP service for net load requests - can be exploited for
           unauthorized file transfers";
      }
      enum udp-packet-limit-tftp-port-en {
        value 114;
        description
          "UDP packet limit for TFTP port configured - can be exploited for
           unauthorized file transfers";
      }
      enum snmp-user-no-auth-priv {
        value 115;
        description
          "SNMP user configured with no auth and no privacy encryption
           - data transmitted in plain text";
      }
      enum tftp-svr-en {
        value 116;
        description
          "TFTP server enabled - unencrypted file transfer protocol
           vulnerable to eavesdropping and tampering";
      }
      enum log-filter-insec-proto {
        value 117;
        description
          "Logging filter configured with insecure protocol";
      }
      enum tcl-init-insec-proto {
        value 118;
        description
          "Indicates that the Tool Command Language init file loaded using insecure protocol";
      }
      enum shell-init-insec-proto {
        value 119;
        description
          "Shell init file loaded using insecure protocol";
      }
      enum shell-map-insec-proto {
        value 120;
        description
          "Shell map operation using insecure protocol";
      }
      enum archive-path-insec-proto {
        value 121;
        description
          "Archive path configured with insecure protocol";
      }
      enum wsma-list-proto {
        value 122;
        description
          "WSMA profile listener using insecure transport protocol";
      }
      enum wsma-init-proto {
        value 123;
        description
          "WSMA profile initiator using insecure transport protocol";
      }
      enum snmp-ft-insec-proto {
        value 124;
        description
          "SNMP file transfer using an insecure protocol";
      }
      enum use-of-weak-pwd-or-key {
        value 125;
        description
          "Configured password or key is weak, uses a default keywords,
           or does not satisfy the AAA default policy requirements";
      }
      enum boot-sys-ft-insec-proto {
        value 126;
        description
          "Indicates that the boot system command is configured to use an insecure file transfer protocol.";
      }
      enum crypto-pki-ft-insec-proto {
        value 127;
        description
          "Indicates that the Crypto PKI command is configured to use an insecure file transfer protocol.";
      }
      enum dhcp-snoop-db-insec-ft {
        value 128;
        description
          "DHCP snooping database configured with an insecure file transfer protocol";
      }
      enum ip-dhcp-bootp-ignore-disable {
        value 129;
        description
          "ip dhcp bootp ignore disabled - device will respond to BOOTP requests, which is a legacy protocol with security vulnerabilities";
      }
      enum action-playmsg {
        value 130;
        description
          "Call treatment action play message configured with an insecure file transfer URL.";
      }
      enum event-trace {
        value 131;
        description
          "VoIP event trace dump file configured with an insecure file transfer URL.";
      }
      enum dnis-map {
        value 132;
        description
          "Voice DNIS map configured with an insecure file transfer URL.";
      }
      enum accounting-template {
        value 133;
        description
          "Voice call accounting template configured with an insecure file transfer URL.";
      }
      enum ivr-autoload {
        value 134;
        description
          "Interactive voice response automatic load URL configured with an insecure file transfer protocol.";
      }
      enum ivr-autoload-mode {
        value 135;
        description
          "Interactive voice response automatic load mode URL configured with an insecure file transfer protocol.";
      }
      enum asr-server {
        value 136;
        description
          "Automatic speech recognition server configured with an insecure real-time streaming URL.";
      }
      enum tts-server {
        value 137;
        description
          "Text-to-speech server configured with an insecure real-time streaming URL.";
      }
      enum service-debitcard {
        value 138;
        description
          "Service debit card configured with an insecure file transfer URL.";
      }
      enum package-language {
        value 139;
        description
          "Package language configured with an insecure file transfer URL.";
      }
      enum param-prompt {
        value 140;
        description
          "Parameter prompt configured with an insecure file transfer URL.";
      }
      enum cred-authenticate {
        value 141;
        description
          "Authenticate credential configured with an insecure file transfer URL.";
      }
      enum e164-pattern-map {
        value 142;
        description
          "Voice class E164 pattern map configured with an insecure file transfer URL.";
      }
      enum e164-translation {
        value 143;
        description
          "Voice class E164 translation configured with an insecure file transfer URL.";
      }
      enum voice-dnis-maps {
        value 144;
        description
          "Voice DNIS maps configured with an insecure file transfer URL.";
      }
      enum voice-proxy-tftp-addr {
        value 145;
        description
          "Voice phone proxy TFTP address configured with an insecure file transfer protocol.";
      }
      enum per-call-export-insecure {
        value 146;
        description
          "Per-call export primary or secondary endpoint configured with an insecure transport protocol.";
      }
      enum srv-pwd-enc {
        value 147;
        description
          "Sensitive information like passwords and keys use weak encryption";
      }
      enum macro-auto-exec-insec-ft {
        value 148;
        description
          "Indicates that the macro auto-execute feature
           is configured to use an insecure file transfer protocol.";
      }
      enum aaa-radius-sa-not-enable {
        value 149;
        description
          "RADIUS Message-Authenticator send is not enabled, leaving the
           configuration vulnerable to Blast Radius attacks";
      }
      enum aaa-radius-va-not-enable {
        value 150;
        description
          "RADIUS Message-Authenticator validation is not enabled, leaving the
           configuration vulnerable to Blast Radius attacks";
      }
      enum aaa-radius-no-tls {
        value 151;
        description
          "RADIUS server is configured without TLS, exposing traffic
           to potential eavesdropping";
      }
      enum aaa-tacacs-no-tls {
        value 152;
        description
          "TACACS+ server is configured without TLS, exposing traffic
           to potential eavesdropping";
      }
      enum aaa-ldap-no-tls {
        value 153;
        description
          "LDAP server is configured without TLS, exposing traffic
           to potential eavesdropping";
      }
      enum tcl-encdir-insec-proto {
        value 154;
        description
          "Indicates that the Tool Command Language encoding directory is configured using an insecure protocol";
      }
      enum ftp-voice-stat {
        value 155;
        description
          "Indicates that voice statistics are configured to use FTP, which is an insecure file transfer protocol.";
      }
      enum http-voice-ivr-prompt {
        value 156;
        description
          "Indicates that the IVR prompt is configured to use HTTP, which is an insecure transport protocol.";
      }
      enum http-voice-ivr-jitter {
        value 157;
        description
          "Indicates that the IVR jitter buffer is configured to use HTTP, which is an insecure transport protocol.";
      }
      enum ftp-voice-gw-acct-pri {
        value 158;
        description
          "Indicates that the primary voice gateway accounting server is configured to use FTP, which is an insecure file transfer protocol.";
      }
      enum ftp-voice-gw-acct-sec {
        value 159;
        description
          "Indicates that the secondary voice gateway accounting server is configured to use FTP, which is an insecure file transfer protocol.";
      }
      enum ftp-voice-call-leg {
        value 160;
        description
          "Indicates that the voice call leg is configured to use FTP, which is an insecure file transfer protocol.";
      }
      enum ftp-voice-event-log {
        value 161;
        description
          "Indicates that the voice event log is configured to use FTP, which is an insecure file transfer protocol.";
      }
      enum ftp-voice-intf-event-log {
        value 162;
        description
          "Indicates that the voice interface event log is configured to use FTP, which is an insecure file transfer protocol.";
      }
      enum http-voice-web-svc {
        value 163;
        description
          "Indicates that the voice web service is configured to use HTTP, which is an insecure transport protocol.";
      }
      enum ntp-allow-mode-ctrl-en {
        value 164;
        description
          "NTP allow mode control enabled - susceptible to Distributed Denial of Service (DDoS) attacks";
      }
      enum ntp-no-auth {
        value 165;
        description
          "NTP configured without authentication";
      }
      enum ipsla-insec-proto {
        value 166;
        description
          "Indicates that the IP SLA command is configured to use an insecure protocol.";
      }
      enum gnxi-srvr-insec {
        value 167;
        description
          "The insecure gNxI (gNMI/gNOI) server is unencrypted and does not support authentication.";
      }
      enum gnxi-tunnel-insec {
        value 168;
        description
          "The insecure gRPC tunnel target type will target the insecure gNxI (gNMI/gNOI) server";
      }
      enum crft-collect-on-reload-insec {
        value 169;
        description
          "Indicates that CRFT collect-on-reload is configured to use FTP, HTTP, or TFTP, which are insecure file transfer protocols.";
      }
    }
    description
      "Insecure configuration description";
  }

  typedef insec-conf-submode {
    type enumeration {
      enum sm-unknown {
        value 0;
        description
          "unknown submode";
      }
      enum sm-config {
        value 1;
        description
          "Global configuration submode. It is a top level config submode
           entered via 'config terminal' CLI";
      }
      enum sm-conf-rad-srvr {
        value 2;
        description
          "configure RADIUS server submode";
      }
      enum sm-conf-tac-srvr {
        value 3;
        description
          "configure TACACS server submode";
      }
      enum sm-sg-radius {
        value 4;
        description
          "SG-RADIUS submode";
      }
      enum sm-radius-da-locsvr {
        value 5;
        description
          "RADIUS-DA local server submode";
      }
      enum sm-conf-ldap-srvr {
        value 6;
        description
          "configure LDAP server submode";
      }
      enum sm-radius-sesm-locsvr {
        value 7;
        description
          "RADIUS SES manager local server submode";
      }
      enum sm-radius-proxy-locsvr {
        value 8;
        description
          "RADIUS proxy local server submode";
      }
      enum sm-radius-policy-device-locsvr {
        value 9;
        description
          "RADIUS policy device local server submode";
      }
      enum sm-sg-tacacs-plus {
        value 10;
        description
          "SG-TACACS+ submode";
      }
      enum sm-key-chain-tcp-key {
        value 11;
        description
          "key-chain TCP key submode";
      }
      enum sm-line {
        value 12;
        description
          "line submode";
      }
      enum sm-router {
        value 13;
        description
          "router submode";
      }
      enum sm-eap-mprofile-mode {
        value 14;
        description
          "EAP managed profile submode";
      }
      enum sm-dot1x-cred-mode {
        value 15;
        description
          "DOT1X credential submode";
      }
      enum sm-eap-profile-mode {
        value 16;
        description
          "EAP profile submode";
      }
      enum sm-param-submode {
        value 17;
        description
          "parameter submode";
      }
      enum sm-view {
        value 18;
        description
          "view submode";
      }
      enum sm-tls-profile {
        value 19;
        description
          "TLS profile submode";
      }
      enum sm-dspfarmprofile {
        value 20;
        description
          "DSPFARM profile submode";
      }
      enum sm-key-chain-key {
        value 21;
        description
          "key-chain-key submode";
      }
      enum sm-key-chain-macsec-key {
        value 22;
        description
          "key-chain MACSEC key submode";
      }
      enum sm-voiceclass {
        value 23;
        description
          "voice class submode";
      }
      enum sm-cm-fallback {
        value 24;
        description
          "CM fallback submode";
      }
      enum sm-sip-ua {
        value 25;
        description
          "SIP-UA submode";
      }
      enum sm-ipv6-pmipv6-domain {
        value 26;
        description
          "IPv6-pm IPv6-domain submode";
      }
      enum sm-ipv6-pmipv6-lma-mag {
        value 27;
        description
          "IPv6-pm IPv6 Local Mobility Anchor - Mobile Access Gateway submode";
      }
      enum sm-ipv6-pmipv6-mag-lma {
        value 28;
        description
          "IPv6-pm IPv6 Mobile Access Gateway -  Local Mobility Anchor submode";
      }
      enum sm-ipv6-pmipv6-lma-cust {
        value 29;
        description
          "IPv6-pm IPv6 Local Mobility Anchor - Customer submode";
      }
      enum sm-ipv6-pmipv6-domain-mn {
        value 30;
        description
          "IPv6-pm IPv6-domain MN submode";
      }
      enum sm-tls-tunnel {
        value 31;
        description
          "TLS tunnel submode";
      }
      enum sm-exec {
        value 32;
        description
          "EXEC submode";
      }
      enum sm-if {
        value 33;
        description
          "interface submode";
      }
      enum sm-archive {
        value 34;
        description
          "Represents the archive configuration submode";
      }
      enum sm-sep-list {
        value 35;
        description
          "sep listener submode";
      }
      enum sm-sep-init {
        value 36;
        description
          "sep initiator submode";
      }
      enum sm-sensor-dhcp-list {
        value 37;
        description
          "Indicates that the insecure configuration was detected in the Device Sensor DHCP filter list submode.";
      }
      enum sm-aaa-filter-server {
        value 38;
        description
          "AAA filter server submode";
      }
      enum sm-aaa-locsvr-client {
        value 39;
        description
          "AAA RADIUS local server client submode";
      }
      enum sm-aaa-snmp {
        value 40;
        description
          "AAA SNMP submode";
      }
      enum sm-user-name {
        value 41;
        description
          "User-name configuration submode";
      }
      enum sm-crypto-ca-tp {
        value 42;
        description
          "Crypto CA trustpoint configuration submode";
      }
      enum sm-config-voice {
        value 43;
        description
          "Voice configuration submode";
      }
      enum sm-config-voice-app {
        value 44;
        description
          "Voice application configuration submode";
      }
      enum sm-config-voice-reg-global {
        value 45;
        description
          "Global voice registration configuration submode";
      }
      enum sm-config-voice-dnis-maps {
        value 46;
        description
          "Voice DNIS maps configuration submode";
      }
      enum sm-gw-acct {
        value 47;
        description
          "Indicates the gateway accounting configuration submode context for an insecure configuration detection entry.";
      }
      enum sm-app-mon {
        value 48;
        description
          "Indicates the application monitor configuration submode context for an insecure configuration detection entry.";
      }
      enum sm-ip-sla {
        value 49;
        description
          "Indicates the IP SLA configuration submode context for an insecure configuration detection entry.";
      }
      enum sm-ip-sla-path-echo {
        value 50;
        description
          "Indicates the IP SLA LSR path echo configuration submode context for an insecure configuration detection entry.";
      }
      enum sm-ip-sla-path-jitter {
        value 51;
        description
          "Indicates the IP SLA LSR path jitter configuration submode context for an insecure configuration detection entry.";
      }
    }
    description
      "Configuration submode which owns the insecure CLI";
  }

  typedef sys-insec-evt-type {
    type enumeration {
      enum insec-conf {
        value 0;
        description
          "Event to notify of newly added insecure configuration";
      }
      enum insec-warn {
        value 1;
        description
          "Event to notify of insecure configuration allowed when system security mode is secure";
      }
    }
    description
      "System insecure configuration event type";
  }

  grouping sys-insec-info {
    description
      "System insecure configuration information";
    leaf config-cli {
      type string;
      description
        "Specifies the configuration CLI command that has been identified as insecure by the system security process.";
    }
    leaf parent-cli {
      type string;
      description
        "Specifies the parent CLI submode or context from which this configuration command is derived";
    }
    leaf desc {
      type system-security-types-ios-xe-oper:insec-conf-desc;
      description
        "Provides a human-readable description of the configuration CLI command or context";
    }
    leaf module {
      type system-security-types-ios-xe-oper:insec-conf-module;
      description
        "Indicates the software module responsible for the insecure configuration CLI command.";
    }
    leaf reason {
      type system-security-types-ios-xe-oper:insec-conf-reason;
      description
        "Describes the reason why the configuration CLI command has been classified as insecure.";
    }
    leaf remedy {
      type system-security-types-ios-xe-oper:insec-conf-remedy;
      description
        "Specifies the recommended remediation action to address the insecure configuration CLI command.";
    }
    leaf submode {
      type system-security-types-ios-xe-oper:insec-conf-submode;
      description
        "Indicates the specific configuration submode or context in which the CLI command is executed";
    }
  }
}
