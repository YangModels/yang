module Cisco-IOS-XE-ipv6-oper {
  yang-version 1.1;
  namespace "http://cisco.com/ns/yang/Cisco-IOS-XE-ipv6-oper";
  prefix ipv6-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for IPv6 operational data.
     Copyright (c) 2017, 2019, 2022, 2026 by Cisco Systems, Inc.
     All rights reserved.";

  revision 2026-08-01 {
    description
      "Updated descriptions of several model elements to clarify their meaning and purpose.";
    reference
      "1.3.1";
    cisco-semver:module-version "1.3.1";
  }
  revision 2022-11-01 {
    description
      "Update yang-version to 1.1";
    reference
      "1.3.0";
    cisco-semver:module-version "1.3.0";
  }
  revision 2019-05-01 {
    description
      "Added semantic version";
    reference
      "1.2.0";
    cisco-semver:module-version "1.2.0";
  }
  revision 2018-10-29 {
    description
      "Cleaned up spelling errors in descriptions.";
    reference
      "1.1.0";
    cisco-semver:module-version "1.1.0";
  }
  revision 2017-11-01 {
    description
      "Initial revision";
    reference
      "1.0.0";
    cisco-semver:module-version "1.0.0";
  }

  typedef ipv6-nd-tdl-state {
    type enumeration {
      enum ipv6-nd-incomplete {
        value 0;
        description
          "Address resolution is in progress and the
           link-layer address of the neighbor has not
           yet been determined.";
      }
      enum ipv6-nd-reachable {
        value 1;
        description
          "The neighbor is known to have been reachable
           recently (within tens of seconds ago).";
      }
      enum ipv6-nd-stale {
        value 2;
        description
          "The neighbor is no longer known to be reachable
           but until traffic is sent to the neighbor, no
           attempt should be made to verify its reachability";
      }
      enum ipv6-nd-glean {
        value 3;
        description
          "Received updated link-layer information.
           Behaviour like STALE.";
      }
      enum ipv6-nd-delay {
        value 4;
        description
          "The neighbor is no longer known to be reachable, and traffic
           has recently been sent to the neighbor. Rather than probe the
           neighbor immediately, however, delay sending probes for a short
           while in order to give upper layer protocols a chance to provide
           reachability confirmation.";
      }
      enum ipv6-nd-probe {
        value 5;
        description
          "The neighbor is no longer known to be reachable, and unicast
           Neighbor Solicitation probes are being sent to verify
           reachability.";
      }
      enum ipv6-nd-delete {
        value 6;
        description
          "Entry is deleted.";
      }
    }
    description
      "Indicate the current state of
       the Neighbor-Discovery entry.";
  }

  grouping nd6-info-key {
    description
      "Key for IPv6 neighbor information table";
    leaf vrf-name {
      type string;
      description
        "The Virtual Router and Forwarding instance that
         this neighbor information is associated with";
    }
    leaf if-name {
      type string;
      description
        "Specifies the name of the interface associated with this IPv6 neighbor entry.";
    }
    leaf ip {
      type inet:ip-address;
      description
        "IPv6 address of this neighbor entry";
    }
  }

  grouping nd6-info {
    description
      "Value for IPv6 neighbor info table entry";
    leaf mac-address {
      type yang:mac-address;
      description
        "Specifies the MAC address associated with this IPv6 neighbor entry.";
    }
    leaf state {
      type ipv6-ios-xe-oper:ipv6-nd-tdl-state;
      description
        "State of the entry";
    }
    leaf idle-timer {
      type uint32;
      description
        "Time before expiration, in seconds.";
    }
    leaf uptime {
      type uint32;
      description
        "Indicates how long this neighbor entry has
         been active, in seconds";
    }
  }

  container ipv6-data {
    config false;
    description
      "Operational state of IPv6";
    list nd6-info {
      key "vrf-name if-name ip";
      description
        "List of IPv6 neighbors";
      uses ipv6-ios-xe-oper:nd6-info-key;
      uses ipv6-ios-xe-oper:nd6-info;
    }
  }
}
