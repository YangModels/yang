/*
 * Generated by confdc --mib2yang-std
 * Source: mgmt/dmi/model/mib/src/CISCO-CBP-TC-MIB.mib
 */
/*
 * This YANG module has been generated by smidump 0.5.0:
 *
 *      smidump -f yang CISCO-CBP-TC-MIB
 *
 * Do not edit. Edit the source file instead!
 */

module CISCO-CBP-TC-MIB {

  namespace "urn:ietf:params:xml:ns:yang:smiv2:CISCO-CBP-TC-MIB";
  prefix CISCO-CBP-TC-MIB;

  import ietf-yang-smiv2 {
    prefix "smiv2";
  }

  organization
   "Cisco Systems, Inc.";

  contact
   "Cisco Systems
    Customer Service
    
    Postal: 170 W Tasman Drive
    San Jose, CA 95134
    
    Tel: +1 800 553-NETS
    
    E-mail: cs-snmp@cisco.com";

  description
   "This MIB module defines textual conventions used by the
    CISCO-CBP-BASE-CFG-MIB, CISCO-CBP-BASE-MON-MIB, and any MIB
    modules extending these MIB modules.";

  revision 2008-06-24 {
    description
     "The initial version of the MIB module.";
  }

  typedef CbpElementName {
    type string;
    description
     "A string-value that identifies an element used to specify
      a class-based policy.  The semantics of the string-value are
      the same those specified by the SnmpAdminString textual
      convention defined by the SNMP-FRAMEWORK-MIB [RFC3411].
      
      Observe that the null string is reserved for cases when an
      instance of an object needs to specify 'no element'.";
    reference
     "D. Harrington, R. Resuhn, B. Wijnen, 'An Architecture for
      Describing Simple Network Management Protocol (SNMP)
      Management Frameworks', RFC-3411, December 2002.";
    smiv2:display-hint "127a";
  }

  typedef CbpElementIdentifier {
    type uint32 {
      range "1..4294967295";
    }
    description
     "A positive, non-zero integer-value that uniquely identifies
      an element used to specify a class-based policy.";
  }

  typedef CbpElementIdentifierOrZero {
    type uint32 {
      range "0..4294967295";
    }
    description
     "This textual convention serves as an extension of the
      CbpElementIdentifier textual convention, which permits the value
      '0'.  The use of the value '0' is specific to an object, thus
      requiring the descriptive text associated with the object to
      describe the semantics of its use.";
  }

  typedef CbpInstanceIdentifier {
    type uint32 {
      range "1..4294967295";
    }
    description
     "A positive, non-zero integer-value that uniquely identifies
      an instance of an element used to define a class-based policy.";
  }

  typedef CbpInstanceIdentifierOrZero {
    type uint32 {
      range "0..4294967295";
    }
    description
     "This textual convention serves as an extension of the
      CbpInstanceIdentifier textual convention, which permits the
      value '0'.  The use of the value '0' is specific to an object,
      thus requiring the descriptive text associated with the object
      to describe the semantics of its use.";
  }

  typedef CbpExecutionPriority {
    type uint32 {
      range "1..4294967295";
    }
    description
     "An positive, integer-value denoting the relative priority of an
      element, where '1' represents the highest priority and greater
      values represent lower priorities.
      
      The priority assigned to an element determines the order in
      which the system processes the elements relative to like
      elements having the same parent, where the system processes
      elements having a greater priority first.  The system processes
      sibling elements having the same priority in the order they were
      created.";
  }

  typedef CbpExecutionStrategy {
    type enumeration {
      enum "other" {
        value "1";
      }
      enum "doUntilSuccess" {
        value "2";
      }
      enum "doUntilFailure" {
        value "3";
      }
      enum "doAll" {
        value "4";
      }
    }
    description
     "An enumerated integer-value describing how to execute an
      ordered set of actions:
      
          'other'
              The implementation of the MIB using this textual
              convention does not recognize the specified execution
              strategy.
      
          'doUntilSuccess'
              The system sequentially executes the actions in the
              set until one succeeds.
      
          'doUntilFailure'
              The system sequentially executes the actions in the
              set until one fails.
      
          'doAll'
              The system sequentially executes all actions in the set,
              regardless of whether they succeed or fail.";
  }

  smiv2:alias "ciscoCbpTcMIB" {
    smiv2:oid "1.3.6.1.4.1.9.9.662";
  }

}
