/*
 * Generated by confdc --mib2yang-std
 * Source: mgmt/dmi/model/mib/src/CISCO-IPSLA-TC-MIB.mib
 */
/*
 * This YANG module has been generated by smidump 0.5.0:
 *
 *      smidump -f yang CISCO-IPSLA-TC-MIB
 *
 * Do not edit. Edit the source file instead!
 */

module CISCO-IPSLA-TC-MIB {

  namespace "urn:ietf:params:xml:ns:yang:smiv2:CISCO-IPSLA-TC-MIB";
  prefix CISCO-IPSLA-TC-MIB;

  import ietf-yang-smiv2 {
    prefix "smiv2";
  }

  organization
   "Cisco Systems, Inc.";

  contact
   "Cisco Systems, Inc.
    Customer Service 
    
    Postal: 170 W Tasman Drive
    San Jose, CA 95134
    
    Tel: +1 800 553 NETS
    Email: cs-ipsla@cisco.com";

  description
   "This MIB contains textual conventions used by
    CISCO IPSLA MIBs.
    
    Acronyms:
     FEC: Forward Equivalence Class
     LPD: Label Path Discovery
     LSP: Label Switched Path
     MPLS: Multi Protocol Label Switching
     RTT: Round Trip Time
     SAA: Service Assurance Agent
     SLA: Service Level Agreement
     VPN: Virtual Private Network
     ICPIF: Calculated Planning Impairment Factor";

  revision 2007-03-23 {
    description
     "Initial version of this MIB module.";
  }

  typedef IpSlaOperType {
    type enumeration {
      enum "icmpEcho" {
        value "1";
      }
      enum "udpEcho" {
        value "2";
      }
      enum "tcpConnect" {
        value "3";
      }
      enum "udpJitter" {
        value "4";
      }
      enum "icmpJitter" {
        value "5";
      }
    }
    description
     "Specifies the type of IP SLA operation to be performed.
      
      icmpEcho(1)   -  The value 'icmpEcho' will cause the
                       IP SLA application to  perform a timed 
                       ICMP echo request/response operation.
      
      
      udpEcho(2)    -  The value 'udpEcho' will cause the IP SLA 
                       application to perform a timed udp packet 
                       send/receive operation. 
      
      tcpConnect(3) -  The value 'tcpConnect' will cause the IP 
                       SLA application to perform a timed TCP 
                       connect operation. 
      
      udpJitter(4)  -  The value 'udpjitter' will cause the IP
                       SLA application to perform delay variance
                       analysis using UDP timestamp packets. 
      
      icmpjitter(5) -  The value 'icmpjitter' will cause the IP 
                       SLA application to perform delay variance 
                       analysis using ICMP timestamp packets.";
  }

  typedef IpSlaCodecType {
    type enumeration {
      enum "notApplicable" {
        value "0";
      }
      enum "g711ulaw" {
        value "1";
      }
      enum "g711alaw" {
        value "2";
      }
      enum "g729a" {
        value "3";
      }
    }
    description
     "Specifies the IP SLA codec type to be used with the UDP 
      jitter operation. The following codec types are defined:
      
      notApplicable(0)     - no CodecType is defined
      
      g711ulaw(1)          - uses G.711 U Law 64000 bps
      
      g711alaw(2)          - uses G.711 A Law 64000 bps
      
      g729a(3)             - uses G.729 8000 bps";
  }

  typedef IpSlaReactVar {
    type enumeration {
      enum "rtt" {
        value "1";
      }
      enum "jitterSDAvg" {
        value "2";
      }
      enum "jitterDSAvg" {
        value "3";
      }
      enum "packetLossSD" {
        value "4";
      }
      enum "packetLossDS" {
        value "5";
      }
      enum "mos" {
        value "6";
      }
      enum "timeout" {
        value "7";
      }
      enum "connectionLoss" {
        value "8";
      }
      enum "verifyError" {
        value "9";
      }
      enum "jitterAvg" {
        value "10";
      }
      enum "icpif" {
        value "11";
      }
      enum "packetMIA" {
        value "12";
      }
      enum "packetLateArrival" {
        value "13";
      }
      enum "packetOutOfSequence" {
        value "14";
      }
      enum "maxOfPositiveSD" {
        value "15";
      }
      enum "maxOfNegativeSD" {
        value "16";
      }
      enum "maxOfPositiveDS" {
        value "17";
      }
      enum "maxOfNegativeDS" {
        value "18";
      }
      enum "successivePacketLoss" {
        value "19";
      }
      enum "maxOfLatencyDS" {
        value "20";
      }
      enum "maxOfLatencySD" {
        value "21";
      }
      enum "latencyDSAvg" {
        value "22";
      }
      enum "latencySDAvg" {
        value "23";
      }
      enum "packetLoss" {
        value "24";
      }
    }
    description
     "The following are specific reaction variables for an
      IP SLA operation to react upon:
      
       rtt(1)            - Round Trip Time
      
       jitterSDAvg(2)    - Jitter average from source to
                           destination  
      
       jitterDSAvg(3)    - Jitter average from destination 
                           to source  
      
       packetLossSD(4)   - Packet loss from source to 
                           destination 
      
       packetLossDS(5)   - Packet loss from destination 
                           to source 
      
       mos(6)            - Mean Opinion Score  
      
       timeout(7)        - Timeout of the operation
      
       connectionLoss(8) - Connection failed to the destination
      
       verifyError(9)    - Data corruption occurs
      
       jitterAvg(10)     - Jitter average in both directions
      
       icpif(11)         - Calculated Planning Impairment Factor
      
       packetMIA(12)     - Missed packets in operation
      
       packetLateArrival(13)   - Packets arriving late
      
       packetOutOfSequence(14) - Packets arriving out of sequence
      
       maxOfPositiveSD(15)     - Maximum positive jitter from
                                 source to destination
      
       maxOfNegativeSD(16)     - Maximum negative jitter from
                                 source to destination
      
       maxOfPositiveDS(17)     - Maximum positive jitter from
                                 destination to source
      
       maxOfNegativeDS(18)     - Maximum negative jitter from
                                 destination to source.
      
       successivePacketLoss(19)- Successive packet dropped 
      
       maxOfLatencyDS(20)      - Maximum Latency from
                                 Destination to Source
      
       maxOfLatencySD(21)      - Maximum Latency from Source 
                                 to Destination
      
       latencyDSAvg(22)        - Latency average from Destination 
                                 to Source
      
       latencySDAvg(23)        - Latency average from Source 
                                 to Destination
      
       packetLoss(24)          - Packets loss in both directions";
  }

  smiv2:alias "ciscoIpSlaTCMIB" {
    smiv2:oid "1.3.6.1.4.1.9.9.624";
  }

}
