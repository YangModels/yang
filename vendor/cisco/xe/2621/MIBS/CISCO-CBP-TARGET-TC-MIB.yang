/*
 * Generated by confdc --mib2yang-std
 * Source: mgmt/dmi/model/mib/src/CISCO-CBP-TARGET-TC-MIB.mib
 */
/*
 * This YANG module has been generated by smidump 0.5.0:
 *
 *      smidump -f yang CISCO-CBP-TARGET-TC-MIB
 *
 * Do not edit. Edit the source file instead!
 */

module CISCO-CBP-TARGET-TC-MIB {

  namespace "urn:ietf:params:xml:ns:yang:smiv2:CISCO-CBP-TARGET-TC-MIB";
  prefix CISCO-CBP-TARGET-TC-MIB;

  import ietf-yang-smiv2 {
    prefix "smiv2";
  }

  organization
   "Cisco Systems, Inc.";

  contact
   "          Cisco Systems
    Customer Service
    
    Postal: 170 W. Tasman Drive
    San Jose, CA 95134-1706
    USA
    
    Tel: +1 800 553-NETS
    
    E-mail: cs-qos@cisco.com, cs-c3pl@cisco.com";

  description
   "This MIB module defines Textual Conventions for
    representing targets which have class based policy 
    mappings. A target can be any logical interface 
    or entity to which a class based policy is able to be 
    associated.";

  revision 2006-03-24 {
    description
     "Initial version.";
  }

  typedef CcbptTargetType {
    type enumeration {
      enum "genIf" {
        value "1";
      }
      enum "atmPvc" {
        value "2";
      }
      enum "frDlci" {
        value "3";
      }
      enum "entity" {
        value "4";
      }
      enum "fwZone" {
        value "5";
      }
      enum "fwZonePair" {
        value "6";
      }
      enum "aaaSession" {
        value "7";
      }
    }
    description
     "A Textual Convention that represents a type of target.
      
      genIf(1)    A target of type interface defined by 
                  CcbptTargetIdIf Textual Convention.
      
      atmPvc(2)   A target of type ATM PVC defined 
                  by the CcbptTargetIdAtmPvc Textual Convention.
      
      frDlci(3)   A target of type Frame Relay DLCI 
                  defined by the CcbptTargetIdFrDlci Textual 
                  Convention.
      
      entity(4) A target of type entity defined by the 
                CcbptTargetIdEntity Textual Convention.  This target
                type is used to indicate the attachment of a Class 
                Based Policy to a physical entity.
      
      fwZone(5)   A target of type Firewall Security Zone
                  defined by the CcbptTargetIdNameString 
                  Textual Convention.
      
      fwZonePair(6) A target of type Firewall Security Zone 
                    defined by the CcbptTargetIdNameString
                    Textual Convention.
      
      aaaSession(7) A target of type AAA Session define by the
                    CcbptTargetIdAaaSession Textual Convention.";
  }

  typedef CcbptTargetDirection {
    type enumeration {
      enum "undirected" {
        value "1";
      }
      enum "input" {
        value "2";
      }
      enum "output" {
        value "3";
      }
      enum "inOut" {
        value "4";
      }
    }
    description
     "A Textual Convention that represents a direction for a target.
      
      undirected(1)    Indicates that direction has no meaning 
                       relative to the target.
      
      input(2)    Refers to the input direction relative to the 
                  target.
      
      output(3)   Refers to the output direction relative to the
                  target.
      
      inOut(4)    Refers to both the input and output directions
                  relative to the target.";
  }

  typedef CcbptTargetId {
    type binary {
      length "0..64";
    }
    description
     "Denotes a generic target ID.
      
      A CcbptTargetId value is always interpreted within the 
      context of an CcbptTargetType value. Every usage of the 
      CcbptTargetId Textual Convention is required to specify the
      CcbptTargetType object which provides the context. It is 
      suggested that the CcbptTargetType object is logically 
      registered before the object(s) which use the CcbptTargetId
      Textual Convention if they appear in the same logical row.
      
      The value of an CcbptTargetId object must always be
      consistent with the value of the associated CcbptTargetType
      object. Attempts to set a CcbptTargetId object to a value
      which is inconsistent with the associated targetType
      must fail with an inconsistentValue error.";
  }

  typedef CcbptTargetIdIf {
    type string;
    description
     "Represents an interface target:
      
      octets   contents              encoding
       1-4     ifIndex               network-byte order";
    smiv2:display-hint "4d";
  }

  typedef CcbptTargetIdAtmPvc {
    type string;
    description
     "Represents an ATM PVC target:
      
      octets    contents              encoding
       1-4      ifIndex               network-byte order
       5-6      atmVclVpi             network-byte order
       7-8      atmVclVci             network-byte order";
    smiv2:display-hint "4d:2d:2d";
  }

  typedef CcbptTargetIdFrDlci {
    type string;
    description
     "Represents a Frame Relay DLCI target:
      
      octets   contents               encoding
       1-4     ifIndex                network-byte order
       5-6     DlciNumber             network-byte order";
    smiv2:display-hint "4d:2d";
  }

  typedef CcbptTargetIdEntity {
    type string;
    description
     "Represents the entPhysicalIndex of the physical entity 
      target:
      
        octets   contents               encoding
         1-4     entPhysicalIndex       network-byte order";
    smiv2:display-hint "4d";
  }

  typedef CcbptTargetIdNameString {
    type binary {
      length "0..64";
    }
    description
     "Represents a target identified by a name string.  
      This is the ASCII name identifying this target.";
  }

  typedef CcbptTargetIdAaaSession {
    type string;
    description
     "Represents a AAA Session target:
      
      octets   contents               encoding
       1-4     casnSessionId      network-byte order";
    smiv2:display-hint "4d";
  }

  typedef CcbptPolicySourceType {
    type enumeration {
      enum "ciscoCbQos" {
        value "1";
      }
      enum "ciscoCbpBase" {
        value "2";
      }
    }
    description
     "This Textual Convention represents the types of sources of 
      policies.
      
      ciscoCbQos(1)      Cisco Class Based QOS policy source.
                         The source of the policy is Cisco Class 
                         Based QOS specific.
      
      ciscoCbpCommon(2)  Cisco Common Class Based Policy type.
                         The source of the policy is Cisco Common
                         Class Based.";
  }

  typedef CcbptPolicyIdentifier {
    type uint32 {
      range "1..4294967295";
    }
    description
     "A type specific, arbitrary identifier uniquely given
      to a policy-map attachment to a target.";
  }

  typedef CcbptPolicyIdentifierOrZero {
    type uint32 {
      range "0..4294967295";
    }
    description
     "This refers to CcbptPolicyIdentifier values, as applies, 
      or 0.  The behavior of the value of 0 should be described
      in the description of objects using this type.";
  }

  smiv2:alias "ciscoCbpTargetTCMIB" {
    smiv2:oid "1.3.6.1.4.1.9.9.511";
  }

}
