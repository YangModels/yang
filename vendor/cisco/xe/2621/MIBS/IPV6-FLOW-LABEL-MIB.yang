/*
 * Generated by confdc --mib2yang-std
 * Source: mgmt/dmi/model/mib/src/IPV6-FLOW-LABEL-MIB.mib
 */
/*
 * This YANG module has been generated by smidump 0.5.0:
 *
 *      smidump -f yang IPV6-FLOW-LABEL-MIB
 *
 * Do not edit. Edit the source file instead!
 */

module IPV6-FLOW-LABEL-MIB {

  namespace "urn:ietf:params:xml:ns:yang:smiv2:IPV6-FLOW-LABEL-MIB";
  prefix IPV6-FLOW-LABEL-MIB;

  import ietf-yang-smiv2 {
    prefix "smiv2";
  }

  organization
   "IETF Operations and Management Area";

  contact
   "Bert Wijnen (Editor) 
    Lucent Technologies 
    Schagen 33 
    3461 GL Linschoten 
    Netherlands 
    Phone: +31 348-407-775 
    EMail: bwijnen@lucent.com 
    
    Send comments to <mibs@ops.ietf.org>. ";

  description
   "This MIB module provides commonly used textual 
    conventions for IPv6 Flow Labels. 
    
    Copyright (C) The Internet Society (2003).  This 
    version of this MIB module is part of RFC 3595, 
    see the RFC itself for full legal notices. ";

  revision 2003-08-28 {
    description
     "Initial version, published as RFC 3595.";
  }

  typedef IPv6FlowLabel {
    type int32 {
      range "0..1048575";
    }
    description
     "The flow identifier or Flow Label in an IPv6 
      packet header that may be used to discriminate 
      traffic flows. ";
    reference
     "Internet Protocol, Version 6 (IPv6) specification, 
      section 6.  RFC 2460. ";
    smiv2:display-hint "d";
  }

  typedef IPv6FlowLabelOrAny {
    type int32 {
      range "-1..1048575";
    }
    description
     "The flow identifier or Flow Label in an IPv6 
      packet header that may be used to discriminate 
      traffic flows.  The value of -1 is used to 
      indicate a wildcard, i.e. any value. ";
    smiv2:display-hint "d";
  }

  smiv2:alias "ipv6FlowLabelMIB" {
    smiv2:oid "1.3.6.1.2.1.103";
  }

}
