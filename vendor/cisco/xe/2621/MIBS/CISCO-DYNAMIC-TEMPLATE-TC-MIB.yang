/*
 * Generated by confdc --mib2yang-std
 * Source: mgmt/dmi/model/mib/src/CISCO-DYNAMIC-TEMPLATE-TC-MIB.mib
 */
/*
 * This YANG module has been generated by smidump 0.5.0:
 *
 *      smidump -f yang CISCO-DYNAMIC-TEMPLATE-TC-MIB
 *
 * Do not edit. Edit the source file instead!
 */

module CISCO-DYNAMIC-TEMPLATE-TC-MIB {

  namespace "urn:ietf:params:xml:ns:yang:smiv2:CISCO-DYNAMIC-TEMPLATE-TC-MIB";
  prefix CISCO-DYNAMIC-TEMPLATE-TC-MIB;

  import ietf-yang-smiv2 {
    prefix "smiv2";
  }

  organization
   "Cisco Systems, Inc.";

  contact
   "Cisco Systems
    Customer Service
    
    Postal: 170 W Tasman Drive
    San Jose, CA 95134
    
    Tel: +1 800 553-NETS
    
    E-mail: cs-snmp@cisco.com";

  description
   "This MIB module defines textual conventions used by the
    CISCO-DYNAMIC-TEMPLATE-MIB and MIB modules that use and expand
    on dynamic templates.";

  revision 2012-01-27 {
    description
     "[Revision added by libsmi due to a LAST-UPDATED clause.]";
  }

  revision 2007-09-06 {
    description
     "The initial version of the MIB module.";
  }

  typedef DynamicTemplateName {
    type binary {
      length "1..64";
    }
    description
     "A string-value that identifies a dynamic template.  The
      semantics of the string-value are the same as those specified
      by the SnmpAdminString textual convention defined by the
      SNMP-FRAMEWORK-MIB [RFC3411].";
    reference
     "D. Harrington, R. Resuhn, B. Wijnen, 'An Architecture for
      Describing Simple Network Management Protocol (SNMP)
      Management
      Frameworks', RFC-3411, December 2002.";
  }

  typedef DynamicTemplateType {
    type enumeration {
      enum "other" {
        value "1";
      }
      enum "derived" {
        value "2";
      }
      enum "ppp" {
        value "3";
      }
      enum "ethernet" {
        value "4";
      }
      enum "ipSubscriber" {
        value "5";
      }
      enum "service" {
        value "6";
      }
    }
    description
     "An enumerated integer-value describing the type of dynamic
      template:
      
      'other'
          The implementation of the MIB module using this textual
          convention does not recognize the type of dynamic template.
      
      'derived'
          A configuration resulting from the union of the attributes
          contained by all the dynamic templates associated with a
          target.  The system generates a derived configuration, and
          an EMS/NMS cannot directly modify it.  An EMS/NMS can only
          affect a derived configuration by modifying one or more of
          the dynamic templates associated with the target.
      
      'ppp'
          A PPP template is a set of locally-configured attributes
          relating to the configuration of a PPP interface.
      
      'ethernet'
          An Ethernet template is a set of locally-configured
          attributes used by the system to configure dynamic
          interfaces initiated on Ethernet virtual interfaces (e.g.,
          EoMPLS) or automatically created VLANs.
      
      'ipSubscriber'
          An IP subscriber template is a set of locally-configured
          attributes used by the system to configure certain types of
          IP and L2 subscriber sessions.
      
      'service'
          A service template is a set of locally-configured attributes
          used by the system to configure subscriber sessions.  These
          attributes specifically relate to services, and the system
          applies these attributes in response to subscriber session
          life-cycle events.";
  }

  typedef DynamicTemplateTargetType {
    type enumeration {
      enum "other" {
        value "1";
      }
      enum "interface" {
        value "2";
      }
    }
    description
     "An enumerated integer-value describing the type of target
      associated with one or more dynamic templates:
      
          'other'
              The implementation of the MIB module using this textual
              convention does not recognize the type of target.
      
          'interface'
              The target is a physical, logical, or virtual interface
              represented by an ifEntry (defined by the IF-MIB).
      
      An implementation must ensure that DynamicTemplateTargetType
      object and any associated DynamicTemplateTargetId objects are
      consistent.  An attempt to set a DynamicTemplateTargetType
      object to a value inconsistent with the associated
      DynamicTemplateTargetId object must result in a response with
      an
      error-status of 'inconsistentValue'.";
    reference
     "K. McCloghrie and F. Kastenholtz, 'The Interfaces Group
      MIB',
      RFC-2863, June 2000.";
  }

  typedef DynamicTemplateTargetId {
    type binary {
      length "1..20";
    }
    description
     "An binary string-value in network byte order identifying a
      target associated with one or more dynamic templates.
      
      An implementation must interpret a DynamicTemplateTargetId
      value
      within the context of a DynamicTemplateTargetType.  Every usage
      of the DynamicTemplateTargetId textual convention must have a
      corresponding object specifying the DynamicTemplateType that
      provides this context.  It is most appropriate that a MIB
      module
      logical registers the DynamicTemplateType object before the use
      of the DynamicTemplateTargetId textual convention within the
      same logical row.
      
      The value of a DynamicTemplateTargetId object must always be
      consistent with the value of the associated
      DynamicTemplateTargetType object.  An attempt to set a
      DynamicTemplateTargetId object to a value inconsistent with the
      with the associated DynamicTemplateTargetType object must
      result
      in a response with an error-status of 'inconsistentValue'.
      
      If the DynamicTemplateTargetType is 'interface', then the representation
      of DynamicTemplateTargetId is as below
      
      octets   contents              encoding
       1-4     ifIndex               network-byte order";
    reference
     "K. McCloghrie and F. Kastenholtz, 'The Interfaces Group
      MIB',
      RFC-2863, June 2000.";
  }

  smiv2:alias "ciscoDynamicTemplateTcMIB" {
    smiv2:oid "1.3.6.1.4.1.9.9.783";
  }

}
