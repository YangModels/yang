/*
 * Generated by confdc --mib2yang-std
 * Source: mgmt/dmi/model/mib/src/CISCO-DIAL-CONTROL-MIB.mib
 */
/*
 * This YANG module has been generated by smidump 0.5.0:
 *
 *      smidump -f yang CISCO-DIAL-CONTROL-MIB
 *
 * Do not edit. Edit the source file instead!
 */

module CISCO-DIAL-CONTROL-MIB {

  namespace "urn:ietf:params:xml:ns:yang:smiv2:CISCO-DIAL-CONTROL-MIB";
  prefix CISCO-DIAL-CONTROL-MIB;

  import DIAL-CONTROL-MIB {
    prefix "dial-control";
  }

  import IF-MIB {
    prefix "if-mib";
  }

  import SNMP-FRAMEWORK-MIB {
    prefix "snmp-framework";
  }

  import SNMPv2-TC {
    prefix "snmpv2-tc";
  }

  import ietf-yang-smiv2 {
    prefix "smiv2";
  }

  import ietf-yang-types {
    prefix "yang";
  }

  organization
   "Cisco systems, Inc.";

  contact
   "        Bibek Das
    Postal: cisco Systems
            170 West Tasman Drive
            San Jose, CA 95134
            U.S.A.
    Phone:  +1 408 526 5225
    E-mail: cs-isdn@cisco.com";

  description
   "The MIB module to describe call history information for
    demand access and possibly other kinds of interfaces.";

  revision 2005-05-26 {
    description
     "Modified DESCRIPTION of cPeerSearchType object.";
  }

  revision 2003-07-10 {
    description
     "1) Changed the SYNTAX of cCallHistoryLogicalIfIndex
      to be InterfaceIndexOrZero instead of 
      InterfaceIndex.
      2) Modified the DESCRIPTION of 
      cCallHistoryLogicalIfIndex.";
  }

  revision 2002-08-21 {
    description
     "1) Deprecated ciscoDialControlMibComplianceRev3 
      2) Added a new table cCallHistoryIecTable
      3) Added a new module-compliance
         ciscoDialControlMibComplianceRev4 
      4) Added gatekeeper and externalGKTMPServer enum labels
         to cCallHistoryReleaseSrc
      5) Added cCallHistoryIecGroup OBJECT-GROUP.";
  }

  revision 2002-05-24 {
    description
     "1) Deprecated ciscoDialControlMibComplianceRev2 
      2) Added a new object subtree (OID)
         cPeerGlobalConfiguration
      3) Added a new object cPeerSearchType 
      4) Added a new object-group cPeerGlobalConfigurationGroup
      5) Added a new module-compliance
         ciscoDialControlMibComplianceRev3.";
  }

  revision 2002-02-20 {
    description
     "1) Deprecated cCallHistoryReleaseSource 
      2) Deprecated cCallHistoryGroupRev1 
      3) Deprecated ciscoDialControlMibComplianceRev1 
      3) Added a new object cCallHistoryReleaseSrc
      4) Added a new object cCallHistoryGroupRev2
      6) Added a new object ciscoDialControlMibComplianceRev2.";
  }

  revision 2001-12-13 {
    description
     "Added a new object cCallHistoryReleaseSource in 
      CallHistory table.";
  }

  revision 1998-01-16 {
    description
     "The initial version of the mib.";
  }


  container CISCO-DIAL-CONTROL-MIB {
    config false;

    container cPeerGlobalConfiguration {
      smiv2:oid "1.3.6.1.4.1.9.10.25.1.5";

      leaf cPeerSearchType {
        type enumeration {
          enum "none" {
            value "1";
          }
          enum "datavoice" {
            value "2";
          }
          enum "voicedata" {
            value "3";
          }
        }
        description
         "Specifies the peer search preference based on the
          type of peers in an universal/integrated port
          platform.
          
          none      - both voice and data peers are searched
                     in same preference.
          datavoice - search data peers first. If no data peers
                     are found, the voice peers are searched.
          voicedata - search voice peers first. If no voice peers
                     are found, the data peers are searched.";
        smiv2:defval "datavoice";
        smiv2:max-access "read-write";
        smiv2:oid "1.3.6.1.4.1.9.10.25.1.5.1";
      }
    }

    container cCallHistoryTable {
      description
       "A table containing information about specific
        calls to a specific destination.";
      smiv2:oid "1.3.6.1.4.1.9.10.25.1.4.3";

      list cCallHistoryEntry {
        key "cCallHistoryIndex";
        description
         "The information regarding a single Connection.";
        smiv2:oid "1.3.6.1.4.1.9.10.25.1.4.3.1";

        leaf cCallHistoryIndex {
          type uint32 {
            range "1..4294967295";
          }
          description
           "A monotonically increasing integer for the sole purpose of
            indexing call disconnection events.  When it reaches the 
            maximum value, an extremely unlikely event, the agent wraps 
            the value back to 1 and may flush existing entries.";
          smiv2:max-access "not-accessible";
          smiv2:oid "1.3.6.1.4.1.9.10.25.1.4.3.1.1";
        }

        leaf cCallHistorySetupTime {
          type yang:timestamp;
          description
           "The value of sysUpTime when the call setup was started.
            This will be useful for an NMS to sort the call history
            entry with call setup time. Also, this object
            can be useful in finding large delays between the time the
            call was started and the time the call was connected.
            For ISDN media, this will be the time when the setup
            message was received from or sent to the network.
            The value of this object is the same as callActiveSetupTime
            in the callActiveTable";
          smiv2:max-access "read-only";
          smiv2:oid "1.3.6.1.4.1.9.10.25.1.4.3.1.2";
        }

        leaf cCallHistoryPeerAddress {
          type snmpv2-tc:DisplayString;
          description
           "The number this call was connected to. If the number is
            not available, then it will have a length of zero.";
          smiv2:max-access "read-only";
          smiv2:oid "1.3.6.1.4.1.9.10.25.1.4.3.1.3";
        }

        leaf cCallHistoryPeerSubAddress {
          type snmpv2-tc:DisplayString;
          description
           "The subaddress this call was connected to. If the subaddress
            is undefined or not available, this will be a zero length
            string.";
          smiv2:max-access "read-only";
          smiv2:oid "1.3.6.1.4.1.9.10.25.1.4.3.1.4";
        }

        leaf cCallHistoryPeerId {
          type int32 {
            range "0..2147483647";
          }
          description
           "This is the Id value of the peer table entry
            to which this call was made. If a peer table entry
            for this call does not exist, the value of this object
            will be zero.";
          smiv2:max-access "read-only";
          smiv2:oid "1.3.6.1.4.1.9.10.25.1.4.3.1.5";
        }

        leaf cCallHistoryPeerIfIndex {
          type int32 {
            range "0..2147483647";
          }
          description
           "This is the ifIndex value of the peer table entry
            to which this call was made. If a peer table entry
            for this call does not exist, the value of this object
            will be zero.";
          smiv2:max-access "read-only";
          smiv2:oid "1.3.6.1.4.1.9.10.25.1.4.3.1.6";
        }

        leaf cCallHistoryLogicalIfIndex {
          type if-mib:InterfaceIndexOrZero;
          description
           "This is the ifIndex value of the logical interface through
            which this call was made. For ISDN media, this would be
            the ifIndex of the B channel which was used for this call.
            If the ifIndex value is unknown, the value of this object 
            will be zero. For an IP call, the value will be zero.";
          smiv2:max-access "read-only";
          smiv2:oid "1.3.6.1.4.1.9.10.25.1.4.3.1.7";
        }

        leaf cCallHistoryDisconnectCause {
          type binary {
            length "0..4";
          }
          description
           "The encoded network cause value associated with this call.
            
            The value of this object will depend on the interface type
            as well as on the protocol and protocol version being
            used on this interface. Some references for possible cause
            values are given below.";
          reference
           "- Bellcore SR-NWT-001953, Generic Guidelines for
            ISDN Terminal Equipment On Basic Access Interfaces,
            chapter 5.2.5.8.
            - Bellcore SR-NWT-002343, ISDN Primary Rate Interface
            Generic Guidelines for Customer Premises Equipment,
            chapter 8.2.5.8.
            - ITU-T Q.931, Appendix I.
            - ITU-T X.25, CAUSE and DIAGNOSTIC field values.
            - German Telekom FTZ 1TR6, chapter 3.2.3.4.4.4.";
          smiv2:max-access "read-only";
          smiv2:oid "1.3.6.1.4.1.9.10.25.1.4.3.1.8";
        }

        leaf cCallHistoryDisconnectText {
          type snmpv2-tc:DisplayString;
          description
           "ASCII text describing the reason for call termination.
            
            This object exists because it would be impossible for
            a management station to store all possible cause values
            for all types of interfaces. It should be used only if
            a management station is unable to decode the value of
            dialCtlPeerStatsLastDisconnectCause.";
          smiv2:max-access "read-only";
          smiv2:oid "1.3.6.1.4.1.9.10.25.1.4.3.1.9";
        }

        leaf cCallHistoryConnectTime {
          type yang:timestamp;
          description
           "The value of sysUpTime when the call was connected.";
          smiv2:max-access "read-only";
          smiv2:oid "1.3.6.1.4.1.9.10.25.1.4.3.1.10";
        }

        leaf cCallHistoryDisconnectTime {
          type yang:timestamp;
          description
           "The value of sysUpTime when the call was disconnected.";
          smiv2:max-access "read-only";
          smiv2:oid "1.3.6.1.4.1.9.10.25.1.4.3.1.11";
        }

        leaf cCallHistoryCallOrigin {
          type enumeration {
            enum "originate" {
              value "1";
            }
            enum "answer" {
              value "2";
            }
            enum "callback" {
              value "3";
            }
          }
          description
           "The call origin.";
          smiv2:max-access "read-only";
          smiv2:oid "1.3.6.1.4.1.9.10.25.1.4.3.1.12";
        }

        leaf cCallHistoryChargedUnits {
          type dial-control:AbsoluteCounter32;
          description
           "The number of charged units for this connection.
            For incoming calls or if charging information is
            not supplied by the switch, the value of this object
            will be zero.";
          smiv2:max-access "read-only";
          smiv2:oid "1.3.6.1.4.1.9.10.25.1.4.3.1.13";
        }

        leaf cCallHistoryInfoType {
          type enumeration {
            enum "other" {
              value "1";
            }
            enum "speech" {
              value "2";
            }
            enum "unrestrictedDigital" {
              value "3";
            }
            enum "unrestrictedDigital56" {
              value "4";
            }
            enum "restrictedDigital" {
              value "5";
            }
            enum "audio31" {
              value "6";
            }
            enum "audio7" {
              value "7";
            }
            enum "video" {
              value "8";
            }
            enum "packetSwitched" {
              value "9";
            }
            enum "fax" {
              value "10";
            }
          }
          description
           "The information type for this call.";
          smiv2:max-access "read-only";
          smiv2:oid "1.3.6.1.4.1.9.10.25.1.4.3.1.14";
        }

        leaf cCallHistoryTransmitPackets {
          type dial-control:AbsoluteCounter32;
          description
           "The number of packets which were transmitted while this
            call was active.";
          smiv2:max-access "read-only";
          smiv2:oid "1.3.6.1.4.1.9.10.25.1.4.3.1.15";
        }

        leaf cCallHistoryTransmitBytes {
          type dial-control:AbsoluteCounter32;
          description
           "The number of bytes which were transmitted while this
            call was active.";
          smiv2:max-access "read-only";
          smiv2:oid "1.3.6.1.4.1.9.10.25.1.4.3.1.16";
        }

        leaf cCallHistoryReceivePackets {
          type dial-control:AbsoluteCounter32;
          description
           "The number of packets which were received while this
            call was active.";
          smiv2:max-access "read-only";
          smiv2:oid "1.3.6.1.4.1.9.10.25.1.4.3.1.17";
        }

        leaf cCallHistoryReceiveBytes {
          type dial-control:AbsoluteCounter32;
          description
           "The number of bytes which were received while this
            call was active.";
          smiv2:max-access "read-only";
          smiv2:oid "1.3.6.1.4.1.9.10.25.1.4.3.1.18";
        }

        leaf cCallHistoryReleaseSource {
          type enumeration {
            enum "callingPartyInPstn" {
              value "1";
            }
            enum "callingPartyInVoip" {
              value "2";
            }
            enum "calledPartyInPstn" {
              value "3";
            }
            enum "calledPartyInVoip" {
              value "4";
            }
            enum "internalRelease" {
              value "5";
            }
            enum "internalCallControlApp" {
              value "6";
            }
            enum "consoleCommand" {
              value "7";
            }
            enum "externalRadiusServer" {
              value "8";
            }
            enum "externalNmsApp" {
              value "9";
            }
            enum "externalCallControlAgent" {
              value "10";
            }
          }
          status deprecated;
          description
           "Originator of the call release.";
          smiv2:max-access "read-only";
          smiv2:oid "1.3.6.1.4.1.9.10.25.1.4.3.1.19";
        }

        leaf cCallHistoryReleaseSrc {
          type enumeration {
            enum "callingPartyInPstn" {
              value "1";
            }
            enum "callingPartyInVoip" {
              value "2";
            }
            enum "calledPartyInPstn" {
              value "3";
            }
            enum "calledPartyInVoip" {
              value "4";
            }
            enum "internalReleaseInPotsLeg" {
              value "5";
            }
            enum "internalReleaseInVoipLeg" {
              value "6";
            }
            enum "internalCallControlApp" {
              value "7";
            }
            enum "internalReleaseInVoipAAA" {
              value "8";
            }
            enum "consoleCommand" {
              value "9";
            }
            enum "externalRadiusServer" {
              value "10";
            }
            enum "externalNmsApp" {
              value "11";
            }
            enum "externalCallControlAgent" {
              value "12";
            }
            enum "gatekeeper" {
              value "13";
            }
            enum "externalGKTMPServer" {
              value "14";
            }
          }
          description
           "Originator of the call release. Indicates the source of 
            the call release as follows : 
            1) callingPartyInPstn : Calling party in PSTN.
            2) callingPartyInVoip : Calling party in VoIP.
            3) calledPartyInPstn : Called party in PSTN.
            4) calledPartyInVoip : Called party in VoIP.
            5) internalReleaseInPotsLeg : Due to an internal error 
               in Telephony call leg.
            6) internalReleaseInVoipLeg : Due to an internal error
               in VoIP call leg.
            7) internalCallControlApp : Due to an internal error
               in Session Application or Tcl or VXML script originated
               release. 
            8) internalReleaseInVoipAAA : Due to an internal error
               in VoIP AAA module.
            9) consoleCommand : Due to CLI or MML.
            10) externalRadiusServer : Call failed during authorization
                , authentication or due to receipt of POD from the 
                RADIUS server.
            11) externalNmsApp : Due to SNMP request to clear 
                the call.
            12) externalCallControlAgent : External Call Control Agent
                initiated clear.
            13) gatekeeper : Gatekeeper initiated clear due to receipt
                of Admission Reject, Disengage Request message.
            14) externalGKTMPServer : External GKTMP server initiated
                clear due to receipt of Admission Reject message from
                the gatekeeper, triggered by RESPONSE.ARJ message from
                the GKTMP server.";
          smiv2:max-access "read-only";
          smiv2:oid "1.3.6.1.4.1.9.10.25.1.4.3.1.20";
        }
      }
    }

    container cCallHistoryIecTable {
      description
       "This table contains information about Internal Error
        Code(s) (IEC) which caused the call to fail.";
      smiv2:oid "1.3.6.1.4.1.9.10.25.1.4.4";

      list cCallHistoryIecEntry {
        key "cCallHistoryIndex cCallHistoryIecIndex";
        description
         "The IEC information regarding a single call.";
        smiv2:oid "1.3.6.1.4.1.9.10.25.1.4.4.1";

        leaf cCallHistoryIndex {
          type leafref {
            path "/CISCO-DIAL-CONTROL-MIB:CISCO-DIAL-CONTROL-MIB/CISCO-DIAL-CONTROL-MIB:cCallHistoryTable/CISCO-DIAL-CONTROL-MIB:cCallHistoryEntry/CISCO-DIAL-CONTROL-MIB:cCallHistoryIndex";
          }
        }

        leaf cCallHistoryIecIndex {
          type uint32 {
            range "1..1024";
          }
          description
           "This object is used to index one or more IECs in the
            context of a single call.  In most cases there will
            only be one IEC when a call fails.  However, it is
            possible for the software processing the call to 
            generate multiple IECs before the call ultimately fails.
            In that scenario, there will be multiple entries in
            this table related to a single call (cCallHistoryIndex)
            and this object will serve to uniquely identify each IEC.";
          smiv2:max-access "not-accessible";
          smiv2:oid "1.3.6.1.4.1.9.10.25.1.4.4.1.1";
        }

        leaf cCallHistoryIec {
          type snmp-framework:SnmpAdminString;
          description
           "This object reflects the Internal Error Code.
            The format is a string of dotted decimal numbers
            composed of the following components:
            
            Version.Entity.Category.Subsystem.Errorcode.Diagnostic
            
            Each component is defined as follows:
            Version     : The version of IEC software.
            Entity      : The network entity that originated
                          the error.
            Category    : The category of the error (eg, software
                          error, hardware resource unavailable, ...)
            Subsystem   : The subsystem in which the error occurred.
            Errorcode   : A subsytem-specific error code.
            Diagnostic  : An implementation-specific diagnostic code.";
          smiv2:max-access "read-only";
          smiv2:oid "1.3.6.1.4.1.9.10.25.1.4.4.1.2";
        }
      }
    }
  }

  smiv2:alias "ciscoDialControlMib" {
    smiv2:oid "1.3.6.1.4.1.9.10.25";
  }

  smiv2:alias "ciscoDialControlMibObjects" {
    smiv2:oid "1.3.6.1.4.1.9.10.25.1";
  }

  smiv2:alias "cCallHistory" {
    smiv2:oid "1.3.6.1.4.1.9.10.25.1.4";
  }

  smiv2:alias "cPeerGlobalConfiguration" {
    smiv2:oid "1.3.6.1.4.1.9.10.25.1.5";
  }

  smiv2:alias "ciscoDialControlMibConformance" {
    smiv2:oid "1.3.6.1.4.1.9.10.25.3";
  }

  smiv2:alias "ciscoDialControlMibCompliances" {
    smiv2:oid "1.3.6.1.4.1.9.10.25.3.1";
  }

  smiv2:alias "ciscoDialControlMibGroups" {
    smiv2:oid "1.3.6.1.4.1.9.10.25.3.2";
  }

}
