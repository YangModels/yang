/*
 * Generated by confdc --mib2yang-std
 * Source: mgmt/dmi/model/mib/src/CISCO-STACKWISE-MIB.mib
 */
/*
 * This YANG module has been generated by smidump 0.5.0:
 *
 *      smidump -f yang CISCO-STACKWISE-MIB
 *
 * Do not edit. Edit the source file instead!
 */

module CISCO-STACKWISE-MIB {

  namespace "urn:ietf:params:xml:ns:yang:smiv2:CISCO-STACKWISE-MIB";
  prefix CISCO-STACKWISE-MIB;

  import CISCO-TC {
    prefix "cisco-tc";
  }

  import ENTITY-MIB {
    prefix "entity-mib";
  }

  import IF-MIB {
    prefix "if-mib";
  }

  import SNMP-FRAMEWORK-MIB {
    prefix "snmp-framework";
  }

  import ietf-yang-smiv2 {
    prefix "smiv2";
  }

  import ietf-yang-types {
    prefix "yang";
  }

  organization
   "Cisco Systems, Inc.";

  contact
   "Cisco Systems
    Customer Service
    
    Postal:   170 W Tasman Drive
    San Jose, CA 95134
    
    Tel:   +1 800 553-NETS
    
    E-mail:   cs-dsbu@cisco.com";

  description
   "This MIB module contain a collection of managed objects
    that apply to network devices supporting the Cisco
    StackWise(TM) technology.
    
    The StackWise technology provides a method for collectively
    utilizing a stack of switches to create a single switching
    unit.
    
    The data stack is used for switching data packets and, in 
    power stack, switches are connected by special stack power 
    cables to share power. Moreover, stackwise is the concept 
    for combining multiple systems to give an impression of a 
    single system so that is why both power stack and data stack
    are supported by single MIB.
    
    Terminology:
    Stack       - A collection of switches connected by the
                  Cisco StackWise technology.
    
    Master      - The switch that is managing the stack.
    
    Member      - A switch in the stack that is
                  NOT the stack master.
    
    Ring        - Components that makes up the connections
                  between the switches in order to create a
                  stack.
    
    Stackport   - A special physical connector used by the ring.
                  It is possible for a switch have more than
                  one stackport.
    
    SDM         - Switch Database Management.
    
    Stack Power - A collection of switches connected by special
                  stack power cables to share the power of 
                  inter-connected power supplies across all switches
                  requiring power. Stack Power is managed by a
                  single data stack. 
    
    Jack-Jack   - It is a device that provides the Power Shelf     
                  capabilities required for Stack Power on
                  the high-end.
    
    POE         - Power Over Ethernet
    
    FEP         - Front End Power Supply
    
    SOC         - Sustained Overload Condition 
    
    GLS         - Graceful Load Shedding
    
    ILS         - Immediate Load Shedding
    
    SRLS        - System Ring Load Shedding
    
    SSLS        - System Star Load Shedding";

  revision 2016-04-16 {
    description
     "Added following objects in cswGlobals
      - cswStackDomainNum
      - cswStackType
      - cswStackBandWidth
      Created following tables
      - cswDistrStackLinkInfoTable
      -cswDistrStackPhyPortInfoTable
      Added cswStatusGroupRev2
      Deprecated cswStatusGroupRev1
      Added cswDistrStackLinkStatusGroup
      Added cswDistrStackPhyPortStatusGroup
      Added cswStackWiseMIBComplianceRev4 MIB COMPLIANCE
      Deprecated cswStackWiseMIBComplianceRev3 MIB COMPLIANCE.";
  }

  revision 2015-11-24 {
    description
     "Added following Objects in cswSwitchInfoTable
      - cswSwitchPowerAllocated
      Added following OBJECT-GROUP
      - cswStackPowerAllocatedGroup
      Deprecated cswStackWiseMIBComplianceRev2 MODULE-COMPLIANCE.
      Added cswStackWiseMIBComplianceRev3 MODULE-COMPLIANCE.";
  }

  revision 2011-12-12 {
    description
     "Modified 'cswSwitchRole' object.";
  }

  revision 2010-02-01 {
    description
     "Added cswStackPowerStatusGroup, cswStackPowerSwitchStatusGroup,
      cswStackPowerPortStatusGroup, cswStatusGroupRev1 and
      cswStackPowerNotificationGroup.
      Deprecated cswStackWiseMIBCompliance compliance statement. 
      Added cswStackWiseMIBComplianceRev1 compliance statement.
      Deprecated cswStatusGroup because we deprecated
      cswEnableStackNotifications";
  }

  revision 2008-06-10 {
    description
     "Modified 'cswSwitchState' object.";
  }

  revision 2005-10-12 {
    description
     "Initial version of this MIB module.";
  }

  typedef CswPowerStackMode {
    type enumeration {
      enum "powerSharing" {
        value "1";
      }
      enum "redundant" {
        value "2";
      }
      enum "powerSharingStrict" {
        value "3";
      }
      enum "redundantStrict" {
        value "4";
      }
    }
    description
     "This textual convention is used to describe the mode of the
      power stack. Since the power stack could only run in either
      power sharing or redundant mode so this TC will also have only
      following valid values,
      powerSharing(1)      :When a power stack is running in power   
                            sharing mode then all the power supplies
                            in the power stack contributes towards
                            the global power budget of the stack.
      
      redundant(2)         :If the user wants the power stack to run
                            in redundant mode then we will take the  
                            capacity of the largest power supply in
                            the power stack out of power stack global
                            power budget pool.
      
      powerSharingStrict(3):This mode is same as power sharing mode
                            but, in this mode, the available power
                            will always be more than the used power.
      
      redundantStrict(4)   :This mode is same as redundant mode but,
                            in this mode, the available power will
                            always be more than the used power.";
  }

  typedef CswPowerStackType {
    type enumeration {
      enum "ring" {
        value "1";
      }
      enum "star" {
        value "2";
      }
    }
    description
     "This textual conventions is used to describe the type of the
      power stack. Since the power stack could only be configured in
      a ring or star topology so this TC will have only following
      valid values,
              ring(1): The power stack has been formed by connecting 
                       the switches in ring topology.
              star(2): The power stack has been formed by connecting 
                         the switches in star topology.";
  }

  typedef CswSwitchNumber {
    type uint32 {
      range "1..4294967295";
    }
    description
     "A unique value, greater than zero, for each switch in a group
      of stackable switches.";
    smiv2:display-hint "d";
  }

  typedef CswSwitchNumberOrZero {
    type uint32 {
      range "0..4294967295";
    }
    description
     "A unique value, greater than or equal to zero, for each switch
      in a group of stackable switches.
      
      A value of zero means that the switch number can not be
      determined.  The value of zero is not unique.";
    smiv2:display-hint "d";
  }

  typedef CswSwitchPriority {
    type uint32 {
      range "0..4294967295";
    }
    description
     "A value, greater than or equal to zero, that defines the
      priority of a switch in a group of stackable switches.  The
      higher the value, the higher the priority.";
    smiv2:display-hint "d";
  }


  container CISCO-STACKWISE-MIB {
    config false;

    container cswGlobals {
      smiv2:oid "1.3.6.1.4.1.9.9.500.1.1";

      leaf cswMaxSwitchNum {
        type CISCO-STACKWISE-MIB:CswSwitchNumber;
        description
         "The maximum number of switches that can be configured on
          this stack.  This is also the maximum value that can be
          set by the cswSwitchNumNextReload object.";
        smiv2:max-access "read-only";
        smiv2:oid "1.3.6.1.4.1.9.9.500.1.1.1";
      }

      leaf cswMaxSwitchConfigPriority {
        type CISCO-STACKWISE-MIB:CswSwitchPriority;
        description
         "The maximum configurable priority for a switch in this stack.
          Highest value equals highest priority.  This is the highest
          value that can be set by the cswSwitchSwPriority object.";
        smiv2:max-access "read-only";
        smiv2:oid "1.3.6.1.4.1.9.9.500.1.1.2";
      }

      leaf cswRingRedundant {
        type boolean;
        description
         "A value of 'true' is returned when the stackports are
          connected in such a way that it forms a redundant ring.";
        smiv2:max-access "read-only";
        smiv2:oid "1.3.6.1.4.1.9.9.500.1.1.3";
      }

      leaf cswEnableStackNotifications {
        type boolean;
        status deprecated;
        description
         "This object indicates whether the system generates the
          notifications defined in this MIB or not.  A value of
          'false' will prevent the notifications from being sent.";
        smiv2:max-access "read-write";
        smiv2:oid "1.3.6.1.4.1.9.9.500.1.1.4";
      }

      leaf cswEnableIndividualStackNotifications {
        type bits {
          bit stackPortChange {
            position "0";
          }
          bit stackNewMaster {
            position "1";
          }
          bit stackMismatch {
            position "2";
          }
          bit stackRingRedundant {
            position "3";
          }
          bit stackNewMember {
            position "4";
          }
          bit stackMemberRemoved {
            position "5";
          }
          bit stackPowerLinkStatusChanged {
            position "6";
          }
          bit stackPowerPortOperStatusChanged {
            position "7";
          }
          bit stackPowerVersionMismatch {
            position "8";
          }
          bit stackPowerInvalidTopology {
            position "9";
          }
          bit stackPowerBudgetWarning {
            position "10";
          }
          bit stackPowerInvalidInputCurrent {
            position "11";
          }
          bit stackPowerInvalidOutputCurrent {
            position "12";
          }
          bit stackPowerUnderBudget {
            position "13";
          }
          bit stackPowerUnbalancedPowerSupplies {
            position "14";
          }
          bit stackPowerInsufficientPower {
            position "15";
          }
          bit stackPowerPriorityConflict {
            position "16";
          }
          bit stackPowerUnderVoltage {
            position "17";
          }
          bit stackPowerGLS {
            position "18";
          }
          bit stackPowerILS {
            position "19";
          }
          bit stackPowerSRLS {
            position "20";
          }
          bit stackPowerSSLS {
            position "21";
          }
          bit stackMemberToBeReloadedForUpgrade {
            position "22";
          }
        }
        description
         "This object is used to enable/disable individual notifications
          defined in this MIB module. Turning on a particular bit would
          enable the corresponding trap and, similarly, turning off a
          particular bit would disable the corresponding trap. The
          following notifications are controlled by this object:
          
           stackPortChange(0): enables/disables cswStackPortChange
                               notification.
          
           stackNewMaster(1): enables/disables cswStackNewMember
                              notification.
          
           stackMismatch(2): enables/disables cswStackMismatch
                             notification.
          
           stackRingRedundant(3): enables/disables cswStackRingRedundant 
                                  notification.
          
           stackNewMember(4): enables/disables cswStackNewMember 
                              notification.
          
           stackMemberRemoved(5): enables/disables cswStackMemberRemoved 
                                  notification.
          
           stackPowerLinkStatusChanged(6): enables/disables 
                         cswStackPowerPortLinkStatusChanged notification.
          
           stackPowerPortOperStatusChanged(7): enables/disables 
                         cswStackPowerPortOperStatusChanged notification.
          
           stackPowerVersionMismatch(8): enables/disables 
                             cswStackPowerVersionMismatch notification.
          
           stackPowerInvalidTopology(9): enables/disables 
                             cswStackPowerInvalidTopology notification
          
           stackPowerBudgetWarning(10): enables/disables 
                          cswStackPowerBudgetWarning notification. 
          
           stackPowerInvalidInputCurrent(11): enables/disables 
                          cswStackPowerInvalidInputCurrent notification.
          
           stackPowerInvalidOutputCurrent(12): enables/disables 
                          cswStackPowerInvalidOutputCurrent notification.
          
           stackPowerUnderBudget(13): enables/disables 
                           cswStackPowerUnderBudget notification.
          
           stackPowerUnbalancedPowerSupplies(14): enables/disables 
                       cswStackPowerUnbalancedPowerSupplies notification.
          
           stackPowerInsufficientPower(15): enables/disables 
                           cswStackPowerInsufficientPower notification.
          
           stackPowerPriorityConflict(16): enables/disables 
                           cswStackPowerPriorityConflict notification.
          
           stackPowerUnderVoltage(17): enables/disables 
                           cswStackPowerUnderVoltage notification.
          
           stackPowerGLS(18): enables/disables cswStackPowerGLS
                              notification. 
          
           stackPowerILS(19): enables/disabled cswStackPowerILS
                              notification.
          
           stackPowerSRLS(20): enables/disables cswStackPowerSRLS 
                               notification.
          
           stackPowerSSLS(21): enables/disables cswStackPowerSSLS 
                               notification.
           stackMemberToBeReloadedForUpgrade(22): enables/disables 
                     cswStackMemberToBeReloadedForUpgrade notification.";
        smiv2:max-access "read-write";
        smiv2:oid "1.3.6.1.4.1.9.9.500.1.1.5";
      }

      leaf cswStackDomainNum {
        type uint32;
        description
         "This object indicates distributed domain of the switch.Only
          Switches with the same domain number can be in the same dist
          ributed domain.0 means no switch domain configured.";
        smiv2:max-access "read-only";
        smiv2:oid "1.3.6.1.4.1.9.9.500.1.1.6";
      }

      leaf cswStackType {
        type uint32;
        description
         "This object indicates type of switch stack. value
          of Switch virtual domain determines if switch is
          distributed or conventional stack. 0 means stack
          is conventional back side stack.";
        smiv2:max-access "read-only";
        smiv2:oid "1.3.6.1.4.1.9.9.500.1.1.7";
      }

      leaf cswStackBandWidth {
        type uint32;
        description
         "This object indicates stack bandwidth.";
        smiv2:max-access "read-only";
        smiv2:oid "1.3.6.1.4.1.9.9.500.1.1.8";
      }
    }

    container cswSwitchInfoTable {
      description
       "This table contains information specific to switches in a
        stack.  Every switch with an entry in the entPhysicalTable
        (ENTITY-MIB) whose entPhysicalClass is 'chassis' will have
        an entry in this table.";
      smiv2:oid "1.3.6.1.4.1.9.9.500.1.2.1";

      list cswSwitchInfoEntry {
        key "entPhysicalIndex";
        description
         "A conceptual row in the cswSwitchInfoTable describing
          a switch information.";
        smiv2:oid "1.3.6.1.4.1.9.9.500.1.2.1.1";

        leaf entPhysicalIndex {
          type leafref {
            path "/entity-mib:ENTITY-MIB/entity-mib:entPhysicalTable/entity-mib:entPhysicalEntry/entity-mib:entPhysicalIndex";
          }
        }

        leaf cswSwitchNumCurrent {
          type CISCO-STACKWISE-MIB:CswSwitchNumber;
          description
           "This object contains the current switch identification number.
            This number should match any logical labeling on the switch.
            For example, a switch whose interfaces are labeled
            'interface #3' this value should be 3.";
          smiv2:max-access "read-only";
          smiv2:oid "1.3.6.1.4.1.9.9.500.1.2.1.1.1";
        }

        leaf cswSwitchNumNextReload {
          type CISCO-STACKWISE-MIB:CswSwitchNumberOrZero;
          description
           "This object contains the cswSwitchNumCurrent to be
            used at next reload.  The maximum value for this object is
            defined by the cswMaxSwitchNum object.
            
            Note: This object will contain 0 and cannot be set if the
            cswSwitchState value is other than 'ready'.";
          smiv2:max-access "read-write";
          smiv2:oid "1.3.6.1.4.1.9.9.500.1.2.1.1.2";
        }

        leaf cswSwitchRole {
          type enumeration {
            enum "master" {
              value "1";
            }
            enum "member" {
              value "2";
            }
            enum "notMember" {
              value "3";
            }
            enum "standby" {
              value "4";
            }
          }
          description
           "This object describes the function of the switch:
            
            master    - stack master.
            
            member    - active member of the stack.
            
            notMember - none-active stack member, see
                        cswSwitchState for status.
            
            standby   - stack standby switch.";
          smiv2:max-access "read-only";
          smiv2:oid "1.3.6.1.4.1.9.9.500.1.2.1.1.3";
        }

        leaf cswSwitchSwPriority {
          type CISCO-STACKWISE-MIB:CswSwitchPriority;
          description
           "A number containing the priority of a switch.  The switch with
            the highest priority will become the master.  The maximum value
            for this object is defined by the cswMaxSwitchConfigPriority
            object.
            
            If after a reload the value of cswMaxSwitchConfigPriority
            changes to a smaller value, and the value of cswSwitchSwPriority
            has been previously set to a value greater or equal to the
            new cswMaxSwitchConfigPriority, then the SNMP agent must set
            cswSwitchSwPriority to the new cswMaxSwitchConfigPriority.
            
            Note: This object will contain the value of 0 if the
            cswSwitchState value is other than 'ready'.";
          smiv2:max-access "read-write";
          smiv2:oid "1.3.6.1.4.1.9.9.500.1.2.1.1.4";
        }

        leaf cswSwitchHwPriority {
          type CISCO-STACKWISE-MIB:CswSwitchPriority;
          description
           "This object contains the hardware priority of a switch.  If
            two or more entries in this table have the same
            cswSwitchSwPriority value during the master election time,
            the switch with the highest cswSwitchHwPriority will become
            the master.
            
            Note: This object will contain the value of 0 if the
            cswSwitchState value is other than 'ready'.";
          smiv2:max-access "read-only";
          smiv2:oid "1.3.6.1.4.1.9.9.500.1.2.1.1.5";
        }

        leaf cswSwitchState {
          type enumeration {
            enum "waiting" {
              value "1";
            }
            enum "progressing" {
              value "2";
            }
            enum "added" {
              value "3";
            }
            enum "ready" {
              value "4";
            }
            enum "sdmMismatch" {
              value "5";
            }
            enum "verMismatch" {
              value "6";
            }
            enum "featureMismatch" {
              value "7";
            }
            enum "newMasterInit" {
              value "8";
            }
            enum "provisioned" {
              value "9";
            }
            enum "invalid" {
              value "10";
            }
            enum "removed" {
              value "11";
            }
          }
          description
           "The current state of a switch:
            
            waiting         - Waiting for a limited time on other
                              switches in the stack to come online.
            
            progressing     - Master election or mismatch checks in
                              progress.
            
            added           - The switch is added to the stack.
            
            ready           - The switch is operational.
            
            sdmMismatch     - The SDM template configured on the master
                              is not supported by the new member.
            
            verMismatch     - The operating system version running on the
                              master is different from the operating
                              system version running on this member.
            
            featureMismatch - Some of the features configured on the
                              master are not supported on this member.
            
            newMasterInit   - Waiting for the new master to finish
                              initialization after master switchover
                              (Master Re-Init).
            
            provisioned     - The switch is not an active member of the
                              stack.
            
            invalid         - The switch's state machine is in an
                              invalid state.
            
            removed         - The switch is removed from the stack.";
          smiv2:max-access "read-only";
          smiv2:oid "1.3.6.1.4.1.9.9.500.1.2.1.1.6";
        }

        leaf cswSwitchMacAddress {
          type yang:mac-address;
          description
           "The MAC address of the switch.
            
            Note: This object will contain the value of 0000:0000:0000
            if the cswSwitchState value is other than 'ready'.";
          smiv2:max-access "read-only";
          smiv2:oid "1.3.6.1.4.1.9.9.500.1.2.1.1.7";
        }

        leaf cswSwitchSoftwareImage {
          type snmp-framework:SnmpAdminString;
          description
           "The software image type running on the switch.
            
            Note: This object will contain an empty string if the
            cswSwitchState value is other than 'ready'.";
          smiv2:max-access "read-only";
          smiv2:oid "1.3.6.1.4.1.9.9.500.1.2.1.1.8";
        }

        leaf cswSwitchPowerBudget {
          type uint32;
          units "Watts";
          description
           "This object indicates the power budget of the switch.";
          smiv2:max-access "read-only";
          smiv2:oid "1.3.6.1.4.1.9.9.500.1.2.1.1.9";
        }

        leaf cswSwitchPowerCommited {
          type uint32;
          units "Watts";
          description
           "This object indicates the power committed to the POE devices
            connected to the switch.";
          smiv2:max-access "read-only";
          smiv2:oid "1.3.6.1.4.1.9.9.500.1.2.1.1.10";
        }

        leaf cswSwitchSystemPowerPriority {
          type uint32;
          description
           "This specifies the system's power priority. In case of
            a power failure then the system with the highest system
            priority will be brought down last.";
          smiv2:max-access "read-write";
          smiv2:oid "1.3.6.1.4.1.9.9.500.1.2.1.1.11";
        }

        leaf cswSwitchPoeDevicesLowPriority {
          type uint32;
          description
           "This object specifies the priority of the system's low
            priority POE devices.";
          smiv2:max-access "read-write";
          smiv2:oid "1.3.6.1.4.1.9.9.500.1.2.1.1.12";
        }

        leaf cswSwitchPoeDevicesHighPriority {
          type uint32;
          description
           "This object specifies the priority of the system's high
            priority POE devices. In order to avoid losing the high 
            priority POE devices before the low priority POE devices, 
            this object's value must be greater than value of 
            cswSwitchPoeDevicesLowPriority.";
          smiv2:max-access "read-write";
          smiv2:oid "1.3.6.1.4.1.9.9.500.1.2.1.1.13";
        }

        leaf cswSwitchPowerAllocated {
          type uint32;
          units "Watts";
          description
           "This object indicates the power committed to the POE devices
            connected to the switch.";
          smiv2:max-access "read-only";
          smiv2:oid "1.3.6.1.4.1.9.9.500.1.2.1.1.14";
        }
      }
    }

    container cswStackPortInfoTable {
      description
       "This table contains stackport specific information.  There
        exists an entry in this table for every physical stack
        port that have an entry in the ifTable (IF-MIB).";
      smiv2:oid "1.3.6.1.4.1.9.9.500.1.2.2";

      list cswStackPortInfoEntry {
        key "ifIndex";
        description
         "A conceptual row in the cswStackPortInfoTable.  An entry
          contains information about a stackport.";
        smiv2:oid "1.3.6.1.4.1.9.9.500.1.2.2.1";

        leaf ifIndex {
          type leafref {
            path "/if-mib:IF-MIB/if-mib:ifTable/if-mib:ifEntry/if-mib:ifIndex";
          }
        }

        leaf cswStackPortOperStatus {
          type enumeration {
            enum "up" {
              value "1";
            }
            enum "down" {
              value "2";
            }
            enum "forcedDown" {
              value "3";
            }
          }
          description
           "The state of the stackport.
            
            up         - Connected and operational.
            
            down       - Not connected to a neighboring switch or
                         administrative down.
            
            forcedDown - Shut down by stack manager due to mismatch or
                         stackport errors.";
          smiv2:max-access "read-only";
          smiv2:oid "1.3.6.1.4.1.9.9.500.1.2.2.1.1";
        }

        leaf cswStackPortNeighbor {
          type cisco-tc:EntPhysicalIndexOrZero;
          description
           "This object contains the value of the entPhysicalIndex of the
            switch's chassis to which this stackport is connected to.  If
            the stackport is not connected, the value 0 is returned.";
          smiv2:max-access "read-only";
          smiv2:oid "1.3.6.1.4.1.9.9.500.1.2.2.1.2";
        }
      }
    }

    container cswDistrStackLinkInfoTable {
      description
       "Distributed Stack Link Information.";
      smiv2:oid "1.3.6.1.4.1.9.9.500.1.2.3";

      list cswDistrStackLinkInfoEntry {
        key "entPhysicalIndex cswDSLindex";
        description
         "An Entry containing information about DSL link.";
        smiv2:oid "1.3.6.1.4.1.9.9.500.1.2.3.1";

        leaf entPhysicalIndex {
          type leafref {
            path "/entity-mib:ENTITY-MIB/entity-mib:entPhysicalTable/entity-mib:entPhysicalEntry/entity-mib:entPhysicalIndex";
          }
        }

        leaf cswDSLindex {
          type uint32 {
            range "1..2";
          }
          description
           "This is  index of the distributed stack link 
            with respect to each interface port";
          smiv2:max-access "not-accessible";
          smiv2:oid "1.3.6.1.4.1.9.9.500.1.2.3.1.1";
        }

        leaf cswDistrStackLinkBundleOperStatus {
          type enumeration {
            enum "up" {
              value "1";
            }
            enum "down" {
              value "2";
            }
          }
          description
           "The state of the stackLink.
            up         - Connected and operational.
            down       - Not connected or administrative down.";
          smiv2:max-access "read-only";
          smiv2:oid "1.3.6.1.4.1.9.9.500.1.2.3.1.2";
        }
      }
    }

    container cswDistrStackPhyPortInfoTable {
      description
       "This table contains  objects for Distributed stack
        Link information Table.";
      smiv2:oid "1.3.6.1.4.1.9.9.500.1.2.4";

      list cswDistrStackPhyPortInfoEntry {
        key "entPhysicalIndex cswDSLindex ifIndex";
        description
         "An Entry containing information about stack port that
          is part of Distributed Stack Link.";
        smiv2:oid "1.3.6.1.4.1.9.9.500.1.2.4.1";

        leaf entPhysicalIndex {
          type leafref {
            path "/entity-mib:ENTITY-MIB/entity-mib:entPhysicalTable/entity-mib:entPhysicalEntry/entity-mib:entPhysicalIndex";
          }
        }

        leaf cswDSLindex {
          type leafref {
            path "/CISCO-STACKWISE-MIB:CISCO-STACKWISE-MIB/CISCO-STACKWISE-MIB:cswDistrStackLinkInfoTable/CISCO-STACKWISE-MIB:cswDistrStackLinkInfoEntry/CISCO-STACKWISE-MIB:cswDSLindex";
          }
        }

        leaf ifIndex {
          type leafref {
            path "/if-mib:IF-MIB/if-mib:ifTable/if-mib:ifEntry/if-mib:ifIndex";
          }
        }

        leaf cswDistrStackPhyPort {
          type snmp-framework:SnmpAdminString;
          description
           "This object indicates the name of distributed stack port.";
          smiv2:max-access "read-only";
          smiv2:oid "1.3.6.1.4.1.9.9.500.1.2.4.1.1";
        }

        leaf cswDistrStackPhyPortOperStatus {
          type enumeration {
            enum "up" {
              value "1";
            }
            enum "down" {
              value "2";
            }
          }
          description
           "The state of the distributed stackport.
            up         - Connected and operational.
            down       - Not connected to a neighboring switch or
                         administrative down.";
          smiv2:max-access "read-only";
          smiv2:oid "1.3.6.1.4.1.9.9.500.1.2.4.1.2";
        }

        leaf cswDistrStackPhyPortNbr {
          type snmp-framework:SnmpAdminString;
          description
           "This object indicates the name of distributed stack port's neighbor.";
          smiv2:max-access "read-only";
          smiv2:oid "1.3.6.1.4.1.9.9.500.1.2.4.1.3";
        }

        leaf cswDistrStackPhyPortNbrsw {
          type cisco-tc:EntPhysicalIndexOrZero;
          description
           "This object indicates the EntPhysicalIndex of
            the distributed stack port's neigbor switch.";
          smiv2:max-access "read-only";
          smiv2:oid "1.3.6.1.4.1.9.9.500.1.2.4.1.4";
        }
      }
    }

    container cswStackPowerInfoTable {
      description
       "This table holds the information about all the power stacks in
        a single data stack.";
      smiv2:oid "1.3.6.1.4.1.9.9.500.1.3.1";

      list cswStackPowerInfoEntry {
        key "cswStackPowerStackNumber";
        description
         "An entry in the cswStackPowerInfoTable for each of the power
          stacks in a single data stack. This entry contains information
          regarding the power stack.";
        smiv2:oid "1.3.6.1.4.1.9.9.500.1.3.1.1";

        leaf cswStackPowerStackNumber {
          type uint32;
          description
           "A unique value, greater than zero, to identify a power stack.";
          smiv2:max-access "not-accessible";
          smiv2:oid "1.3.6.1.4.1.9.9.500.1.3.1.1.1";
        }

        leaf cswStackPowerMode {
          type CISCO-STACKWISE-MIB:CswPowerStackMode;
          description
           "This object specifies the information about the mode of the
            power stack. 
            Power-sharing mode: All of the input power can be used for
            loads, and the total available power appears as one huge power
            supply. The power budget includes all power from all supplies.
            No power is set aside for power supply failures, so if a power
            supply fails, load shedding (shutting down of powered devices or
            switches) might occur. This is the default. 
            Redundant mode: The largest power supply is removed from the
            power pool to be used as backup power in case one of the other
            power supplies fails. The available power budget is the total
            power minus the largest power supply. This reduces the available
            power in the pool for switches and powered devices to draw from,
            but in case of a failure or an extreme power load, there is less
            chance of having to shut down switches or powered devices. This
            is the recommended operating mode if your system has enough
            power. 
            In addition, you can configure each mode to run a strict power
            budget or a non-strict (loose) power budget. If the mode is
            strict, the stack power needs cannot exceed the available power.
            When the power budgeted to devices reaches the maximum available
            PoE power, power is denied to the next device seeking power. In
            this mode the stack never goes into an over-budgeted power mode.
            When the mode is non-strict, budgeted power is allowed to exceed
            available power. This is normally not a problem because most
            devices do not run at full power and the chances of all powered
            devices in the stack requiring maximum power at the same time is
            small.";
          smiv2:max-access "read-write";
          smiv2:oid "1.3.6.1.4.1.9.9.500.1.3.1.1.2";
        }

        leaf cswStackPowerMasterMacAddress {
          type yang:mac-address;
          description
           "This object indicates the Mac address of the power stack
            master.";
          smiv2:max-access "read-only";
          smiv2:oid "1.3.6.1.4.1.9.9.500.1.3.1.1.3";
        }

        leaf cswStackPowerMasterSwitchNum {
          type uint32;
          description
           "This object indicates the switch number of the power stack
            master.
            The value of this object would be zero if the power stack
            master is not part of this data stack.";
          smiv2:max-access "read-only";
          smiv2:oid "1.3.6.1.4.1.9.9.500.1.3.1.1.4";
        }

        leaf cswStackPowerNumMembers {
          type uint32;
          description
           "This object indicates the number of members in the power
            stack.";
          smiv2:max-access "read-only";
          smiv2:oid "1.3.6.1.4.1.9.9.500.1.3.1.1.5";
        }

        leaf cswStackPowerType {
          type CISCO-STACKWISE-MIB:CswPowerStackType;
          description
           "This object indicates the topology of the power stack, that is,
            whether the switch is running in RING or STAR topology.";
          smiv2:max-access "read-only";
          smiv2:oid "1.3.6.1.4.1.9.9.500.1.3.1.1.6";
        }

        leaf cswStackPowerName {
          type snmp-framework:SnmpAdminString;
          description
           "This object specifies a unique name of this power stack. A
            zero-length string indicates no name is assigned.";
          smiv2:max-access "read-write";
          smiv2:oid "1.3.6.1.4.1.9.9.500.1.3.1.1.7";
        }
      }
    }

    container cswStackPowerPortInfoTable {
      description
       "This table contains information about the stack power ports.
        There exists an entry in this table for each physical stack
        power port.";
      smiv2:oid "1.3.6.1.4.1.9.9.500.1.3.2";

      list cswStackPowerPortInfoEntry {
        key "entPhysicalIndex cswStackPowerPortIndex";
        description
         "A conceptual row in the cswStackPowerPortInfoTable. This entry
          contains information about a power stack port.";
        smiv2:oid "1.3.6.1.4.1.9.9.500.1.3.2.1";

        leaf entPhysicalIndex {
          type leafref {
            path "/entity-mib:ENTITY-MIB/entity-mib:entPhysicalTable/entity-mib:entPhysicalEntry/entity-mib:entPhysicalIndex";
          }
        }

        leaf cswStackPowerPortIndex {
          type uint32;
          description
           "A unique value, greater than zero, for each stack power port.";
          smiv2:max-access "not-accessible";
          smiv2:oid "1.3.6.1.4.1.9.9.500.1.3.2.1.1";
        }

        leaf cswStackPowerPortOperStatus {
          type enumeration {
            enum "enabled" {
              value "1";
            }
            enum "disabled" {
              value "2";
            }
          }
          description
           "This object is used to either set or unset the operational
            status of the stack port. This object will have following valid
            values,
            
                enabled(1)  : The port is enabled
                disabled(2) : The port is forced down";
          smiv2:max-access "read-write";
          smiv2:oid "1.3.6.1.4.1.9.9.500.1.3.2.1.2";
        }

        leaf cswStackPowerPortNeighborMacAddress {
          type yang:mac-address;
          description
           "This objects indicates the port neighbor's Mac Address.";
          smiv2:max-access "read-only";
          smiv2:oid "1.3.6.1.4.1.9.9.500.1.3.2.1.3";
        }

        leaf cswStackPowerPortNeighborSwitchNum {
          type CISCO-STACKWISE-MIB:CswSwitchNumberOrZero;
          description
           "This objects indicates the port neighbor's switch number. If
            either there is no switch connected or the neighbor is not
            Jack-Jack then the value of this object is going to be 0.";
          smiv2:max-access "read-only";
          smiv2:oid "1.3.6.1.4.1.9.9.500.1.3.2.1.4";
        }

        leaf cswStackPowerPortLinkStatus {
          type enumeration {
            enum "up" {
              value "1";
            }
            enum "down" {
              value "2";
            }
          }
          description
           "This object is used to describe the link status of the stack
            port. This object will have following valid
            values,
            
                up(1)  : The port is connected and operational
                down(2): The port is either forced down or not connected";
          smiv2:max-access "read-only";
          smiv2:oid "1.3.6.1.4.1.9.9.500.1.3.2.1.5";
        }

        leaf cswStackPowerPortOverCurrentThreshold {
          type uint32;
          units "Amperes";
          description
           "This object is used to retrieve the over current threshold. The
            stack power cables are limited to carry current up to the limit
            retrieved by this object. The stack power cables would not be
            able to function properly if either the input or output current
            goes beyond the threshold retrieved by this object.";
          smiv2:max-access "read-write";
          smiv2:oid "1.3.6.1.4.1.9.9.500.1.3.2.1.6";
        }

        leaf cswStackPowerPortName {
          type snmp-framework:SnmpAdminString;
          description
           "This object specifies a unique name of the stack power port as
            shown on the face plate of the system. A zero-length string
            indicates no name is assigned.";
          smiv2:max-access "read-only";
          smiv2:oid "1.3.6.1.4.1.9.9.500.1.3.2.1.7";
        }
      }
    }
  }

  notification cswStackPortChange {
    description
     "This notification is generated when the state
      of a stack port has changed.";
    smiv2:oid "1.3.6.1.4.1.9.9.500.0.0.1";

    container object-1 {

      leaf ifIndex {
        type leafref {
          path "/if-mib:IF-MIB/if-mib:ifTable/if-mib:ifEntry/if-mib:ifIndex";
        }
      }
    }

    container object-2 {

      leaf ifIndex {
        type leafref {
          path "/if-mib:IF-MIB/if-mib:ifTable/if-mib:ifEntry/if-mib:ifIndex";
        }
      }

      leaf cswStackPortOperStatus {
        type leafref {
          path "/CISCO-STACKWISE-MIB:CISCO-STACKWISE-MIB/CISCO-STACKWISE-MIB:cswStackPortInfoTable/CISCO-STACKWISE-MIB:cswStackPortInfoEntry/CISCO-STACKWISE-MIB:cswStackPortOperStatus";
        }
      }
    }

    container object-3 {

      leaf entPhysicalIndex {
        type leafref {
          path "/entity-mib:ENTITY-MIB/entity-mib:entPhysicalTable/entity-mib:entPhysicalEntry/entity-mib:entPhysicalIndex";
        }
      }

      leaf cswSwitchNumCurrent {
        type leafref {
          path "/CISCO-STACKWISE-MIB:CISCO-STACKWISE-MIB/CISCO-STACKWISE-MIB:cswSwitchInfoTable/CISCO-STACKWISE-MIB:cswSwitchInfoEntry/CISCO-STACKWISE-MIB:cswSwitchNumCurrent";
        }
      }
    }
  }

  notification cswStackNewMaster {
    description
     "This notification is generated when a new master has been
      elected.  The notification will contain the cswSwitchNumCurrent
      object to indicate the new master ID.";
    smiv2:oid "1.3.6.1.4.1.9.9.500.0.0.2";

    container object-1 {

      leaf entPhysicalIndex {
        type leafref {
          path "/entity-mib:ENTITY-MIB/entity-mib:entPhysicalTable/entity-mib:entPhysicalEntry/entity-mib:entPhysicalIndex";
        }
      }

      leaf cswSwitchNumCurrent {
        type leafref {
          path "/CISCO-STACKWISE-MIB:CISCO-STACKWISE-MIB/CISCO-STACKWISE-MIB:cswSwitchInfoTable/CISCO-STACKWISE-MIB:cswSwitchInfoEntry/CISCO-STACKWISE-MIB:cswSwitchNumCurrent";
        }
      }
    }
  }

  notification cswStackMismatch {
    description
     "This notification is generated when a new member attempt
      to join the stack but was denied due to a mismatch.  The
      cswSwitchState object will indicate the type of mismatch.";
    smiv2:oid "1.3.6.1.4.1.9.9.500.0.0.3";

    container object-1 {

      leaf entPhysicalIndex {
        type leafref {
          path "/entity-mib:ENTITY-MIB/entity-mib:entPhysicalTable/entity-mib:entPhysicalEntry/entity-mib:entPhysicalIndex";
        }
      }

      leaf cswSwitchState {
        type leafref {
          path "/CISCO-STACKWISE-MIB:CISCO-STACKWISE-MIB/CISCO-STACKWISE-MIB:cswSwitchInfoTable/CISCO-STACKWISE-MIB:cswSwitchInfoEntry/CISCO-STACKWISE-MIB:cswSwitchState";
        }
      }
    }

    container object-2 {

      leaf entPhysicalIndex {
        type leafref {
          path "/entity-mib:ENTITY-MIB/entity-mib:entPhysicalTable/entity-mib:entPhysicalEntry/entity-mib:entPhysicalIndex";
        }
      }

      leaf cswSwitchNumCurrent {
        type leafref {
          path "/CISCO-STACKWISE-MIB:CISCO-STACKWISE-MIB/CISCO-STACKWISE-MIB:cswSwitchInfoTable/CISCO-STACKWISE-MIB:cswSwitchInfoEntry/CISCO-STACKWISE-MIB:cswSwitchNumCurrent";
        }
      }
    }
  }

  notification cswStackRingRedundant {
    description
     "This notification is generated when the redundancy of the
      ring has changed.";
    smiv2:oid "1.3.6.1.4.1.9.9.500.0.0.4";

    container object-1 {

      leaf cswRingRedundant {
        type leafref {
          path "/CISCO-STACKWISE-MIB:CISCO-STACKWISE-MIB/CISCO-STACKWISE-MIB:cswGlobals/CISCO-STACKWISE-MIB:cswRingRedundant";
        }
      }
    }
  }

  notification cswStackNewMember {
    description
     "This notification is generated when a new member joins the
      stack.";
    smiv2:oid "1.3.6.1.4.1.9.9.500.0.0.5";

    container object-1 {

      leaf entPhysicalIndex {
        type leafref {
          path "/entity-mib:ENTITY-MIB/entity-mib:entPhysicalTable/entity-mib:entPhysicalEntry/entity-mib:entPhysicalIndex";
        }
      }

      leaf cswSwitchNumCurrent {
        type leafref {
          path "/CISCO-STACKWISE-MIB:CISCO-STACKWISE-MIB/CISCO-STACKWISE-MIB:cswSwitchInfoTable/CISCO-STACKWISE-MIB:cswSwitchInfoEntry/CISCO-STACKWISE-MIB:cswSwitchNumCurrent";
        }
      }
    }
  }

  notification cswStackMemberRemoved {
    description
     "This notification is generated when a member is removed
      from the stack.";
    smiv2:oid "1.3.6.1.4.1.9.9.500.0.0.6";

    container object-1 {

      leaf entPhysicalIndex {
        type leafref {
          path "/entity-mib:ENTITY-MIB/entity-mib:entPhysicalTable/entity-mib:entPhysicalEntry/entity-mib:entPhysicalIndex";
        }
      }

      leaf cswSwitchNumCurrent {
        type leafref {
          path "/CISCO-STACKWISE-MIB:CISCO-STACKWISE-MIB/CISCO-STACKWISE-MIB:cswSwitchInfoTable/CISCO-STACKWISE-MIB:cswSwitchInfoEntry/CISCO-STACKWISE-MIB:cswSwitchNumCurrent";
        }
      }
    }
  }

  notification cswStackPowerPortLinkStatusChanged {
    description
     "This notification is generated when the link status of a stack
      power port is changed from up to down or down to up. This
      notification is for informational purposes only and no action
      is required. cswStackPowerPortLinkStatus indicates link status
      of the stack power ports. cswSwitchNumCurrent indicates the
      switch number of the system. cswStackPowerPortName specifies a
      unique name of the stack power port as shown on the face plate
      of the system.";
    smiv2:oid "1.3.6.1.4.1.9.9.500.0.0.7";

    container object-1 {

      leaf entPhysicalIndex {
        type leafref {
          path "/entity-mib:ENTITY-MIB/entity-mib:entPhysicalTable/entity-mib:entPhysicalEntry/entity-mib:entPhysicalIndex";
        }
      }

      leaf cswStackPowerPortIndex {
        type leafref {
          path "/CISCO-STACKWISE-MIB:CISCO-STACKWISE-MIB/CISCO-STACKWISE-MIB:cswStackPowerPortInfoTable/CISCO-STACKWISE-MIB:cswStackPowerPortInfoEntry/CISCO-STACKWISE-MIB:cswStackPowerPortIndex";
        }
      }

      leaf cswStackPowerPortLinkStatus {
        type leafref {
          path "/CISCO-STACKWISE-MIB:CISCO-STACKWISE-MIB/CISCO-STACKWISE-MIB:cswStackPowerPortInfoTable/CISCO-STACKWISE-MIB:cswStackPowerPortInfoEntry/CISCO-STACKWISE-MIB:cswStackPowerPortLinkStatus";
        }
      }
    }

    container object-2 {

      leaf entPhysicalIndex {
        type leafref {
          path "/entity-mib:ENTITY-MIB/entity-mib:entPhysicalTable/entity-mib:entPhysicalEntry/entity-mib:entPhysicalIndex";
        }
      }

      leaf cswSwitchNumCurrent {
        type leafref {
          path "/CISCO-STACKWISE-MIB:CISCO-STACKWISE-MIB/CISCO-STACKWISE-MIB:cswSwitchInfoTable/CISCO-STACKWISE-MIB:cswSwitchInfoEntry/CISCO-STACKWISE-MIB:cswSwitchNumCurrent";
        }
      }
    }

    container object-3 {

      leaf entPhysicalIndex {
        type leafref {
          path "/entity-mib:ENTITY-MIB/entity-mib:entPhysicalTable/entity-mib:entPhysicalEntry/entity-mib:entPhysicalIndex";
        }
      }

      leaf cswStackPowerPortIndex {
        type leafref {
          path "/CISCO-STACKWISE-MIB:CISCO-STACKWISE-MIB/CISCO-STACKWISE-MIB:cswStackPowerPortInfoTable/CISCO-STACKWISE-MIB:cswStackPowerPortInfoEntry/CISCO-STACKWISE-MIB:cswStackPowerPortIndex";
        }
      }

      leaf cswStackPowerPortName {
        type leafref {
          path "/CISCO-STACKWISE-MIB:CISCO-STACKWISE-MIB/CISCO-STACKWISE-MIB:cswStackPowerPortInfoTable/CISCO-STACKWISE-MIB:cswStackPowerPortInfoEntry/CISCO-STACKWISE-MIB:cswStackPowerPortName";
        }
      }
    }
  }

  notification cswStackPowerPortOperStatusChanged {
    description
     "This notification is generated when the operational status of a
      stack power port is changed from enabled to disabled or from
      disabled to enabled. This notification is for informational
      purposes only and no action is required. cswSwitchNumCurrent
      indicates the switch number of the system.
      cswStackPowerPortOperStatus indicates operational status
      of the stack power ports. cswStackPowerPortName specifies
      a unique name of the stack power port as shown on the face
      plate of the system.";
    smiv2:oid "1.3.6.1.4.1.9.9.500.0.0.8";

    container object-1 {

      leaf entPhysicalIndex {
        type leafref {
          path "/entity-mib:ENTITY-MIB/entity-mib:entPhysicalTable/entity-mib:entPhysicalEntry/entity-mib:entPhysicalIndex";
        }
      }

      leaf cswSwitchNumCurrent {
        type leafref {
          path "/CISCO-STACKWISE-MIB:CISCO-STACKWISE-MIB/CISCO-STACKWISE-MIB:cswSwitchInfoTable/CISCO-STACKWISE-MIB:cswSwitchInfoEntry/CISCO-STACKWISE-MIB:cswSwitchNumCurrent";
        }
      }
    }

    container object-2 {

      leaf entPhysicalIndex {
        type leafref {
          path "/entity-mib:ENTITY-MIB/entity-mib:entPhysicalTable/entity-mib:entPhysicalEntry/entity-mib:entPhysicalIndex";
        }
      }

      leaf cswStackPowerPortIndex {
        type leafref {
          path "/CISCO-STACKWISE-MIB:CISCO-STACKWISE-MIB/CISCO-STACKWISE-MIB:cswStackPowerPortInfoTable/CISCO-STACKWISE-MIB:cswStackPowerPortInfoEntry/CISCO-STACKWISE-MIB:cswStackPowerPortIndex";
        }
      }

      leaf cswStackPowerPortOperStatus {
        type leafref {
          path "/CISCO-STACKWISE-MIB:CISCO-STACKWISE-MIB/CISCO-STACKWISE-MIB:cswStackPowerPortInfoTable/CISCO-STACKWISE-MIB:cswStackPowerPortInfoEntry/CISCO-STACKWISE-MIB:cswStackPowerPortOperStatus";
        }
      }
    }

    container object-3 {

      leaf entPhysicalIndex {
        type leafref {
          path "/entity-mib:ENTITY-MIB/entity-mib:entPhysicalTable/entity-mib:entPhysicalEntry/entity-mib:entPhysicalIndex";
        }
      }

      leaf cswStackPowerPortIndex {
        type leafref {
          path "/CISCO-STACKWISE-MIB:CISCO-STACKWISE-MIB/CISCO-STACKWISE-MIB:cswStackPowerPortInfoTable/CISCO-STACKWISE-MIB:cswStackPowerPortInfoEntry/CISCO-STACKWISE-MIB:cswStackPowerPortIndex";
        }
      }

      leaf cswStackPowerPortName {
        type leafref {
          path "/CISCO-STACKWISE-MIB:CISCO-STACKWISE-MIB/CISCO-STACKWISE-MIB:cswStackPowerPortInfoTable/CISCO-STACKWISE-MIB:cswStackPowerPortInfoEntry/CISCO-STACKWISE-MIB:cswStackPowerPortName";
        }
      }
    }
  }

  notification cswStackPowerVersionMismatch {
    description
     "This notification is generated when the major version of the
      stack power protocol is different from the other members of the
      power stack. Upon receiving this notification, the user should
      make sure that he/she is using the same software version on all
      the members of the same power stack. cswSwitchNumCurrent
      indicates the switch number of the system seeing the power
      stack version mismatch.";
    smiv2:oid "1.3.6.1.4.1.9.9.500.0.0.9";

    container object-1 {

      leaf entPhysicalIndex {
        type leafref {
          path "/entity-mib:ENTITY-MIB/entity-mib:entPhysicalTable/entity-mib:entPhysicalEntry/entity-mib:entPhysicalIndex";
        }
      }

      leaf cswSwitchNumCurrent {
        type leafref {
          path "/CISCO-STACKWISE-MIB:CISCO-STACKWISE-MIB/CISCO-STACKWISE-MIB:cswSwitchInfoTable/CISCO-STACKWISE-MIB:cswSwitchInfoEntry/CISCO-STACKWISE-MIB:cswSwitchNumCurrent";
        }
      }
    }
  }

  notification cswStackPowerInvalidTopology {
    description
     "This notification is generated when an invalid stack power
      topology is discovered by a switch. cswSwitchNumCurrent
      indicates the switch number of the system where the invalid
      topology is discovered.";
    smiv2:oid "1.3.6.1.4.1.9.9.500.0.0.10";

    container object-1 {

      leaf entPhysicalIndex {
        type leafref {
          path "/entity-mib:ENTITY-MIB/entity-mib:entPhysicalTable/entity-mib:entPhysicalEntry/entity-mib:entPhysicalIndex";
        }
      }

      leaf cswSwitchNumCurrent {
        type leafref {
          path "/CISCO-STACKWISE-MIB:CISCO-STACKWISE-MIB/CISCO-STACKWISE-MIB:cswSwitchInfoTable/CISCO-STACKWISE-MIB:cswSwitchInfoEntry/CISCO-STACKWISE-MIB:cswSwitchNumCurrent";
        }
      }
    }
  }

  notification cscwStackPowerBudgetWarrning {
    description
     "This notification is generated when the switch power budget is
      more than 1000W above its power supplies rated power output.
      cswSwitchNumCurrent indicates the switch number of the system
      where the invalid power budget has been detected.";
    smiv2:oid "1.3.6.1.4.1.9.9.500.0.0.11";

    container object-1 {

      leaf entPhysicalIndex {
        type leafref {
          path "/entity-mib:ENTITY-MIB/entity-mib:entPhysicalTable/entity-mib:entPhysicalEntry/entity-mib:entPhysicalIndex";
        }
      }

      leaf cswSwitchNumCurrent {
        type leafref {
          path "/CISCO-STACKWISE-MIB:CISCO-STACKWISE-MIB/CISCO-STACKWISE-MIB:cswSwitchInfoTable/CISCO-STACKWISE-MIB:cswSwitchInfoEntry/CISCO-STACKWISE-MIB:cswSwitchNumCurrent";
        }
      }
    }
  }

  notification cswStackPowerInvalidInputCurrent {
    description
     "This notification is generated when the input current in the
      stack power cable is over the limit of the threshold retrieved
      by the agent through cswStackPowerPortOverCurrentThreshold
      object. Upon receiving this notification, the user should add a
      power supply to the system whose switch number is generated
      with this notification. cswSwitchNumCurrent
      indicates the switch number of the system.
      cswStackPowerPortOverCurrentThreshold indicates the over current
      threshold of power stack cables. cswStackPowerPortName specifies
      a unique name of the stack power port as shown on the face
      plate of the system.";
    smiv2:oid "1.3.6.1.4.1.9.9.500.0.0.12";

    container object-1 {

      leaf entPhysicalIndex {
        type leafref {
          path "/entity-mib:ENTITY-MIB/entity-mib:entPhysicalTable/entity-mib:entPhysicalEntry/entity-mib:entPhysicalIndex";
        }
      }

      leaf cswSwitchNumCurrent {
        type leafref {
          path "/CISCO-STACKWISE-MIB:CISCO-STACKWISE-MIB/CISCO-STACKWISE-MIB:cswSwitchInfoTable/CISCO-STACKWISE-MIB:cswSwitchInfoEntry/CISCO-STACKWISE-MIB:cswSwitchNumCurrent";
        }
      }
    }

    container object-2 {

      leaf entPhysicalIndex {
        type leafref {
          path "/entity-mib:ENTITY-MIB/entity-mib:entPhysicalTable/entity-mib:entPhysicalEntry/entity-mib:entPhysicalIndex";
        }
      }

      leaf cswStackPowerPortIndex {
        type leafref {
          path "/CISCO-STACKWISE-MIB:CISCO-STACKWISE-MIB/CISCO-STACKWISE-MIB:cswStackPowerPortInfoTable/CISCO-STACKWISE-MIB:cswStackPowerPortInfoEntry/CISCO-STACKWISE-MIB:cswStackPowerPortIndex";
        }
      }

      leaf cswStackPowerPortOverCurrentThreshold {
        type leafref {
          path "/CISCO-STACKWISE-MIB:CISCO-STACKWISE-MIB/CISCO-STACKWISE-MIB:cswStackPowerPortInfoTable/CISCO-STACKWISE-MIB:cswStackPowerPortInfoEntry/CISCO-STACKWISE-MIB:cswStackPowerPortOverCurrentThreshold";
        }
      }
    }

    container object-3 {

      leaf entPhysicalIndex {
        type leafref {
          path "/entity-mib:ENTITY-MIB/entity-mib:entPhysicalTable/entity-mib:entPhysicalEntry/entity-mib:entPhysicalIndex";
        }
      }

      leaf cswStackPowerPortIndex {
        type leafref {
          path "/CISCO-STACKWISE-MIB:CISCO-STACKWISE-MIB/CISCO-STACKWISE-MIB:cswStackPowerPortInfoTable/CISCO-STACKWISE-MIB:cswStackPowerPortInfoEntry/CISCO-STACKWISE-MIB:cswStackPowerPortIndex";
        }
      }

      leaf cswStackPowerPortName {
        type leafref {
          path "/CISCO-STACKWISE-MIB:CISCO-STACKWISE-MIB/CISCO-STACKWISE-MIB:cswStackPowerPortInfoTable/CISCO-STACKWISE-MIB:cswStackPowerPortInfoEntry/CISCO-STACKWISE-MIB:cswStackPowerPortName";
        }
      }
    }
  }

  notification cswStackPowerInvalidOutputCurrent {
    description
     "This notification is generated when the output current in the
      stack power cable is over the limit of the threshold retrieved
      by the agent through cswStackPowerPortOverCurrentThreshold
      object. Upon receiving this notification, the user should
      remove a power supply from the system whose switch number is
      generated with this notification. cswSwitchNumCurrent
      indicates the switch number of the system.
      cswStackPowerPortOverCurrentThreshold indicates the over current
      threshold of power stack cables. cswStackPowerPortName specifies
      a unique name of the stack power port as shown on the face
      plate of the system.";
    smiv2:oid "1.3.6.1.4.1.9.9.500.0.0.13";

    container object-1 {

      leaf entPhysicalIndex {
        type leafref {
          path "/entity-mib:ENTITY-MIB/entity-mib:entPhysicalTable/entity-mib:entPhysicalEntry/entity-mib:entPhysicalIndex";
        }
      }

      leaf cswSwitchNumCurrent {
        type leafref {
          path "/CISCO-STACKWISE-MIB:CISCO-STACKWISE-MIB/CISCO-STACKWISE-MIB:cswSwitchInfoTable/CISCO-STACKWISE-MIB:cswSwitchInfoEntry/CISCO-STACKWISE-MIB:cswSwitchNumCurrent";
        }
      }
    }

    container object-2 {

      leaf entPhysicalIndex {
        type leafref {
          path "/entity-mib:ENTITY-MIB/entity-mib:entPhysicalTable/entity-mib:entPhysicalEntry/entity-mib:entPhysicalIndex";
        }
      }

      leaf cswStackPowerPortIndex {
        type leafref {
          path "/CISCO-STACKWISE-MIB:CISCO-STACKWISE-MIB/CISCO-STACKWISE-MIB:cswStackPowerPortInfoTable/CISCO-STACKWISE-MIB:cswStackPowerPortInfoEntry/CISCO-STACKWISE-MIB:cswStackPowerPortIndex";
        }
      }

      leaf cswStackPowerPortOverCurrentThreshold {
        type leafref {
          path "/CISCO-STACKWISE-MIB:CISCO-STACKWISE-MIB/CISCO-STACKWISE-MIB:cswStackPowerPortInfoTable/CISCO-STACKWISE-MIB:cswStackPowerPortInfoEntry/CISCO-STACKWISE-MIB:cswStackPowerPortOverCurrentThreshold";
        }
      }
    }

    container object-3 {

      leaf entPhysicalIndex {
        type leafref {
          path "/entity-mib:ENTITY-MIB/entity-mib:entPhysicalTable/entity-mib:entPhysicalEntry/entity-mib:entPhysicalIndex";
        }
      }

      leaf cswStackPowerPortIndex {
        type leafref {
          path "/CISCO-STACKWISE-MIB:CISCO-STACKWISE-MIB/CISCO-STACKWISE-MIB:cswStackPowerPortInfoTable/CISCO-STACKWISE-MIB:cswStackPowerPortInfoEntry/CISCO-STACKWISE-MIB:cswStackPowerPortIndex";
        }
      }

      leaf cswStackPowerPortName {
        type leafref {
          path "/CISCO-STACKWISE-MIB:CISCO-STACKWISE-MIB/CISCO-STACKWISE-MIB:cswStackPowerPortInfoTable/CISCO-STACKWISE-MIB:cswStackPowerPortInfoEntry/CISCO-STACKWISE-MIB:cswStackPowerPortName";
        }
      }
    }
  }

  notification cswStackPowerUnderBudget {
    description
     "This notification is generated when the switch's budget is less
      than maximum possible switch power consumption.
      cswSwitchNumCurrent indicates the switch number of the system
      that is running with the power budget less than the power
      consumption.";
    smiv2:oid "1.3.6.1.4.1.9.9.500.0.0.14";

    container object-1 {

      leaf entPhysicalIndex {
        type leafref {
          path "/entity-mib:ENTITY-MIB/entity-mib:entPhysicalTable/entity-mib:entPhysicalEntry/entity-mib:entPhysicalIndex";
        }
      }

      leaf cswSwitchNumCurrent {
        type leafref {
          path "/CISCO-STACKWISE-MIB:CISCO-STACKWISE-MIB/CISCO-STACKWISE-MIB:cswSwitchInfoTable/CISCO-STACKWISE-MIB:cswSwitchInfoEntry/CISCO-STACKWISE-MIB:cswSwitchNumCurrent";
        }
      }
    }
  }

  notification cswStackPowerUnbalancedPowerSupplies {
    description
     "This notification is generated when the switch has no power
      supply but another switch in the same stack has more than one
      power supplies. cswStackPowerName specifies a unique name of the
      power stack where the unbalanced power supplies are detected.";
    smiv2:oid "1.3.6.1.4.1.9.9.500.0.0.15";

    container object-1 {

      leaf cswStackPowerStackNumber {
        type leafref {
          path "/CISCO-STACKWISE-MIB:CISCO-STACKWISE-MIB/CISCO-STACKWISE-MIB:cswStackPowerInfoTable/CISCO-STACKWISE-MIB:cswStackPowerInfoEntry/CISCO-STACKWISE-MIB:cswStackPowerStackNumber";
        }
      }

      leaf cswStackPowerName {
        type leafref {
          path "/CISCO-STACKWISE-MIB:CISCO-STACKWISE-MIB/CISCO-STACKWISE-MIB:cswStackPowerInfoTable/CISCO-STACKWISE-MIB:cswStackPowerInfoEntry/CISCO-STACKWISE-MIB:cswStackPowerName";
        }
      }
    }
  }

  notification cswStackPowerInsufficientPower {
    description
     "This notification is generated when the switch's power stack
      does not have enough power to bring up all the switches in the
      power stack. cswStackPowerName specifies a unique name of the
      power stack where insufficient power condition is detected.";
    smiv2:oid "1.3.6.1.4.1.9.9.500.0.0.16";

    container object-1 {

      leaf cswStackPowerStackNumber {
        type leafref {
          path "/CISCO-STACKWISE-MIB:CISCO-STACKWISE-MIB/CISCO-STACKWISE-MIB:cswStackPowerInfoTable/CISCO-STACKWISE-MIB:cswStackPowerInfoEntry/CISCO-STACKWISE-MIB:cswStackPowerStackNumber";
        }
      }

      leaf cswStackPowerName {
        type leafref {
          path "/CISCO-STACKWISE-MIB:CISCO-STACKWISE-MIB/CISCO-STACKWISE-MIB:cswStackPowerInfoTable/CISCO-STACKWISE-MIB:cswStackPowerInfoEntry/CISCO-STACKWISE-MIB:cswStackPowerName";
        }
      }
    }
  }

  notification cswStackPowerPriorityConflict {
    description
     "This notification is generated when the switch's power
      priorities are conflicting with power priorities of another
      switch in the same power stack. cswStackPowerPortName specifies
      the unique name of the power stack where the conflicting power
      priorities are detected.";
    smiv2:oid "1.3.6.1.4.1.9.9.500.0.0.17";

    container object-1 {

      leaf cswStackPowerStackNumber {
        type leafref {
          path "/CISCO-STACKWISE-MIB:CISCO-STACKWISE-MIB/CISCO-STACKWISE-MIB:cswStackPowerInfoTable/CISCO-STACKWISE-MIB:cswStackPowerInfoEntry/CISCO-STACKWISE-MIB:cswStackPowerStackNumber";
        }
      }

      leaf cswStackPowerName {
        type leafref {
          path "/CISCO-STACKWISE-MIB:CISCO-STACKWISE-MIB/CISCO-STACKWISE-MIB:cswStackPowerInfoTable/CISCO-STACKWISE-MIB:cswStackPowerInfoEntry/CISCO-STACKWISE-MIB:cswStackPowerName";
        }
      }
    }
  }

  notification cswStackPowerUnderVoltage {
    description
     "This notification is generated when the switch had an under
      voltage condition on last boot up. cswSwitchNumCurrent
      indicates the switch number of the system that was forced
      down with the under voltage condition.";
    smiv2:oid "1.3.6.1.4.1.9.9.500.0.0.18";

    container object-1 {

      leaf entPhysicalIndex {
        type leafref {
          path "/entity-mib:ENTITY-MIB/entity-mib:entPhysicalTable/entity-mib:entPhysicalEntry/entity-mib:entPhysicalIndex";
        }
      }

      leaf cswSwitchNumCurrent {
        type leafref {
          path "/CISCO-STACKWISE-MIB:CISCO-STACKWISE-MIB/CISCO-STACKWISE-MIB:cswSwitchInfoTable/CISCO-STACKWISE-MIB:cswSwitchInfoEntry/CISCO-STACKWISE-MIB:cswSwitchNumCurrent";
        }
      }
    }
  }

  notification cswStackPowerGLS {
    description
     "This notification is generated when the switch had to shed
      loads based on a sustained over load (SOC) condition.
      cswSwitchNumCurrent indicates the switch number of the system
      that goes through graceful load shedding.";
    smiv2:oid "1.3.6.1.4.1.9.9.500.0.0.19";

    container object-1 {

      leaf entPhysicalIndex {
        type leafref {
          path "/entity-mib:ENTITY-MIB/entity-mib:entPhysicalTable/entity-mib:entPhysicalEntry/entity-mib:entPhysicalIndex";
        }
      }

      leaf cswSwitchNumCurrent {
        type leafref {
          path "/CISCO-STACKWISE-MIB:CISCO-STACKWISE-MIB/CISCO-STACKWISE-MIB:cswSwitchInfoTable/CISCO-STACKWISE-MIB:cswSwitchInfoEntry/CISCO-STACKWISE-MIB:cswSwitchNumCurrent";
        }
      }
    }
  }

  notification cswStackPowerILS {
    description
     "This notification is generated when the switch had to shed
      loads based on power supply fail condition. cswSwitchNumCurrent
      indicates the switch number of the system that goes through
      immediate load shedding.";
    smiv2:oid "1.3.6.1.4.1.9.9.500.0.0.20";

    container object-1 {

      leaf entPhysicalIndex {
        type leafref {
          path "/entity-mib:ENTITY-MIB/entity-mib:entPhysicalTable/entity-mib:entPhysicalEntry/entity-mib:entPhysicalIndex";
        }
      }

      leaf cswSwitchNumCurrent {
        type leafref {
          path "/CISCO-STACKWISE-MIB:CISCO-STACKWISE-MIB/CISCO-STACKWISE-MIB:cswSwitchInfoTable/CISCO-STACKWISE-MIB:cswSwitchInfoEntry/CISCO-STACKWISE-MIB:cswSwitchNumCurrent";
        }
      }
    }
  }

  notification cswStackPowerSRLS {
    description
     "This notification is generated when the switch had to shed
      loads based on loss of a system in ring topology.
      cswSwitchNumCurrent indicates the switch number of the system
      that detects the loss of system in ring topology.";
    smiv2:oid "1.3.6.1.4.1.9.9.500.0.0.21";

    container object-1 {

      leaf entPhysicalIndex {
        type leafref {
          path "/entity-mib:ENTITY-MIB/entity-mib:entPhysicalTable/entity-mib:entPhysicalEntry/entity-mib:entPhysicalIndex";
        }
      }

      leaf cswSwitchNumCurrent {
        type leafref {
          path "/CISCO-STACKWISE-MIB:CISCO-STACKWISE-MIB/CISCO-STACKWISE-MIB:cswSwitchInfoTable/CISCO-STACKWISE-MIB:cswSwitchInfoEntry/CISCO-STACKWISE-MIB:cswSwitchNumCurrent";
        }
      }
    }
  }

  notification cswStackPowerSSLS {
    description
     "This notification is generated when the switch had to shed
      loads based on loss of a system in star topology.
      cswSwitchNumCurrent indicates the switch number of the system
      that detects the loss of system in star topology.";
    smiv2:oid "1.3.6.1.4.1.9.9.500.0.0.22";

    container object-1 {

      leaf entPhysicalIndex {
        type leafref {
          path "/entity-mib:ENTITY-MIB/entity-mib:entPhysicalTable/entity-mib:entPhysicalEntry/entity-mib:entPhysicalIndex";
        }
      }

      leaf cswSwitchNumCurrent {
        type leafref {
          path "/CISCO-STACKWISE-MIB:CISCO-STACKWISE-MIB/CISCO-STACKWISE-MIB:cswSwitchInfoTable/CISCO-STACKWISE-MIB:cswSwitchInfoEntry/CISCO-STACKWISE-MIB:cswSwitchNumCurrent";
        }
      }
    }
  }

  notification cswStackMemberToBeReloadedForUpgrade {
    description
     "This notification is generated when a member is to be reloaded
      for upgrade.";
    smiv2:oid "1.3.6.1.4.1.9.9.500.0.0.23";

    container object-1 {

      leaf entPhysicalIndex {
        type leafref {
          path "/entity-mib:ENTITY-MIB/entity-mib:entPhysicalTable/entity-mib:entPhysicalEntry/entity-mib:entPhysicalIndex";
        }
      }

      leaf cswSwitchNumCurrent {
        type leafref {
          path "/CISCO-STACKWISE-MIB:CISCO-STACKWISE-MIB/CISCO-STACKWISE-MIB:cswSwitchInfoTable/CISCO-STACKWISE-MIB:cswSwitchInfoEntry/CISCO-STACKWISE-MIB:cswSwitchNumCurrent";
        }
      }
    }
  }

  smiv2:alias "ciscoStackWiseMIB" {
    smiv2:oid "1.3.6.1.4.1.9.9.500";
  }

  smiv2:alias "ciscoStackWiseMIBNotifs" {
    smiv2:oid "1.3.6.1.4.1.9.9.500.0";
  }

  smiv2:alias "cswMIBNotifications" {
    smiv2:oid "1.3.6.1.4.1.9.9.500.0.0";
  }

  smiv2:alias "ciscoStackWiseMIBObjects" {
    smiv2:oid "1.3.6.1.4.1.9.9.500.1";
  }

  smiv2:alias "cswGlobals" {
    smiv2:oid "1.3.6.1.4.1.9.9.500.1.1";
  }

  smiv2:alias "cswStackInfo" {
    smiv2:oid "1.3.6.1.4.1.9.9.500.1.2";
  }

  smiv2:alias "cswStackPowerInfo" {
    smiv2:oid "1.3.6.1.4.1.9.9.500.1.3";
  }

  smiv2:alias "ciscoStackWiseMIBConform" {
    smiv2:oid "1.3.6.1.4.1.9.9.500.2";
  }

  smiv2:alias "cswStackWiseMIBCompliances" {
    smiv2:oid "1.3.6.1.4.1.9.9.500.2.1";
  }

  smiv2:alias "cswStackWiseMIBGroups" {
    smiv2:oid "1.3.6.1.4.1.9.9.500.2.2";
  }

}
