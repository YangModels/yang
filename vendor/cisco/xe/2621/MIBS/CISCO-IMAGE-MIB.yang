/*
 * Generated by confdc --mib2yang-std
 * Source: mgmt/dmi/model/mib/src/CISCO-IMAGE-MIB.mib
 */
/*
 * This YANG module has been generated by smidump 0.5.0:
 *
 *      smidump -f yang CISCO-IMAGE-MIB
 *
 * Do not edit. Edit the source file instead!
 */

module CISCO-IMAGE-MIB {

  namespace "urn:ietf:params:xml:ns:yang:smiv2:CISCO-IMAGE-MIB";
  prefix CISCO-IMAGE-MIB;

  import SNMPv2-TC {
    prefix "snmpv2-tc";
  }

  import ietf-yang-smiv2 {
    prefix "smiv2";
  }

  organization
   "Cisco Systems, Inc.";

  contact
   "Cisco Systems
    Customer Service
    
    Postal: 170 W Tasman Drive
    San Jose, CA  95134
    USA
    
    Tel: +1 800 553-NETS
    
    E-mail: cs-snmp@cisco.com";

  description
   "Router image MIB which identify the capabilities
    and characteristics of the image";

  revision 1995-08-15 {
    description
     "Specify a correct (non-negative) range for an index
      object.";
  }

  revision 1995-01-16 {
    description
     "Initial version of this MIB module.";
  }


  container CISCO-IMAGE-MIB {
    config false;

    container ciscoImageTable {
      description
       "A table provides content information describing the
        executing IOS image.";
      smiv2:oid "1.3.6.1.4.1.9.9.25.1.1";

      list ciscoImageEntry {
        key "ciscoImageIndex";
        description
         "A image characteristic string entry.";
        smiv2:oid "1.3.6.1.4.1.9.9.25.1.1.1";

        leaf ciscoImageIndex {
          type int32 {
            range "0..2147483647";
          }
          description
           "A sequence number for each string stored
            in the IOS image.";
          smiv2:max-access "not-accessible";
          smiv2:oid "1.3.6.1.4.1.9.9.25.1.1.1.1";
        }

        leaf ciscoImageString {
          type snmpv2-tc:DisplayString;
          description
           "The string of this entry.";
          smiv2:max-access "read-only";
          smiv2:oid "1.3.6.1.4.1.9.9.25.1.1.1.2";
        }
      }
    }
  }

  smiv2:alias "ciscoImageMIB" {
    smiv2:oid "1.3.6.1.4.1.9.9.25";
  }

  smiv2:alias "ciscoImageMIBObjects" {
    smiv2:oid "1.3.6.1.4.1.9.9.25.1";
  }

  smiv2:alias "ciscoImageMIBConformance" {
    smiv2:oid "1.3.6.1.4.1.9.9.25.2";
  }

  smiv2:alias "ciscoImageMIBCompliances" {
    smiv2:oid "1.3.6.1.4.1.9.9.25.2.1";
  }

  smiv2:alias "ciscoImageMIBGroups" {
    smiv2:oid "1.3.6.1.4.1.9.9.25.2.2";
  }

}
