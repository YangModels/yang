/*
 * Generated by confdc --mib2yang-std
 * Source: mgmt/dmi/model/mib/src/patched/CISCO-VTP-MIB.mib
 */
/*
 * This YANG module has been generated by smidump 0.5.0:
 *
 *      smidump -f yang CISCO-VTP-MIB
 *
 * Do not edit. Edit the source file instead!
 */

module CISCO-VTP-MIB {

  namespace "urn:ietf:params:xml:ns:yang:smiv2:CISCO-VTP-MIB";
  prefix CISCO-VTP-MIB;

  import CISCO-TC {
    prefix "cisco-tc";
  }

  import IF-MIB {
    prefix "if-mib";
  }

  import INET-ADDRESS-MIB {
    prefix "inet-address";
  }

  import RMON-MIB {
    prefix "rmon-mib";
  }

  import SNMP-FRAMEWORK-MIB {
    prefix "snmp-framework";
  }

  import SNMPv2-TC {
    prefix "snmpv2-tc";
  }

  import ietf-inet-types {
    prefix "inet";
  }

  import ietf-yang-smiv2 {
    prefix "smiv2";
  }

  import ietf-yang-types {
    prefix "yang";
  }

  organization
   "Cisco Systems, Inc.";

  contact
   "Cisco Systems
    Customer Service
    
    Postal: 170 W Tasman Drive
    San Jose, CA  95134
    USA
    
    Tel: +1 800 553-NETS
    
    E-mail: cs-wbu@cisco.com, 
            cs-lan-switch-snmp@cisco.com";

  description
   "The MIB module for entities implementing the VTP
    protocol and Vlan management.";

  revision 2013-10-14 {
    description
     "Added following OBJECT-GROUP
      - vtpSourceInterfaceGroup
      - vtpConfigFileGroup
      - vtpVlanLocalShutdownGroup
      - vtpLocalUpdaterGroup
      - vtpDeviceIdGroup
      Added new compliance
      - vtpMIBCompliance16.";
  }

  revision 2010-05-12 {
    description
     "Added vlanTrunkPortActiveVlansGroup.
      Updated the description of vtpServerDisabled.";
  }

  revision 2009-12-03 {
    description
     "Added vtpTrunkPruningGroup3 and
      vtpConfigNotificationsGroup8. Modified the
      description of vtpNotificationsEnabled and
      managementDomainPruningState.";
  }

  revision 2008-03-07 {
    description
     "Added vlanStatsGroup. Deprecated
      vtpConfigNotificationsGroup5 and replaced
      it with vtpConfigNotificationsGroup6 and
      vtpConfigNotificationsGroup7.";
  }

  revision 2007-10-04 {
    description
     "Correct the descriptions of the object
      vtpConfigDigestErrors and the tables vtpVlanTable
      and vtpInternalVlanTable.";
  }

  revision 2006-02-17 {
    description
     "Removed the OwnerString TEXTUAL-CONVENTION and
      imported the same from RMON-MIB.";
  }

  revision 2004-02-11 {
    description
     "Added 'dynamicGvrp(4)' for the TC VlanTypeExt.";
  }

  revision 2003-11-21 {
    description
     "Add vtpInternalVlanGrp to configure internal
      VLANs' allocation policy and show the owner 
      application names.";
  }

  revision 2003-08-08 {
    description
     "Split vtpConfigNotificationsGroup into two groups:
      vtpConfigNotificationsGroupRev1 and 
      vtpConfigNotificationsGroup5. Write a new compliance
      statement to list vtpConfigNotificationsGroupRev1 in
      instead of vtpConfigNotificationsGroup in the 
      MANDATORY-GROUPS.";
  }

  revision 2003-07-11 {
    description
     "Modify the description of the TC VlanIndex.";
  }

  revision 2003-04-16 {
    description
     "Add support for VTP version 3 features.
      -- Add enumerators and modify the 'DESCRIPTION' of 6 
         existing objects: 
         vtpVersion, managementDomainLocalMode,
         managementDomainConfigRevNumber, 
         managementDomainLastUpdater,
         managementDomainLastChange,  
         managementDomainVersionInUse.
      -- Add 3 new groups: vtpAuthGroup, 
         vtpDiscoverGroup, vtpDatabaseGroup.";
  }

  revision 2002-04-10 {
    description
     "-- Add 4 new notifications/traps vtpLocalModeChanged,
      vtpVersionInUseChanged, vtpVlanCreated and 
      vtpVlanDeleted. 
      -- Add 2 new objects vtpVlanCreatedNotifEnabled and 
      vtpVlanDeletedNotifEnabled to control the
      generation of vtpVlanCreated and vtpVlanDeleted.
      -- Use vtpNotificationsEnabled to control the
      generation of vtpLocalModeChanged and
      vtpVersionInUseChanged by grouping them in a
      new group vtpConfigNotificationsGroup2.  
      -- Deprecate the object vlanTrunkPortsDot1qTag and
      its related group.";
  }

  revision 2002-02-28 {
    description
     "Deprecate the object, vlanTrunkPortDot1qTunnel.";
  }

  revision 2001-08-03 {
    description
     "Add a new off(4) mode to managementDomainLocalMode.";
  }

  revision 2001-02-26 {
    description
     "Deprecate read-only object vtpVlanEditTypeExt and
      add a new read-create object vtpVlanEditTypeExt2.
      Enable Notification groups.";
  }

  revision 2001-02-12 {
    description
     "Added Remote SPAN (RSPAN) VLAN feature, VLAN
      management features without supporting VTP protocol
      and a new object to handle one-VLAN-editing.";
  }

  revision 2000-09-19 {
    description
     "Added the mapping from VLAN ID to its corresponding
      ifIndex";
  }

  revision 2000-04-10 {
    description
     "Added 4k VLAN editing and Dot1qTunnel support";
  }

  revision 2000-01-06 {
    description
     "Added 4k VLAN support";
  }

  revision 1999-02-25 {
    description
     "Added import of NOTIFICATION-GROUP";
  }

  revision 1999-01-05 {
    description
     "Added support for encapsulation type notApplicable";
  }

  revision 1998-05-19 {
    description
     "Added support for encapsulation type negotiation";
  }

  revision 1997-08-08 {
    description
     "Added Backup CRF object";
  }

  revision 1997-05-09 {
    description
     "Added ARE and STE hop counts.";
  }

  revision 1997-02-24 {
    description
     "Added support for turning on VTP for Trunk cards.";
  }

  revision 1997-01-27 {
    description
     "Added support for version 2 features.";
  }

  revision 1996-09-16 {
    description
     "Updated the Token-Ring support.";
  }

  revision 1996-07-17 {
    description
     "Updated to include objects in support of VTP pruning.";
  }

  revision 1996-01-18 {
    description
     "Initial version of this MIB module.";
  }

  typedef VlanIndex {
    type int32 {
      range "0..4095";
    }
    description
     "The VLAN-id of a VLAN on ISL or 802.1q trunks.
      
      Modification of default parameters is allowed.
      Implementations are allowed to restrict
      the range of VLANs.
      
      For entities support up to 1024 VLANS.
      VLANs above 1000 are reserved for default VLANs and
      future use. Modification of default parameters is
      allowed. Creation or deletion of VLANs above 1000 is not
      allowed.
      
      For a new object which needs the vlan-id of a VLAN as
      its SYNTAX, it is suggested to import VlanIndex from
      Q-BRIDGE-MIB instead of importing this TC here in 
      CISCO-VTP-MIB.";
  }

  typedef ManagementDomainIndex {
    type int32 {
      range "1..255";
    }
    description
     "An arbitrary integer-value to uniquely identify a
      management domain on the local system.";
  }

  typedef VlanType {
    type enumeration {
      enum "ethernet" {
        value "1";
      }
      enum "fddi" {
        value "2";
      }
      enum "tokenRing" {
        value "3";
      }
      enum "fddiNet" {
        value "4";
      }
      enum "trNet" {
        value "5";
      }
      enum "deprecated" {
        value "6";
      }
    }
    description
     "The type of a VLAN.
      
      Note that the 'ethernet' type, is used for any ethernet or
      802.3 VLAN, including an ATM Ethernet ELAN; and the
      'tokenRing' ('trCrf') type is used for each VLAN
      representing a single logical 802.5 ring including an ATM
      Token-Ring ELAN.
      
      The 'trCrf' type is used for token ring VLANs made up of
      (at most) one transparently bridged LAN segment.
      
      The 'trBrf' type is used for VLANs which represent the
      scope of many 'trCrf' VLANs all connected together via
      source route bridging.  The token ring 'trBrf' can be said
      to represent the bridged broadcast domain.";
  }

  typedef VlanTypeExt {
    type bits {
      bit vtpmanageable {
        position "0";
      }
      bit internal {
        position "1";
      }
      bit reserved {
        position "2";
      }
      bit rspan {
        position "3";
      }
      bit dynamicGvrp {
        position "4";
      }
    }
    description
     "The additional type information of VLAN.
      vtpmanageable(0)    An user defined VLAN which is 
                          manageable through VTP protocol.
                          The value of this bit cannot be 
                          changed.
      internal(1)         An internal VLAN created by the device.
                          Internal VLANs cannot be created or
                          deleted. The value of this bit cannot
                          be changed.
      reserved(2)         A VLAN reserved by the device.
                          Reserved VLANs cannot be created or
                          deleted. The value of this bit cannot
                          be changed.
      rspan(3)            A VLAN created to exclusively carry
                          the traffic for a Remote Switched
                          Port Analyzer (RSPAN). This bit can
                          only be set or cleared during the
                          VLAN creation. Once the VLAN is
                          created, the value of this bit cannot
                          be modified.
      dynamicGvrp(4)      A VLAN dynamically created by GVRP
                          (GARP VLAN Registration Protocol)
                          propagation. The value of this bit 
                          cannot be changed.";
    reference
     "RFC2674.";
  }


  container CISCO-VTP-MIB {
    config false;

    container vtpStatus {
      smiv2:oid "1.3.6.1.4.1.9.9.46.1.1";

      leaf vtpVersion {
        type enumeration {
          enum "one" {
            value "1";
          }
          enum "two" {
            value "2";
          }
          enum "none" {
            value "3";
          }
          enum "three" {
            value "4";
          }
        }
        description
         "The version of VTP in use on the local system.  A device
          will report its version capability and not any particular
          version in use on the device. If the device does not support
          vtp, the version is none(3).";
        smiv2:max-access "read-only";
        smiv2:oid "1.3.6.1.4.1.9.9.46.1.1.1";
      }

      leaf vtpMaxVlanStorage {
        type int32 {
          range "-1..1023";
        }
        description
         "An estimate of the maximum number of VLANs about which the
          local system can recover complete VTP information after a
          reboot.  If the number of defined VLANs is greater than this
          value, then the system can not act as a VTP Server. For a
          device which has no means to calculate the estimated number,
          this value is -1.";
        smiv2:max-access "read-only";
        smiv2:oid "1.3.6.1.4.1.9.9.46.1.1.2";
      }

      leaf vtpNotificationsEnabled {
        type boolean;
        description
         "An indication of whether the notifications/traps defined by
          the vtpConfigNotificationsGroup, vtpConfigNotificationsGroup2,
          and vtpConfigNotificationsGroup8 are enabled.";
        smiv2:max-access "read-write";
        smiv2:oid "1.3.6.1.4.1.9.9.46.1.1.3";
      }

      leaf vtpVlanCreatedNotifEnabled {
        type boolean;
        description
         "An indication of whether the notification should
          be generated when a VLAN is created. 
          
          If the value of this object is 'true' then the
          vtpVlanCreated notification will be generated.
          
          If the value of this object is 'false' then the
          vtpVlanCreated notification will not be generated.";
        smiv2:max-access "read-write";
        smiv2:oid "1.3.6.1.4.1.9.9.46.1.1.4";
      }

      leaf vtpVlanDeletedNotifEnabled {
        type boolean;
        description
         "An indication of whether the notification should
          be generated when a VLAN is deleted.  
          
          If the value of this object is 'true' then the
          vtpVlanDeleted notification will be generated.
          
          If the value of this object is 'false' then the
          vtpVlanDeleted notification will not be generated.";
        smiv2:max-access "read-write";
        smiv2:oid "1.3.6.1.4.1.9.9.46.1.1.5";
      }
    }

    container internalVlanInfo {
      smiv2:oid "1.3.6.1.4.1.9.9.46.1.3.2";

      leaf vtpInternalVlanAllocPolicy {
        type enumeration {
          enum "ascending" {
            value "1";
          }
          enum "descending" {
            value "2";
          }
        }
        description
         "The internal VLAN allocation policy.
          
          'ascending'  - internal VLANs are allocated
                         starting from a lowwer VLAN ID and 
                         upwards.
          'descending' - internal VLANs are allocated
                         starting from a higher VLAN ID and
                         downwards.";
        smiv2:max-access "read-write";
        smiv2:oid "1.3.6.1.4.1.9.9.46.1.3.2.1";
      }
    }

    container vlanTrunkPorts {
      smiv2:oid "1.3.6.1.4.1.9.9.46.1.6";

      leaf vlanTrunkPortSetSerialNo {
        type snmpv2-tc:TestAndIncr;
        description
         "An advisory lock used to allow several cooperating SNMPv2
          managers to coordinate their use of the SNMPv2 set operation
          acting upon any instance of vlanTrunkPortVlansEnabled.";
        smiv2:max-access "read-write";
        smiv2:oid "1.3.6.1.4.1.9.9.46.1.6.2";
      }

      leaf vlanTrunkPortsDot1qTag {
        type boolean;
        status deprecated;
        description
         "An indication of whether the tagging on all VLANs including
          native VLAN for all 802.1q trunks is enabled.
          
          If this object has a value of true(1) then all VLANs
          including native VLAN are tagged.  If the value is false(2)
          then all VLANs excluding native VLAN are tagged.
          
          This object has been deprecated and is replaced by the
          object 'cltcDot1qAllTaggedEnabled' in the
          CISCO-L2-TUNNEL-CONFIG-MIB";
        smiv2:defval "false";
        smiv2:max-access "read-write";
        smiv2:oid "1.3.6.1.4.1.9.9.46.1.6.3";
      }
    }

    container vlanStatistics {
      smiv2:oid "1.3.6.1.4.1.9.9.46.1.10";

      leaf vlanStatsVlans {
        type uint32;
        description
         "This object indicates the number of the existing
          manageable VLANs with VLAN indices from 1 to
          1024 in the system.";
        smiv2:max-access "read-only";
        smiv2:oid "1.3.6.1.4.1.9.9.46.1.10.1";
      }

      leaf vlanStatsExtendedVlans {
        type uint32;
        description
         "This object indicates the number of the
          existing manageable VLANs with VLAN indices
          greater than 1024 in the system.";
        smiv2:max-access "read-only";
        smiv2:oid "1.3.6.1.4.1.9.9.46.1.10.2";
      }

      leaf vlanStatsInternalVlans {
        type uint32;
        description
         "This object indicates the number of the
          internal VLANs existing in the system.";
        smiv2:max-access "read-only";
        smiv2:oid "1.3.6.1.4.1.9.9.46.1.10.3";
      }

      leaf vlanStatsFreeVlans {
        type uint32;
        description
         "This object indicates the number of the
          free or unused VLANs in the system.";
        smiv2:max-access "read-only";
        smiv2:oid "1.3.6.1.4.1.9.9.46.1.10.4";
      }
    }

    container managementDomainTable {
      description
       "The table containing information on the management domains
        in which the local system is participating.  Devices which
        support only one management domain will support just one row
        in this table, and will not let it be deleted nor let other
        rows be created.  Devices which support multiple management
        domains will allow rows to be created and deleted, but will
        not allow the last row to be deleted. If the device does 
        not support VTP, the table is read-only.";
      smiv2:oid "1.3.6.1.4.1.9.9.46.1.2.1";

      list managementDomainEntry {
        key "managementDomainIndex";
        description
         "Information about the status of one management domain.";
        smiv2:oid "1.3.6.1.4.1.9.9.46.1.2.1.1";

        leaf managementDomainIndex {
          type CISCO-VTP-MIB:ManagementDomainIndex;
          description
           "An arbitrary value to uniquely identify the management
            domain on the local system.";
          smiv2:max-access "not-accessible";
          smiv2:oid "1.3.6.1.4.1.9.9.46.1.2.1.1.1";
        }

        leaf managementDomainName {
          type snmpv2-tc:DisplayString {
            length "0..32";
          }
          description
           "The management name of a domain in which the local system
            is participating.  The zero-length name corresponds to the
            'no management-domain' state which is the initial value at
            installation-time if not configured otherwise.  Note that
            the zero-length name does not correspond to an operational
            management domain, and a device does not send VTP
            advertisements while in the 'no management-domain' state.  A
            device leaves the 'no management-domain' state when it
            obtains a management-domain name, either through
            configuration or through inheriting the management-domain
            name from a received VTP advertisement.
            
            When the value of an existing instance of this object is
            modified by network management, the local system should re-
            initialize its VLAN information (for the given management
            domain) as if it had just been configured with a management
            domain name at installation time.";
          smiv2:max-access "read-write";
          smiv2:oid "1.3.6.1.4.1.9.9.46.1.2.1.1.2";
        }

        leaf managementDomainLocalMode {
          type enumeration {
            enum "client" {
              value "1";
            }
            enum "server" {
              value "2";
            }
            enum "transparent" {
              value "3";
            }
            enum "off" {
              value "4";
            }
          }
          description
           "The local VTP mode in this management domain when
            managementDomainVersionInUse is version1(1) or
            version2(2).
            
            If managementDomainVersionInUse is version3(4), this 
            object has the same value with vtpDatabaseLocalMode 
            of VLAN database type.
            
            - 'client' indicates that the local system is acting
              as a VTP client.
            
            - 'server' indicates that the local system is acting
              as a VTP server.
            
            - 'transparent' indicates that the local system does
              not generate or listen to VTP messages, but forwards
              messages. This mode can also be set by the device
              itself when the amount of VLAN information is too
              large for it to hold in DRAM.
            
            - 'off' indicates that the local system does not
              generate, listen to or forward any VTP messages.";
          smiv2:max-access "read-write";
          smiv2:oid "1.3.6.1.4.1.9.9.46.1.2.1.1.3";
        }

        leaf managementDomainConfigRevNumber {
          type yang:gauge32;
          description
           "The current Configuration Revision Number as known by
            the local device for this management domain when 
            managementDomainVersionInUse is version1(1) or 
            version2(2).
            
            If managementDomainVersionInUse is version3(4), this 
            object has the same value with vtpDatabaseRevisionNumber 
            of VLAN database type.
            
            This value is updated (if necessary) whenever a VTP
            advertisement is received or generated. When in the
            'no management-domain' state, this value is 0.";
          smiv2:max-access "read-only";
          smiv2:oid "1.3.6.1.4.1.9.9.46.1.2.1.1.4";
        }

        leaf managementDomainLastUpdater {
          type inet:ipv4-address;
          description
           "The IP-address (or one of them) of the VTP Server which
            last updated the Configuration Revision Number, as indicated
            in the most recently received VTP advertisement for this
            management domain, when managementDomainVersionInUse is
            version1(1) or version2(2). 
            
            If managementDomainVersionInUse is version3(4), this object
            has the value of 0.0.0.0.
            
            Before an advertisement has been received, this value is
            0.0.0.0.";
          smiv2:max-access "read-only";
          smiv2:oid "1.3.6.1.4.1.9.9.46.1.2.1.1.5";
        }

        leaf managementDomainLastChange {
          type snmpv2-tc:DateAndTime;
          description
           "The time at which the Configuration Revision Number was
            (last) increased to its current value, as indicated in the
            most recently received VTP advertisement for this management
            domain when managementDomainVersionInUse is not version3(4)
            or in the most recently received VTP VLAN database 
            advertisement for this management domain when 
            managementDomainVersionInUse is version3(4).
            
            The value 0x0000010100000000 indicates that the device which
            last increased the Configuration Revision Number had no idea
            of the date/time, or that no advertisement has been
            received.";
          smiv2:max-access "read-only";
          smiv2:oid "1.3.6.1.4.1.9.9.46.1.2.1.1.6";
        }

        leaf managementDomainRowStatus {
          type snmpv2-tc:RowStatus;
          description
           "The status of this conceptual row.";
          smiv2:max-access "read-write";
          smiv2:oid "1.3.6.1.4.1.9.9.46.1.2.1.1.7";
        }

        leaf managementDomainTftpServer {
          type inet:ipv4-address;
          description
           "The IP address of a TFTP Server in/from which VTP VLAN
            information for this management domain is to be
            stored/retrieved.  If the information is being locally
            stored in NVRAM, this object should take the value 0.0.0.0.";
          smiv2:max-access "read-write";
          smiv2:oid "1.3.6.1.4.1.9.9.46.1.2.1.1.8";
        }

        leaf managementDomainTftpPathname {
          type snmpv2-tc:DisplayString;
          description
           "The complete pathname of the file at the TFTP Server
            identified by the value of managementDomainTftpServer
            in/from which VTP VLAN information for this management
            domain is to be stored/retrieved.  If the value of
            corresponding instance of managementDomainTftpServer is
            0.0.0.0, the value of this object is ignored.";
          smiv2:max-access "read-write";
          smiv2:oid "1.3.6.1.4.1.9.9.46.1.2.1.1.9";
        }

        leaf managementDomainPruningState {
          type enumeration {
            enum "enabled" {
              value "1";
            }
            enum "disabled" {
              value "2";
            }
          }
          description
           "An indication of whether VTP pruning is enabled or disabled
            in this managament domain. 
            
            This object can only be modified, either when the 
            corresponding instance value of managementDomainVersionInUse 
            is 'version1' or 'version2' and the corresponding instance 
            value of managementDomainLocalMode is 'server', or when the 
            corresponding instance value of managementDomainVersionInUse 
            is 'version3' and the corresponding instance value of 
            managementDomainLocalMode is 'server' or 'client'.";
          smiv2:max-access "read-write";
          smiv2:oid "1.3.6.1.4.1.9.9.46.1.2.1.1.10";
        }

        leaf managementDomainVersionInUse {
          type enumeration {
            enum "version1" {
              value "1";
            }
            enum "version2" {
              value "2";
            }
            enum "none" {
              value "3";
            }
            enum "version3" {
              value "4";
            }
          }
          description
           "The current version of the VTP that is in use by the
            designated management domain. 
            
            This object can be set to none(3) only when 
            vtpVersion is none(3).";
          smiv2:max-access "read-write";
          smiv2:oid "1.3.6.1.4.1.9.9.46.1.2.1.1.11";
        }

        leaf managementDomainPruningStateOper {
          type enumeration {
            enum "enabled" {
              value "1";
            }
            enum "disabled" {
              value "2";
            }
          }
          description
           "Indicates whether VTP pruning is operationally enabled or
            disabled in this managament domain.";
          smiv2:max-access "read-only";
          smiv2:oid "1.3.6.1.4.1.9.9.46.1.2.1.1.12";
        }

        leaf managementDomainAdminSrcIf {
          type snmp-framework:SnmpAdminString;
          description
           "The object specifies the interface to be used as the
            preferred source interface for the VTP IP updater address.
            
            A zero length value indicates that a source interface is not
            specified.";
          smiv2:max-access "read-write";
          smiv2:oid "1.3.6.1.4.1.9.9.46.1.2.1.1.13";
        }

        leaf managementDomainSourceOnlyMode {
          type boolean;
          description
           "The object specifies whether to use only the IP address of
            managementDomainAdminSrcIf as the VTP IP updater address. 
            
            'true' indicates to only use the IP address of 
                   managementDomainAdminSrcIf as the VTP IP 
                   updater address. 
            
            'false' indicates to use the IP address of 
                    managementDomainAdminSrcIf as the VTP IP 
                    updater address if managementDomainAdminSrcIf 
                    is configured with an IP address.  Otherwise, the 
                    first available IP address of the system will
                    be used.";
          smiv2:defval "false";
          smiv2:max-access "read-write";
          smiv2:oid "1.3.6.1.4.1.9.9.46.1.2.1.1.14";
        }

        leaf managementDomainOperSrcIf {
          type snmp-framework:SnmpAdminString;
          description
           "The object indicates the interface used as the
            preferred source interface for the VTP IP updater address.
            
            A zero length string indicates that a source interface is not
            available.";
          smiv2:max-access "read-only";
          smiv2:oid "1.3.6.1.4.1.9.9.46.1.2.1.1.15";
        }

        leaf managementDomainConfigFile {
          type snmp-framework:SnmpAdminString;
          description
           "The object specifies the file name where VTP configuration
            is stored in the format of <filename> or <devices>:[<filename>].
            
            <device> can be (but not limited to): flash, bootflash,
            slot0, slot1, disk0.";
          smiv2:max-access "read-write";
          smiv2:oid "1.3.6.1.4.1.9.9.46.1.2.1.1.16";
        }

        leaf managementDomainLocalUpdaterType {
          type inet-address:InetAddressType;
          description
           "The object indicates the type of the Internet address
            of the preferred source interface for the VTP IP updater.
            
            The value of this object is 'unknown' if
            managementDomainVersionInUse is 'version3' or
            managementDomainLocalMode is not 'server'.";
          smiv2:max-access "read-only";
          smiv2:oid "1.3.6.1.4.1.9.9.46.1.2.1.1.17";
        }

        leaf managementDomainLocalUpdater {
          type inet-address:InetAddress;
          description
           "The object indicates the Internet address of the
            preferred source interface for the VTP IP updater.";
          smiv2:max-access "read-only";
          smiv2:oid "1.3.6.1.4.1.9.9.46.1.2.1.1.18";
        }

        leaf managementDomainDeviceID {
          type snmp-framework:SnmpAdminString;
          description
           "The object indicates a value that uniquely identifies
            this device within a VTP Domain.
            
            The value of this object is zero length string if
            managementDomainVersionInUse is not 'version3'.";
          smiv2:max-access "read-only";
          smiv2:oid "1.3.6.1.4.1.9.9.46.1.2.1.1.19";
        }
      }
    }

    container vtpVlanTable {
      description
       "This table contains information on the VLANs which
        currently exist.";
      smiv2:oid "1.3.6.1.4.1.9.9.46.1.3.1";

      list vtpVlanEntry {
        key "managementDomainIndex vtpVlanIndex";
        description
         "Information about one current VLAN.  The
          managementDomainIndex value in the INDEX clause indicates
          which management domain the VLAN is in.";
        smiv2:oid "1.3.6.1.4.1.9.9.46.1.3.1.1";

        leaf managementDomainIndex {
          type leafref {
            path "/CISCO-VTP-MIB:CISCO-VTP-MIB/CISCO-VTP-MIB:managementDomainTable/CISCO-VTP-MIB:managementDomainEntry/CISCO-VTP-MIB:managementDomainIndex";
          }
        }

        leaf vtpVlanIndex {
          type CISCO-VTP-MIB:VlanIndex;
          description
           "The VLAN-id of this VLAN on ISL or 802.1q trunks.";
          smiv2:max-access "not-accessible";
          smiv2:oid "1.3.6.1.4.1.9.9.46.1.3.1.1.1";
        }

        leaf vtpVlanState {
          type enumeration {
            enum "operational" {
              value "1";
            }
            enum "suspended" {
              value "2";
            }
            enum "mtuTooBigForDevice" {
              value "3";
            }
            enum "mtuTooBigForTrunk" {
              value "4";
            }
          }
          description
           "The state of this VLAN.
            
            The state 'mtuTooBigForDevice' indicates that this device
            cannot participate in this VLAN because the VLAN's MTU is
            larger than the device can support.
            
            The state 'mtuTooBigForTrunk' indicates that while this
            VLAN's MTU is supported by this device, it is too large for
            one or more of the device's trunk ports.";
          smiv2:max-access "read-only";
          smiv2:oid "1.3.6.1.4.1.9.9.46.1.3.1.1.2";
        }

        leaf vtpVlanType {
          type CISCO-VTP-MIB:VlanType;
          description
           "The type of this VLAN.";
          smiv2:max-access "read-only";
          smiv2:oid "1.3.6.1.4.1.9.9.46.1.3.1.1.3";
        }

        leaf vtpVlanName {
          type snmpv2-tc:DisplayString {
            length "1..32";
          }
          description
           "The name of this VLAN.  This name is used as the ELAN-name
            for an ATM LAN-Emulation segment of this VLAN.";
          smiv2:max-access "read-only";
          smiv2:oid "1.3.6.1.4.1.9.9.46.1.3.1.1.4";
        }

        leaf vtpVlanMtu {
          type int32 {
            range "1500..18190";
          }
          description
           "The MTU size on this VLAN, defined as the size of largest
            MAC-layer (information field portion of the) data frame
            which can be transmitted on the VLAN.";
          smiv2:max-access "read-only";
          smiv2:oid "1.3.6.1.4.1.9.9.46.1.3.1.1.5";
        }

        leaf vtpVlanDot10Said {
          type binary {
            length "4";
          }
          description
           "The value of the 802.10 SAID field for this VLAN.";
          smiv2:max-access "read-only";
          smiv2:oid "1.3.6.1.4.1.9.9.46.1.3.1.1.6";
        }

        leaf vtpVlanRingNumber {
          type int32 {
            range "0..4095";
          }
          description
           "The ring number of this VLAN.  This object is only
            instantiated when the value of the corresponding instance of
            vtpVlanType has a value of 'fddi' or 'tokenRing' and Source
            Routing is in use on this VLAN.";
          smiv2:max-access "read-only";
          smiv2:oid "1.3.6.1.4.1.9.9.46.1.3.1.1.7";
        }

        leaf vtpVlanBridgeNumber {
          type int32 {
            range "0..15";
          }
          description
           "The bridge number of the VTP-capable switches for this
            VLAN.  This object is only instantiated for VLANs that are
            involved with emulating token ring segments.";
          smiv2:max-access "read-only";
          smiv2:oid "1.3.6.1.4.1.9.9.46.1.3.1.1.8";
        }

        leaf vtpVlanStpType {
          type enumeration {
            enum "ieee" {
              value "1";
            }
            enum "ibm" {
              value "2";
            }
            enum "hybrid" {
              value "3";
            }
          }
          description
           "The type of the Spanning Tree Protocol (STP) running on
            this VLAN.  This object is only instanciated when the
            value of the corresponding instance of vtpVlanType has a
            value of 'fddiNet' or 'trNet'.
            
            The value returned by this object depends upon the value
            of the corresponding instance of vtpVlanEditStpType.
            
            - 'ieee' indicates IEEE STP is running exclusively.
            
            - 'ibm' indicates IBM STP is running exclusively.
            
            - 'hybrid' indicates a STP that allows a combination of
              IEEE and IBM is running.
            
            The 'hybrid' STP type results from tokenRing/fddi VLANs
            that are children of this trNet/fddiNet parent VLAN being
            configured in a combination of SRT and SRB
            vtpVlanBridgeTypes while the instance of
            vtpVlanEditStpType that corresponds to this object is set
            to 'auto'.";
          smiv2:max-access "read-only";
          smiv2:oid "1.3.6.1.4.1.9.9.46.1.3.1.1.9";
        }

        leaf vtpVlanParentVlan {
          type CISCO-VTP-MIB:VlanIndex;
          description
           "The parent VLAN for this VLAN.  This object is only
            instantiated when the value of the corresponding instance of
            vtpVlanType has a value of 'fddi' or 'tokenRing' and Source
            Routing is in use on this VLAN.  The parent VLAN must have 
            a vtpVlanType value of fddiNet(4) or trNet(5), 
            respectively.";
          smiv2:max-access "read-only";
          smiv2:oid "1.3.6.1.4.1.9.9.46.1.3.1.1.10";
        }

        leaf vtpVlanTranslationalVlan1 {
          type CISCO-VTP-MIB:VlanIndex;
          description
           "A VLAN to which this VLAN is being translational-bridged.
            If this value and the corresponding instance of
            vtpVlanTranslationalVlan2 are both zero, then this VLAN is
            not being translational-bridged.";
          smiv2:max-access "read-only";
          smiv2:oid "1.3.6.1.4.1.9.9.46.1.3.1.1.11";
        }

        leaf vtpVlanTranslationalVlan2 {
          type CISCO-VTP-MIB:VlanIndex;
          description
           "Another VLAN, i.e., other than that indicated by
            vtpVlanTranslationalVlan1, to which this VLAN is being
            translational-bridged.  If this value and the corresponding
            instance of vtpVlanTranslationalVlan1 are both zero, then
            this VLAN is not being translational-bridged.";
          smiv2:max-access "read-only";
          smiv2:oid "1.3.6.1.4.1.9.9.46.1.3.1.1.12";
        }

        leaf vtpVlanBridgeType {
          type enumeration {
            enum "none" {
              value "0";
            }
            enum "srt" {
              value "1";
            }
            enum "srb" {
              value "2";
            }
          }
          description
           "The type of the Source Route bridging mode in use on this
            VLAN.  This object is only instantiated when the value of 
            the corresponding instance of vtpVlanType has a value of 
            fddi(2) or tokenRing(3) and Source Routing is in use on
            this VLAN.";
          smiv2:max-access "read-only";
          smiv2:oid "1.3.6.1.4.1.9.9.46.1.3.1.1.13";
        }

        leaf vtpVlanAreHopCount {
          type int32 {
            range "1..13";
          }
          description
           "The maximum number of bridge hops allowed in
            All Routes Explorer frames on this VLAN.  This
            object is only instantiated when the value of the
            corresponding instance of vtpVlanType has a value of fddi(2)
            or tokenRing(3) and Source Routing is in use on this VLAN.";
          smiv2:max-access "read-only";
          smiv2:oid "1.3.6.1.4.1.9.9.46.1.3.1.1.14";
        }

        leaf vtpVlanSteHopCount {
          type int32 {
            range "1..13";
          }
          description
           "The maximum number of bridge hops allowed in
            Spanning Tree Explorer frames on this VLAN.  This
            object is only instantiated when the value of the
            corresponding instance of vtpVlanType has a value of fddi(2)
            or tokenRing(3) and Source Routing is in use on this VLAN.";
          smiv2:max-access "read-only";
          smiv2:oid "1.3.6.1.4.1.9.9.46.1.3.1.1.15";
        }

        leaf vtpVlanIsCRFBackup {
          type boolean;
          description
           "True if this VLAN is of type trCrf and also is acting as
            a backup trCrf for the ISL distributed BRF";
          smiv2:max-access "read-only";
          smiv2:oid "1.3.6.1.4.1.9.9.46.1.3.1.1.16";
        }

        leaf vtpVlanTypeExt {
          type CISCO-VTP-MIB:VlanTypeExt;
          description
           "The additional type information of this VLAN.";
          smiv2:max-access "read-only";
          smiv2:oid "1.3.6.1.4.1.9.9.46.1.3.1.1.17";
        }

        leaf vtpVlanIfIndex {
          type if-mib:InterfaceIndexOrZero;
          description
           "The value of the ifIndex corresponding to this VLAN ID.
            If the VLAN ID does not have its corresponding interface, 
            this object has the value of zero.";
          smiv2:max-access "read-only";
          smiv2:oid "1.3.6.1.4.1.9.9.46.1.3.1.1.18";
        }
      }
    }

    container vtpInternalVlanTable {
      description
       "A vtpInternalVlanTable entry contains
        information on an existing internal
        VLAN. It is internally created by the
        device for a specific application program 
        and hence owned by the application.  
        It cannot be modified or deleted by (local 
        or network) management.";
      smiv2:oid "1.3.6.1.4.1.9.9.46.1.3.2.2";

      list vtpInternalVlanEntry {
        key "managementDomainIndex vtpVlanIndex";
        description
         "Information about one current internal
          VLAN.";
        smiv2:oid "1.3.6.1.4.1.9.9.46.1.3.2.2.1";

        leaf managementDomainIndex {
          type leafref {
            path "/CISCO-VTP-MIB:CISCO-VTP-MIB/CISCO-VTP-MIB:managementDomainTable/CISCO-VTP-MIB:managementDomainEntry/CISCO-VTP-MIB:managementDomainIndex";
          }
        }

        leaf vtpVlanIndex {
          type leafref {
            path "/CISCO-VTP-MIB:CISCO-VTP-MIB/CISCO-VTP-MIB:vtpVlanTable/CISCO-VTP-MIB:vtpVlanEntry/CISCO-VTP-MIB:vtpVlanIndex";
          }
        }

        leaf vtpInternalVlanOwner {
          type snmp-framework:SnmpAdminString;
          description
           "The program name of the internal VLAN's
            owner application. This internal VLAN
            is allocated by the device specifically
            for this application and no one else
            could create, modify or delete this 
            VLAN.";
          smiv2:max-access "read-only";
          smiv2:oid "1.3.6.1.4.1.9.9.46.1.3.2.2.1.1";
        }
      }
    }

    container vtpVlanEditTable {
      description
       "The table which contains the information in the Edit
        Buffers, one Edit Buffer per management domain.  The
        information for a particular management domain is
        initialized, by a 'copy' operation, to be the current global
        VLAN information for that management domain.  After
        initialization, editing can be performed to add VLANs,
        delete VLANs, or modify their global parameters.  The
        information as modified through editing is local to this
        Edit Buffer.  An apply operation using the
        vtpVlanEditOperation object is necessary to instanciate the
        modified information as the new global VLAN information for
        that management domain.
        
        To use the Edit Buffer, a manager acts as follows:
        
        1. ensures the Edit Buffer for a management domain is empty,
        i.e., there are no rows in this table for this management
        domain.
        
        2. issues a SNMP set operation which sets
        vtpVlanEditOperation to 'copy', and vtpVlanEditBufferOwner
        to its own identifier (e.g., its own IP address).
        
        3. if this set operation is successful, proceeds to edit the
        information in the vtpVlanEditTable.
        
        4. if and when the edited information is to be instantiated,
        issues a SNMP set operation which sets vtpVlanEditOperation
        to 'apply'.
        
        5. issues retrieval requests to obtain the value of
        vtpVlanApplyStatus, until the result of the apply is
        determined.
        
        6. releases the Edit Buffer by issuing a SNMP set operation
        which sets vtpVlanEditOperation to 'release'.
        
        Note that the information contained in this table is not
        saved across agent reboots.";
      smiv2:oid "1.3.6.1.4.1.9.9.46.1.4.2";

      list vtpVlanEditEntry {
        key "managementDomainIndex vtpVlanEditIndex";
        description
         "Information about one VLAN in the Edit Buffer for a
          particular management domain.";
        smiv2:oid "1.3.6.1.4.1.9.9.46.1.4.2.1";

        leaf managementDomainIndex {
          type leafref {
            path "/CISCO-VTP-MIB:CISCO-VTP-MIB/CISCO-VTP-MIB:managementDomainTable/CISCO-VTP-MIB:managementDomainEntry/CISCO-VTP-MIB:managementDomainIndex";
          }
        }

        leaf vtpVlanEditIndex {
          type CISCO-VTP-MIB:VlanIndex;
          description
           "The VLAN-id which this VLAN would have on ISL or
            802.1q trunks.";
          smiv2:max-access "not-accessible";
          smiv2:oid "1.3.6.1.4.1.9.9.46.1.4.2.1.1";
        }

        leaf vtpVlanEditState {
          type enumeration {
            enum "operational" {
              value "1";
            }
            enum "suspended" {
              value "2";
            }
          }
          description
           "The state which this VLAN would have.";
          smiv2:defval "operational";
          smiv2:max-access "read-write";
          smiv2:oid "1.3.6.1.4.1.9.9.46.1.4.2.1.2";
        }

        leaf vtpVlanEditType {
          type CISCO-VTP-MIB:VlanType;
          description
           "The type which this VLAN would have.
            An implementation may restrict access to this object.";
          smiv2:defval "ethernet";
          smiv2:max-access "read-write";
          smiv2:oid "1.3.6.1.4.1.9.9.46.1.4.2.1.3";
        }

        leaf vtpVlanEditName {
          type snmpv2-tc:DisplayString {
            length "1..32";
          }
          description
           "The name which this VLAN would have.  This name would be
            used as the ELAN-name for an ATM LAN-Emulation segment of
            this VLAN.
            
            An implementation may restrict access to this object.";
          smiv2:max-access "read-write";
          smiv2:oid "1.3.6.1.4.1.9.9.46.1.4.2.1.4";
        }

        leaf vtpVlanEditMtu {
          type int32 {
            range "1500..18190";
          }
          description
           "The MTU size which this VLAN would have, defined as the
            size of largest MAC-layer (information field portion of the)
            data frame which can be transmitted on the VLAN.
            
            An implementation may restrict access to this object.";
          smiv2:defval "1500";
          smiv2:max-access "read-write";
          smiv2:oid "1.3.6.1.4.1.9.9.46.1.4.2.1.5";
        }

        leaf vtpVlanEditDot10Said {
          type binary {
            length "4";
          }
          description
           "The value of the 802.10 SAID field which would be used for
            this VLAN.
            
            An implementation may restrict access to this object.";
          smiv2:max-access "read-write";
          smiv2:oid "1.3.6.1.4.1.9.9.46.1.4.2.1.6";
        }

        leaf vtpVlanEditRingNumber {
          type int32 {
            range "0..4095";
          }
          description
           "The ring number which would be used for this VLAN.  This
            object is only instantiated when the value of the
            corresponding instance of vtpVlanEditType has a value of
            'fddi' or 'tokenRing' and Source Routing is in use on 
            this VLAN.";
          smiv2:max-access "read-write";
          smiv2:oid "1.3.6.1.4.1.9.9.46.1.4.2.1.7";
        }

        leaf vtpVlanEditBridgeNumber {
          type int32 {
            range "0..15";
          }
          description
           "The bridge number of the VTP-capable switches which would
            be used for this VLAN.  This object is only instantiated
            when the value of the corresponding instance of
            vtpVlanEditType has a value of fddiNet(4) or trNet(5).";
          smiv2:max-access "read-write";
          smiv2:oid "1.3.6.1.4.1.9.9.46.1.4.2.1.8";
        }

        leaf vtpVlanEditStpType {
          type enumeration {
            enum "ieee" {
              value "1";
            }
            enum "ibm" {
              value "2";
            }
            enum "auto" {
              value "3";
            }
          }
          description
           "The type of the Spanning Tree Protocol which would be
            running on this VLAN.  This object is only instantiated
            when the value of the corresponding instance of
            vtpVlanEditType has a value of fddiNet(4) or trNet(5).
            
            If 'ieee' is selected, the STP that runs will be IEEE.
            
            If 'ibm' is selected, the STP that runs will be IBM.
            
            If 'auto' is selected, the STP that runs will be
            dependant on the values of vtpVlanEditBridgeType for all
            children tokenRing/fddi type VLANs.  This will result in
            a 'hybrid' STP (see vtpVlanStpType).";
          smiv2:max-access "read-write";
          smiv2:oid "1.3.6.1.4.1.9.9.46.1.4.2.1.9";
        }

        leaf vtpVlanEditParentVlan {
          type CISCO-VTP-MIB:VlanIndex;
          description
           "The VLAN index of the VLAN which would be the parent for
            this VLAN.  This object is only instantiated when the value
            of the corresponding instance of vtpVlanEditType has a value
            of 'fddi' or 'tokenRing' and Source Routing is in use on
            this VLAN.  The parent VLAN must have a vtpVlanEditType 
            value of fddiNet(4) or trNet(5), respectively.";
          smiv2:max-access "read-write";
          smiv2:oid "1.3.6.1.4.1.9.9.46.1.4.2.1.10";
        }

        leaf vtpVlanEditRowStatus {
          type snmpv2-tc:RowStatus;
          description
           "The status of this row.  Any and all columnar objects in an
            existing row can be modified irrespective of the status of
            the row.
            
            A row is not qualified for activation until instances of at
            least its vtpVlanEditType, vtpVlanEditName and
            vtpVlanEditDot10Said columns have appropriate values.
            
            The management station should endeavor to make all rows
            consistent in the table before 'apply'ing the buffer.  An
            inconsistent entry in the table will cause the entire
            buffer to be rejected with the vtpVlanApplyStatus object
            set to the appropriate error value.";
          smiv2:max-access "read-write";
          smiv2:oid "1.3.6.1.4.1.9.9.46.1.4.2.1.11";
        }

        leaf vtpVlanEditTranslationalVlan1 {
          type CISCO-VTP-MIB:VlanIndex;
          description
           "A VLAN to which this VLAN would be translational-bridged.
            If this value and the corresponding instance of
            vtpVlanTranslationalVlan2 are both zero, then this VLAN
            would not be translational-bridged.
            
            An implementation may restrict access to this object.";
          smiv2:defval "0";
          smiv2:max-access "read-write";
          smiv2:oid "1.3.6.1.4.1.9.9.46.1.4.2.1.12";
        }

        leaf vtpVlanEditTranslationalVlan2 {
          type CISCO-VTP-MIB:VlanIndex;
          description
           "Another VLAN, i.e., other than that indicated by
            vtpVlanEditTranslationalVlan1, to which this VLAN would be
            translational-bridged.  If this value and the corresponding
            instance of vtpVlanTranslationalVlan1 are both zero, then
            this VLAN would not be translational-bridged.
            
            An implementation may restrict access to this object.";
          smiv2:defval "0";
          smiv2:max-access "read-write";
          smiv2:oid "1.3.6.1.4.1.9.9.46.1.4.2.1.13";
        }

        leaf vtpVlanEditBridgeType {
          type enumeration {
            enum "srt" {
              value "1";
            }
            enum "srb" {
              value "2";
            }
          }
          description
           "The type of Source Route bridging mode which would be in
            use on this VLAN.  This object is only instantiated when 
            the value of  the corresponding instance of vtpVlanEditType
            has a value of fddi(2) or tokenRing(3) and Source Routing 
            is in use on this VLAN.";
          smiv2:max-access "read-write";
          smiv2:oid "1.3.6.1.4.1.9.9.46.1.4.2.1.14";
        }

        leaf vtpVlanEditAreHopCount {
          type int32 {
            range "1..13";
          }
          description
           "The maximum number of bridge hops allowed in
            All Routes Explorer frames on this VLAN.  This
            object is only instantiated when the value of the
            corresponding instance of vtpVlanType has a value of fddi(2)
            or tokenRing(3) and Source Routing is in use on this VLAN.";
          smiv2:max-access "read-write";
          smiv2:oid "1.3.6.1.4.1.9.9.46.1.4.2.1.15";
        }

        leaf vtpVlanEditSteHopCount {
          type int32 {
            range "1..13";
          }
          description
           "The maximum number of bridge hops allowed in
            Spanning Tree Explorer frames on this VLAN.  This
            object is only instantiated when the value of the
            corresponding instance of vtpVlanType has a value of fddi(2)
            or tokenRing(3) and Source Routing is in use on this VLAN.";
          smiv2:max-access "read-write";
          smiv2:oid "1.3.6.1.4.1.9.9.46.1.4.2.1.16";
        }

        leaf vtpVlanEditIsCRFBackup {
          type boolean;
          description
           "True if this VLAN is of type trCrf and also is acting as
            a backup trCrf for the ISL distributed BRF.  This object is
            only instantiated when the value of the corresponding
            instance of vtpVlanEditType has a value of tokenRing(3).";
          smiv2:max-access "read-write";
          smiv2:oid "1.3.6.1.4.1.9.9.46.1.4.2.1.17";
        }

        leaf vtpVlanEditTypeExt {
          type CISCO-VTP-MIB:VlanTypeExt;
          status deprecated;
          description
           "The additional type information of this VLAN.
            vtpVlanEditTypeExt object is superseded by vtpVlanEditTypeExt2.";
          smiv2:max-access "read-only";
          smiv2:oid "1.3.6.1.4.1.9.9.46.1.4.2.1.18";
        }

        leaf vtpVlanEditTypeExt2 {
          type CISCO-VTP-MIB:VlanTypeExt;
          description
           "The additional type information of this VLAN.
            The VlanTypeExt TC specifies which bits may
            be written by a management application.
            The agent should provide a default value.";
          smiv2:max-access "read-write";
          smiv2:oid "1.3.6.1.4.1.9.9.46.1.4.2.1.19";
        }
      }
    }

    container vtpVlanLocalShutdownTable {
      description
       "Ths table contains the VLAN local shutdown
        information within management domain.";
      smiv2:oid "1.3.6.1.4.1.9.9.46.1.4.3";

      list vtpVlanLocalShutdownEntry {
        key "managementDomainIndex vtpVlanIndex";
        description
         "An entry containing VLAN local shutdown information for a
          particular VLAN in the management domain.
          
          An entry is created if a VLAN which supports local shutdown
          has been created.
          
          An entry is deleted if a VLAN which supports local shutdown
          has been removed.";
        smiv2:oid "1.3.6.1.4.1.9.9.46.1.4.3.1";

        leaf managementDomainIndex {
          type leafref {
            path "/CISCO-VTP-MIB:CISCO-VTP-MIB/CISCO-VTP-MIB:managementDomainTable/CISCO-VTP-MIB:managementDomainEntry/CISCO-VTP-MIB:managementDomainIndex";
          }
        }

        leaf vtpVlanIndex {
          type leafref {
            path "/CISCO-VTP-MIB:CISCO-VTP-MIB/CISCO-VTP-MIB:vtpVlanTable/CISCO-VTP-MIB:vtpVlanEntry/CISCO-VTP-MIB:vtpVlanIndex";
          }
        }

        leaf vtpVlanLocalShutdown {
          type enumeration {
            enum "up" {
              value "1";
            }
            enum "down" {
              value "2";
            }
          }
          description
           "The object specifies the VLAN local shutdown state.";
          smiv2:max-access "read-write";
          smiv2:oid "1.3.6.1.4.1.9.9.46.1.4.3.1.1";
        }
      }
    }

    container vlanTrunkPortTable {
      description
       "The table containing information on the local system's VLAN
        trunk ports.";
      smiv2:oid "1.3.6.1.4.1.9.9.46.1.6.1";

      list vlanTrunkPortEntry {
        key "vlanTrunkPortIfIndex";
        description
         "Information about one trunk port.";
        smiv2:oid "1.3.6.1.4.1.9.9.46.1.6.1.1";

        leaf vlanTrunkPortIfIndex {
          type if-mib:InterfaceIndex;
          description
           "The value of ifIndex for the interface corresponding to
            this trunk port.";
          smiv2:max-access "not-accessible";
          smiv2:oid "1.3.6.1.4.1.9.9.46.1.6.1.1.1";
        }

        leaf vlanTrunkPortManagementDomain {
          type CISCO-VTP-MIB:ManagementDomainIndex;
          description
           "The value of managementDomainIndex for the management
            domain on this trunk port.  Devices which support only one
            management domain will support this object read-only.";
          smiv2:max-access "read-write";
          smiv2:oid "1.3.6.1.4.1.9.9.46.1.6.1.1.2";
        }

        leaf vlanTrunkPortEncapsulationType {
          type enumeration {
            enum "isl" {
              value "1";
            }
            enum "dot10" {
              value "2";
            }
            enum "lane" {
              value "3";
            }
            enum "dot1Q" {
              value "4";
            }
            enum "negotiate" {
              value "5";
            }
          }
          description
           "The type of VLAN encapsulation desired to be used on this
            trunk port. It is either a particular type, or 'negotiate'
            meaning whatever type results from the negotiation.
            negotiate(5) is not allowed if the port does not support
            negotiation or if its vlanTrunkPortDynamicState is set to
            on(1) or onNoNegotiate(5). Whether writing to this object
            in order to modify the encapsulation is supported is both
            device and interface specific.";
          smiv2:max-access "read-write";
          smiv2:oid "1.3.6.1.4.1.9.9.46.1.6.1.1.3";
        }

        leaf vlanTrunkPortVlansEnabled {
          type binary {
            length "128";
          }
          description
           "A string of octets containing one bit per VLAN in the
            management domain on this trunk port.  The first octet
            corresponds to VLANs with VlanIndex values of 0 through 7;
            the second octet to VLANs 8 through 15; etc.  The most
            significant bit of each octet corresponds to the lowest
            value VlanIndex in that octet.  If the bit corresponding to
            a VLAN is set to '1', then the local system is enabled for
            sending and receiving frames on that VLAN; if the bit is set
            to '0', then the system is disabled from sending and
            receiving frames on that VLAN.
            
            To avoid conflicts between overlapping partial updates by
            multiple managers, i.e., updates which modify only a portion
            of an instance of this object (e.g., enable/disable a single
            VLAN on the trunk port), any SNMP Set operation accessing an
            instance of this object should also write the value of
            vlanTrunkPortSetSerialNo.";
          smiv2:max-access "read-write";
          smiv2:oid "1.3.6.1.4.1.9.9.46.1.6.1.1.4";
        }

        leaf vlanTrunkPortNativeVlan {
          type CISCO-VTP-MIB:VlanIndex;
          description
           "The VlanIndex of the VLAN which is represented by native
            frames on this trunk port.  For trunk ports not supporting
            the sending and receiving of native frames, this value
            should be set to zero.";
          smiv2:max-access "read-write";
          smiv2:oid "1.3.6.1.4.1.9.9.46.1.6.1.1.5";
        }

        leaf vlanTrunkPortRowStatus {
          type snmpv2-tc:RowStatus;
          description
           "The status of this row.  In some circumstances, the
            creation of a row in this table is needed to enable the
            appropriate trunking/tagging protocol on the port, to enable
            the use of VTP on the port, and to assign the port to the
            appropriate management domain.  In other circumstances, rows
            in this table will be created as a by-product of other
            operations.";
          smiv2:max-access "read-write";
          smiv2:oid "1.3.6.1.4.1.9.9.46.1.6.1.1.6";
        }

        leaf vlanTrunkPortInJoins {
          type yang:counter32;
          description
           "The number of VTP Join messages received on this trunk
            port.";
          smiv2:max-access "read-only";
          smiv2:oid "1.3.6.1.4.1.9.9.46.1.6.1.1.7";
        }

        leaf vlanTrunkPortOutJoins {
          type yang:counter32;
          description
           "The number of VTP Join messages sent on this trunk port.";
          smiv2:max-access "read-only";
          smiv2:oid "1.3.6.1.4.1.9.9.46.1.6.1.1.8";
        }

        leaf vlanTrunkPortOldAdverts {
          type yang:counter32;
          description
           "The number of VTP Advertisement messages which indicated
            the sender does not support VLAN-pruning received on this
            trunk port.";
          smiv2:max-access "read-only";
          smiv2:oid "1.3.6.1.4.1.9.9.46.1.6.1.1.9";
        }

        leaf vlanTrunkPortVlansPruningEligible {
          type binary {
            length "128";
          }
          description
           "A string of octets containing one bit per VLAN in the
            management domain on this trunk port.  The first octet
            corresponds to VLANs with VlanIndex values of 0 through 7;
            the second octet to VLANs 8 through 15; etc.  The most
            significant bit of each octet corresponds to the lowest
            value VlanIndex in that octet.
            
            If the bit corresponding to a VLAN is set to '1', then the
            local system is permitted to prune that VLAN on this trunk
            port; if the bit is set to '0', then the system must not
            prune that VLAN on this trunk port.
            
            To avoid conflicts between overlapping partial updates by
            multiple managers, i.e., updates which modify only a portion
            of an instance of this object (e.g., enable/disable a single
            VLAN on the trunk port), any SNMP Set operation accessing an
            instance of this object should also write the value of
            vlanTrunkPortSetSerialNo.";
          smiv2:max-access "read-write";
          smiv2:oid "1.3.6.1.4.1.9.9.46.1.6.1.1.10";
        }

        leaf vlanTrunkPortVlansXmitJoined {
          type binary {
            length "128";
          }
          description
           "A string of octets containing one bit per VLAN in the
            management domain on this trunk port.  The first octet
            corresponds to VLANs with VlanIndex values of 0 through 7;
            the second octet to VLANs 8 through 15; etc.  The most
            significant bit of each octet corresponds to the lowest
            value VlanIndex in that octet.
            
            If the bit corresponding to a VLAN is set to '1', then this
            VLAN is presently being forwarded on this trunk port, i.e.,
            it is not pruned; if the bit is set to '0', then this VLAN
            is presently not being forwarded on this trunk port, either
            because it is pruned or for some other reason.";
          smiv2:max-access "read-only";
          smiv2:oid "1.3.6.1.4.1.9.9.46.1.6.1.1.11";
        }

        leaf vlanTrunkPortVlansRcvJoined {
          type binary {
            length "128";
          }
          description
           "A string of octets containing one bit per VLAN in the
            management domain on this trunk port.  The first octet
            corresponds to VLANs with VlanIndex values of 0 through 7;
            the second octet to VLANs 8 through 15; etc.  The most
            significant bit of each octet corresponds to the lowest
            value VlanIndex in that octet.
            
            If the bit corresponding to a VLAN is set to '1', then the
            local switch is currently sending joins for this VLAN on
            this trunk port, i.e., it is asking to receive frames for
            this VLAN; if the bit is set to '0', then the local switch
            is not currently sending joins for this VLAN on this trunk
            port.";
          smiv2:max-access "read-only";
          smiv2:oid "1.3.6.1.4.1.9.9.46.1.6.1.1.12";
        }

        leaf vlanTrunkPortDynamicState {
          type enumeration {
            enum "on" {
              value "1";
            }
            enum "off" {
              value "2";
            }
            enum "desirable" {
              value "3";
            }
            enum "auto" {
              value "4";
            }
            enum "onNoNegotiate" {
              value "5";
            }
          }
          description
           "For devices that allows dynamic determination of whether
            a link between two switches should be a trunk or not, this
            object allows the operator to mandate the behavior of that
            dynamic mechanism.
            
            on(1) dictates that the interface will always be a
            trunk. This is the value for static entries (those that
            show no dynamic behavior). If the negotiation is supported
            on this port, negotiation will take place with the far end
            to attempt to bring the far end into trunking state.
            
            off(2) allows an operator to specify that the specified
            interface is never to be trunk, regardless of any dynamic
            mechanisms to the contrary.  This value is useful for
            overriding the default behavior of some switches. If the
            negotiation is supported on this port, negotiation will take
            place with the far end to attempt on the link to bring the
            far end into non-trunking state.
            
            desirable(3) is used to indicate that it is desirable for
            the interface to become a trunk.  The device will initiate
            any negotiation necessary to become a trunk but will not
            become a trunk unless it receives confirmation from the far
            end on the link.
            
            auto(4) is used to indicate that the interface is capable
            and willing to become a trunk but will not initiate
            trunking negotiations.  The far end on the link are
            required to either start negotiations or start sending
            encapsulated packets, on which event the specified
            interface will become a trunk.
            
            onNoNegotiate(5) is used to indicate that the interface is
            permanently set to be a trunk, and no negotiation takes
            place with the far end on the link to ensure consistent
            operation. This is similar to on(1) except no negotiation
            takes place with the far end.
            
            If the port does not support negotiation or its
            vlanTrunkPortEncapsulationType is set to negotiate(5),
            onNoNegotiate(5) is not allowed.
            
            Devices that do no support dynamic determination (for just
            a particular interface, encapsulation or for the whole
            device) need only support the 'on', and 'off' values.";
          smiv2:max-access "read-write";
          smiv2:oid "1.3.6.1.4.1.9.9.46.1.6.1.1.13";
        }

        leaf vlanTrunkPortDynamicStatus {
          type enumeration {
            enum "trunking" {
              value "1";
            }
            enum "notTrunking" {
              value "2";
            }
          }
          description
           "Indicates whether the specified interface is either
            acting as a trunk or not. This is a result of the
            vlanTrunkPortDynamicState and the ifOperStatus of the
            trunk port itself.";
          smiv2:max-access "read-only";
          smiv2:oid "1.3.6.1.4.1.9.9.46.1.6.1.1.14";
        }

        leaf vlanTrunkPortVtpEnabled {
          type boolean;
          description
           "Some trunk interface modules allow VTP to be
            enabled/disabled seperately from that of the central
            device.  In such a case this object provides management a
            way to remotely enable VTP on that module.  If a module
            does not support a seperate VTP enabled state then this
            object shall always return 'true' and will accept no other
            value during a SET operation.";
          smiv2:max-access "read-write";
          smiv2:oid "1.3.6.1.4.1.9.9.46.1.6.1.1.15";
        }

        leaf vlanTrunkPortEncapsulationOperType {
          type enumeration {
            enum "isl" {
              value "1";
            }
            enum "dot10" {
              value "2";
            }
            enum "lane" {
              value "3";
            }
            enum "dot1Q" {
              value "4";
            }
            enum "negotiating" {
              value "5";
            }
            enum "notApplicable" {
              value "6";
            }
          }
          description
           "The type of VLAN encapsulation in use on this trunk port.
            For intefaces with vlanTrunkPortDynamicStatus of
            notTrunking(2) the vlanTrunkPortEncapsulationOperType shall
            be notApplicable(6).";
          smiv2:max-access "read-only";
          smiv2:oid "1.3.6.1.4.1.9.9.46.1.6.1.1.16";
        }

        leaf vlanTrunkPortVlansEnabled2k {
          type binary {
            length "0..128";
          }
          description
           "A string of octets containing one bit per VLAN for VLANS
            with VlanIndex values of 1024 through 2047 in the management
            domain on this trunk port.  The first octet corresponds to
            VLANs with VlanIndex values of 1024 through 1031; the second
            octet to VLANs 1032 through 1039; etc.  The most significant
            bit of each octet corresponds to the lowest value VlanIndex
            in that octet. If the bit corresponding to a VLAN is set to
            '1', then the local system is enabled for sending and
            receiving frames on that VLAN; if the bit is set to '0',
            then the system is disabled from sending and receiving
            frames on that VLAN. The default value is zero length
            string.
            
            To avoid conflicts between overlapping partial updates by
            multiple managers, i.e., updates which modify only a portion
            of an instance of this object (e.g., enable/disable a single
            VLAN on the trunk port), any SNMP Set operation accessing an
            instance of this object should also write the value of
            vlanTrunkPortSetSerialNo.";
          smiv2:max-access "read-write";
          smiv2:oid "1.3.6.1.4.1.9.9.46.1.6.1.1.17";
        }

        leaf vlanTrunkPortVlansEnabled3k {
          type binary {
            length "0..128";
          }
          description
           "A string of octets containing one bit per VLAN for VLANS
            with VlanIndex values of 2048 through 3071 in the management
            domain on this trunk port.  The first octet corresponds to
            VLANs with VlanIndex values of 2048 through 2055; the second
            octet to VLANs 2056 through 2063; etc.  The most significant
            bit of each octet corresponds to the lowest value VlanIndex
            in that octet. If the bit corresponding to a VLAN is set to
            '1', then the local system is enabled for sending and
            receiving frames on that VLAN; if the bit is set to '0',
            then the system is disabled from sending and receiving
            frames on that VLAN. The default value is zero length
            string.
            
            To avoid conflicts between overlapping partial updates by
            multiple managers, i.e., updates which modify only a portion
            of an instance of this object (e.g., enable/disable a single
            VLAN on the trunk port), any SNMP Set operation accessing an
            instance of this object should also write the value of
            vlanTrunkPortSetSerialNo.";
          smiv2:max-access "read-write";
          smiv2:oid "1.3.6.1.4.1.9.9.46.1.6.1.1.18";
        }

        leaf vlanTrunkPortVlansEnabled4k {
          type binary {
            length "0..128";
          }
          description
           "A string of octets containing one bit per VLAN for VLANS
            with VlanIndex values of 3072 through 4095 in the management
            domain on this trunk port.  The first octet corresponds to
            VLANs with VlanIndex values of 3072 through 3079; the second
            octet to VLANs 3080 through 3087; etc.  The most significant
            bit of each octet corresponds to the lowest value VlanIndex
            in that octet. If the bit corresponding to a VLAN is set to
            '1', then the local system is enabled for sending and
            receiving frames on that VLAN; if the bit is set to '0',
            then the system is disabled from sending and receiving
            frames on that VLAN. The default value is zero length
            string.
            
            To avoid conflicts between overlapping partial updates by
            multiple managers, i.e., updates which modify only a portion
            of an instance of this object (e.g., enable/disable a single
            VLAN on the trunk port), any SNMP Set operation accessing an
            instance of this object should also write the value of
            vlanTrunkPortSetSerialNo.";
          smiv2:max-access "read-write";
          smiv2:oid "1.3.6.1.4.1.9.9.46.1.6.1.1.19";
        }

        leaf vtpVlansPruningEligible2k {
          type binary {
            length "0..128";
          }
          description
           "A string of octets containing one bit per VLAN for VLANS
            with VlanIndex values of 1024 through 2047 in the management
            domain on this trunk port.  The first octet corresponds to
            VLANs with VlanIndex values of 1024 through 1031; the second
            octet to VLANs 1032 through 1039; etc.  The most significant
            bit of each octet corresponds to the lowest value VlanIndex
            in that octet.
            
            If the bit corresponding to a VLAN is set to '1', then the
            local system is permitted to prune that VLAN on this trunk
            port; if the bit is set to '0', then the system must not
            prune that VLAN on this trunk port.
            The default value is zero length string.
            
            To avoid conflicts between overlapping partial updates by
            multiple managers, i.e., updates which modify only a portion
            of an instance of this object (e.g., enable/disable a single
            VLAN on the trunk port), any SNMP Set operation accessing an
            instance of this object should also write the value of
            vlanTrunkPortSetSerialNo.";
          smiv2:max-access "read-write";
          smiv2:oid "1.3.6.1.4.1.9.9.46.1.6.1.1.20";
        }

        leaf vtpVlansPruningEligible3k {
          type binary {
            length "0..128";
          }
          description
           "A string of octets containing one bit per VLAN for VLANS
            with VlanIndex values of 2048 through 3071 in the management
            domain on this trunk port.  The first octet corresponds to
            VLANs with VlanIndex values of 2048 through 2055; the second
            octet to VLANs 2056 through 2063; etc.  The most significant
            bit of each octet corresponds to the lowest value VlanIndex
            in that octet.
            
            If the bit corresponding to a VLAN is set to '1', then the
            local system is permitted to prune that VLAN on this trunk
            port; if the bit is set to '0', then the system must not
            prune that VLAN on this trunk port.
            The default value is zero length string.
            
            To avoid conflicts between overlapping partial updates by
            multiple managers, i.e., updates which modify only a portion
            of an instance of this object (e.g., enable/disable a single
            VLAN on the trunk port), any SNMP Set operation accessing an
            instance of this object should also write the value of
            vlanTrunkPortSetSerialNo.";
          smiv2:max-access "read-write";
          smiv2:oid "1.3.6.1.4.1.9.9.46.1.6.1.1.21";
        }

        leaf vtpVlansPruningEligible4k {
          type binary {
            length "0..128";
          }
          description
           "A string of octets containing one bit per VLAN for VLANS
            with VlanIndex values of 3072 through 4095 in the management
            domain on this trunk port.  The first octet corresponds to
            VLANs with VlanIndex values of 3072 through 3079; the second
            octet to VLANs 3080 through 3087; etc.  The most significant
            bit of each octet corresponds to the lowest value VlanIndex
            in that octet.
            
            If the bit corresponding to a VLAN is set to '1', then the
            local system is permitted to prune that VLAN on this trunk
            port; if the bit is set to '0', then the system must not
            prune that VLAN on this trunk port.
            The default value is zero length string.
            
            To avoid conflicts between overlapping partial updates by
            multiple managers, i.e., updates which modify only a portion
            of an instance of this object (e.g., enable/disable a single
            VLAN on the trunk port), any SNMP Set operation accessing an
            instance of this object should also write the value of
            vlanTrunkPortSetSerialNo.";
          smiv2:max-access "read-write";
          smiv2:oid "1.3.6.1.4.1.9.9.46.1.6.1.1.22";
        }

        leaf vlanTrunkPortVlansXmitJoined2k {
          type binary {
            length "0..128";
          }
          description
           "A string of octets containing one bit per VLAN for VLANS
            with VlanIndex values of 1024 through 2047 in the management
            domain on this trunk port.  The first octet corresponds to
            VLANs with VlanIndex values of 1024 through 1031; the second
            octet to VLANs 1032 through 1039; etc.  The most significant
            bit of each octet corresponds to the lowest value VlanIndex
            in that octet.
            
            If the bit corresponding to a VLAN is set to '1', then this
            VLAN is presently being forwarded on this trunk port, i.e.,
            it is not pruned; if the bit is set to '0', then this VLAN
            is presently not being forwarded on this trunk port, either
            because it is pruned or for some other reason.";
          smiv2:max-access "read-only";
          smiv2:oid "1.3.6.1.4.1.9.9.46.1.6.1.1.23";
        }

        leaf vlanTrunkPortVlansXmitJoined3k {
          type binary {
            length "0..128";
          }
          description
           "A string of octets containing one bit per VLAN for VLANS
            with VlanIndex values of 2048 through 3071 in the management
            domain on this trunk port.  The first octet corresponds to
            VLANs with VlanIndex values of 2048 through 2055; the second
            octet to VLANs 2056 through 2063; etc.  The most significant
            bit of each octet corresponds to the lowest value VlanIndex
            in that octet.
            
            If the bit corresponding to a VLAN is set to '1', then this
            VLAN is presently being forwarded on this trunk port, i.e.,
            it is not pruned; if the bit is set to '0', then this VLAN
            is presently not being forwarded on this trunk port, either
            because it is pruned or for some other reason.";
          smiv2:max-access "read-only";
          smiv2:oid "1.3.6.1.4.1.9.9.46.1.6.1.1.24";
        }

        leaf vlanTrunkPortVlansXmitJoined4k {
          type binary {
            length "0..128";
          }
          description
           "A string of octets containing one bit per VLAN for VLANS
            with VlanIndex values of 3072 through 4095 in the management
            domain on this trunk port.  The first octet corresponds to
            VLANs with VlanIndex values of 3072 through 3079; the second
            octet to VLANs 3080 through 3087; etc.  The most significant
            bit of each octet corresponds to the lowest value VlanIndex
            in that octet.
            
            If the bit corresponding to a VLAN is set to '1', then this
            VLAN is presently being forwarded on this trunk port, i.e.,
            it is not pruned; if the bit is set to '0', then this VLAN
            is presently not being forwarded on this trunk port, either
            because it is pruned or for some other reason.";
          smiv2:max-access "read-only";
          smiv2:oid "1.3.6.1.4.1.9.9.46.1.6.1.1.25";
        }

        leaf vlanTrunkPortVlansRcvJoined2k {
          type binary {
            length "0..128";
          }
          description
           "A string of octets containing one bit per VLAN for VLANS
            with VlanIndex values of 1024 through 2047 in the management
            domain on this trunk port.  The first octet corresponds to
            VLANs with VlanIndex values of 1024 through 1031; the second
            octet to VLANs 1032 through 1039; etc.  The most significant
            bit of each octet corresponds to the lowest value VlanIndex
            in that octet.
            
            If the bit corresponding to a VLAN is set to '1', then the
            local switch is currently sending joins for this VLAN on
            this trunk port, i.e., it is asking to receive frames for
            this VLAN; if the bit is set to '0', then the local switch
            is not currently sending joins for this VLAN on this trunk
            port.";
          smiv2:max-access "read-only";
          smiv2:oid "1.3.6.1.4.1.9.9.46.1.6.1.1.26";
        }

        leaf vlanTrunkPortVlansRcvJoined3k {
          type binary {
            length "0..128";
          }
          description
           "A string of octets containing one bit per VLAN for VLANS
            with VlanIndex values of 2048 through 3071 in the management
            domain on this trunk port.  The first octet corresponds to
            VLANs with VlanIndex values of 2048 through 2055; the second
            octet to VLANs 2056 through 2063; etc.  The most significant
            bit of each octet corresponds to the lowest value VlanIndex
            in that octet.
            
            If the bit corresponding to a VLAN is set to '1', then the
            local switch is currently sending joins for this VLAN on
            this trunk port, i.e., it is asking to receive frames for
            this VLAN; if the bit is set to '0', then the local switch
            is not currently sending joins for this VLAN on this trunk
            port.";
          smiv2:max-access "read-only";
          smiv2:oid "1.3.6.1.4.1.9.9.46.1.6.1.1.27";
        }

        leaf vlanTrunkPortVlansRcvJoined4k {
          type binary {
            length "0..128";
          }
          description
           "A string of octets containing one bit per VLAN for VLANS
            with VlanIndex values of 3072 through 4095 in the management
            domain on this trunk port.  The first octet corresponds to
            VLANs with VlanIndex values of 3072 through 3079; the second
            octet to VLANs 3080 through 3087; etc.  The most significant
            bit of each octet corresponds to the lowest value VlanIndex
            in that octet.
            
            If the bit corresponding to a VLAN is set to '1', then the
            local switch is currently sending joins for this VLAN on
            this trunk port, i.e., it is asking to receive frames for
            this VLAN; if the bit is set to '0', then the local switch
            is not currently sending joins for this VLAN on this trunk
            port.";
          smiv2:max-access "read-only";
          smiv2:oid "1.3.6.1.4.1.9.9.46.1.6.1.1.28";
        }

        leaf vlanTrunkPortDot1qTunnel {
          type enumeration {
            enum "trunk" {
              value "1";
            }
            enum "access" {
              value "2";
            }
            enum "disabled" {
              value "3";
            }
          }
          status deprecated;
          description
           "Indicates dot1qtunnel mode of the port.
            
            If the portDot1qTunnel  is set to 'trunk' mode, the port's
            vlanTrunkPortDynamicState will be changed to 'onNoNegotiate'
            and the vlanTrunkPortEncapsulationType will be set to
            'dot1Q'. These values cannot be changed unless dot1q tunnel
            is disabled on this port.
            
            If the portDot1qTunnel mode is set to 'access' mode, the
            port's vlanTrunkPortDynamicState will be set to 'off'.And
            the value of vlanTrunkPortDynamicState cannot be changed
            unless dot1q tunnel is disabled on this port. 1Q packets
            received on this access port will remain.
            
            Setting the port to dot1q tunnel 'disabled' mode causes the
            dot1q tunnel feature to be disabled on this port.  This
            object can't be set to 'trunk' or 'access' mode, when
            vlanTrunkPortsDot1qTag  object is set to 'false'.
            
            This object has been deprecated and is replaced by the
            object 'cltcDot1qTunnelMode' in the
            CISCO-L2-TUNNEL-CONFIG-MIB";
          smiv2:defval "disabled";
          smiv2:max-access "read-write";
          smiv2:oid "1.3.6.1.4.1.9.9.46.1.6.1.1.29";
        }

        leaf vlanTrunkPortVlansActiveFirst2k {
          type cisco-tc:Cisco2KVlanList;
          description
           "A string of octets containing one bit per VLAN
            with VlanIndex values of 0 through 2047.
            
            If the bit corresponding to a VLAN is set to 1,
            it indicates that vlan is allowed and active in
            management domain.
            
            If the bit corresponding to a VLAN is set to 0,
            it indicates that vlan is not allowed or not active
            in management domain.";
          smiv2:max-access "read-only";
          smiv2:oid "1.3.6.1.4.1.9.9.46.1.6.1.1.30";
        }

        leaf vlanTrunkPortVlansActiveSecond2k {
          type cisco-tc:Cisco2KVlanList;
          description
           "A string of octets containing one bit per VLAN
            with VlanIndex values of 2048 through 4095.
            
            If the bit corresponding to a VLAN is set to 1,
            it indicates that vlan is allowed and active in
            management domain.
            
            If the bit corresponding to a VLAN is set to 0,
            it indicates that vlan is not allowed or not active
            in management domain.";
          smiv2:max-access "read-only";
          smiv2:oid "1.3.6.1.4.1.9.9.46.1.6.1.1.31";
        }
      }
    }

    container vtpDiscoverTable {
      description
       "This table contains information related to the discovery
        of the VTP members in the designated management
        domain. This table is not instantiated when 
        managementDomainVersionInUse is version1(1), version2(3)
        or none(3).";
      smiv2:oid "1.3.6.1.4.1.9.9.46.1.7.1";

      list vtpDiscoverEntry {
        key "managementDomainIndex";
        description
         "Information related to the discovery of the
          VTP members in one management domain.";
        smiv2:oid "1.3.6.1.4.1.9.9.46.1.7.1.1";

        leaf managementDomainIndex {
          type leafref {
            path "/CISCO-VTP-MIB:CISCO-VTP-MIB/CISCO-VTP-MIB:managementDomainTable/CISCO-VTP-MIB:managementDomainEntry/CISCO-VTP-MIB:managementDomainIndex";
          }
        }

        leaf vtpDiscoverAction {
          type enumeration {
            enum "discover" {
              value "1";
            }
            enum "noOperation" {
              value "2";
            }
            enum "purgeResult" {
              value "3";
            }
          }
          description
           "When this object is set to discover(1), all the
            entries in vtpDiscoverResultTable for the
            corresponding management domain will be removed 
            and the local device will begin to discover all
            VTP members in the management domain. Upon the
            successful completion of discovery, the discovered
            result will be stored in the vtpDiscoverResultTable.
            
            If vtpDiscoverStatus is inProgress(1), setting 
            vtpDiscoverAction to discover(1) will fail. 
            
            When this object is set to purgeResult(3), 
            all the entries of vtpDiscoverResultTable for 
            the corresponding management domain will be
            removed from vtpDiscoverResultTable.
            
            When this object is set to noOperation(2), no
            action will be taken. When read, this object
            always returns noOperation(2).";
          smiv2:max-access "read-write";
          smiv2:oid "1.3.6.1.4.1.9.9.46.1.7.1.1.1";
        }

        leaf vtpDiscoverStatus {
          type enumeration {
            enum "inProgress" {
              value "1";
            }
            enum "succeeded" {
              value "2";
            }
            enum "resourceUnavailable" {
              value "3";
            }
            enum "someOtherError" {
              value "4";
            }
          }
          description
           "The current status of VTP discovery.
            
            inProgress - a discovery is in progress;
            
            succeeded - the discovery was completed successfully
                        (this value is also used when 
                        no discover has been invoked since the
                        last time the local system restarted);
            
            resourceUnavailable - the discovery failed because
                        the required allocation of a resource is
                        presently unavailable.
            
            someOtherError - 'the discovery failed due to a
                        reason no listed.";
          smiv2:max-access "read-only";
          smiv2:oid "1.3.6.1.4.1.9.9.46.1.7.1.1.2";
        }

        leaf vtpLastDiscoverTime {
          type yang:timestamp;
          description
           "The value of sysUpTime at which the last discovery
            was completed.
            
            A value of zero indicates that no discovery has been
            invoked since last time the local system restarted.";
          smiv2:max-access "read-only";
          smiv2:oid "1.3.6.1.4.1.9.9.46.1.7.1.1.3";
        }
      }
    }

    container vtpDiscoverResultTable {
      description
       "The table containing information of discovered VTP members
        in the management domain in which the local system is
        participating. This table is not instantiated when 
        managementDomainVersionInUse is version1(1), version2(2) or
        none(3).";
      smiv2:oid "1.3.6.1.4.1.9.9.46.1.7.2";

      list vtpDiscoverResultEntry {
        key "managementDomainIndex vtpDiscoverResultIndex";
        description
         "A conceptual row is created for each VTP member which
          is found through successful discovery.";
        smiv2:oid "1.3.6.1.4.1.9.9.46.1.7.2.1";

        leaf managementDomainIndex {
          type leafref {
            path "/CISCO-VTP-MIB:CISCO-VTP-MIB/CISCO-VTP-MIB:managementDomainTable/CISCO-VTP-MIB:managementDomainEntry/CISCO-VTP-MIB:managementDomainIndex";
          }
        }

        leaf vtpDiscoverResultIndex {
          type uint32;
          description
           "A value assigned by the system which identifies
            a VTP member and the associated database in the 
            management domain.";
          smiv2:max-access "read-only";
          smiv2:oid "1.3.6.1.4.1.9.9.46.1.7.2.1.1";
        }

        leaf vtpDiscoverResultDatabaseName {
          type snmp-framework:SnmpAdminString {
            length "0..64";
          }
          description
           "The database name associated with the
            discovered VTP member.";
          smiv2:max-access "read-only";
          smiv2:oid "1.3.6.1.4.1.9.9.46.1.7.2.1.2";
        }

        leaf vtpDiscoverResultConflicting {
          type boolean;
          description
           "Indicates whether this VTP member contains
            conflicting information.
            
            true(1) indicates that this member has conflicting 
            information of the database type in the management domain.
            
            false(2) indicates that there is no conflicting information
            of the database type in the management domain.";
          smiv2:max-access "read-only";
          smiv2:oid "1.3.6.1.4.1.9.9.46.1.7.2.1.3";
        }

        leaf vtpDiscoverResultDeviceId {
          type snmp-framework:SnmpAdminString {
            length "0..64";
          }
          description
           "The unique identifier of the device for this VTP member.";
          smiv2:max-access "read-only";
          smiv2:oid "1.3.6.1.4.1.9.9.46.1.7.2.1.4";
        }

        leaf vtpDiscoverResultPrimaryServer {
          type snmp-framework:SnmpAdminString {
            length "0..64";
          }
          description
           "The unique identifier of the primary server for this VTP
            member and the associated database type.
            
            There are two different VTP servers, the primary server
            and the secondary server.  When a local device is
            configured as a server for a certain database type,
            it becomes secondary server by default. 
            Primary server is an operational role under which a
            server can initiate or change the VTP configuration of the
            database type.
            
            If this VTP member itself is the primary server, the   
            value of this object is the same as the value of 
            vtpDiscoverResultDeviceId of the instance.";
          smiv2:max-access "read-only";
          smiv2:oid "1.3.6.1.4.1.9.9.46.1.7.2.1.5";
        }

        leaf vtpDiscoverResultRevNumber {
          type yang:gauge32;
          description
           "The current configuration revision number as known by the
            VTP member. When the database type is unknown for
            the VTP member, this value is 0.";
          smiv2:max-access "read-only";
          smiv2:oid "1.3.6.1.4.1.9.9.46.1.7.2.1.6";
        }

        leaf vtpDiscoverResultSystemName {
          type snmp-framework:SnmpAdminString {
            length "0..64";
          }
          description
           "sysName of the VTP member.";
          smiv2:max-access "read-only";
          smiv2:oid "1.3.6.1.4.1.9.9.46.1.7.2.1.7";
        }
      }
    }

    container vtpDatabaseTable {
      description
       "This table contains information of the VTP
        databases. It is not instantiated when
        managementDomainVersionInUse is version1(1), 
        version2(3) or none(3).";
      smiv2:oid "1.3.6.1.4.1.9.9.46.1.8.1";

      list vtpDatabaseEntry {
        key "managementDomainIndex vtpDatabaseIndex";
        description
         "Information about the status of the VTP database
          in the domain.  Each VTP database type known to the
          local device type has an entry in this table.
          An entry is also created for unknown database which is
          notified through VTP advertisements from other VTP
          servers.";
        smiv2:oid "1.3.6.1.4.1.9.9.46.1.8.1.1";

        leaf managementDomainIndex {
          type leafref {
            path "/CISCO-VTP-MIB:CISCO-VTP-MIB/CISCO-VTP-MIB:managementDomainTable/CISCO-VTP-MIB:managementDomainEntry/CISCO-VTP-MIB:managementDomainIndex";
          }
        }

        leaf vtpDatabaseIndex {
          type uint32;
          description
           "A value assigned by the system which uniquely identifies
            a VTP database in the local system.";
          smiv2:max-access "not-accessible";
          smiv2:oid "1.3.6.1.4.1.9.9.46.1.8.1.1.1";
        }

        leaf vtpDatabaseName {
          type snmp-framework:SnmpAdminString {
            length "0..64";
          }
          description
           "The name of the database.";
          smiv2:max-access "read-only";
          smiv2:oid "1.3.6.1.4.1.9.9.46.1.8.1.1.2";
        }

        leaf vtpDatabaseLocalMode {
          type enumeration {
            enum "client" {
              value "1";
            }
            enum "server" {
              value "2";
            }
            enum "transparent" {
              value "3";
            }
            enum "off" {
              value "4";
            }
          }
          description
           "The local VTP mode for a particular database type
            in this administrative domain.
            
            - 'client' indicates that the local system is acting
              as a VTP client of the database type.
            
            - 'server' indicates that the local system is acting
              as a VTP server of the database type.
            
            - 'transparent' indicates that the local system does
              not generate or listen to VTP messages of this 
              database type, but forwards
              messages. This mode can also be set by the device
              itself when the size of database is too large for it
              to hold in DRAM.
            
            - 'off' indicates that the local system does not
              generate, listen to or forward any VTP messages
              of this database type.
            
            The default mode is 'client' for the database type 
            known to the local device and 'transparent' for the
            unknown database type.";
          smiv2:max-access "read-write";
          smiv2:oid "1.3.6.1.4.1.9.9.46.1.8.1.1.3";
        }

        leaf vtpDatabaseRevNumber {
          type yang:gauge32;
          description
           "The current configuration revision number as known by the
            local device for this VTP 3 database type in the management
            domain.  This value is updated (if necessary) whenever a 
            VTP advertisement for the database type is received 
            or generated. When the database type is unknown to the 
            local device or no VTP advertisement for the database
            type is received or generated, its value is 0.";
          smiv2:max-access "read-only";
          smiv2:oid "1.3.6.1.4.1.9.9.46.1.8.1.1.4";
        }

        leaf vtpDatabasePrimaryServer {
          type boolean;
          description
           "There are two kinds of VTP version 3 servers for a certain
            database type - the primary server and the secondary server.
            When a local device is configured as a server for a certain
            database type, it becomes secondary server by default.
            Primary server is an operational role under which a
            server can initiate or change the VTP configuration of the
            database type.
            
            A true(1) value indicates that the local device is the 
            primary server of the database type in the management
            domain. A false(2) value indicates that the local device
            is not the primary server, or the database type is unknown
            to the local device.";
          smiv2:max-access "read-only";
          smiv2:oid "1.3.6.1.4.1.9.9.46.1.8.1.1.5";
        }

        leaf vtpDatabasePrimaryServerId {
          type snmp-framework:SnmpAdminString {
            length "0..64";
          }
          description
           "The unique identifier of the primary server in the
            management domain for the database type. 
            
            If no primary server is discovered for the database
            type, the object has a value of zero length string.";
          smiv2:max-access "read-only";
          smiv2:oid "1.3.6.1.4.1.9.9.46.1.8.1.1.6";
        }

        leaf vtpDatabaseTakeOverPrimary {
          type boolean;
          description
           "There are two kinds of VTP version 3 servers for a certain
            database type - the primary server and the secondary server.
            When a local device is configured as a server for a certain
            database type, it becomes secondary server by default.
            Primary server is an operational role under which a
            server can initiate or change the VTP configuration of the
            database type.
            
            Setting this object to a true(1) value will advertise the
            configuration of this database type to the whole domain.
            
            In order to successfully setting this object to true(1),
            the value of vtpDatabaseLocalMode must be server(2). Besides
            that, when the VTP password is hidden from the configuration
            file, the password (vtpDatabaseTakeOverPassword) which 
            matches  the secret key (vtpAuthSecretKey) must be provided
            in the same data packet. 
            
            When read, the object always returns false(2).";
          smiv2:max-access "read-write";
          smiv2:oid "1.3.6.1.4.1.9.9.46.1.8.1.1.7";
        }

        leaf vtpDatabaseTakeOverPassword {
          type snmp-framework:SnmpAdminString {
            length "0..64";
          }
          description
           "When read, this object always returns the value of a
            zero-length octet string.
            
            In the case that the VTP password is hidden from the 
            configuration and the local device intends
            to take over the whole domain, this object must be 
            set to the matching password with the secret key 
            (vtpAuthSecretKey) in the same data packet as which 
            the vtpDatabaseTakeOverPrimary is in. In all the 
            other situations, setting a valid value to this object 
            has no impact on the system.";
          smiv2:max-access "read-write";
          smiv2:oid "1.3.6.1.4.1.9.9.46.1.8.1.1.8";
        }
      }
    }

    container vtpAuthenticationTable {
      description
       "The table contains the authentication information of VTP
        in which the local system participates.
        
        The security mechanism of VTP relies on a secret key
        that is used to alter the MD5 digest of the packets
        transmitted on the wire.  The secret value is
        created from a password that may be saved in plain text
        in the configuration or hidden from the configuration.
        
        The device creating or modifying the VTP configuration
        signs it using the MD5 digest generated from the secret
        key before advertising it. Other devices in the domain
        receive this configuration use the same secret key
        to accept it if correctly signed or drop it otherwise.
        
        The user has the option to hide the password from the
        configuration. Once the password is hidden, the secret
        key generated from the password is shown in the 
        configuration instead, and there is no other way to 
        show the password in plain text again but clearing 
        it or resetting it. 
        
        In an un-trusted area, the password on a device can 
        be configured without being unveiled. After that,
        it has to be provided again by setting the same 
        value to vtpDatabaseTakeOverPassword if the user 
        wants to take over the whole VTP management domain
        of the database type.
        
        When managementDomainVersionInUse is version3(4), the 
        authentication mechanism is common to all VTP
        database type.";
      smiv2:oid "1.3.6.1.4.1.9.9.46.1.9.1";

      list vtpAuthEntry {
        key "managementDomainIndex";
        description
         "Information about the status of the VTP
          authentication information in one domain.";
        smiv2:oid "1.3.6.1.4.1.9.9.46.1.9.1.1";

        leaf managementDomainIndex {
          type leafref {
            path "/CISCO-VTP-MIB:CISCO-VTP-MIB/CISCO-VTP-MIB:managementDomainTable/CISCO-VTP-MIB:managementDomainEntry/CISCO-VTP-MIB:managementDomainIndex";
          }
        }

        leaf vtpAuthPassword {
          type snmp-framework:SnmpAdminString {
            length "0..64";
          }
          description
           "By default, this object has a value of a zero-length
            character string and is considered to be not
            configured.
            
            The device uses the password to generate the 
            secret key. It can be stored in the configuration in 
            plain text or hidden from the configuration. If a VTP 
            server intends to modify the database's configuration
            in the domain but the password was hidden from the
            configuration, the same password
            (vtpDatabaseTakeOverPassword) as the hidden one
            has to be provided.
            
            When this object is set alone, vtpAuthPasswordType is
            set to plaintext(1) automatically by the system.
            Setting this object to a zero length character string
            resets the password to its default value and the
            password is considered as not configured.
            
            This object is not allowed to be set at the same time
            when  vtpAuthSecretKey is set.
            
            When the vtpAuthPasswordType is hidden(2), this object 
            will return a zero-length character string when read.";
          smiv2:max-access "read-write";
          smiv2:oid "1.3.6.1.4.1.9.9.46.1.9.1.1.1";
        }

        leaf vtpAuthPasswordType {
          type enumeration {
            enum "plaintext" {
              value "1";
            }
            enum "hidden" {
              value "2";
            }
          }
          description
           "By default this object has the value as plaintext(1)
            and the VTP password is stored in the configuration
            file in plain text.
            
            Setting this object to hidden(2) will hide the
            password from the configuration.
            
            Once this object is set to hidden(2), it cannot
            be set to plaintext(1) alone. However, it may
            be set to plaintext(1) at the same time the
            password is set.";
          smiv2:max-access "read-write";
          smiv2:oid "1.3.6.1.4.1.9.9.46.1.9.1.1.2";
        }

        leaf vtpAuthSecretKey {
          type binary {
            length "0|16";
          }
          description
           "The device creating or modifying the VTP configuration
            signs it using the MD5 digest generated from the secret
            key before advertising it. Other devices in the domain
            receiving this configuration use the same secret key
            to accept it if it was correctly signed or drop it 
            otherwise.
            
            By default, the object has the value as a zero-length
            string and this value is read only. It is set 
            to this value automatically when the password 
            (vtpAuthPassword) is set to a zero-length octet string.
            
            The secret key can be either generated using
            the password or configured by the user. Once
            the secret key is configured by the user, it is
            stored as a hexadecimal string in the device's
            configuration and the password is considered to be
            the secret key's matching password and hidden
            from the configuration automatically.
            
            This object is not allowed to be set at the same
            time when vtpAuthPassword is set.
            
            The secret key is overwritten by a newly generated
            secret key when the password is re-configured.";
          smiv2:max-access "read-write";
          smiv2:oid "1.3.6.1.4.1.9.9.46.1.9.1.1.3";
        }
      }
    }
  }

  smiv2:alias "vtpEditControlTable" {
    description
     "This table provides the means to control the editing of the
      VLANs for a particular management domain.  Each and every
      entry in this table augments its corresponding entry in the
      managementDomainTable; thus, an entry in this table is
      created/deleted only as a by-product of creating/deleting an
      entry in the managementDomainTable.";
    smiv2:oid "1.3.6.1.4.1.9.9.46.1.4.1";
  }

  smiv2:alias "vtpEditControlEntry" {
    description
     "Control information for editing the VLANs in one management
      domain.";
    smiv2:oid "1.3.6.1.4.1.9.9.46.1.4.1.1";
  }

  augment "/CISCO-VTP-MIB:CISCO-VTP-MIB/CISCO-VTP-MIB:managementDomainTable/CISCO-VTP-MIB:managementDomainEntry" {
    description
     "Control information for editing the VLANs in one management
      domain.";
    smiv2:oid "1.3.6.1.4.1.9.9.46.1.4.1.1";

    leaf vtpVlanEditOperation {
      type enumeration {
        enum "none" {
          value "1";
        }
        enum "copy" {
          value "2";
        }
        enum "apply" {
          value "3";
        }
        enum "release" {
          value "4";
        }
        enum "restartTimer" {
          value "5";
        }
      }
      description
       "This object always has the value 'none' when read.  When
        written, each value causes the appropriate action:
        
         'copy' - causes the creation of rows in the
        vtpVlanEditTable exactly corresponding to the current global
        VLAN information for this management domain.  If the Edit
        Buffer (for this management domain) is not currently empty,
        a copy operation fails.  A successful copy operation starts
        the deadman-timer.
        
         'apply' - first performs a consistent check on the the
        modified information contained in the Edit Buffer, and if
        consistent, then tries to instanciate the modified
        information as the new global VLAN information.  Note that
        an empty Edit Buffer (for the management domain) would
        always result in an inconsistency since the default VLANs
        are required to be present.
        
         'release' - flushes the Edit Buffer (for this management
        domain), clears the Owner information, and aborts the
        deadman-timer.  A release is generated automatically if the
        deadman-timer ever expires.
        
         'restartTimer' - restarts the deadman-timer.
        
         'none' - no operation is performed.";
      smiv2:max-access "read-write";
      smiv2:oid "1.3.6.1.4.1.9.9.46.1.4.1.1.1";
    }

    leaf vtpVlanApplyStatus {
      type enumeration {
        enum "inProgress" {
          value "1";
        }
        enum "succeeded" {
          value "2";
        }
        enum "configNumberError" {
          value "3";
        }
        enum "inconsistentEdit" {
          value "4";
        }
        enum "tooBig" {
          value "5";
        }
        enum "localNVStoreFail" {
          value "6";
        }
        enum "remoteNVStoreFail" {
          value "7";
        }
        enum "editBufferEmpty" {
          value "8";
        }
        enum "someOtherError" {
          value "9";
        }
        enum "notPrimaryServer" {
          value "10";
        }
      }
      description
       "The current status of an 'apply' operation to instanciate
        the Edit Buffer as the new global VLAN information (for this
        management domain).  If no apply is currently active, the
        status represented is that of the most recently completed
        apply.  The possible values are:
        
           inProgress - 'apply' operation in progress;
        
           succeeded - the 'apply' was successful (this value is
                  also used when no apply has been invoked since the
                  last time the local system restarted);
        
           configNumberError - the apply failed because the value of
                  vtpVlanEditConfigRevNumber was less or equal to
                  the value of current value of 
                  managementDomainConfigRevNumber;
        
           inconsistentEdit - the apply failed because the modified
                  information was not self-consistent;
        
           tooBig - the apply failed because the modified
                  information was too large to fit in this VTP
                  Server's non-volatile storage location;
        
           localNVStoreFail - the apply failed in trying to store
                  the new information in a local non-volatile
                  storage location;
        
           remoteNVStoreFail - the apply failed in trying to store
                  the new information in a remote non-volatile
                  storage location;
        
           editBufferEmpty - the apply failed because the Edit
                  Buffer was empty (for this management domain).
        
           someOtherError - the apply failed for some other reason
                  (e.g., insufficient memory).
        
           notPrimaryServer - the apply failed because the local 
                  device is not a VTP primary server for VLAN 
                  database type when managementDomainVersionInUse
                  is version3(4).";
      smiv2:max-access "read-only";
      smiv2:oid "1.3.6.1.4.1.9.9.46.1.4.1.1.2";
    }

    leaf vtpVlanEditBufferOwner {
      type rmon-mib:OwnerString;
      description
       "The management station which is currently using the Edit
        Buffer for this management domain.  When the Edit Buffer for
        a management domain is not currently in use, the value of
        this object is the zero-length string.  Note that it is also
        the zero-length string if a manager fails to set this object
        when invoking a copy operation.";
      smiv2:max-access "read-write";
      smiv2:oid "1.3.6.1.4.1.9.9.46.1.4.1.1.3";
    }

    leaf vtpVlanEditConfigRevNumber {
      type yang:gauge32;
      description
       "The Configuration Revision Number to be used for the next
        apply operation.  This value is initialized (by the agent)
        on a copy operation to be one greater than the value of
        managementDomainConfigRevNumber. On an apply, if the 
        number is less or equal to the value of 
        managementDomainConfigRevNumber, then the apply fails.
        The value can be modified (increased) by network management
        before an apply to ensure that an apply does not fail for 
        this reason.
        
        This object is used to allow management control over whether
        a configuration revision received via a VTP advertisement
        after a copy operation but before the succeeding apply
        operation is lost by being overwritten by the (local) edit
        operation.  By default, the apply operation will fail in
        this situation.  By increasing this object's value after the
        copy but before the apply, management can control whether
        the apply is to succeed (with the update via VTP
        advertisement being lost).";
      smiv2:max-access "read-write";
      smiv2:oid "1.3.6.1.4.1.9.9.46.1.4.1.1.4";
    }

    leaf vtpVlanEditModifiedVlan {
      type CISCO-VTP-MIB:VlanIndex;
      description
       "The VLAN-id of the modified VLAN in the Edit Buffer.
        If the object has the value of zero, any VLAN can 
        be edited. If the value of the object is not zero,
        only this VLAN can be edited.
        
        The object's value is reset to zero after a successful
        'apply' operation or a 'release' operation. 
        
        This object is only supported for devices which allow 
        only one VLAN editing for each 'apply' operation. For
        devices which allow multiple VLAN editing for each
        'apply' operation, this object is not supported.";
      smiv2:max-access "read-only";
      smiv2:oid "1.3.6.1.4.1.9.9.46.1.4.1.1.5";
    }
  }

  smiv2:alias "vtpStatsTable" {
    description
     "A table of VTP statistics.";
    smiv2:oid "1.3.6.1.4.1.9.9.46.1.5.1";
  }

  smiv2:alias "vtpStatsEntry" {
    description
     "VTP statistics for one management domain.";
    smiv2:oid "1.3.6.1.4.1.9.9.46.1.5.1.1";
  }

  augment "/CISCO-VTP-MIB:CISCO-VTP-MIB/CISCO-VTP-MIB:managementDomainTable/CISCO-VTP-MIB:managementDomainEntry" {
    description
     "VTP statistics for one management domain.";
    smiv2:oid "1.3.6.1.4.1.9.9.46.1.5.1.1";

    leaf vtpInSummaryAdverts {
      type yang:counter32;
      description
       "The total number of VTP Summary Adverts received for this
        management domain.";
      smiv2:max-access "read-only";
      smiv2:oid "1.3.6.1.4.1.9.9.46.1.5.1.1.1";
    }

    leaf vtpInSubsetAdverts {
      type yang:counter32;
      description
       "The total number of VTP Subset Adverts received for this
        management domain.";
      smiv2:max-access "read-only";
      smiv2:oid "1.3.6.1.4.1.9.9.46.1.5.1.1.2";
    }

    leaf vtpInAdvertRequests {
      type yang:counter32;
      description
       "The total number of VTP Advert Requests received for this
        management domain.";
      smiv2:max-access "read-only";
      smiv2:oid "1.3.6.1.4.1.9.9.46.1.5.1.1.3";
    }

    leaf vtpOutSummaryAdverts {
      type yang:counter32;
      description
       "The total number of VTP Summary Adverts sent for this
        management domain.";
      smiv2:max-access "read-only";
      smiv2:oid "1.3.6.1.4.1.9.9.46.1.5.1.1.4";
    }

    leaf vtpOutSubsetAdverts {
      type yang:counter32;
      description
       "The total number of VTP Subset Adverts sent for this
        management domain.";
      smiv2:max-access "read-only";
      smiv2:oid "1.3.6.1.4.1.9.9.46.1.5.1.1.5";
    }

    leaf vtpOutAdvertRequests {
      type yang:counter32;
      description
       "The total number of VTP Advert Requests sent for this
        management domain.";
      smiv2:max-access "read-only";
      smiv2:oid "1.3.6.1.4.1.9.9.46.1.5.1.1.6";
    }

    leaf vtpConfigRevNumberErrors {
      type yang:counter32;
      description
       "The number of occurrences of configuration revision number
        errors for this management domain.  A configuration revision
        number error occurs when a device receives a VTP
        advertisement for which:
        
        - the advertisement's Configuration Revision Number is the
          same as the current locally-held value, and
        
        - the advertisement's digest value is different from the
          current locally-held value.";
      smiv2:max-access "read-only";
      smiv2:oid "1.3.6.1.4.1.9.9.46.1.5.1.1.7";
    }

    leaf vtpConfigDigestErrors {
      type yang:counter32;
      description
       "The number of occurrences of configuration digest errors
        for this management domain.  A configuration digest error
        occurs when a device receives a VTP advertisement for which:
        
        - the advertisement's Configuration Revision Number is
          greater than the current locally-held value, and
        
        -  the advertisement's digest value computed by the
         receiving device does not match the checksum in the
         summary advertisement that was received earlier. This
         can happen, for example, if there is a mismatch in VTP
         passwords between the VTP devices.";
      smiv2:max-access "read-only";
      smiv2:oid "1.3.6.1.4.1.9.9.46.1.5.1.1.8";
    }
  }

  notification vtpConfigRevNumberError {
    description
     "A configuration revision number error notification
      signifies that a device has incremented its
      vtpConfigRevNumberErrors counter.
      
      Generation of this notification is suppressed if the
      vtpNotificationsEnabled has the value 'false'.
      
      The device must throttle the generation of consecutive
      vtpConfigRevNumberError notifications so that there is at
      least a five-second gap between notification of this type.
      When notification are throttled, they are dropped, not
      queued for sending at a future time.  (Note that
      'generating' a notification means sending to all configured
      recipients.)";
    smiv2:oid "1.3.6.1.4.1.9.9.46.2.0.1";

    container object-1 {

      leaf managementDomainIndex {
        type leafref {
          path "/CISCO-VTP-MIB:CISCO-VTP-MIB/CISCO-VTP-MIB:managementDomainTable/CISCO-VTP-MIB:managementDomainEntry/CISCO-VTP-MIB:managementDomainIndex";
        }
      }

      leaf managementDomainConfigRevNumber {
        type leafref {
          path "/CISCO-VTP-MIB:CISCO-VTP-MIB/CISCO-VTP-MIB:managementDomainTable/CISCO-VTP-MIB:managementDomainEntry/CISCO-VTP-MIB:managementDomainConfigRevNumber";
        }
      }
    }
  }

  notification vtpConfigDigestError {
    description
     "A configuration digest error notification signifies that a
      device has incremented its vtpConfigDigestErrors counter.
      
      Generation of this notification is suppressed if the
      vtpNotificationsEnabled has the value 'false'.
      
      The device must throttle the generation of consecutive
      vtpConfigDigestError notifications so that there is at least
      a five-second gap between notification of this type.  When
      notification are throttled, they are dropped, not queued for
      sending at a future time.  (Note that 'generating' a
      notification means sending to all configured recipients.)";
    smiv2:oid "1.3.6.1.4.1.9.9.46.2.0.2";

    container object-1 {

      leaf managementDomainIndex {
        type leafref {
          path "/CISCO-VTP-MIB:CISCO-VTP-MIB/CISCO-VTP-MIB:managementDomainTable/CISCO-VTP-MIB:managementDomainEntry/CISCO-VTP-MIB:managementDomainIndex";
        }
      }

      leaf managementDomainConfigRevNumber {
        type leafref {
          path "/CISCO-VTP-MIB:CISCO-VTP-MIB/CISCO-VTP-MIB:managementDomainTable/CISCO-VTP-MIB:managementDomainEntry/CISCO-VTP-MIB:managementDomainConfigRevNumber";
        }
      }
    }
  }

  notification vtpServerDisabled {
    description
     "A VTP Server disabled notification is generated when the
      local system is no longer able to function as a VTP Server
      because the number of defined VLANs is greater than
      vtpMaxVlanStorage or the local system is not able to
      recover complete VTP information after a reboot.
      
      Generation of this notification is suppressed if the
      vtpNotificationsEnabled has the value 'false'.";
    smiv2:oid "1.3.6.1.4.1.9.9.46.2.0.3";

    container object-1 {

      leaf managementDomainIndex {
        type leafref {
          path "/CISCO-VTP-MIB:CISCO-VTP-MIB/CISCO-VTP-MIB:managementDomainTable/CISCO-VTP-MIB:managementDomainEntry/CISCO-VTP-MIB:managementDomainIndex";
        }
      }

      leaf managementDomainConfigRevNumber {
        type leafref {
          path "/CISCO-VTP-MIB:CISCO-VTP-MIB/CISCO-VTP-MIB:managementDomainTable/CISCO-VTP-MIB:managementDomainEntry/CISCO-VTP-MIB:managementDomainConfigRevNumber";
        }
      }
    }

    container object-2 {

      leaf vtpMaxVlanStorage {
        type leafref {
          path "/CISCO-VTP-MIB:CISCO-VTP-MIB/CISCO-VTP-MIB:vtpStatus/CISCO-VTP-MIB:vtpMaxVlanStorage";
        }
      }
    }
  }

  notification vtpMtuTooBig {
    description
     "A VTP MTU tooBig notification is generated when a VLAN's
      MTU size is larger than can be supported either:
      
      - by one or more of its trunk ports:
        the included vtpVlanState has the value
        'mtuTooBigForTrunk' and the included
        vlanTrunkPortManagementDomain is for the first (or only)
        trunk port,
        or
      
      - by the device itself:
        vtpVlanState has the value 'mtuTooBigForDevice' and any
        instance of vlanTrunkPortManagementDomain is included.
      
      Devices which have no trunk ports do not send vtpMtuTooBig
      notifications.
      
      Generation of this notification is suppressed if the
      vtpNotificationsEnabled has the value 'false'.";
    smiv2:oid "1.3.6.1.4.1.9.9.46.2.0.4";

    container object-1 {

      leaf vlanTrunkPortIfIndex {
        type leafref {
          path "/CISCO-VTP-MIB:CISCO-VTP-MIB/CISCO-VTP-MIB:vlanTrunkPortTable/CISCO-VTP-MIB:vlanTrunkPortEntry/CISCO-VTP-MIB:vlanTrunkPortIfIndex";
        }
      }

      leaf vlanTrunkPortManagementDomain {
        type leafref {
          path "/CISCO-VTP-MIB:CISCO-VTP-MIB/CISCO-VTP-MIB:vlanTrunkPortTable/CISCO-VTP-MIB:vlanTrunkPortEntry/CISCO-VTP-MIB:vlanTrunkPortManagementDomain";
        }
      }
    }

    container object-2 {

      leaf managementDomainIndex {
        type leafref {
          path "/CISCO-VTP-MIB:CISCO-VTP-MIB/CISCO-VTP-MIB:managementDomainTable/CISCO-VTP-MIB:managementDomainEntry/CISCO-VTP-MIB:managementDomainIndex";
        }
      }

      leaf vtpVlanIndex {
        type leafref {
          path "/CISCO-VTP-MIB:CISCO-VTP-MIB/CISCO-VTP-MIB:vtpVlanTable/CISCO-VTP-MIB:vtpVlanEntry/CISCO-VTP-MIB:vtpVlanIndex";
        }
      }

      leaf vtpVlanState {
        type leafref {
          path "/CISCO-VTP-MIB:CISCO-VTP-MIB/CISCO-VTP-MIB:vtpVlanTable/CISCO-VTP-MIB:vtpVlanEntry/CISCO-VTP-MIB:vtpVlanState";
        }
      }
    }
  }

  notification vtpVersionOneDeviceDetected {
    description
     "A VTP version one device detected notification is
      generated by a device when:
      
      a) a management domain has been put into version 2 mode
         (as accessed by managementDomainVersionInUse).
      b) 15 minutes has passed since a).
      c) a version 1 PDU is detected on a trunk on the device
         that is in that management domain which has a lower
         revision number than the current configuration.";
    smiv2:oid "1.3.6.1.4.1.9.9.46.2.0.6";

    container object-1 {

      leaf vlanTrunkPortIfIndex {
        type leafref {
          path "/CISCO-VTP-MIB:CISCO-VTP-MIB/CISCO-VTP-MIB:vlanTrunkPortTable/CISCO-VTP-MIB:vlanTrunkPortEntry/CISCO-VTP-MIB:vlanTrunkPortIfIndex";
        }
      }

      leaf vlanTrunkPortManagementDomain {
        type leafref {
          path "/CISCO-VTP-MIB:CISCO-VTP-MIB/CISCO-VTP-MIB:vlanTrunkPortTable/CISCO-VTP-MIB:vlanTrunkPortEntry/CISCO-VTP-MIB:vlanTrunkPortManagementDomain";
        }
      }
    }
  }

  notification vlanTrunkPortDynamicStatusChange {
    description
     "A vlanTrunkPortDynamicStatusChange notification is
      generated by a device when the value of
      vlanTrunkPortDynamicStatus object has been changed.";
    smiv2:oid "1.3.6.1.4.1.9.9.46.2.0.7";

    container object-1 {

      leaf vlanTrunkPortIfIndex {
        type leafref {
          path "/CISCO-VTP-MIB:CISCO-VTP-MIB/CISCO-VTP-MIB:vlanTrunkPortTable/CISCO-VTP-MIB:vlanTrunkPortEntry/CISCO-VTP-MIB:vlanTrunkPortIfIndex";
        }
      }

      leaf vlanTrunkPortDynamicStatus {
        type leafref {
          path "/CISCO-VTP-MIB:CISCO-VTP-MIB/CISCO-VTP-MIB:vlanTrunkPortTable/CISCO-VTP-MIB:vlanTrunkPortEntry/CISCO-VTP-MIB:vlanTrunkPortDynamicStatus";
        }
      }
    }
  }

  notification vtpLocalModeChanged {
    description
     "A vtpLocalModeChanged notification is generated
      by a device when the value of the object 
      managementDomainLocalMode is changed.";
    smiv2:oid "1.3.6.1.4.1.9.9.46.2.0.8";

    container object-1 {

      leaf managementDomainIndex {
        type leafref {
          path "/CISCO-VTP-MIB:CISCO-VTP-MIB/CISCO-VTP-MIB:managementDomainTable/CISCO-VTP-MIB:managementDomainEntry/CISCO-VTP-MIB:managementDomainIndex";
        }
      }

      leaf managementDomainLocalMode {
        type leafref {
          path "/CISCO-VTP-MIB:CISCO-VTP-MIB/CISCO-VTP-MIB:managementDomainTable/CISCO-VTP-MIB:managementDomainEntry/CISCO-VTP-MIB:managementDomainLocalMode";
        }
      }
    }
  }

  notification vtpVersionInUseChanged {
    description
     "A vtpVersionInUseChanged notification is
      generated by a device when the value of the  
      object managementDomainVersionInUse is 
      changed.";
    smiv2:oid "1.3.6.1.4.1.9.9.46.2.0.9";

    container object-1 {

      leaf managementDomainIndex {
        type leafref {
          path "/CISCO-VTP-MIB:CISCO-VTP-MIB/CISCO-VTP-MIB:managementDomainTable/CISCO-VTP-MIB:managementDomainEntry/CISCO-VTP-MIB:managementDomainIndex";
        }
      }

      leaf managementDomainVersionInUse {
        type leafref {
          path "/CISCO-VTP-MIB:CISCO-VTP-MIB/CISCO-VTP-MIB:managementDomainTable/CISCO-VTP-MIB:managementDomainEntry/CISCO-VTP-MIB:managementDomainVersionInUse";
        }
      }
    }
  }

  notification vtpVlanCreated {
    description
     "A vtpVlanCreated notification is generated by a
      device when a VLAN is created.";
    smiv2:oid "1.3.6.1.4.1.9.9.46.2.0.10";

    container object-1 {

      leaf managementDomainIndex {
        type leafref {
          path "/CISCO-VTP-MIB:CISCO-VTP-MIB/CISCO-VTP-MIB:managementDomainTable/CISCO-VTP-MIB:managementDomainEntry/CISCO-VTP-MIB:managementDomainIndex";
        }
      }

      leaf vtpVlanIndex {
        type leafref {
          path "/CISCO-VTP-MIB:CISCO-VTP-MIB/CISCO-VTP-MIB:vtpVlanTable/CISCO-VTP-MIB:vtpVlanEntry/CISCO-VTP-MIB:vtpVlanIndex";
        }
      }

      leaf vtpVlanName {
        type leafref {
          path "/CISCO-VTP-MIB:CISCO-VTP-MIB/CISCO-VTP-MIB:vtpVlanTable/CISCO-VTP-MIB:vtpVlanEntry/CISCO-VTP-MIB:vtpVlanName";
        }
      }
    }
  }

  notification vtpVlanDeleted {
    description
     "A vtpVlanDeleted notification is generated by a
      device when a VLAN is deleted.";
    smiv2:oid "1.3.6.1.4.1.9.9.46.2.0.11";

    container object-1 {

      leaf managementDomainIndex {
        type leafref {
          path "/CISCO-VTP-MIB:CISCO-VTP-MIB/CISCO-VTP-MIB:managementDomainTable/CISCO-VTP-MIB:managementDomainEntry/CISCO-VTP-MIB:managementDomainIndex";
        }
      }

      leaf vtpVlanIndex {
        type leafref {
          path "/CISCO-VTP-MIB:CISCO-VTP-MIB/CISCO-VTP-MIB:vtpVlanTable/CISCO-VTP-MIB:vtpVlanEntry/CISCO-VTP-MIB:vtpVlanIndex";
        }
      }

      leaf vtpVlanName {
        type leafref {
          path "/CISCO-VTP-MIB:CISCO-VTP-MIB/CISCO-VTP-MIB:vtpVlanTable/CISCO-VTP-MIB:vtpVlanEntry/CISCO-VTP-MIB:vtpVlanName";
        }
      }
    }
  }

  notification vtpVlanRingNumberConflict {
    description
     "A VTP ring number configuration conflict notification is
      generated if, and only at the time when, a device learns of
      a conflict between:
      
      a) the ring number (vtpVlanPortLocalSegment) being used on a
         token ring segment attached to the port identified by
         ifIndex, and
      
      b) the VTP-obtained ring number (vtpVlanRingNumber) for the
         VLAN identified by vtpVlanIndex.
      
      When such a conflict occurs, the bridge port is put into an
      administrative down position until the conflict is resolved
      through local/network management intervention.
      
      This notification is only applicable to VLANs of type
      'tokenRing'.";
    smiv2:oid "1.3.6.1.4.1.9.9.46.2.0.12";

    container object-1 {

      leaf managementDomainIndex {
        type leafref {
          path "/CISCO-VTP-MIB:CISCO-VTP-MIB/CISCO-VTP-MIB:managementDomainTable/CISCO-VTP-MIB:managementDomainEntry/CISCO-VTP-MIB:managementDomainIndex";
        }
      }

      leaf vtpVlanIndex {
        type leafref {
          path "/CISCO-VTP-MIB:CISCO-VTP-MIB/CISCO-VTP-MIB:vtpVlanTable/CISCO-VTP-MIB:vtpVlanEntry/CISCO-VTP-MIB:vtpVlanIndex";
        }
      }

      leaf vtpVlanRingNumber {
        type leafref {
          path "/CISCO-VTP-MIB:CISCO-VTP-MIB/CISCO-VTP-MIB:vtpVlanTable/CISCO-VTP-MIB:vtpVlanEntry/CISCO-VTP-MIB:vtpVlanRingNumber";
        }
      }
    }

    container object-2 {

      leaf ifIndex {
        type leafref {
          path "/if-mib:IF-MIB/if-mib:ifTable/if-mib:ifEntry/if-mib:ifIndex";
        }
      }
    }

    container object-3 {

      leaf vtpVlanPortLocalSegment {
        type int32 {
          range "0..65535";
        }
        description
         "The ring (segment) number in use on a 802.5 ring.  For
          bridges supporting RFC 1525, this value is the same as given
          by dot1dSrPortLocalSegment for the bridge port attached to
          that ring.  When tokenRing VLANs are in use, each 'trNet'
          VLAN can/does have a different instance of
          dot1dSrPortLocalSegment for each physical port.  Note that
          access to the particuler instance of dot1dSrPortLocalSegment
          requires knowledge of how the agent supports the multiple
          'contexts' required to implement RFC 1525 for multiple
          VLANs; also note that the assignment of ifIndex values may
          be different in different 'contexts'.";
        smiv2:max-access "accessible-for-notify";
        smiv2:oid "1.3.6.1.4.1.9.9.46.2.1.1";
      }
    }
  }

  notification vtpPruningStateOperChange {
    description
     "A vtpPruningStateOperChange notification is generated
      by the device when the instance value of
      managementDomainPruningStateOper is changed.";
    smiv2:oid "1.3.6.1.4.1.9.9.46.2.0.13";

    container object-1 {

      leaf managementDomainIndex {
        type leafref {
          path "/CISCO-VTP-MIB:CISCO-VTP-MIB/CISCO-VTP-MIB:managementDomainTable/CISCO-VTP-MIB:managementDomainEntry/CISCO-VTP-MIB:managementDomainIndex";
        }
      }

      leaf managementDomainPruningStateOper {
        type leafref {
          path "/CISCO-VTP-MIB:CISCO-VTP-MIB/CISCO-VTP-MIB:managementDomainTable/CISCO-VTP-MIB:managementDomainEntry/CISCO-VTP-MIB:managementDomainPruningStateOper";
        }
      }
    }
  }

  smiv2:alias "ciscoVtpMIB" {
    smiv2:oid "1.3.6.1.4.1.9.9.46";
  }

  smiv2:alias "vtpMIBObjects" {
    smiv2:oid "1.3.6.1.4.1.9.9.46.1";
  }

  smiv2:alias "vtpStatus" {
    smiv2:oid "1.3.6.1.4.1.9.9.46.1.1";
  }

  smiv2:alias "vlanManagementDomains" {
    smiv2:oid "1.3.6.1.4.1.9.9.46.1.2";
  }

  smiv2:alias "vlanInfo" {
    smiv2:oid "1.3.6.1.4.1.9.9.46.1.3";
  }

  smiv2:alias "internalVlanInfo" {
    smiv2:oid "1.3.6.1.4.1.9.9.46.1.3.2";
  }

  smiv2:alias "vlanEdit" {
    smiv2:oid "1.3.6.1.4.1.9.9.46.1.4";
  }

  smiv2:alias "vtpStats" {
    smiv2:oid "1.3.6.1.4.1.9.9.46.1.5";
  }

  smiv2:alias "vlanTrunkPorts" {
    smiv2:oid "1.3.6.1.4.1.9.9.46.1.6";
  }

  smiv2:alias "vtpDiscover" {
    smiv2:oid "1.3.6.1.4.1.9.9.46.1.7";
  }

  smiv2:alias "vtpDatabase" {
    smiv2:oid "1.3.6.1.4.1.9.9.46.1.8";
  }

  smiv2:alias "vtpAuthentication" {
    smiv2:oid "1.3.6.1.4.1.9.9.46.1.9";
  }

  smiv2:alias "vlanStatistics" {
    smiv2:oid "1.3.6.1.4.1.9.9.46.1.10";
  }

  smiv2:alias "vtpNotifications" {
    smiv2:oid "1.3.6.1.4.1.9.9.46.2";
  }

  smiv2:alias "vtpNotificationsPrefix" {
    smiv2:oid "1.3.6.1.4.1.9.9.46.2.0";
  }

  smiv2:alias "vtpNotificationsObjects" {
    smiv2:oid "1.3.6.1.4.1.9.9.46.2.1";
  }

  smiv2:alias "vtpMIBConformance" {
    smiv2:oid "1.3.6.1.4.1.9.9.46.3";
  }

  smiv2:alias "vtpMIBCompliances" {
    smiv2:oid "1.3.6.1.4.1.9.9.46.3.1";
  }

  smiv2:alias "vtpMIBGroups" {
    smiv2:oid "1.3.6.1.4.1.9.9.46.3.2";
  }

}
