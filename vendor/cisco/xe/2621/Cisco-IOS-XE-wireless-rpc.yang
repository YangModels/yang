submodule Cisco-IOS-XE-wireless-rpc {
  yang-version 1.1;
  belongs-to Cisco-IOS-XE-rpc {
    prefix ios-xe-rpc;
  }

  import Cisco-IOS-XE-types {
    prefix ios-types;
  }

  organization
    "Cisco Systems";
  contact
    "<mailto:cs-yang@cisco.com>";
  description
    "Cisco XE Wireless RPC Yang model.
     Copyright (c) 2025 by Cisco Systems, Inc.
     All rights reserved.";

  revision 2026-02-01 {
    description
      "Added support for Wireless RPC";
  }

  grouping debug-wireless-mac-grouping {
    description
      "Debug wireless MAC grouping";
    leaf mac {
      description
        "H.H.H 48 bit mac address";
      type ios-types:cisco-mac-address-type;
      mandatory true;
    }
    leaf no {
      description
        "for no debug platform condition feature wireless mac <mac-address>";
      type empty;
    }
  }

  grouping debug-platform-condition-feature-wireless-grouping {
    description
      "Debug platform condition feature wireless grouping";
    container wireless {
      description
        "Wireless feature";
      uses debug-wireless-mac-grouping;
    }
  }
}
