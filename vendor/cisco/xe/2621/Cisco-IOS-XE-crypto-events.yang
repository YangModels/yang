module Cisco-IOS-XE-crypto-events {
  yang-version 1.1;
  namespace "http://cisco.com/ns/yang/Cisco-IOS-XE-crypto-events";
  prefix crypto-ios-xe-events;

  import Cisco-IOS-XE-ios-common-oper {
    prefix ios-common-ios-xe-oper;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for crypto events data.
     Copyright (c) 2024 by Cisco Systems, Inc.
     All rights reserved.";

  revision 2024-11-01 {
    description
      "Initial revision";
    reference
      "1.0.0";
    cisco-semver:module-version "1.0.0";
  }

  typedef crypto-ike-ipsec-event-id {
    type enumeration {
      enum crypto-event-ipsec-tunnel-down {
        value 0;
        description
          "Tunnel interface associated with the IPSec profile is down";
      }
      enum crypto-event-sa-create-fail {
        value 1;
        description
          "Creation of security association failed for IKE/IPSEC";
      }
      enum crypto-event-sa-create-success {
        value 2;
        description
          "Security association is successfully created";
      }
      enum crypto-event-ikev2-cac-limit {
        value 3;
        description
          "Failed to form security association due to Call Admission Control (CAC) limit on device";
      }
      enum crypto-event-ike-low-queue-limit {
        value 4;
        description
          "Failed to form security association due to low queue limit on device";
      }
    }
    description
      "IKE, IPSec module event identifiers";
  }

  typedef crypto-ike-ipsec-cause-id {
    type enumeration {
      enum ike-ipsec-cause-none {
        value 0;
        description
          "No cause for this notification";
      }
      enum ike-ipsec-cause-dpd-sa-del {
        value 1;
        description
          "Crypto session is deleted due to DPD timeout";
      }
      enum ike-ipsec-cause-idle-life-timeout {
        value 2;
        description
          "IPsec security association idle timeout";
      }
      enum ike-ipsec-cause-hard-life-timeout {
        value 3;
        description
          "Ipsec security association hard life timeout";
      }
      enum ike-ipsec-cause-tnl-down {
        value 4;
        description
          "Tunnel interface down";
      }
      enum ike-ipsec-cause-ipsec-active {
        value 5;
        description
          "IKE exchange success and security association created successful";
      }
      enum ike-ipsec-cause-auth-mismatch {
        value 6;
        description
          "Authentication exchange hash mismatch";
      }
      enum ike-ipsec-cause-prop-val-fail {
        value 7;
        description
          "Authentication exchange proposal validation failed";
      }
      enum ike-ipsec-cause-invalid-ike-payload {
        value 8;
        description
          "IPsec security association rekey, PFS mismatch";
      }
      enum ike-ipsec-cause-soft-lifetime-expire {
        value 9;
        description
          "IPsec security association soft lifetime expired";
      }
      enum ike-ipsec-cause-delete-from-peer {
        value 10;
        description
          "IKE received delete notification from peer";
      }
      enum ike-ipsec-cause-peer-not-reachable {
        value 11;
        description
          "IKE request timed out, peer not reachable";
      }
      enum ike-ipsec-cause-cmap-fail-to-find {
        value 12;
        description
          "Failed to find map during proposal validation";
      }
      enum ike-ipsec-cause-va-create-fail {
        value 13;
        description
          "Virtual access creation failed";
      }
      enum ike-ipsec-cause-apply-attr-va-fail {
        value 14;
        description
          "Failed to apply interface attributes on virtual access";
      }
      enum ike-ipsec-cause-reject-cac {
        value 15;
        description
          "Failed to form security association due to CAC limit on device";
      }
      enum ike-ipsec-cause-reject-low-q-limit {
        value 16;
        description
          "Failed to form security association due to low queue limit on device";
      }
      enum ike-ipsec-cause-cert-verify-fail {
        value 17;
        description
          "Certificate verification failed";
      }
      enum ike-ipsec-cause-hw-req-fail {
        value 18;
        description
          "Hardware request failed";
      }
    }
    description
      "IKE, IPSEC module cause identifiers";
  }

  typedef crypto-ike-ipsec-action-id {
    type enumeration {
      enum ike-ipsec-action-none {
        value 0;
        description
          "IKE, IPSEC no action";
      }
    }
    description
      "Crypto IKE/IPSEC action identifiers";
  }

  typedef crypto-nhrp-alarm-id {
    type enumeration {
      enum nhrp-alarm-nhs-state-change {
        value 0;
        description
          "Next hop server state change";
      }
      enum nhrp-alarm-nhc-state-change {
        value 1;
        description
          "Next hop client state change";
      }
      enum nhrp-alarm-ctrl-pkt-rate-limit {
        value 2;
        description
          "NHRP control packet rate limit exceeded";
      }
    }
    description
      "Next Hop Resolution Protocol (NHRP) alarm identifiers";
  }

  typedef crypto-nhrp-event-id {
    type enumeration {
      enum nhrp-event-all-conn-down {
        value 0;
        description
          "All connections going down";
      }
      enum nhrp-event-next-hop-peer-up {
        value 1;
        description
          "Shortcut tunnel is created";
      }
      enum nhrp-event-next-hop-peer-down {
        value 2;
        description
          "Shortcut tunnel is deleted";
      }
      enum nhrp-event-pkt-sanity-failure {
        value 3;
        description
          "Packet sanity failed for a received packet";
      }
      enum nhrp-event-err-indication-sent {
        value 4;
        description
          "NHRP error indication sent";
      }
      enum nhrp-event-err-indication-rcv {
        value 5;
        description
          "NHRP error indication received";
      }
      enum nhrp-event-internal-errors {
        value 6;
        description
          "NHRP internal errors observed";
      }
      enum nhrp-event-ctrl-msg-max-transm-fail {
        value 7;
        description
          "Max retransmission reached for control packet";
      }
      enum nhrp-event-ctrl-msg-pkt-nack-sent {
        value 8;
        description
          "NACK sent for control packet";
      }
      enum nhrp-event-ctrl-msg-pkt-nack-rcv {
        value 9;
        description
          "NACK received for control packet";
      }
      enum nhrp-event-cache-mode-change {
        value 10;
        description
          "Cache mode changed from dynamic to static";
      }
    }
    description
      "NHRP event identifiers";
  }

  typedef crypto-nhrp-cause-id {
    type enumeration {
      enum nhrp-cause-none {
        value 0;
        description
          "No cause for this notification";
      }
      enum nhrp-cause-unknown {
        value 1;
        description
          "Cause for notification is unknown";
      }
      enum nhrp-cause-loop {
        value 2;
        description
          "Loop detected";
      }
      enum nhrp-cause-admin {
        value 3;
        description
          "Administratively prohibited";
      }
      enum nhrp-cause-no-resource {
        value 4;
        description
          "Insufficient resources";
      }
      enum nhrp-cause-unreachable {
        value 5;
        description
          "Protocol address unreachable";
      }
      enum nhrp-cause-protocol {
        value 6;
        description
          "Protocol generic error";
      }
      enum nhrp-cause-toobig {
        value 7;
        description
          "Service data unit size exceeded MTU";
      }
      enum nhrp-cause-invalid-ext {
        value 8;
        description
          "Invalid extension";
      }
      enum nhrp-cause-invalid-res {
        value 9;
        description
          "Invalid resolution reply received";
      }
      enum nhrp-cause-auth-fail {
        value 10;
        description
          "Authentication failure";
      }
      enum nhrp-cause-no-binding {
        value 11;
        description
          "No address binding exists";
      }
      enum nhrp-cause-not-unique {
        value 12;
        description
          "Binding exists but is not unique";
      }
      enum nhrp-cause-registered {
        value 13;
        description
          "Unique address already registered";
      }
      enum nhrp-cause-hopcount {
        value 14;
        description
          "Hop count exceeded";
      }
      enum nhrp-cause-reg-failure {
        value 15;
        description
          "NHRP registration Failure";
      }
      enum nhrp-cause-res-failure {
        value 16;
        description
          "NHRP resolution Failure";
      }
      enum nhrp-cause-purge-rcvd {
        value 17;
        description
          "NHRP purge received";
      }
      enum nhrp-cause-hold-time-expiry {
        value 18;
        description
          "NHRP hold time expiry";
      }
      enum nhrp-cause-internal-stale {
        value 19;
        description
          "Stale entry";
      }
      enum nhrp-cause-internal-incomplete {
        value 20;
        description
          "Incomplete entry";
      }
      enum nhrp-cause-internal-temp-mapping {
        value 21;
        description
          "Temporary mapping";
      }
      enum nhrp-cause-max-send-limit {
        value 22;
        description
          "Max Send limit";
      }
      enum nhrp-cause-max-transm-fail {
        value 23;
        description
          "Maximum retransmission failed";
      }
      enum nhrp-cause-cie-incorrect-code {
        value 24;
        description
          "Incorrect CIE code";
      }
      enum nhrp-cause-cie-invalid-length {
        value 25;
        description
          "Invalid CIE length";
      }
      enum nhrp-cause-ext-invalid-id {
        value 26;
        description
          "Invalid vendor identifier";
      }
      enum nhrp-cause-ext-max-count {
        value 27;
        description
          "Max extension count";
      }
      enum nhrp-cause-ext-invalid-sub-type-len {
        value 28;
        description
          "Invalid sub type length";
      }
      enum nhrp-cause-pkt-invalid-size {
        value 29;
        description
          "Invalid packet size";
      }
      enum nhrp-cause-pkt-unsupported-af {
        value 30;
        description
          "Unsupported address family";
      }
      enum nhrp-cause-pkt-incorrect-nbma-len {
        value 31;
        description
          "Incorrect NBMA length";
      }
      enum nhrp-cause-pkt-incorrect-sub-len {
        value 32;
        description
          "Incorrect NBMA sub length";
      }
      enum nhrp-cause-pkt-incorrect-total-len {
        value 33;
        description
          "Incorrect NBMA total length";
      }
      enum nhrp-cause-pkt-unsupported-proto {
        value 34;
        description
          "Unsupported protocol";
      }
      enum nhrp-cause-pkt-non-nhrp-intf {
        value 35;
        description
          "NHRP packet on an interface where NHRP is not enabled";
      }
      enum nhrp-cause-pkt-invalid-snap {
        value 36;
        description
          "Invalid SNAP encoded value";
      }
      enum nhrp-cause-pkt-invalid-packet-type {
        value 37;
        description
          "Invalid packet type";
      }
      enum nhrp-cause-pkt-invalid-proto-ver {
        value 38;
        description
          "Invalid protocol version";
      }
      enum nhrp-cause-pkt-zero-hop-count {
        value 39;
        description
          "Zero hop count";
      }
      enum nhrp-cause-pkt-inconsistent-size {
        value 40;
        description
          "Inconsistent size";
      }
      enum nhrp-cause-pkt-bad-ckhsum {
        value 41;
        description
          "Bad checksum";
      }
      enum nhrp-cause-pkt-invalid-proto-len {
        value 42;
        description
          "Invalid protocol length";
      }
      enum nhrp-cause-pkt-extra-cie {
        value 43;
        description
          "Extra CIE";
      }
      enum nhrp-cause-pkt-ext-invalid-len {
        value 44;
        description
          "Invalid extension length";
      }
      enum nhrp-cause-pkt-ext-len-mismatch {
        value 45;
        description
          "Extension length mismatched";
      }
      enum nhrp-cause-pkt-incorrect-auth-len {
        value 46;
        description
          "Incorrect authentication extension length";
      }
      enum nhrp-cause-pkt-auth-type-not-clear {
        value 47;
        description
          "Authentication type is not clear text";
      }
      enum nhrp-cause-pkt-invalid-ext {
        value 48;
        description
          "Invalid NHRP extension";
      }
      enum nhrp-cause-pkt-invalid-ext-len {
        value 49;
        description
          "Invalid extension length";
      }
      enum nhrp-cause-ext-admin {
        value 50;
        description
          "Clear or show commands executed by user";
      }
      enum nhrp-cause-ext-delete-nho {
        value 51;
        description
          "Next hop deleted";
      }
      enum nhrp-cause-ext-delete-summary-map {
        value 52;
        description
          "Summary map deleted";
      }
      enum nhrp-cause-ext-intf-down {
        value 53;
        description
          "Tunnel interface down";
      }
      enum nhrp-cause-ext-intf-admindown {
        value 54;
        description
          "Tunnel interface administratively down";
      }
      enum nhrp-cause-ext-tp-socket-down {
        value 55;
        description
          "Tunnel protection socket down";
      }
      enum nhrp-cause-ext-tunnel-mode-leave {
        value 56;
        description
          "Tunnel mode change";
      }
      enum nhrp-cause-ext-vrf-config-changed {
        value 57;
        description
          "Tunnel VRF config change";
      }
      enum nhrp-cause-ext-dhcp {
        value 58;
        description
          "DHCP initiated delete";
      }
      enum nhrp-cause-ext-bfd-down {
        value 59;
        description
          "BFD down";
      }
      enum nhrp-cause-ext-rw-nhop-intf-mismatch {
        value 60;
        description
          "Route watch, next hop interface mismatch";
      }
      enum nhrp-cause-ext-rw-rib-unreachable {
        value 61;
        description
          "Route watch, RIB unreachable";
      }
      enum nhrp-cause-ext-rib-route-add-failed {
        value 62;
        description
          "RIB route add failed";
      }
      enum nhrp-cause-ext-export-failed {
        value 63;
        description
          "BGP export failed";
      }
      enum nhrp-cause-ext-bgp-delete-all {
        value 64;
        description
          "BGP delete all notification";
      }
      enum nhrp-cause-ext-route-down {
        value 65;
        description
          "Route down notification";
      }
      enum nhrp-cause-ext-bgp-down {
        value 66;
        description
          "BGP route down notification";
      }
      enum nhrp-cause-ext-ipfib-change {
        value 67;
        description
          "IP FIB change";
      }
      enum nhrp-cause-external-metadata-neg {
        value 68;
        description
          "Metadata negotiation";
      }
    }
    description
      "NHRP cause identifiers";
  }

  typedef crypto-nhrp-action-id {
    type enumeration {
      enum nhrp-action-none {
        value 0;
        description
          "NHRP no action";
      }
    }
    description
      "Crypto NHRP action identifiers";
  }

  typedef crypto-nhrp-alarm-state {
    type enumeration {
      enum nhrp-state-up {
        value 0;
        description
          "For alarms that notify connection state, this value is used when state changes to up";
      }
      enum nhrp-state-down {
        value 1;
        description
          "For alarms that notify connection state, this value is used when state changes to down";
      }
      enum nhrp-state-exceeded {
        value 2;
        description
          "For alarms that notify threshold state, this value is used when value is above threshold";
      }
      enum nhrp-state-cleared {
        value 3;
        description
          "For alarms that notify threshold state, this value is used when value is below threshold";
      }
    }
    description
      "Indicates the alarm state";
  }

  grouping crypto-ike-ipsec-event-notification {
    description
      "Crypto event notification";
    leaf severity-level {
      type ios-common-ios-xe-oper:notification-severity;
      description
        "Severity level";
    }
    leaf host-name {
      type string;
      description
        "Host name";
    }
    leaf system-ip {
      type inet:ip-address;
      description
        "System IP";
    }
    leaf event-id {
      type crypto-ios-xe-events:crypto-ike-ipsec-event-id;
      description
        "Uniquely identifies the event type";
    }
    leaf cause {
      type crypto-ios-xe-events:crypto-ike-ipsec-cause-id;
      description
        "If known, provides an explanation of why the alarm was generated";
    }
    leaf action {
      type crypto-ios-xe-events:crypto-ike-ipsec-action-id;
      description
        "Any action, including steps that can be taken";
    }
    leaf local-ip {
      type inet:ip-address;
      description
        "Local IP address";
    }
    leaf remote-ip {
      type inet:ip-address;
      description
        "Remote IP address";
    }
    leaf resp-port {
      type uint16;
      description
        "Port number of responder";
    }
    leaf init-port {
      type uint16;
      description
        "Port number of initiator";
    }
    leaf detail {
      type string;
      description
        "Detailed description of the event";
    }
  }

  grouping crypto-nhrp-alarm-notification {
    description
      "NHRP alarm notification";
    leaf severity-level {
      type ios-common-ios-xe-oper:notification-severity;
      description
        "Alarm notification severity";
    }
    leaf host-name {
      type string;
      description
        "Host name";
    }
    leaf system-ip {
      type inet:ip-address;
      description
        "System IP";
    }
    leaf alarm-id {
      type crypto-ios-xe-events:crypto-nhrp-alarm-id;
      description
        "Uniquely identifies the alarm type";
    }
    leaf cause {
      type crypto-ios-xe-events:crypto-nhrp-cause-id;
      description
        "If known, provides an explanation of why the alarm was generated";
    }
    leaf action {
      type crypto-ios-xe-events:crypto-nhrp-action-id;
      description
        "Any action, including steps that can be taken";
    }
    leaf local-ip {
      type inet:ip-address;
      description
        "Local IP address";
    }
    leaf remote-ip {
      type inet:ip-address;
      description
        "Remote IP address";
    }
    leaf if-name {
      type string;
      description
        "Interface name";
    }
    leaf detail {
      type string;
      description
        "Detailed description of the alarm";
    }
    leaf state {
      type crypto-ios-xe-events:crypto-nhrp-alarm-state;
      description
        "State of the alarm";
    }
  }

  grouping crypto-nhrp-event-notification {
    description
      "NHRP event notification";
    leaf severity-level {
      type ios-common-ios-xe-oper:notification-severity;
      description
        "Event notification severity";
    }
    leaf host-name {
      type string;
      description
        "Host name";
    }
    leaf system-ip {
      type inet:ip-address;
      description
        "System IP";
    }
    leaf event-id {
      type crypto-ios-xe-events:crypto-nhrp-event-id;
      description
        "Uniquely identifies the alarm type";
    }
    leaf cause {
      type crypto-ios-xe-events:crypto-nhrp-cause-id;
      description
        "If known, provides an explanation of why the alarm was generated";
    }
    leaf action {
      type crypto-ios-xe-events:crypto-nhrp-action-id;
      description
        "Any action, including steps that can be taken";
    }
    leaf local-ip {
      type inet:ip-address;
      description
        "Local IP address";
    }
    leaf remote-ip {
      type inet:ip-address;
      description
        "Remote IP address";
    }
    leaf if-name {
      type string;
      description
        "Interface name";
    }
    leaf detail {
      type string;
      description
        "Detailed description of the event";
    }
  }

  notification ike-ipsec-event {
    description
      "IKE, IPSEC event notification";
    uses crypto-ios-xe-events:crypto-ike-ipsec-event-notification;
  }

  notification nhrp-alarm {
    description
      "NHRP alarm notification";
    uses crypto-ios-xe-events:crypto-nhrp-alarm-notification;
  }

  notification nhrp-event {
    description
      "NHRP event notification";
    uses crypto-ios-xe-events:crypto-nhrp-event-notification;
  }
}
