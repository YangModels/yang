module Cisco-IOS-XE-transceiver-oper {
  yang-version 1.1;
  namespace "http://cisco.com/ns/yang/Cisco-IOS-XE-transceiver-oper";
  prefix xcvr-ios-xe-oper;

  import Cisco-IOS-XE-ios-common-oper {
    prefix ios-common-ios-xe-oper;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     monitoring transceivers in a Network Element.
     Copyright (c) 2017-2019, 2021-2022, 2026 by Cisco Systems, Inc.
     All rights reserved.";

  revision 2026-08-01 {
    description
      "Updated description of transceiver elements to clarify their meaning and purpose";
    reference
      "1.7.1";
    cisco-semver:module-version "1.7.1";
  }
  revision 2025-03-01 {
    description
      "- Added support to read supply voltage for transceiver.
       - Updated descriptions for 'statistics values' , 'output power', 'input power' and 'laser bias current'.
       - Added support to read supply voltage, current, input, output , internal-temp threshold values  for transceiver.
       - Updated descriptions for 'threshold values', 'voltage' , 'internal-temp' , 'output power', 'input power' and 'laser bias current'.
       - Added Diagnostic Monitoring, which lists the types of digital diagnostic monitoring supported for the interface, such as
         'temperature', 'voltage', 'bias current', 'transmit power' and 'receive power'.";
    reference
      "1.7.0";
    cisco-semver:module-version "1.7.0";
  }
  revision 2023-11-01 {
    description
      "Added more transceiver attributes";
    reference
      "1.6.0";
    cisco-semver:module-version "1.6.0";
  }
  revision 2022-11-01 {
    description
      "Update yang-version to 1.1";
    reference
      "1.5.0";
    cisco-semver:module-version "1.5.0";
  }
  revision 2022-03-01 {
    description
      "Added interval in statistics values for calculating min/max/average over the period.";
    reference
      "1.4.0";
    cisco-semver:module-version "1.4.0";
  }
  revision 2020-03-01 {
    description
      "Update copyright";
    reference
      "1.3.1";
    cisco-semver:module-version "1.3.1";
  }
  revision 2019-11-01 {
    description
      "Added fault reason and time of last transceiver event";
    reference
      "1.3.0";
    cisco-semver:module-version "1.3.0";
  }
  revision 2019-05-01 {
    description
      "Added semantic version";
    reference
      "1.2.0";
    cisco-semver:module-version "1.2.0";
  }
  revision 2018-10-29 {
    description
      "Cleaned up spelling errors in descriptions.";
    reference
      "1.1.0";
    cisco-semver:module-version "1.1.0";
  }
  revision 2018-01-18 {
    description
      "Initial revision";
    reference
      "1.0.0";
    cisco-semver:module-version "1.0.0";
  }

  typedef xcvr-sonet-code {
    type enumeration {
      enum oc-48-short-reach {
        value 0;
      }
      enum oc-48-intermediate-reach {
        value 1;
      }
      enum oc-48-long-reach {
        value 2;
      }
      enum sonet-sr-compliant {
        value 3;
      }
      enum sonet-lr-compliant {
        value 4;
      }
      enum oc-192-short-reach {
        value 5;
      }
      enum escon-smf-1310-laser {
        value 6;
      }
      enum escon-mmf-1310-led {
        value 7;
      }
      enum unknown {
        value 8;
      }
    }
    description
      "SONET/SDH application code supported by the port";
  }

  typedef xcvr-otn-code {
    type enumeration {
      enum p1l1-2d1 {
        value 0;
      }
      enum p1s1-2d2 {
        value 1;
      }
      enum p1l1-2d2 {
        value 2;
      }
      enum otn-undefined {
        value 3;
      }
    }
    description
      "OTN application code supported by the port";
  }

  typedef xcvr-ext-identifier {
    type enumeration {
      enum ext-id-unknown {
        value 0;
        description
          "External identifier unknown";
      }
      enum ext-id-mod-def-1-compliant {
        value 1;
        description
          "Compliance with mode definition 1";
      }
      enum ext-id-mod-def-2-compliant {
        value 2;
        description
          "Compliance with mode definition 2";
      }
      enum ext-id-mod-def-3-compliant {
        value 3;
        description
          "Compliance with mode definition 3";
      }
      enum ext-id-defined-by-two-wire-interface {
        value 4;
        description
          "SFP function is defined by two-wire interface ID only";
      }
      enum ext-id-mod-def-5-compliant {
        value 5;
        description
          "Compliance with mode definition 15";
      }
      enum ext-id-mod-def-6-compliant {
        value 6;
        description
          "Compliance with mode definition 6";
      }
      enum ext-id-mod-def-7-compliant {
        value 7;
        description
          "Compliance with mode definition 7";
      }
    }
    description
      "External identifier";
  }

  typedef xcvr-ten-gig-comp-code {
    type enumeration {
      enum comp-unknown {
        value 0;
        description
          "10 Gigabit comp code unknown";
      }
      enum comp-40g-active-cable-xlppi {
        value 1;
        description
          "40 Gigabit active cable";
      }
      enum comp-40g-base-lr4 {
        value 2;
        description
          "40 Gigabit base LR";
      }
      enum comp-40g-base-sr4 {
        value 4;
        description
          "40 Gigabit base SR";
      }
      enum comp-40g-base-cr4 {
        value 8;
        description
          "40 Gigabit base CR";
      }
      enum comp-10g-base-sr {
        value 16;
        description
          "10 Gigabit base SR";
      }
      enum comp-10g-base-lr {
        value 32;
        description
          "10 Gigabit base LR";
      }
      enum comp-10g-base-lrm {
        value 64;
        description
          "10 Gigabit base LR multi mode";
      }
      enum comp-10g-base-er4 {
        value 128;
        description
          "10 Gigabit base ER";
      }
    }
    description
      "10 Gigabit or 40 Gigabit comp code supported by the port";
  }

  typedef xcvr-one-gig-comp-code {
    type enumeration {
      enum gecomp-unknown {
        value 0;
        description
          "1 Gigabit comp code unknown";
      }
      enum gecomp-1000-base-sx {
        value 1;
        description
          "1000 base short wavelength";
      }
      enum gecomp-1000-base-lx {
        value 2;
        description
          "1000 base long wavelength";
      }
      enum gecomp-1000-base-cx {
        value 4;
        description
          "1000 base copper";
      }
      enum gecomp-1000-base {
        value 8;
        description
          "1000 base twisted pair";
      }
      enum gecomp-100-base-lx {
        value 16;
        description
          "100 base long wavelength";
      }
      enum gecomp-100-base-fx {
        value 32;
        description
          "100 base fiber";
      }
      enum gecomp-base-bx10 {
        value 64;
        description
          "Base bidirectional";
      }
      enum gecomp-base-px {
        value 128;
        description
          "Base pair";
      }
    }
    description
      "1 Gigabit comp code supported by the port";
  }

  typedef xcvr-tech-value {
    type enumeration {
      enum tech-unknown {
        value 0;
        description
          "Technology unknown";
      }
      enum tech-unallocated {
        value 1;
        description
          "Unallocated";
      }
      enum tech-unallocated-2 {
        value 2;
        description
          "Unallocated 2";
      }
      enum tech-passive-cable {
        value 4;
        description
          "Passive cable";
      }
      enum tech-active-cable {
        value 8;
        description
          "Active cable";
      }
      enum tech-long-wave-laser {
        value 16;
        description
          "Long wave laser";
      }
      enum tech-short-wave-laser-with-fiber {
        value 32;
        description
          "Shortwave laser with fiber";
      }
      enum tech-short-wave-laswer-wo-fiber {
        value 64;
        description
          "Shortwave laser without fiber";
      }
      enum tech-electrical-intra-enclosure {
        value 128;
        description
          "Electrical intra-enclosure";
      }
    }
    description
      "Transceiver technology value";
  }

  typedef xcvr-media-value {
    type enumeration {
      enum media-unknown {
        value 0;
        description
          "Media unknown";
      }
      enum media-single-mode {
        value 1;
        description
          "Single mode";
      }
      enum media-reserved {
        value 2;
        description
          "Media reserved value";
      }
      enum media-multimode-50 {
        value 4;
        description
          "Multi mode 50 micro meters";
      }
      enum media-multimode-62 {
        value 8;
        description
          "Multi mode 62 and half micro meters";
      }
      enum media-video-coax {
        value 16;
        description
          "Video coax";
      }
      enum media-miniature-coax {
        value 32;
        description
          "Miniature coax";
      }
      enum media-shielded-twisted-pair {
        value 64;
        description
          "Shielded twisted pair";
      }
      enum media-twin-axial-pair {
        value 128;
        description
          "Twin axial pair";
      }
    }
    description
      "Transceiver media value";
  }

  typedef xcvr-speed-value {
    type enumeration {
      enum speed-unknown {
        value 0;
        description
          "Speed unknown";
      }
      enum speed-100-mbps {
        value 1;
        description
          "100 Mbps";
      }
      enum speed-reserved {
        value 2;
        description
          "Speed reserved value";
      }
      enum speed-200-mbps {
        value 4;
        description
          "200 Mbps";
      }
      enum speed-reserved-2 {
        value 8;
        description
          "Speed reserved 2 value";
      }
      enum speed-400-mbps {
        value 16;
        description
          "400 Mbps";
      }
      enum speed-1600-mbps {
        value 32;
        description
          "1600 Mbps";
      }
      enum speed-800-mbps {
        value 64;
        description
          "800 Mbps";
      }
      enum speed-1200-mbps {
        value 128;
        description
          "1200 Mbps";
      }
    }
    description
      "Transceiver speed value";
  }

  typedef xcvr-link-length-value {
    type enumeration {
      enum ll-unknown {
        value 0;
        description
          "Link length unknown";
      }
      enum ll-medium-distance {
        value 8;
        description
          "Medium distance";
      }
      enum ll-long-distance {
        value 16;
        description
          "Long distance";
      }
      enum ll-intermediate-distance {
        value 32;
        description
          "Intermediate distance";
      }
      enum ll-short-distance {
        value 64;
        description
          "Short distance";
      }
      enum ll-very-long-distance {
        value 128;
        description
          "Very long distance";
      }
    }
    description
      "Transceiver link length value";
  }

  typedef xcvr-encoding-value {
    type enumeration {
      enum enc-unknown {
        value 0;
        description
          "Encoding unknown";
      }
      enum enc-8b10b {
        value 1;
        description
          "8 bit 10 bit";
      }
      enum enc-4b5b {
        value 2;
        description
          "4 bit 5 bit";
      }
      enum enc-nrz {
        value 3;
        description
          "Non return to zero";
      }
      enum enc-manchester {
        value 4;
        description
          "Manchester";
      }
      enum enc-sonet-scrambled {
        value 5;
        description
          "Sonet scrambled";
      }
      enum enc-64b66b {
        value 6;
        description
          "64 bit 66 bit";
      }
    }
    description
      "Transceiver encoding";
  }

  typedef xcvr-rx-pwr-msmt {
    type enumeration {
      enum rx-power-unknown {
        value 0;
        description
          "Rx power measurement unknown";
      }
      enum rx-power-avg {
        value 1;
        description
          "Average";
      }
      enum rx-power-oma {
        value 2;
        description
          "Optical modulation amplitude";
      }
    }
    description
      "Transceiver rx power measurement";
  }

  typedef xcvr-addr-change {
    type enumeration {
      enum address-change-unknown {
        value 0;
        description
          "Address change unknown";
      }
      enum address-change-required {
        value 1;
        description
          "Address change required";
      }
      enum address-change-not-required {
        value 2;
        description
          "Address change not required";
      }
    }
    description
      "Transceiver address change";
  }

  typedef xcvr-link-status {
    type enumeration {
      enum link-not-applicable {
        value 0;
        description
          "Link not applicable";
      }
      enum link-no-fault {
        value 1;
        description
          "Link no fault";
      }
      enum link-near-end-fault {
        value 2;
        description
          "Link near end fault";
      }
      enum link-near-end-config-fail {
        value 3;
        description
          "Link near end config fail";
      }
      enum link-far-end-fault {
        value 4;
        description
          "Link far end fault";
      }
      enum link-far-end-config-fail {
        value 5;
        description
          "Link far end config fail";
      }
      enum link-far-end-disabled {
        value 6;
        description
          "Link far end disabled";
      }
    }
    description
      "Transceiver link status";
  }

  typedef xcvr-flowcontrol {
    type enumeration {
      enum flowcontrol-unknown {
        value -1;
        description
          "Flow control unknown";
      }
      enum flowcontrol-off {
        value 0;
        description
          "Flow control off";
      }
      enum flowcontrol-on {
        value 1;
        description
          "Flow control on";
      }
      enum flowcontrol-desired {
        value 2;
        description
          "Flow control desired";
      }
      enum flowcontrol-disagree {
        value 3;
        description
          "Flow control disagree";
      }
    }
    description
      "Transceiver flow control";
  }

  typedef idprom-duplex {
    type enumeration {
      enum duplex-unknown {
        value -1;
        description
          "Duplex unknown";
      }
      enum duplex-auto {
        value 0;
        description
          "Duplex auto";
      }
      enum duplex-half {
        value 1;
        description
          "Duplex half";
      }
      enum duplex-full {
        value 2;
        description
          "Duplex full";
      }
      enum duplex-full-auto {
        value 3;
        description
          "duplex full auto";
      }
    }
    description
      "Transceiver duplex info";
  }

  typedef xcvr-port-speed {
    type enumeration {
      enum port-speed-unknown {
        value -1;
        description
          "Speed unknown";
      }
      enum port-speed-auto {
        value 0;
        description
          "Speed auto";
      }
      enum port-speed-10-mbps {
        value 1;
        description
          "Speed 10 Mbps";
      }
      enum port-speed-100-mbps {
        value 2;
        description
          "Speed 100 Mbps";
      }
      enum port-speed-1-gbps {
        value 3;
        description
          "Speed 1 Gbps";
      }
      enum port-speed-10-gbps {
        value 4;
        description
          "Speed 10 Gbps";
      }
      enum port-speed-2500-mbps {
        value 8;
        description
          "Speed 2500 Mbps";
      }
      enum port-speed-5000-mbps {
        value 9;
        description
          "Speed 5000 Mbps";
      }
      enum port-speed-40-gbps {
        value 10;
        description
          "Speed 40 Gbps";
      }
      enum port-speed-25-gbps {
        value 41;
        description
          "Speed 25 Gbps";
      }
      enum port-speed-100-gbps {
        value 42;
        description
          "Speed 100 Gbps";
      }
      enum port-speed-400-gbps {
        value 49;
        description
          "Speed 400 Gbps";
      }
      enum port-speed-50-gbps {
        value 50;
        description
          "Speed 50 Gbps";
      }
      enum port-speed-200-gbps {
        value 51;
        description
          "Speed 200 Gbps";
      }
    }
    description
      "Transceiver port speed";
  }

  typedef xcvr-diag-mon-list {
    type bits {
      bit dm-nt-impl {
        position 0;
        description
          "Diagnostic monitoring not implemented";
      }
      bit dm-impl {
        position 1;
        description
          "Diagnostic monitoring implemented";
      }
      bit dm-leg-sup {
        position 2;
        description
          "Legacy diagnostics supported";
      }
      bit dm-digi-sup {
        position 3;
        description
          "Digital diagnostics supported";
      }
      bit dm-in-cal {
        position 4;
        description
          "Diagnostics are internally calibrated";
      }
      bit dm-ext-cal {
        position 5;
        description
          "Diagnostics are externally calibrated";
      }
      bit dm-rx-avg-pwr {
        position 6;
        description
          "Received power is average";
      }
      bit dm-addr-chn-req {
        position 7;
        description
          "Address change required";
      }
      bit dm-nw-lane-lsr-temp {
        position 8;
        description
          "Network Lane laser temperature monitor";
      }
      bit dm-nw-lane-rx-pwr {
        position 9;
        description
          "Network Lane received power monitor";
      }
      bit dm-nw-lane-lsr-bias {
        position 10;
        description
          "Network Lane laser bias current monitor";
      }
      bit dm-nw-lane-lsr-op-pwr {
        position 11;
        description
          "Network Lane laser output power monitor";
      }
      bit dm-txvr-pwr-volt {
        position 12;
        description
          "Transceiver power supply voltage monitor";
      }
    }
    description
      "List of diagnostic monitoring supported features for
       transceivers including SFP, SFP+, QSFP, QSFP+ and QSA";
  }

  grouping idprom-bit-rate {
    description
      "Bit rate nominal, min and max on transceiver";
    leaf nominal {
      type uint16;
      units "Mbps";
      description
        "Nominal bit rate in Mbps";
    }
    leaf min {
      type uint8;
      units "percentage";
      description
        "Minimum bit rate as percentage of nominal bit rate";
    }
    leaf max {
      type uint8;
      units "percentage";
      description
        "Maximum bit rate as percentage of nominal bit rate";
    }
  }

  grouping add-info {
    description
      "Additional operational information related to the transceiver,
       such as link status, flow control, and speed/duplex settings.";
    leaf link-status {
      type xcvr-ios-xe-oper:xcvr-link-status;
      description
        "Indicates the current operational status of the transceiver's network link";
    }
    leaf flow-control-rx {
      type xcvr-ios-xe-oper:xcvr-flowcontrol;
      description
        "Indicates operational status of receive (Rx) flow control on the transceiver's network interface";
    }
    leaf flow-control-tx {
      type xcvr-ios-xe-oper:xcvr-flowcontrol;
      description
        "Operational status of transmit (TX) flow control on the transceiver's network interface";
    }
    leaf admin-speed {
      type xcvr-ios-xe-oper:xcvr-port-speed;
      description
        "Administratively configured speed for the transceiver port";
    }
    leaf admin-duplex {
      type xcvr-ios-xe-oper:idprom-duplex;
      description
        "Administratively configured duplex mode (half or full) for the transceiver port";
    }
    leaf oper-speed {
      type xcvr-ios-xe-oper:xcvr-port-speed;
      description
        "Current operational speed of the transceiver port";
    }
    leaf oper-duplex {
      type xcvr-ios-xe-oper:idprom-duplex;
      description
        "Current operational duplex mode (half or full) of the transceiver port";
    }
  }

  grouping statistics-values {
    description
      "Statistics values includes the instantaneous, average, minimum, and
       maximum statistics computed over an time interval in minutes for
       output power(dBM), input power(dBM), laser bias current(mA) and voltage(volts)";
    leaf instant {
      type decimal64 {
        fraction-digits 2;
      }
      description
        "Instantaneous value measured for the transceiver over the specified time interval";
    }
    leaf avg {
      type decimal64 {
        fraction-digits 2;
      }
      description
        "Average value measured for the transceiver over the specified time interval";
    }
    leaf max {
      type decimal64 {
        fraction-digits 2;
      }
      description
        "Maximum value measured for the transceiver over the specified time interval";
    }
    leaf min {
      type decimal64 {
        fraction-digits 2;
      }
      description
        "Minimum value measured for the transceiver over the specified time interval";
    }
    leaf interval {
      type uint32;
      units "minutes";
      description
        "The time interval over which the min/max/average statistics are computed by the system.";
    }
  }

  grouping thrsld-val {
    description
      "Threshold values includes the high alarm, low alarm, high warning and
       low warning  threshold computed for internal-temp(Celsius), output power(dBM), input power(dBM),
       laser bias current(mA) and voltage(volts)";
    leaf high-alarm {
      type decimal64 {
        fraction-digits 2;
      }
      description
        "High alarm threshold value computed for internal-temp(Celsius), output power(dBM),
         input power(dBM), laser bias current(mA) and voltage(volts)";
    }
    leaf low-alarm {
      type decimal64 {
        fraction-digits 2;
      }
      description
        "Low alarm threshold value computed for internal-temp(Celsius), output power(dBM),
         input power(dBM), laser bias current(mA) and voltage(volts)";
    }
    leaf high-warn {
      type decimal64 {
        fraction-digits 2;
      }
      description
        "High warning threshold value computed for internal-temp(Celsius), output power(dBM),
         input power(dBM), laser bias current(mA) and voltage(volts)";
    }
    leaf low-warn {
      type decimal64 {
        fraction-digits 2;
      }
      description
        "Low warning threshold value computed for internal-temp(Celsius), output power(dBM),
         input power(dBM), laser bias current(mA) and voltage(volts)";
    }
  }

  grouping fiber-length {
    description
      "Fiber length detail";
    leaf nine-micron-km {
      type int16;
      units "kilometers";
      description
        "9 micron single mode fiber length in kilometers, -1 for unsupported";
    }
    leaf nine-micron {
      type int16;
      units "meters";
      description
        "9 micron single mode fiber length in meters, -1 for unsupported";
    }
    leaf fifty-micron {
      type int16;
      units "meters";
      description
        "50 micron multi mode optical module 2 fiber length in meters, -1 for unsupported";
    }
    leaf sixty-two-micron {
      type int16;
      units "meters";
      description
        "62.5 micron multi mode optical module 1 fiber length in meters, -1 for unsupported";
    }
    leaf copper {
      type int16;
      units "meters";
      description
        "50 micron multi mode optical module 4 fiber length in meters, -1 for unsupported";
    }
  }

  grouping xcvr-physical-channel {
    description
      "List of physical channel for transceiver";
    leaf index {
      type uint16;
      description
        "Index of the physical channel";
    }
    leaf description {
      type string;
      description
        "Text description for the client physical channel";
    }
    leaf tx-laser {
      type boolean;
      description
        "Enable (true) or disable (false) the transmit label for the channel";
    }
    leaf target-output-power {
      type decimal64 {
        fraction-digits 2;
      }
      description
        "Target output optical power level of the optical channel(dBm)";
    }
    leaf output-frequency {
      type uint64;
      description
        "The frequency in MHz of the individual physical channel";
    }
    container output-power {
      description
        "The output optical power of a physical channel(dBm)";
      uses xcvr-ios-xe-oper:statistics-values;
    }
    container input-power {
      description
        "The input optical power of a physical channel(dBm)";
      uses xcvr-ios-xe-oper:statistics-values;
    }
    container laser-bias-current {
      description
        "The current applied by the system to the transmit laser to achieve the output power(mA)";
      uses xcvr-ios-xe-oper:statistics-values;
    }
  }

  grouping xcvr {
    description
      "Attributes of transceiver";
    leaf name {
      type string;
      description
        "Port name";
    }
    leaf enabled {
      type boolean;
      description
        "Turns power on/off to the transceiver";
    }
    leaf present {
      type boolean;
      description
        "Transceiver is present on the port";
    }
    leaf identifier {
      type string;
      description
        "Indicates the type of optical transceiver used on this port";
    }
    leaf connector {
      type string;
      description
        "Connector type used on this port";
    }
    leaf ethernet-pmd {
      type string;
      description
        "Ethernet PMD (physical medium dependent sub layer) that the transceiver supports. The SFF/QSFP MSAs have registers for this and CFP MSA has similar.";
    }
    leaf vendor {
      type string;
      description
        "Full name of transceiver vendor";
    }
    leaf vendor-part {
      type string;
      description
        "Transceiver vendor's part number";
    }
    leaf vendor-rev {
      type string;
      description
        "Transceiver vendor's revision number";
    }
    leaf serial-no {
      type string;
      description
        "Transceiver serial number";
    }
    leaf fault-condition {
      type boolean;
      description
        "Indicates if a fault condition exists in the transceiver";
    }
    leaf date {
      type string;
      description
        "Representation of the transceiver date";
    }
    leaf sonet {
      type xcvr-ios-xe-oper:xcvr-sonet-code;
      description
        "SONET/SDH application code supported by the port";
    }
    leaf otn {
      type xcvr-ios-xe-oper:xcvr-otn-code;
      description
        "OTN application code supported by the port";
    }
    leaf internal-temp {
      type decimal64 {
        fraction-digits 2;
      }
      description
        "Internally measured temperature in degrees Celsius";
    }
    container output-power {
      description
        "The output optical power of a physical channel in units
         of dBm, which may be associated with individual
         physical channels, or an aggregate of multiple physical
         channels (i.e., for the overall transceiver). For an
         aggregate, this may be a measurement from a photo detector
         or a calculation performed on the device by summing up
         all of the related individual physical channels.
         Values include the instantaneous, average, minimum, and
         maximum statistics. If average or minimum or maximum statistics are not
         supported, the target is expected to just supply the
         instant value";
      uses xcvr-ios-xe-oper:statistics-values;
    }
    container input-power {
      description
        "The input optical power of a physical channel in units
         of dBm, which may be associated with individual
         physical channels, or an aggregate of multiple physical
         channels (i.e., for the overall transceiver). For an
         aggregate, this may be a measurement from a photo detector
         or a a calculation performed on the device by summing up
         all of the related individual physical channels.
         Values include the instantaneous, average, minimum, and
         maximum statistics. If average or minimum or  maximum statistics are not
         supported, the target is expected to just supply the
         instant value";
      uses xcvr-ios-xe-oper:statistics-values;
    }
    container laser-bias-current {
      description
        "The current applied by the system to the transmit laser to
         achieve the output power. The current is expressed in mA.
         Values include the instantaneous, average, minimum, and
         maximum statistics. If average or minimum or maximum statistics are not supported,
         the target is expected to just supply the instant value";
      uses xcvr-ios-xe-oper:statistics-values;
    }
    list xcvr-physical-channel {
      key "index";
      description
        "List of physical channel for transceiver";
      uses xcvr-ios-xe-oper:xcvr-physical-channel;
    }
    leaf fault-reason {
      type ios-common-ios-xe-oper:port-err-reason;
      description
        "The error disable on the port is to inform the administrator
         when there is a port problem or error. The port can go into
         error disabled state where the traffic is not allowed in this port.";
    }
    leaf last-event-time {
      type yang:date-and-time;
      description
        "Time of the last transceiver event.
         Events include module insertion or removal or port error";
    }
    leaf ext-id {
      type xcvr-ios-xe-oper:xcvr-ext-identifier;
      description
        "Indicates the extended identifier info";
    }
    leaf ten-gig-comp {
      type xcvr-ios-xe-oper:xcvr-ten-gig-comp-code;
      description
        "Ten gig or forty gig comp code supported by the port";
    }
    leaf ge-comp {
      type xcvr-ios-xe-oper:xcvr-one-gig-comp-code;
      description
        "GE comp code supported by the port";
    }
    leaf link-length {
      type xcvr-ios-xe-oper:xcvr-link-length-value;
      description
        "Transceiver link length";
    }
    leaf tech {
      type xcvr-ios-xe-oper:xcvr-tech-value;
      description
        "Transceiver technology";
    }
    leaf media {
      type xcvr-ios-xe-oper:xcvr-media-value;
      description
        "Transceiver media";
    }
    leaf speed {
      type xcvr-ios-xe-oper:xcvr-speed-value;
      description
        "Transceiver speed";
    }
    leaf enc {
      type xcvr-ios-xe-oper:xcvr-encoding-value;
      description
        "Transceiver encoding";
    }
    container bit-rate {
      description
        "Bit rate of transceiver";
      uses xcvr-ios-xe-oper:idprom-bit-rate;
    }
    container length {
      description
        "Fiber length";
      uses xcvr-ios-xe-oper:fiber-length;
    }
    leaf wavelength {
      type decimal64 {
        fraction-digits 2;
      }
      units "nanometers";
      description
        "Wavelength in nano meters";
    }
    leaf check-code-base {
      type yang:hex-string;
      description
        "Check code base";
    }
    leaf check-code-ext {
      type yang:hex-string;
      description
        "Check code extension";
    }
    leaf options {
      type yang:hex-string;
      description
        "Transceiver options";
    }
    leaf int-clbr {
      type boolean;
      description
        "Indicates whether the transceiver module uses internal calibration
         for its digital diagnostic monitoring values.";
    }
    leaf ext-clbr {
      type boolean;
      description
        "Indicates whether the transceiver module uses external calibration
         for its digital diagnostic monitoring values.";
    }
    leaf rx-power {
      type xcvr-ios-xe-oper:xcvr-rx-pwr-msmt;
      description
        "Specifies the method used for measuring the received optical power
         on the transceiver (e.g., average or optical modulation amplitude).";
    }
    leaf address-change {
      type xcvr-ios-xe-oper:xcvr-addr-change;
      description
        "Indicates whether an I2C address change is required for the transceiver module.";
    }
    container other-info {
      description
        "Other information";
      uses xcvr-ios-xe-oper:add-info;
    }
    leaf raw-data {
      type yang:hex-string;
      description
        "Transceiver raw contents";
    }
    container voltage {
      description
        "The voltage applied by the system to the transceiver
         to achieve the output power. The voltage is expressed in Volts.
         Values include the instantaneous, average, minimum, and
         maximum statistics. If average or minimum or maximum statistics are not supported,
         the target is expected to just supply the instant value";
      uses xcvr-ios-xe-oper:statistics-values;
    }
    container int-temp-thold {
      description
        "The internal-temp  reports internally measured transceiver temperature as a signed
         twos compliment value in increments of 1/256 degrees Celsius.
         Values include the high alarm, low alarm, high warning and
         low warning  as a threshold values.";
      uses xcvr-ios-xe-oper:thrsld-val;
    }
    container cur-thold {
      description
        "The current applied by the system to the transmit laser to
         achieve the output power. The current is expressed in mA.
         Values include the high alarm, low alarm, high warning and
         low warning threshold values.";
      uses xcvr-ios-xe-oper:thrsld-val;
    }
    container op-thold {
      description
        "The output optical power of a physical channel in units
         of dBm, which may be associated with individual
         physical channels, or an aggregate of multiple physical
         channels (i.e., for the overall transceiver). For an
         aggregate, this may be a measurement from a photo detector
         or a calculation performed on the device by summing up
         all of the related individual physical channels.
         Values include the high alarm, low alarm, high warning and
         low warning threshold values.";
      uses xcvr-ios-xe-oper:thrsld-val;
    }
    container ip-thold {
      description
        "The input optical power of a physical channel in units
         of dBm, which may be associated with individual
         physical channels, or an aggregate of multiple physical
         channels (i.e., for the overall transceiver). For an
         aggregate, this may be a measurement from a photo detector
         or a a calculation performed on the device by summing up
         all of the related individual physical channels.
         Values include the  high alarm, low alarm, high warning and
         low warning threshold values.";
      uses xcvr-ios-xe-oper:thrsld-val;
    }
    container volt-thold {
      description
        "The voltage applied by the system to the transceiver
         to achieve the output power. The voltage is expressed in Volts.
         Values include the high alarm, low alarm, high warning and
         low warning threshold values.";
      uses xcvr-ios-xe-oper:thrsld-val;
    }
    leaf diag-mon-impl {
      type xcvr-ios-xe-oper:xcvr-diag-mon-list;
      description
        "Added list of diagnostic monitoring results
         including 'network lane - laser temperature', 'network lane - received power',
         'network lane - laser bias current', 'network lane - laser output power',
         'transceiver power voltage', 'legacy support', 'digital support', 'internal calibration',
         'external calibration', 'received average power' and 'address change'.";
    }
  }

  container transceiver-oper-data {
    config false;
    description
      "Top-level container for transceiver operational data";
    list transceiver {
      key "name";
      description
        "List of transceiver instance, keyed by name";
      uses xcvr-ios-xe-oper:xcvr;
    }
  }
}
