module Cisco-IOS-XE-dp-tcam-usage-oper {
  yang-version 1.1;
  namespace "http://cisco.com/ns/yang/Cisco-IOS-XE-dp-tcam-usage-oper";
  prefix dp-tcam-usage-ios-xe-oper;

  import Cisco-IOS-XE-common-types {
    prefix common-types-ios-xe;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Datapath TCAM classification operational data.
     Copyright (c) 2025-2026 by Cisco Systems, Inc.
     All rights reserved.";

  revision 2026-08-01 {
    description
      "Initial revision";
    reference
      "1.0.0";
    cisco-semver:module-version "1.0.0";
  }

  grouping tcam-usage {
    description
      "The TCAM usage statistics for datapath classification features";
    leaf feature-id {
      type uint32;
      description
        "The internally assigned identifier for the feature";
    }
    leaf client-name {
      type string;
      description
        "The human readable name of the feature";
    }
    leaf vmr-entries-160bit {
      type uint32;
      description
        "The number of 160-bit VMR (Value/Mask/Result) entries allocated for this feature";
    }
    leaf vmr-entries-320bit {
      type uint32;
      description
        "The number of 320-bit VMR (Value/Mask/Result) entries allocated for this feature";
    }
    leaf total-tcam-cell {
      type uint32;
      units "cells";
      description
        "Total TCAM cells used by this feature";
    }
    leaf total-percent {
      type uint8;
      units "percentage";
      description
        "Percentage of total TCAM capacity used by this feature";
    }
  }

  container dp-tcam-usage-oper-data {
    config false;
    description
      "Datapath tcam classification operational data";
    list location {
      key "fru slot bay chassis node";
      description
        "A list of data provider locations";
      uses common-types-ios-xe:extended-location;
      list tcam-usage {
        key "feature-id";
        description
          "The utilization of TCAM resources by various features within the Quantum Flow Processor";
        uses dp-tcam-usage-ios-xe-oper:tcam-usage;
      }
    }
  }
}
