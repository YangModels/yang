module Cisco-IOS-XE-dlr {
  yang-version 1.1;
  namespace "http://cisco.com/ns/yang/Cisco-IOS-XE-dlr";
  prefix dlr;

  import cisco-semver {
    prefix cisco-semver;
  }
  import Cisco-IOS-XE-native {
    prefix ios;
  }

  organization
    "Cisco Systems, Inc.";
  contact
    "Cisco Systems, Inc.
     Customer Service
     Postal: 170 W Tasman Drive
     San Jose, CA 95134
     Tel: +1 1800 553-NETS
     E-mail: cs-yang@cisco.com";
  description
    "Cisco XE DLR (Device Level Ring) model";

  revision 2023-11-01 {
    description
      "Initial revision";
    cisco-semver:module-version "1.0.0";
  }

  grouping config-dlr-grouping {
    container dlr {
      description
        "DLR Configuration";
      list ring {
        description
          "configure dlr ring node as beacon-node or supervisor";
        key "id";
        leaf id {
          description
            "dlr id";
          type enumeration {
            enum 1;
            enum 2;
            enum 3;
          }
        }
        container mode {
          description
            "configure dlr node as beacon-node or supervisor";
          choice mode-choice {
            default "beacon-case";
            case beacon-case {
              leaf beacon-node {
                description
                  "configure dlr beacon-node mode";
                must ". = 'true'" {
                  error-message "mode beacon-node cannot be set to false";
                }
                type boolean;
                default "true";
              }
            }
            case supervisor-case {
              container supervisor {
                description
                  "configure dlr supervisor mode";
                presence "true";
                leaf beacon-interval {
                  description
                    "beacon-interval timer (ms)";
                  type uint32 {
                    range "100..100000";
                  }
                  default "400";
                }
                leaf beacon-timeout {
                  description
                    "beacon-timeout timer (ms)";
                  type uint32 {
                    range "200..500000";
                  }
                  default "1960";
                }
                leaf control-vlan-id {
                  description
                    "vlan id of supervisor";
                  type int32 {
                    range "0..4094";
                  }
                  default "0";
                }
                leaf precedence {
                  description
                    "precedence of supervisor node";
                  type uint8 {
                    range "0..255";
                  }
                  default "0";
                }
              }
            }
          }
        }
        container gateway {
          description
            "configure DLR gateway";
          choice gateway-choice {
            default "gateway-disable-case";
            case gateway-enable-case {
              container enable {
                description
                  "enable gateway functionality";
                presence "true";
                leaf advertise-interval {
                  description
                    "gateway advertise interval";
                  type uint32 {
                    range "1000..100000";
                  }
                  default "2000";
                }
                leaf advertise-timeout {
                  description
                    "gateway advertise timeout";
                  type uint32 {
                    range "2500..500000";
                  }
                  default "5000";
                }
                leaf gateway-precedence {
                  description
                    "gateway precedence";
                  type uint8 {
                    range "0..255";
                  }
                  default "0";
                }
                container learning-update {
                  description
                    "gateway learning update capability (default enable)";
                  choice learning-update-choice {
                    default "enable-case";
                    case enable-case {
                      leaf enable {
                        description
                          "enable gateway learning update capability";
                        must ". = 'true'" {
                          error-message "enable cannot be set to false, use disable instead.";
                        }
                        type boolean;
                        default "true";
                      }
                    }
                    case disable-case {
                      leaf disable {
                        description
                          "disable gateway learning update capability";
                        type empty;
                      }
                    }
                  }
                }
              }
            }
            case gateway-disable-case {
              leaf disable {
                description
                  "disable gateway functionality";
                must ". = 'true'" {
                  error-message "gateway disable cannot be set to false, use gateway enable";
                }
                type boolean;
                default "true";
              }
            }
          }
        }
      }
    }
  }

  grouping config-interface-dlr-grouping {
    container dlr {
      description
        "attach the interface to the DLR ring";
      list ring {
        description
          "attach the interface to the DLR ring";
        key "id";
        leaf id {
          description
            "dlr id";
          type enumeration {
            enum 1;
            enum 2;
            enum 3;
          }
        }
        leaf uplink {
          description
            "attach the interface as uplink port of dlr gateway";
          type empty;
        }
      }
    }
  }

  grouping config-interface-uplink-dlr-grouping {
    container dlr {
      description
        "attach the interface to the DLR ring";
      list ring {
        description
          "attach the interface to the DLR ring";
        key "id";
        leaf id {
          description
            "dlr id";
          must '../uplink';
          type enumeration {
            enum 1;
            enum 2;
            enum 3;
          }
        }
        leaf uplink {
          description
            "attach the interface as uplink port of dlr gateway";
          type empty;
        }
      }
    }
  }

  augment "/ios:native" {
    uses config-dlr-grouping;
  }

  augment "/ios:native/ios:interface/ios:GigabitEthernet" {
    uses config-interface-dlr-grouping;
  }

  augment "/ios:native/ios:interface/ios:FastEthernet" {
    uses config-interface-dlr-grouping;
  }

  augment "/ios:native/ios:interface/ios:Port-channel" {
    uses config-interface-uplink-dlr-grouping;
  }

  augment "/ios:native/ios:interface/ios:PRP-channel" {
    uses config-interface-uplink-dlr-grouping;
  }
}
