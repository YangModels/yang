module Cisco-IOS-XE-dns-defense-oper {
  yang-version 1.1;
  namespace "http://cisco.com/ns/yang/Cisco-IOS-XE-dns-defense-oper";
  prefix dns-defense-ios-xe-oper;

  import Cisco-IOS-XE-common-types {
    prefix common-types-ios-xe;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains collection of YANG
     definitions for DNS Defense operational data.
     Copyright (c) 2025 by Cisco Systems, Inc.
     All rights reserved.";

  revision 2026-02-01 {
    description
      "Initial revision";
    reference
      "1.0.0";
    cisco-semver:module-version "1.0.0";
  }

  typedef dns-defense-dev-reg-resp-code {
    type enumeration {
      enum dns-def-rc-none {
        value 0;
        description
          "Indicates that no response was received";
      }
      enum dns-def-rc-200 {
        value 1;
        description
          "Indicates a successful response HTTP 200";
      }
      enum dns-def-rc-201 {
        value 2;
        description
          "Indicates that the resource was created successfully HTTP 201";
      }
      enum dns-def-rc-400 {
        value 3;
        description
          "Indicates a bad request HTTP 400";
      }
      enum dns-def-rc-401 {
        value 4;
        description
          "Indicates unauthorized access HTTP 401";
      }
      enum dns-def-rc-403 {
        value 5;
        description
          "Indicates forbidden access HTTP 403";
      }
      enum dns-def-rc-404 {
        value 6;
        description
          "Indicates that the resource was not found HTTP 404";
      }
      enum dns-def-rc-409 {
        value 7;
        description
          "Indicates a conflict in the request HTTP 409";
      }
      enum dns-def-rc-429 {
        value 8;
        description
          "Indicates too many requests HTTP 429";
      }
      enum dns-def-rc-500 {
        value 9;
        description
          "Indicates an internal server error HTTP 500";
      }
      enum dns-def-rc-invalid {
        value 10;
        description
          "Indicates an invalid response code";
      }
    }
    description
      "Defines response codes for DNS defense device registration";
  }

  grouping dns-defense-dev-reg-data {
    description
      "Contains data related to DNS defense device registration";
    leaf ni-name {
      type string;
      description
        "Network instance name. If the type is net-inst-default, the name is not meaningful";
    }
    leaf ni-type {
      type common-types-ios-xe:net-inst-type;
      description
        "Network instance type. Differentiates between the default routing instance and VRFs";
    }
    leaf resp-code {
      type dns-defense-ios-xe-oper:dns-defense-dev-reg-resp-code;
      description
        "The response code returned by the cloud provider during registration";
    }
    leaf tag {
      type string;
      description
        "Specifies the tag associated with the network interface, used in API requests.";
    }
    leaf device-id {
      type string;
      description
        "The unique identifier of the network interface which is added in Enhanced DNS header";
    }
    leaf descr {
      type string;
      description
        "Briefly describes the current phase in the device registration request. ";
    }
  }

  grouping dns-defense-info {
    description
      "Contains general information about DNS defense";
    leaf reg-done {
      type uint16;
      description
        "The total number of completed device registrations";
    }
    leaf reg-req {
      type uint16;
      description
        "The total number of requested device registrations";
    }
    leaf dnscrypt {
      type boolean;
      description
        "Indicates whether DNSCrypt is enabled or disabled";
    }
    leaf last-success {
      type yang:date-and-time;
      description
        "The timestamp of the last successful DNSCrypt attempt";
    }
  }

  container dns-defense-oper-data {
    config false;
    description
      "Contains operational data for DNS defense";
    list dns-defense-dev-reg-data {
      key "ni-name";
      description
        "A list of DNS defense device registration data";
      uses dns-defense-ios-xe-oper:dns-defense-dev-reg-data;
    }
    container dns-defense-info {
      presence "dns-defense-info";
      description
        "A container for general DNS defense information";
      uses dns-defense-ios-xe-oper:dns-defense-info;
    }
  }
}
