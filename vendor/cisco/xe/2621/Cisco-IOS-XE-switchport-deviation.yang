module Cisco-IOS-XE-switchport-deviation {
  yang-version 1.1;
  namespace "http://cisco.com/ns/yang/Cisco-IOS-XE-switchport-deviation";
  prefix ios-sw-de;

  import Cisco-IOS-XE-native {
    prefix ios;
  }

  organization
    "Cisco Systems";
  description
    "Cisco XE Native Deviation YANG module for IOS
     Copyright (c) 2024 by Cisco Systems, Inc.
     All rights reserved.";

  revision 2024-07-01 {
    description
      " - Add deviation for switchport
        - Add deviation for switchport on tengig and fortygig";
  }

  deviation "/ios:native/ios:interface/ios:TwoHundredGigE/ios:switchport-conf/ios:switchport" {
    deviate add {
      default "true";
    }
  }

  deviation "/ios:native/ios:interface/ios:FourHundredGigE/ios:switchport-conf/ios:switchport" {
    deviate add {
      default "true";
    }
  }

  deviation "/ios:native/ios:interface/ios:Port-channel/ios:switchport-conf/ios:switchport" {
    deviate add {
      default "true";
    }
  }

  deviation "/ios:native/ios:interface/ios:TwentyFiveGigE/ios:switchport-conf/ios:switchport" {
    deviate add {
      default "true";
    }
  }

  deviation "/ios:native/ios:interface/ios:GigabitEthernet/ios:switchport-conf/ios:switchport" {
    deviate add {
      default "true";
    }
  }

  deviation "/ios:native/ios:interface/ios:HundredGigE/ios:switchport-conf/ios:switchport" {
    deviate add {
      default "true";
    }
  }

  deviation "/ios:native/ios:interface/ios:FiftyGigabitEthernet/ios:switchport-conf/ios:switchport" {
    deviate add {
      default "true";
    }
  }

  deviation "/ios:native/ios:interface/ios:AppGigabitEthernet/ios:switchport-conf/ios:switchport" {
    deviate add {
      default "true";
    }
  }

  deviation "/ios:native/ios:interface/ios:TwoGigabitEthernet/ios:switchport-conf/ios:switchport" {
    deviate add {
      default "true";
    }
  }

  deviation "/ios:native/ios:interface/ios:FiveGigabitEthernet/ios:switchport-conf/ios:switchport" {
    deviate add {
      default "true";
    }
  }

  deviation "/ios:native/ios:interface/ios:TenGigabitEthernet/ios:switchport-conf/ios:switchport" {
    deviate add {
      default "true";
    }
  }

  deviation "/ios:native/ios:interface/ios:FortyGigabitEthernet/ios:switchport-conf/ios:switchport" {
    deviate add {
      default "true";
    }
  }
}
