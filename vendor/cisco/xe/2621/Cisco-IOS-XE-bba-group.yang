module Cisco-IOS-XE-bba-group {
  yang-version 1.1;
  namespace "http://cisco.com/ns/yang/Cisco-IOS-XE-bba-group";
  prefix ios-bba;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Broadband Aggregation (BBA) group Yang model.
     Copyright (c) 2016-2021 by Cisco Systems, Inc.
     All rights reserved.";

  revision 2022-11-01 {
    description
      "- Update yang-version to 1.1";
    cisco-semver:module-version "1.2.0";
  }
  revision 2021-07-01 {
    description
      "
       - Provided pppoe Service profile support";
    cisco-semver:module-version "1.1.0";
  }
  revision 2019-07-01 {
    description
      "Establish semantic version baseline";
    cisco-semver:module-version "1.0.0";
  }
  revision 2017-02-07 {
    description
      "Initial revision";
  }

  grouping config-bba-group-grouping {
    container bba-group {
      description
        "Configure BBA Group";
      list pppoe {
        description
          "PPPoE type";
        key "id";
        leaf id {
          type union {
            type string;
            type enumeration {
              enum global;
            }
          }
        }
        container vendor-tag {
          description
            "PPPoE Vendor Specific Tag";
          container circuit-id {
            description
              "Circuit-Id";
            leaf service {
              description
                "Enable processing";
              type empty;
            }
          }
          container dsl-sync-rate {
            description
              "DSL-Sync-Rate";
            leaf service {
              description
                "Enable processing";
              type empty;
            }
          }
          container remote-id {
            description
              "Remote-Id";
            leaf service {
              description
                "Enable processing";
              type empty;
            }
          }
          leaf strip {
            description
              "Strip all vendor tags";
            type empty;
          }
        }
        leaf virtual-template {
          description
            "BBA virtual template command";
          type uint16 {
            range "1..4095";
          }
        }
        container service {
          description
            "Services to be associated with this group";
          leaf profile {
            description
              "Subscriber profile to be associated with this group";
            type string {
              length "1..230";
            }
          }
        }
      }
    }
  }

  augment "/ios:native" {
    uses config-bba-group-grouping;
  }
}
