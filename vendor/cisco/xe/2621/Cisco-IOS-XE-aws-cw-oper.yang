module Cisco-IOS-XE-aws-cw-oper {
  yang-version 1.1;
  namespace "http://cisco.com/ns/yang/Cisco-IOS-XE-aws-cw-oper";
  prefix aws-cw-oper;

  import Cisco-IOS-XE-aws-common-oper {
    prefix aws-common-oper;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for AWS Cloudwatch operational data.
     Copyright (c) 2023-2026 by Cisco Systems, Inc.
     All rights reserved.";

  revision 2026-08-01 {
    description
      "Improved YANG descriptions for AWS CloudWatch operational data.";
    reference
      "1.0.1";
    cisco-semver:module-version "1.0.1";
  }
  revision 2025-07-01 {
    description
      "Initial revision";
    reference
      "1.0.0";
    cisco-semver:module-version "1.0.0";
  }

  grouping aws-cw-log-oper {
    description
      "AWS cloudwatch log data";
    leaf cw-log-file-path {
      type string;
      description
        "Specifies the file system path to the log file monitored by AWS CloudWatch.";
    }
    leaf cw-log-group-name {
      type string;
      description
        "Name of the AWS CloudWatch log group to which the log data is sent.";
    }
    leaf cw-log-stream-name {
      type string;
      description
        "Name of the AWS CloudWatch log stream within the specified log group.";
    }
  }

  grouping cw-service-oper {
    description
      "AWS Cloudwatch service information";
    leaf cw-profile-name {
      type string;
      description
        "Name of the AWS CloudWatch profile.";
    }
    leaf cw-pid {
      type uint32;
      description
        "Cloudwatch agent process ID";
    }
    leaf cw-state {
      type aws-common-oper:aws-agent-state;
      description
        "Current operational state of the AWS CloudWatch agent.";
    }
    leaf cw-vrf {
      type aws-common-oper:aws-vrf-name;
      description
        "Name of the VRF (Virtual Routing and Forwarding) instance used for AWS CloudWatch communication.";
    }
    leaf cw-trace {
      type aws-common-oper:aws-agent-trace;
      description
        "Cloudwatch trace level";
    }
    leaf cw-region {
      type string;
      description
        "Cloudwatch region";
    }
    leaf cw-profile-descr {
      type string;
      description
        "Cloudwatch profile description";
    }
    container cw-proxy {
      description
        "Cloudwatch proxy settings";
      uses aws-common-oper:aws-proxy-config;
    }
    leaf cw-shutdown {
      type boolean;
      description
        "Cloudwatch shutdown variable";
    }
    list aws-oper-log-cw {
      key "cw-log-stream-name";
      description
        "AWS cloudwatch log data";
      uses aws-cw-oper:aws-cw-log-oper;
    }
  }

  container aws-cw-oper-data {
    config false;
    description
      "Container for operational data related to AWS CloudWatch integration on the device.";
    list aws-oper-cw {
      key "cw-profile-name";
      description
        "Operational data for each AWS CloudWatch profile configured on the device.";
      uses aws-cw-oper:cw-service-oper;
    }
  }
}
