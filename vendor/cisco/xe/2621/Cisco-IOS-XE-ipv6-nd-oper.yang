module Cisco-IOS-XE-ipv6-nd-oper {
  yang-version 1.1;
  namespace "http://cisco.com/ns/yang/Cisco-IOS-XE-ipv6-nd-oper";
  prefix ipv6-nd-ios-xe-oper;

  import Cisco-IOS-XE-common-types {
    prefix common-types-ios-xe;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for IPv6 ND operational data. Compared to other model
     Cisco-IOS-XE-ipv6-oper, this model supports high scale queries
     and on-change telemetry subscriptions.
     Copyright (c) 2025-2026 by Cisco Systems, Inc.
     All rights reserved.";

  revision 2026-08-01 {
    description
      "Updated descriptions of several model elements to clarify their meaning and purpose.";
    reference
      "1.0.1";
    cisco-semver:module-version "1.0.1";
  }
  revision 2025-07-01 {
    description
      "Initial revision";
    reference
      "1.0.0";
    cisco-semver:module-version "1.0.0";
  }

  typedef ipv6-nd-en-state {
    type enumeration {
      enum v6-nd-st-incomplete {
        value 0;
        description
          "Neighbor entry is unresolved. The device
           is performing IPv6 address resolution by
           sending Neighbor Solicitation messages and
           is waiting for a Neighbor Advertisement
           containing the neighbor's MAC address.";
      }
      enum v6-nd-st-reachable {
        value 1;
        description
          "Neighbor is confirmed active based on recent protocol
           communication. The stored link-layer address is valid,
           and packets can be forwarded without sending additional
           Neighbor Solicitation messages.";
      }
      enum v6-nd-st-stale {
        value 2;
        description
          "The neighbor has not been recently verified
           as active. The stored link-layer address may
           still be used, but confirmation is delayed
           until new traffic is sent.";
      }
      enum v6-nd-st-glean {
        value 3;
        description
          "Received neighbor messages containing link layer information.
           Based on this information, entry is created. In this case, there
           is no initiation of active neighbor resolution from current node.";
      }
      enum v6-nd-st-delay {
        value 4;
        description
          "The neighbor is no longer known to be reachable, and traffic
           has recently been sent to the neighbor. Rather than probe the
           neighbor immediately, however, delay sending probes for a short
           while in order to give upper layer protocols a chance to provide
           reachability confirmation.";
      }
      enum v6-nd-st-probe {
        value 5;
        description
          "Neighbor reachability is unconfirmed. The device actively sends
           unicast Neighbor Solicitation messages to the neighbor to verify
           whether it is still reachable.";
      }
    }
    description
      "Defines the operational state of an
       IPv6 Neighbor Discovery (ND) entry,
       indicating the progress of address
       resolution and the reachability
       status of the neighboring device.";
  }

  typedef ipv6-nd-mode {
    type enumeration {
      enum v6-nd-mode-static {
        value 0;
        description
          "Statically configured neighbor entry. Manually
           created by an operator and remains unchanged
           unless explicitly modified or deleted. It is
           not updated through IPv6 Neighbor Discovery
           learning.";
      }
      enum v6-nd-mode-dyn {
        value 1;
        description
          "Neighbor entry learned automatically through IPv6
           Neighbor Discovery protocol exchanges (ICMPv6).
           The entry is updated based on protocol activity
           and may be removed after inactivity.";
      }
      enum v6-nd-mode-other {
        value 2;
        description
          "Neighbor entry created through internal or implementation-
           specific mechanisms that are not strictly classified
           as static configuration or dynamic ND learning.";
      }
    }
    description
      "Defines how the IPv6 Neighbor Discovery entry
       was created, indicating whether it was statically configured,
       dynamically learned through ND, or generated by other
       internal mechanisms.";
  }

  grouping ipv6-nd-entry-key {
    description
      "Key fields that uniquely identify an IPv6
       Neighbor Discovery (ND) cache entry in the
       operational state.";
    leaf v6addr {
      type inet:ipv6-address;
      description
        "IPv6 address of the neighbor. This is
         the Layer 3 address for which the
         ND cache entry is maintained.";
    }
    leaf if-name {
      type string;
      description
        "Name of the interface on which this
         neighbor entry is learned and maintained. The
         same IPv6 address may appear on different
         interfaces as separate ND entries.";
    }
  }

  grouping ipv6-nd-entry {
    description
      "Operational attributes of a single IPv6
       ND cache entry, including the resolved Layer
       2 address, protocol state,and related metadata.";
    leaf mac-addr {
      type yang:mac-address;
      description
        "Layer-2 MAC address associated with the
         IPv6 neighbor entry, used to map the neighbor's IPv6
         address to its corresponding hardware address.";
    }
    leaf mode {
      type ipv6-nd-ios-xe-oper:ipv6-nd-mode;
      description
        "Operational mode of the ND cache
         entry, indicating whether it was learned dynamically,
         configured statically, or created through another
         mechanism.";
    }
    leaf state {
      type ipv6-nd-ios-xe-oper:ipv6-nd-en-state;
      description
        "Current IPv6 Neighbor Discovery state of
         this entry, indicating the reachability or address
         resolution status of the neighboring device.";
    }
    leaf update-time {
      type yang:date-and-time;
      description
        "Time when this IPv6 Neighbor Discovery
         entry was last updated or refreshed based on
         neighbor communication or protocol activity.";
    }
    leaf is-router {
      type boolean;
      description
        "Indicates whether the neighboring device is acting
         as an IPv6 router (true) or a host device (false).";
    }
  }

  grouping ni-ipv6-nd {
    description
      "Represents the IPv6 Neighbor Discovery table
       associated with a specific network instance, containing
       all neighbor cache entries maintained within
       that instance.";
    leaf ni-name {
      type string;
      description
        "Name of the Network Instance (VRF) that owns
         this IPv6 Neighbor Discovery table, identifying
         the routing domain whose neighbor entries
         are represented.";
    }
    leaf ni-type {
      type common-types-ios-xe:net-inst-type;
      description
        "Type of the network instance, such as
         default or VRF, to which the IPv6
         Neighbor Discovery table entries
         belong.";
    }
    list ipv6-nd-entry {
      key "v6addr if-name";
      description
        "List of IPv6 Neighbor Discovery cache entries
         within this Network Instance. Each entry represents
         a discovered neighbor, keyed by its IPv6 address
         and interface name, with operational state and
         reachability attributes.";
      uses ipv6-nd-ios-xe-oper:ipv6-nd-entry-key;
      uses ipv6-nd-ios-xe-oper:ipv6-nd-entry;
    }
  }

  container ipv6-nd-oper-data {
    config false;
    description
      "This module contains a collection of YANG definitions for
       monitoring the operation of IOS-XE IPv6 Neighbour.
       Copyright (c) 2025-2026 by Cisco Systems, Inc.
       All rights reserved.";
    list ni-ipv6-nd {
      key "ni-name";
      description
        "List of IPv6 Neighbor Discovery tables belong
         to specific network instances (VRFs). Each entry
         represents the ND cache for that routing domain,
         identified by instance type and name.";
      uses ipv6-nd-ios-xe-oper:ni-ipv6-nd;
    }
  }
}
