module Cisco-IOS-XE-wireless-rrm-cfg {
  yang-version 1.1;
  namespace "http://cisco.com/ns/yang/Cisco-IOS-XE-wireless-rrm-cfg";
  prefix wireless-rrm-cfg;

  import Cisco-IOS-XE-wireless-apf-cfg {
    prefix wireless-apf-cfg;
  }
  import Cisco-IOS-XE-wireless-enum-types {
    prefix wireless-enum-types;
  }
  import Cisco-IOS-XE-wireless-types {
    prefix wireless-types;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Model for managing rrm configurations
     Copyright (c) 2016-2024, 2026 by Cisco Systems, Inc.
     All rights reserved.";

  revision 2026-08-01 {
    description
      "Deprecated chan-width-cap leaf and disallowed its modification";
    reference
      "12.0.0";
    cisco-semver:module-version "12.0.0";
  }
  revision 2025-03-01 {
    description
      "- Added a range validation for automatic configuration in the default radio configuration";
    reference
      "11.0.0";
    cisco-semver:module-version "11.0.0";
  }
  revision 2024-07-01 {
    description
      "- Updated description of leaf channel width,
       - Updated constraint for leaf DCA long interval";
    reference
      "10.0.0";
    cisco-semver:module-version "10.0.0";
  }
  revision 2024-03-01 {
    description
      "Added leaf for optimised roaming hysteresis";
    reference
      "9.2.0";
    cisco-semver:module-version "9.2.0";
  }
  revision 2022-11-01 {
    description
      "Update yang-version to 1.1
       -  Added config knob to disable aggressive DCA run on WLC startup";
    reference
      "9.1.0";
    cisco-semver:module-version "9.1.0";
  }
  revision 2021-11-01 {
    description
      "- Added constraint for DCA long interval";
    reference
      "9.0.0";
    cisco-semver:module-version "9.0.0";
  }
  revision 2021-07-01 {
    description
      "- Added constraints in DCA mode, Tx power mode and DCA min metric RSSI configuration for 6 GHz band";
    reference
      "8.0.0";
    cisco-semver:module-version "8.0.0";
  }
  revision 2021-03-01 {
    description
      "Deprecated DCA channel width configuration,
       use channel width present in Cisco-IOS-XE-wireless-rf-cfg model";
    reference
      "7.1.0";
    cisco-semver:module-version "7.1.0";
  }
  revision 2020-07-01 {
    description
      "Added obsolete status to unused leaf nodes in CHD feature and moved to Cisco-IOS-XE-wireless-rf-cfg model";
    reference
      "7.0.0";
    cisco-semver:module-version "7.0.0";
  }
  revision 2019-11-01 {
    description
      "Added bss-color-mode for selecting between automatic and static BSS coloring";
    reference
      "6.1.0";
    cisco-semver:module-version "6.1.0";
  }
  revision 2019-06-02 {
    description
      "- Updated constraint for dca-mode, txpower-mode and grouping-mode.
       - Added semantic version
       - Update the default values as per WLC configuration best practice";
    reference
      "6.0.0";
    cisco-semver:module-version "6.0.0";
  }
  revision 2019-01-02 {
    description
      "- Leaf addition and removal of unwanted leaf nodes. Updating band enum type
       - Removal of unused leaves
       - Cleaned up spelling errors in descriptions
       - Updated descriptions with the units and enum strings wherever required
       - Converted data types of few leaves and fixed revision
       - Modified description of leaves dca-thresh and data-rate-thresh.";
    reference
      "5.0.0";
    cisco-semver:module-version "5.0.0";
  }
  revision 2018-08-09 {
    description
      "Added range set and must constraints for Radio band";
    reference
      "4.0.0";
    cisco-semver:module-version "4.0.0";
  }
  revision 2018-03-21 {
    description
      "Leaf removal";
    reference
      "3.0.0";
    cisco-semver:module-version "3.0.0";
  }
  revision 2018-01-24 {
    description
      "The first generally available version";
    reference
      "2.0.0";
    cisco-semver:module-version "2.0.0";
  }
  revision 2017-05-05 {
    description
      "Initial revision";
    reference
      "1.0.0";
    cisco-semver:module-version "1.0.0";
  }

  grouping rrm-rrm-config {
    description
      "General configurations for RRM";
    leaf dca-mode {
      type wireless-enum-types:rrm-control-mode;
      must "(../dca-mode = 'rrm-automatic' or
            (../dca-mode = 'rrm-run-once' and ../../band != 'dot11-6-ghz-band') or
             ../dca-mode = 'rrm-static')" {
        error-message
          "Dynamic channel assignment mode must be one of the following :
           1. rrm-automatic (allowed for 2.4/5/6 GHz radio band)
           2. rrm-run-once (allowed for 2.4/5 GHz radio band)
           3. rrm-static (allowed for 2.4/5/6 GHz radio band)";
        error-app-tag "must-violation";
      }
      default "rrm-automatic";
      description
        "Dynamic channel assignment(DCA) has three modes. When the mode is auto, the channel assignment will be periodically updated for all Access Points that permit this operation. When the DCA is run once, channel assignments are updated based on the UPDATE_CMD received from the management. When the DCA is static, no dynamic channel assignments occurs and value are set to their global default. Default is auto.
         Possible values are:
         rrm-automatic = Automatic Channel selection
         rrm-run-once = Channel selection is done only once
         rrm-static = Static channel selection";
    }
    leaf dca-update-interval-sec {
      type uint32;
      units "seconds";
      default "600";
      description
        "When Channel dynamic algorithm is running, this interval (in seconds) specifies how often Channel assignment updates are attempted on an Access Point. NOTE: hysteresis is built into the algorithms so we will not have unproductive changes occuring. Default value is 600 seconds";
    }
    leaf dca-contribution-noise {
      type boolean;
      default "true";
      description
        "State of noise on the controller.
         True - detection is enabled
         False - detection is disabled";
    }
    leaf dca-contribution-interference {
      type boolean;
      default "true";
      description
        "State of interference on the controller.
         True - detection is enabled
         False - detection is disabled.";
    }
    leaf dca-contribution-load {
      type boolean;
      default "false";
      description
        "State of load on the controller.
         True - detection is enabled
         False - detection is disabled.";
    }
    leaf dca-contribution-device {
      type boolean;
      default "false";
      description
        "State of device detection on the controller.
         True - detection is enabled
         False - detection is disabled.";
    }
    leaf txpower-mode {
      type wireless-enum-types:rrm-control-mode;
      must "(../txpower-mode = 'rrm-automatic' or
            (../txpower-mode = 'rrm-run-once' and ../../band != 'dot11-6-ghz-band') or
             ../txpower-mode = 'rrm-static')" {
        error-message
          "Transmit power mode must be one of the following :
           1. rrm-automatic (allowed for 2.4/5/6 GHz radio band)
           2. rrm-run-once (allowed for 2.4/5 GHz radio band)
           3. rrm-static (allowed for 2.4/5/6 GHz radio band)";
        error-app-tag "must-violation";
      }
      default "rrm-automatic";
      description
        "Dynamic transmit power (DTP) has three modes. When the mode is auto, the transmit power of each Access Point will be periodically updated for all Access Points that permit this operation. When the DTP is run once,transmit power update will occur based on the UPDATE_CMD received from the management. When the DTP is static, no dynamic transmit power updates occur and their global defaults are used. Default is auto.
         Possible values are:
         rrm-automatic = Automatic power selection
         rrm-run-once = Power selection is done only once
         rrm-static = Static power selection";
    }
    leaf monitor-channel-mode {
      type wireless-enum-types:channel-monitor-mode;
      default "rrm-channels-country";
      description
        "Channels on which the switch monitors noise, interference and rogues.
         Possible values:
         rrm-channels-country = Monitoring on channels that are supported by the country of operation,
         rrm-channels-all = Monitoring on all channels,
         rrm-channels-dca = Monitoring on those channels that are used by automatic channel assignment";
    }
    leaf monitor-rssi-normalization {
      type boolean;
      default "true";
      description
        "802.11 configured RRM Neighbor Discovery RSSI Normalization";
    }
    leaf channel-monitor-status {
      type boolean;
      default "true";
      description
        "Neighbor monitoring mode.
         True - monitoring is disabled
         False - monitoring is enabled";
    }
    leaf monitor-load-interval {
      type uint32 {
        range "60 .. 3600";
      }
      units "seconds";
      default "60";
      description
        "Interval(in seconds) specifying how often we get new load measurements at each Access Point. Default is 300 seconds";
    }
    leaf monitor-coverage-interval {
      type uint32 {
        range "60 .. 3600";
      }
      units "seconds";
      default "180";
      description
        "Interval(in seconds) specifying how often we get new coverage measurements at each Access Point. Default is 300 seconds";
    }
    leaf sys-log-load {
      type boolean;
      default "false";
      description
        "Logging mode for load profile.
         True - logging is enabled
         False - monitoring is disabled";
    }
    leaf sys-log-noise {
      type boolean;
      default "false";
      description
        "Logging mode for noise profile.
         True - logging is enabled
         False - monitoring is disabled";
    }
    leaf sys-log-foreign {
      type boolean;
      default "false";
      description
        "Logging mode for foreign profile.
         True - logging is enabled
         False - monitoring is disabled";
    }
    leaf sys-log-tx-power {
      type boolean;
      default "false";
      description
        "Logging mode for transmit power change.
         True - logging is enabled
         False - monitoring is disabled";
    }
    leaf sys-log-coverage {
      type boolean;
      default "false";
      description
        "Logging mode for coverage profile.
         True - logging is enabled
         False - monitoring is disabled";
    }
    leaf sys-log-performance {
      type boolean;
      default "false";
      description
        "Logging mode for performance profile.
         True - logging is enabled
         False - monitoring is disabled";
    }
    leaf sys-log-channel {
      type boolean;
      default "false";
      description
        "Logging mode for dynamic channel change.
         True - logging is enabled
         False - monitoring is disabled";
    }
    leaf ndp-type-data {
      type wireless-enum-types:ndp-type;
      default "ndp-type-transparent";
      description
        "Mode of NDP.
         Possible values:
         transparent = NDP mode is transparent
         protected = NDP mode is protected";
    }
    leaf roaming-en {
      type boolean;
      default "false";
      description
        "Optimized roaming mode.
         True - optimized roaming is enabled
         False - optimized roaming is disabled";
    }
    leaf data-rate-threshold {
      type wireless-enum-types:datarate;
      units "dBm";
      default "optroam-rate-0";
      description
        "This attribute indicates configured data rate threshold for 802.11 Optimized Roaming
         optroam-rate-1-m = Data rate threshold will be set to 1 Mbps.
         optroam-rate-2-m = Data rate threshold will be set to 2 Mbps.
         optroam-rate-5-5-m = Data rate threshold will be set to 5 Mbps.
         optroam-rate-6-m = Data rate threshold will be set to 6 Mbps.
         optroam-rate-9-m = Data rate threshold will be set to 9 Mbps.
         optroam-rate-11-m = Data rate threshold will be set to 11 Mbps.
         optroam-rate-12-m = Data rate threshold will be set to 12 Mbps.
         optroam-rate-18-m = Data rate threshold will be set to 18 Mbps.
         optroam-rate-24-m = Data rate threshold will be set to 24 Mbps.
         optroam-rate-36-m = Data rate threshold will be set to 36 Mbps.
         optroam-rate-48-m = Data rate threshold will be set to 48 Mbps.
         optroam-rate-54-m = Data rate threshold will be set to 54 Mbps.
         optroam-rate-0 = Data rate threshold will be set to 0 Mbps.";
    }
    leaf roaming-hysteresis {
      type int32 {
        range "0..10";
      }
      units "dBm";
      default "6";
      description
        "Hysteresis for optimized roaming. Recommended range is 3 dBm to 6 dBm.";
    }
    leaf rrm-meas-req-state {
      type boolean;
      default "false";
      description
        "Support of 802.11 CCX Client Location Measurements";
    }
    leaf rrm-meas-req-interval {
      type uint32 {
        range "10 .. 32400";
      }
      units "seconds";
      default "60";
      description
        "802.11 CCX Client Location Measurements interval";
    }
    leaf dca-long-interval {
      type uint8;
      units "hours";
      must '(/wireless-apf-cfg:apf-cfg-data/wireless-apf-cfg:apf/wireless-apf-cfg:fra-interval >= current())' {
        error-message "DCA interval must be less than FRA interval";
        error-app-tag "must-violation";
      }
      default "0";
      description
        "DCA interval value in hours. Possible values are 1,2,3,4,6,8,12 and 24 hours, 0 = 10 minutes (default).";
    }
    leaf dca-anchor-hour {
      type uint8 {
        range "0 .. 23";
      }
      default "0";
      description
        "Anchor time for DCA, hour of the day. Valid value should be in the range 0-23";
    }
    leaf dca-threshold {
      type wireless-enum-types:dca-threshold;
      default "dca-threshold-medium";
      description
        "Dynamic Channel Assignment sensitivity level to change in the environment
         dca-threshold-low = Low DCA sensitivity level.
         dca-threshold-medium = Medium DCA sensitivity level.
         dca-threshold-high = High DCA sensitivity level";
    }
    leaf coverage-global-enable {
      type boolean;
      default "true";
      description
        "State of CHD (Coverage Hole Detection) on the controller.
         True - detection is enabled
         False - detection is disabled";
    }
    leaf coverage-data-failed-packet-count {
      type uint8 {
        range "1 .. 255";
      }
      default "50";
      description
        "Minimum threshold on the Data packet count required to trigger the CHD algorithm on the controller.";
    }
    leaf coverage-data-failed-packet-percentage {
      type uint8 {
        range "1 .. 100";
      }
      default "50";
      description
        "Threshold on the percent of Data packets dropped, that is required to trigger the CHD algorithm on the controller.";
    }
    leaf coverage-data-packet-rssi-threshold {
      type int8 {
        range "-90 .. -60";
      }
      units "dBm";
      default "-80";
      status obsolete;
      description
        "RSSI threshold value for Data packets,
         that is required to trigger the CHD algorithm on the controller.
         Use coverage-data-packet-rssi-threshold, present in container rf-profile-default-entries,
         part of Cisco-IOS-XE-wireless-rf-cfg model";
    }
    leaf coverage-voice-failed-packet-count {
      type uint8 {
        range "1 .. 255";
      }
      default "100";
      description
        "Minimum threshold on the Voice packet count required to trigger the CHD algorithm on the controller.";
    }
    leaf coverage-voice-failed-packet-percentage {
      type uint8 {
        range "1 .. 100";
      }
      default "50";
      description
        "Threshold on the percent of Voice packets dropped, that is required to trigger the CHD algorithm on the controller.";
    }
    leaf coverage-voice-packet-rssi-threshold {
      type int8 {
        range "-90 .. -60";
      }
      units "dBm";
      default "-80";
      status obsolete;
      description
        "RSSI threshold value for Voice packets,
         that is required to trigger the CHD algorithm on the controller.
         Use coverage-voice-packet-rssi-threshold, present in container rf-profile-default-entries,
         part of Cisco-IOS-XE-wireless-rf-cfg model";
    }
    leaf dca-chan-width {
      type wireless-enum-types:dca-chan-width;
      default "dca-chan-width-best";
      status deprecated;
      description
        "DCA channel width selection.
         Possible values:
         dca-chan-width-20mhz = Channel width will be set to 20Mhz
         dca-chan-width-40mhz = Channel width will be set to 40Mhz
         dca-chan-width-80mhz = Channel width will be set to 80Mhz
         dca-chan-width-best = Best channel width will be selected by DCA algorithm
         dca-chan-width-160mhz = Channel width will be set to 160Mhz
         Use rf-dca-chan-width, present in container rf-profile-default-entries,
         part of Cisco-IOS-XE-wireless-rf-cfg model";
    }
    leaf reporting-interval {
      type uint32 {
        range "60 .. 3600";
      }
      units "seconds";
      default "180";
      description
        "Interval(in seconds) between each measurements report.";
    }
    leaf notification-tx-power-enable {
      type boolean;
      default "false";
      description
        "Transmission power change notification mode.
         True - notification is enabled
         False - notification is disabled";
    }
    leaf notification-min-tx-power-threshold {
      type uint32 {
        range "3 .. 30";
      }
      units "dBm";
      default "6";
      description
        "Minimum threshold that the TPC will assign to each radio";
    }
    leaf notification-max-tx-power-threshold {
      type uint32 {
        range "3 .. 30";
      }
      units "dBm";
      default "6";
      description
        "Maximum threshold that the TPC will assign to each radio";
    }
    leaf notification-channel-enable {
      type boolean;
      default "false";
      description
        "Channel change notification mode.
         True - notification will be sent
         False - notification will not be sent";
    }
    leaf notification-channel-threshold {
      type uint32 {
        range "1 .. 1000";
      }
      default "1";
      description
        "Number of channel changes after which the channel change notification is sent out.";
    }
    leaf dpc-min-tx-power-limit {
      type int32 {
        range "-10 .. 30";
      }
      units "dBm";
      default "-10";
      description
        "Lower limit of transmit power in dBm. The value should be less than equal to value of tx-power-max.";
    }
    leaf dpc-max-tx-power-limit {
      type int32 {
        range "-10 .. 30";
      }
      units "dBm";
      default "30";
      description
        "Upper limit of transmit power in dBm. The value should be greater than equal to value of tx-power-min.";
    }
    leaf dca-min-metric-rssi {
      type int32 {
        range "-100 .. -60";
      }
      units "dBm";
      must "(../../band != 'dot11-6-ghz-band')" {
        error-message "Not configurable on 6 Ghz radio band ";
        error-app-tag "must-violation";
      }
      default "-95";
      description
        "Minimum RSSI energy metric required for DCA to change the channel";
    }
    leaf chan-width-cap {
      type wireless-types:dca-ewlc-chan-width-cap;
      must "(. = 'dca-ewlc-chan-width-cap-40-mhz')" {
        error-message "Only 40 MHz channel width is allowed for global width max configuration";
        error-app-tag "must-violation";
      }
      default "dca-ewlc-chan-width-cap-40-mhz";
      description
        "Deprecated in favor of channel-width-min and channel-width-max for per-RF-profile configuration. This leaf specified the global Dynamic Channel Assignment (DCA) channel width cap and is now restricted to 40 MHz";
    }
    leaf measurement-interval {
      type uint32 {
        range "60 .. 3600";
      }
      units "seconds";
      default "180";
      description
        "Interval (in seconds) specifying how often we get new signal strength, noise and interference measurements at each Access Point.";
    }
    leaf neighbor-timeout-factor {
      type uint8 {
        range "5 .. 60";
      }
      units "seconds";
      default "20";
      description
        "Factor specifying how long a neighbor expires if not receiving its neighbor packets.";
    }
    leaf bss-color-mode {
      type wireless-enum-types:rrm-control-mode;
      must "((../bss-color-mode = 'rrm-automatic' and ../dca-mode = 'rrm-automatic') or
             ../bss-color-mode = 'rrm-static')" {
        error-message
          "BSS color mode must be one of the following:
           1. rrm-automatic, for which dynamic channel assignment (DCA) mode must also be rrm-automatic
           2. rrm-static";
        error-app-tag "must-violation";
      }
      default "rrm-automatic";
      description
        "BSS Color Optimization (BCO) has two modes. When the mode is auto, the BSS color will be periodically updated for all Access Points that permit this operation. When the BCO is static, no dynamic BSS color selections occur and BSS color must be manually configured.";
    }
    leaf dca-aggr-startup {
      type boolean;
      default "true";
      description
        "Aggressive DCA algorithm is run on WLC startup when enabled";
    }
  }

  grouping rrm-defaultlradcfg-config {
    description
      "Default configuration related to radios";
    leaf bytes-per-sec {
      type uint32 {
        range "1000 .. 10000000";
      }
      units "bytes per sec";
      default "1000000";
      description
        "802.11A throughput threshold between 1000 and 1000000";
    }
    leaf exception-level {
      type uint16 {
        range "0 .. 100";
      }
      default "25";
      status obsolete;
      description
        "Minimum percentage of clients in the coverage hole region of the AP,
         required to trigger a coverage hole exception.
         Use exception-level, present in container rf-profile-default-entries,
         part of Cisco-IOS-XE-wireless-rf-cfg model";
    }
    leaf min-num-clients {
      type int32 {
        range "1 .. 200";
      }
      default "3";
      status obsolete;
      description
        "Minimum number of clients required to trigger coverage hole.
         Use min-num-clients, present in container rf-profile-default-entries,
         part of Cisco-IOS-XE-wireless-rf-cfg model";
    }
    leaf automatic-cfg {
      type uint8 {
        range "1..2";
      }
      default "1";
      description
        "Performance profile Mode.
         True - Performance profile is enabled
         False - Performance profile is disabled";
    }
  }

  grouping rrm-cfg {
    description
      "All the configurations related to radio resource management";
    leaf band {
      type wireless-types:enm-ewlc-dot11-radio-band;
      description
        "Key to the st_rrm table, indicates the band of the configurations.";
    }
    container rrm {
      description
        "All the basic rrm algorithms configurations.";
      uses wireless-rrm-cfg:rrm-rrm-config;
    }
    container default-radio-cfg {
      description
        "All the radio related configuration";
      uses wireless-rrm-cfg:rrm-defaultlradcfg-config;
    }
    container rrm-static-member-add-delete-entries {
      description
        "Static member configuration";
      list rrm-static-member-add-delete-entry {
        key "ip";
        description
          "A list of static member configurations";
        uses wireless-rrm-cfg:rrm-staticmember-add-delete;
      }
    }
  }

  grouping rrm-staticmember-add-delete {
    description
      "Details about the static member configured";
    leaf ip {
      type inet:ip-address;
      description
        "IP address of the static member configured";
    }
    leaf name {
      type string;
      description
        "Name of the static member configured";
    }
  }

  grouping rrm-mgr-rrm-config {
    description
      "All the rrm grouping algorithm related configuration";
    leaf grouping-mode {
      type wireless-enum-types:rrm-control-mode;
      must "(../grouping-mode = 'rrm-automatic' or
             ../grouping-mode = 'rrm-static' or
             ../grouping-mode = 'rrm-leader')" {
        error-message
          "RF grouping mode must be one of the following:
           1. rrm-automatic
           2. rrm-static
           3. rrm-leader";
        error-app-tag "must-violation";
      }
      default "rrm-automatic";
      description
        "RF grouping has three modes. When RF grouping is set to AUTO the controller can be either in Auto leader or Auto member and when the mode is set to static the controller can be either in static member or static leader.
         Possible values:
         rrm-automatic = RF leader selected automatically
         rrm-static = RF leader selection is stopped
         rrm-leader = RF leader selection is static, and set this controller as group leader";
    }
    leaf grouping-update-interval-sec {
      type uint32;
      units "seconds";
      default "600";
      description
        "The period used by the grouping algorithm. The grouping algorithm runs when the group contents changes and automatic grouping is enabled. The system administrator can start grouping on demand.";
    }
  }

  grouping rrm-mgr {
    description
      "RRM Manager configuration";
    leaf band {
      type wireless-types:enm-ewlc-dot11-radio-band;
      description
        "Key to the st_rrm_mgr table ,indicates the band of the configurations.
         Possible values:
         ewlc-dot11-2-dot-4-ghz-band = 802.11bg
         ewlc-dot11-5-ghz-band = 802.11a";
    }
    container rrm {
      description
        "RRM Grouping Attributes";
      uses wireless-rrm-cfg:rrm-mgr-rrm-config;
    }
  }

  container rrm-cfg-data {
    description
      "This yang file contains all the fields related rrm feature";
    container rrms {
      description
        "RRM configuration";
      list rrm {
        key "band";
        description
          "All the rrm grouping algorithm related configurations";
        uses wireless-rrm-cfg:rrm-cfg;
      }
    }
    container rrm-mgr-cfg-entries {
      description
        "Configuration related to RRM Algorithms";
      list rrm-mgr-cfg-entry {
        key "band";
        description
          "A list of entries related to RRM Algorithms";
        uses wireless-rrm-cfg:rrm-mgr;
      }
    }
  }
}
