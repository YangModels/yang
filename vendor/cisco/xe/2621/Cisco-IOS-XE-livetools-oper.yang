module Cisco-IOS-XE-livetools-oper {
  yang-version 1.1;
  namespace "http://cisco.com/ns/yang/Cisco-IOS-XE-livetools-oper";
  prefix livetools-ios-xe-oper;

  import Cisco-IOS-XE-common-types {
    prefix common-types-ios-xe;
  }
  import Cisco-IOS-XE-livetools-common-types {
    prefix livetools-common-types-ios-xe;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for live tools operational data.
     Copyright (c) 2024-2026 by Cisco Systems, Inc.
     All rights reserved.";

  revision 2026-08-01 {
    description
      "Updated descriptions of several model elements to clarify their meaning and purpose.";
    reference
      "2.2.0";
    cisco-semver:module-version "2.2.0";
  }
  revision 2025-07-01 {
    description
      "- Added IP ping egress and next-hop support";
    reference
      "2.1.0";
    cisco-semver:module-version "2.1.0";
  }
  revision 2025-03-01 {
    description
      "- Added DNS lookup support
       - Added enums un-sent, timeout for echo status
       - Added enums ping-failed for ip ping error
       - Obsolete 'latency' leaf
       - Added 'latency-msec' leaf in milliseconds.
       - Adding MTR error codes for memory and address case";
    reference
      "2.0.0";
    cisco-semver:module-version "2.0.0";
  }
  revision 2024-07-01 {
    description
      "Initial revision";
    reference
      "1.0.0";
    cisco-semver:module-version "1.0.0";
  }

  typedef wol-errors {
    type enumeration {
      enum err-none {
        value 0;
        description
          "Indicates that the WAKE-ON-LAN operation completed without any errors.";
      }
      enum err-in-buff-alloc {
        value 1;
        description
          "Failure occurred while allocating an internal packet buffer required to
           construct the WAKE-ON-LAN message.";
      }
      enum err-in-process-send {
        value 2;
        description
          "Failure occurred during the internal processing or transmission routine
           responsible for sending the WAKE-ON-LAN packet.";
      }
      enum err-in-pak-encap {
        value 3;
        description
          "Failure occurred while encapsulating the WAKE-ON-LAN packet before it
           could be transmitted.";
      }
    }
    description
      "Enumeration of possible errors that may occur during execution of a WAKE-ON-LAN operation.";
  }

  typedef thrpt-mode-result {
    type enumeration {
      enum thrpt-mode-avg {
        value 0;
        description
          "Throughput is calculated as the average data transfer rate over the entire duration of
           the throughput measurement test.";
      }
      enum thrpt-mode-full {
        value 1;
        description
          "Throughput is measured considering the full data transfer capacity achieved during the
           throughput test execution.";
      }
      enum thrpt-mode-peak {
        value 2;
        description
          "Throughput is measured based on the highest data transfer rate observed at any point
           during the throughput test.";
      }
    }
    description
      "Indicates the available modes used to calculate throughput results during network throughput
       measurement operations.";
  }

  typedef thrpt-proto-result {
    type enumeration {
      enum thrpt-tcp-client {
        value 0;
        description
          "Indicates the device operates as a TCP client during the throughput test, initiating the
           connection and transmitting traffic to a server.";
      }
    }
    description
      "Indicates protocol and operational role used during the throughput test, specifying whether
       TCP or UDP is used and whether the device acts as client or server.";
  }

  typedef thrpt-err-msg {
    type enumeration {
      enum thrpt-err-no-error {
        value 0;
        description
          "Indicates that the throughput test completed successfully without encountering any internal
           processing or network communication errors.";
      }
      enum thrpt-err-proc-send-msg-fail {
        value 1;
        description
          "Failure occurred while sending an internal process message required to coordinate or control
           the throughput test execution.";
      }
      enum thrpt-err-no-mem {
        value 2;
        description
          "Throughput test failed because sufficient memory could not be allocated for buffers or internal
           data structures.";
      }
      enum thrpt-err-read-fail {
        value 3;
        description
          "Failure occurred while reading data from the network socket during the throughput test data
           transfer phase.";
      }
      enum thrpt-err-write-fail {
        value 4;
        description
          "Failure occurred while writing or transmitting data through the socket during the throughput
           test execution.";
      }
      enum thrpt-err-data-overflow {
        value 5;
        description
          "Data volume exceeded the allowed buffer limits during throughput measurement processing, causing
           an overflow condition.";
      }
      enum thrpt-err-sock-open-fail {
        value 6;
        description
          "The throughput test could not start because creation or opening of the required network socket failed.";
      }
      enum thrpt-err-vrf-no-match {
        value 7;
        description
          "The specified VRF was not found or does not exist on the device, preventing the throughput test
           execution.";
      }
      enum thrpt-err-vrf-sock-opt-fail {
        value 8;
        description
          "Failed to apply the VRF-related socket configuration required to bind the throughput test traffic
           to a VRF.";
      }
      enum thrpt-err-tos-sock-opt-fail {
        value 9;
        description
          "Failed to configure the DSCP or Type-of-Service socket option used to mark packets during throughput
           testing.";
      }
      enum thrpt-err-sock-conn-fail {
        value 10;
        description
          "The socket connection to the remote endpoint failed, preventing establishment of the data session
           required for throughput testing.";
      }
    }
    description
      "Enumeration of possible errors that may occur during execution of a network throughput measurement operation.";
  }

  typedef ip-tracert-err {
    type enumeration {
      enum ip-tracert-no-err {
        value 0;
        description
          "IP traceroute request was processed successfully by the system and probes were generated without encountering any
           errors.";
      }
      enum ip-tracert-host-nm-not-rsvld {
        value 1;
        description
          "The provided destination host name could not be resolved to a valid IP address using configured DNS resolution.";
      }
      enum ip-tracert-src-if-inv {
        value 2;
        description
          "The specified source interface does not exist on the device or cannot be used for the traceroute operation.";
      }
      enum ip-tracert-src-if-dwn {
        value 3;
        description
          "The specified source interface is currently not operational and therefore cannot be used to originate traceroute
           probe packets.";
      }
      enum ip-tracert-inv-addr {
        value 4;
        description
          "The provided source IP address is not valid or cannot be assigned to the traceroute request.";
      }
      enum ip-tracert-ip-disbl {
        value 5;
        description
          "IP functionality is disabled on the device processing the traceroute request, preventing execution of the
           operation from the specified source.";
      }
      enum ip-tracert-vrf-not-ex {
        value 6;
        description
          "The specified VRF instance referenced in the traceroute request is not configured on the device processing the
           request.";
      }
      enum ip-tracert-vrf-not-acc {
        value 7;
        description
          "The specified VRF instance exists on the device, but is not accessible for processing the traceroute operation.";
      }
      enum ip-tracert-topo-not-ex {
        value 8;
        description
          "The device handling the IP traceroute request does not have the specified topology configured.";
      }
      enum ip-tracert-minttl-grt-maxttl {
        value 9;
        description
          "The specified minimum TTL value in the traceroute request is greater than the configured maximum TTL value.";
      }
    }
    description
      "Indicates possible error conditions encountered while processing an IP traceroute request on the device.";
  }

  typedef ip-tracert-probe-rslt {
    type enumeration {
      enum ip-tracert-no-rch-port {
        value 0;
        description
          "Destination host was reachable, but the specified port could not be contacted, preventing successful
           communication.";
      }
      enum ip-tracert-no-rch-adm {
        value 1;
        description
          "Packet was dropped by a router or intermediate device due to administrative filtering or policy restrictions.";
      }
      enum ip-tracert-no-rch-net {
        value 2;
        description
          "Probe packet could not be forwarded because no routing entry existed for the destination network
           in the router forwarding table.";
      }
      enum ip-tracert-no-rch-host {
        value 3;
        description
          "Probe packet reached the destination network but the specific host within that network was not reachable or
           responding.";
      }
      enum ip-tracert-no-rch-proto {
        value 4;
        description
          "Destination host received the probe but does not support the transport protocol specified in the packet.";
      }
      enum ip-tracert-timeout {
        value 5;
        description
          "No reply was received from an intermediate router or the destination host before the configured timeout period.";
      }
      enum ip-tracert-ttl-exp {
        value 6;
        description
          "Probe packet exceeded the allowed hop limit and was discarded by an intermediate router after the TTL value expired.";
      }
      enum ip-tracert-src-qench {
        value 7;
        description
          "Probe packet was not forwarded because the router indicated network congestion and requested the sender to reduce
           traffic rate.";
      }
      enum ip-tracert-no-rch-rt {
        value 8;
        description
          "Router could not forward the probe because no routing entry existed for the destination address in the routing table.";
      }
      enum ip-tracert-no-rch-src-addr-pol {
        value 9;
        description
          "Probe packet was blocked because network security policy or filtering rules prevented communication with the
           destination host.";
      }
      enum ip-tracert-no-rch-rej-rt {
        value 10;
        description
          "Router explicitly rejected forwarding of the probe packet because the route to destination was configured as
           unreachable.";
      }
    }
    description
      "Enumeration representing the outcome of an IP traceroute probe, indicating success, failure, or specific
       errors encountered.";
  }

  typedef echo-status {
    type enumeration {
      enum echo-failed {
        value 0;
        description
          "Indicates that the ICMP echo request was transmitted but no successful response was received from the
           destination host.";
      }
      enum echo-success {
        value 1;
        description
          "Indicates that the ICMP echo request was successfully delivered and a valid reply was received from the destination.";
      }
      enum echo-unsent {
        value 2;
        description
          "Indicates that the ICMP echo request was not transmitted due to configuration, validation, or internal processing
           conditions.";
      }
      enum echo-timeout {
        value 3;
        description
          "Indicates that the ICMP echo request was sent but no reply was received within the configured response waiting period.";
      }
    }
    description
      "Represents the outcome status of an ICMP echo request generated during an IP ping diagnostic operation.";
  }

  typedef ip-ping-error {
    type enumeration {
      enum ip-ping-no-err {
        value 0;
        description
          "Indicates that the IP ping request was validated and processed successfully without any internal or configuration
           errors.";
      }
      enum ip-ping-host-name-not-reslvd {
        value 1;
        description
          "Indicates that the host name provided in the IP ping request could not be resolved to a valid IP address by the
           system or configured name resolution services.";
      }
      enum ip-ping-dest-addr-inv {
        value 2;
        description
          "Indicates that the destination IP address specified in the IP ping request is not valid, malformed, unsupported,
           or outside the acceptable address range for the device.";
      }
      enum ip-ping-src-addr-inv {
        value 3;
        description
          "Indicates that the source IP address specified in the IP ping request is invalid, incorrectly formatted, or not
           configured on any interface
           of the device.";
      }
      enum ip-ping-src-int-inv {
        value 4;
        description
          "Indicates that the source interface specified in the IP ping request is not valid, does not exist, or is not
           available for originating the ping operation.";
      }
      enum ip-ping-vrf-inv {
        value 5;
        description
          "Indicates that the device processing the IP ping request does not have access to the specified VRF instance or
           the VRF is not configured or available.";
      }
      enum ip-ping-err-unkwn {
        value 6;
        description
          "Indicates that an unexpected or unidentified error occurred while processing the IP ping request and the system
           could not determine a more specific failure reason.";
      }
      enum ip-ping-failed {
        value 7;
        description
          "Indicates that the IP ping request was executed but did not receive a successful response from the destination
           host within the allowed attempts or timeout period.";
      }
      enum ip-ping-egress-int-inv {
        value 8;
        description
          "Indicates that the egress interface specified in the IP ping request is invalid, does not exist on the device,
           or cannot be used to forward the ping packet.";
      }
      enum ip-ping-egress-nh-inv {
        value 9;
        description
          "Indicates that the egress next-hop IP address specified in the IP ping request is invalid, incorrectly formatted,
           or not reachable through the specified routing context.";
      }
    }
    description
      "Represents possible errors encountered while validating or processing an IP ping diagnostic request on the device.";
  }

  typedef mtr-err {
    type enumeration {
      enum mtr-no-err {
        value 0;
        description
          "Indicates the MTR request completed successfully without encountering any processing errors or failures on the device.";
      }
      enum mtr-host-nm-not-rsvld {
        value 1;
        description
          "The provided destination host name cannot be resolved using configured DNS services available on the device.";
      }
      enum mtr-src-if-inv {
        value 2;
        description
          "Specified source interface in the MTR request does not exist or is incorrectly configured.";
      }
      enum mtr-src-if-dwn {
        value 3;
        description
          "Indicates the specified source interface exists but is currently operationally down and cannot send probes.";
      }
      enum mtr-inv-addr {
        value 4;
        description
          "Specified source IP address in the MTR request is invalid or incorrectly formatted.";
      }
      enum mtr-ip-disbl {
        value 5;
        description
          "Indicates the device processing the MTR request does not have IP functionality enabled.";
      }
      enum mtr-vrf-not-ex {
        value 6;
        description
          "Indicates the specified VRF instance referenced in the MTR request does not exist on the device.";
      }
      enum mtr-vrf-not-acc {
        value 7;
        description
          "Device handling the MTR request does not have access to the specified VRF instance.";
      }
      enum mtr-topo-not-ex {
        value 8;
        description
          "Device handling the MTR request does not have specified topology configured.";
      }
      enum mtr-minttl-grt-maxttl {
        value 9;
        description
          "Specified minimum TTL value in the MTR request is greater than maximum TTL value.";
      }
      enum mtr-unsptd-addr {
        value 10;
        description
          "Indicates the provided destination IP address type is unsupported for processing the MTR request.";
      }
      enum mtr-int-failure {
        value 11;
        description
          "MTR operation failed due to an unexpected internal processing failure in the system.";
      }
      enum mtr-inv-addr-zone {
        value 12;
        description
          "The specified IPv6 address contains an invalid or unresolvable zone identifier, preventing the MTR
           operation from determining the correct interface scope.";
      }
      enum mtr-dest-failure {
        value 13;
        description
          "Trace operation completed but probe packets did not reach the intended final destination host.";
      }
    }
    description
      "Specifies possible errors encountered during execution and processing of the MTR trace request on the device.";
  }

  typedef dns-error {
    type enumeration {
      enum dns-lookup-no-error {
        value 0;
        description
          "Indicates that the DNS lookup request completed successfully without encountering any resolution or processing errors.";
      }
      enum dns-lookup-not-supported {
        value 1;
        description
          "Indicates that the device or system does not support performing DNS lookup operations for the requested query.";
      }
      enum dns-lookup-internal-error {
        value 2;
        description
          "Signals that the DNS lookup operation failed due to an internal system error or unexpected processing condition.";
      }
      enum dns-lookup-timeout {
        value 3;
        description
          "Indicates that the DNS query did not receive a response within the allowed time period.";
      }
      enum dns-lookup-host-name-not-rsvld {
        value 4;
        description
          "Indicates that the provided hostname could not be resolved into a valid IP address by DNS services.";
      }
    }
    description
      "Enumerates possible error conditions encountered during DNS lookup processing while resolving host names in network operations.";
  }

  typedef dns-class {
    type enumeration {
      enum dns-class-internet {
        value 0;
        description
          "Represents the Internet class used for standard DNS queries involving hosts, services, and related records.";
      }
    }
    description
      "Specifies the class of the DNS query, such as IN (Internet), which indicates the protocol family for the DNS request.";
  }

  typedef dns-rec-type {
    type enumeration {
      enum dns-rec-none {
        value 0;
        description
          "Represents an undefined or invalid DNS resource record type used as a default placeholder when no
           valid record type is available.";
      }
      enum dns-rec-a {
        value 1;
        description
          "Represents a DNS A record type that maps a domain name to an IPv4 address associated with the host.";
      }
      enum dns-rec-aaaa {
        value 2;
        description
          "Represents a DNS AAAA record type that maps a domain name
           to an IPv6 address associated with the destination host.";
      }
      enum dns-rec-cname {
        value 3;
        description
          "Represents a DNS canonical name record indicating that the queried
           domain name is an alias of another canonical domain name.";
      }
    }
    description
      "Enumeration defining supported DNS resource record types that may appear within DNS query results or response sections.";
  }

  typedef dns-flags {
    type bits {
      bit dns-flag-qr-query {
        position 0;
        description
          "Identifies the DNS message as a query generated by a client requesting information from a DNS server.";
      }
      bit dns-flag-qr-response {
        position 1;
        description
          "Indicates that the DNS message is a response returned by a server answering a previous query.";
      }
      bit dns-flag-opcode-query {
        position 2;
        description
          "Represents the standard DNS query operation used to request resource records associated with a domain name.";
      }
      bit dns-flag-opcode-iquery {
        position 3;
        description
          "Represents the inverse DNS query operation where a response returns a domain name for a given record.";
      }
      bit dns-flag-opcode-status {
        position 4;
        description
          "Represents a DNS STATUS operation used to request the current status information from a DNS server.";
      }
      bit dns-flag-opcode-notify {
        position 5;
        description
          "DNS NOTIFY operation used to inform secondary name servers that zone data has changed.";
      }
      bit dns-flag-opcode-update {
        position 6;
        description
          "DNS UPDATE operation allowing dynamic modification of resource records within an authoritative DNS zone.";
      }
      bit dns-flag-aa {
        position 7;
        description
          "Shows that the responding DNS server is authoritative for the queried domain name in the answer section.";
      }
      bit dns-flag-tc {
        position 8;
        description
          "Signals that the DNS response message was truncated because it exceeded allowed message size limits.";
      }
      bit dns-flag-rd {
        position 9;
        description
          "Indicates the client requested recursive resolution, asking the DNS server to fully resolve the query.";
      }
      bit dns-flag-ra {
        position 10;
        description
          "Shows that the responding DNS server supports recursive query processing for resolving domain names.";
      }
      bit dns-flag-z {
        position 11;
        description
          "Reserved flag field within the DNS header intended for future protocol extensions and enhancements.";
      }
      bit dns-rcode-noerror {
        position 12;
        description
          "Response code indicating that the DNS query completed successfully without encountering any resolution errors.";
      }
      bit dns-rcode-formerr {
        position 13;
        description
          "Response code indicating the DNS server could not interpret the query because of invalid message format.";
      }
      bit dns-rcode-servfail {
        position 14;
        description
          "Response code indicating the DNS server failed to process the query due to internal processing errors.";
      }
      bit dns-rcode-nxdomain {
        position 15;
        description
          "Response code showing the queried domain name does not exist within the DNS namespace.";
      }
      bit dns-rcode-notimp {
        position 16;
        description
          "Response code indicating the requested DNS operation is not supported or implemented by the server.";
      }
      bit dns-rcode-refused {
        position 17;
        description
          "Response code indicating the DNS server refused to process the query due to policy restrictions.";
      }
      bit dns-rcode-yxdomain {
        position 18;
        description
          "Response code indicating the domain name exists when the query expected it not to exist.";
      }
      bit dns-rcode-yxrrset {
        position 19;
        description
          "Response code indicating a resource record set already exists when the request expected absence.";
      }
      bit dns-rcode-nxrrset {
        position 20;
        description
          "Response code indicating the requested resource record set does not exist in the DNS zone.";
      }
      bit dns-rcode-notauth {
        position 21;
        description
          "Response code showing the server is not authoritative for the requested domain zone.";
      }
      bit dns-rcode-notzone {
        position 22;
        description
          "Response code indicating the domain name referenced in the request is outside the server's zone.";
      }
    }
    description
      "Defines bit flags present in the DNS message header used to describe query or response behavior.";
  }

  grouping wol-response {
    description
      "Response details returned after executing the WAKE-ON-LAN operation.";
    leaf vlan {
      type uint16;
      description
        "VLAN identifier used to transmit the WAKE-ON-LAN magic packet to the target device.";
    }
    leaf mac-addr {
      type yang:mac-address;
      description
        "The destination MAC address of the target device to which the WAKE-ON-LAN magic packets
         will be sent to initiate the wake-up sequence.";
    }
    leaf interval {
      type uint16;
      units "seconds";
      description
        "The time interval in seconds between successive WAKE-ON-LAN packet transmission attempts,
         allowing the target device adequate time to respond between retries.";
    }
    leaf count {
      type uint8;
      description
        "The total number of WAKE-ON-LAN magic packets that will be transmitted to the
         target device during the complete poke or wake-up operation sequence.";
    }
    leaf pak-sent {
      type uint8;
      description
        "The number of WAKE-ON-LAN packets that have been successfully transmitted to the
         target device during the current or last execution attempt.";
    }
    leaf last-pak-sent {
      type yang:date-and-time;
      description
        "The timestamp or time value indicating when the most recent successful WAKE-ON-LAN packet
         was transmitted to the target device in the last operation.";
    }
    leaf error {
      type livetools-ios-xe-oper:wol-errors;
      description
        "Error information describing the reason for failure if the WAKE-ON-LAN operation does not
         complete successfully or is terminated due to internal issues.";
    }
  }

  grouping wol-results {
    description
      "Represents the operational result of a WAKE-ON-LAN RPC action, including status
       and error information for the executed wake request.";
    leaf job-id {
      type uint32;
      description
        "The ID is a unique identifier generated per WAKE-ON-LAN actions RPC request.
         It allows us to retrieve the operational data associated with a specific ID.
         This is useful for matching an action RPC response ID with the corresponding operational data";
    }
    container job-info {
      description
        "Job execution details associated with the WAKE-ON-LAN RPC action, including
         information about the initiated operation.";
      uses livetools-common-types-ios-xe:job-response;
    }
    container wol-info {
      description
        "Parameters and operational information associated with the execution of the
         WAKE-ON-LAN RPC action.";
      uses livetools-ios-xe-oper:wol-response;
    }
  }

  grouping thrpt-response {
    description
      "Contains the response data and configuration details returned after executing a throughput measurement operation.";
    leaf proto {
      type livetools-ios-xe-oper:thrpt-proto-result;
      description
        "Specifies the protocol and role used by the throughput tool, indicating whether it operates as a client or server.";
    }
    leaf dest-addr {
      type inet:ip-address;
      description
        "Indicates the destination IP address of the remote server participating in the throughput measurement test session.";
    }
    leaf ni-type {
      type common-types-ios-xe:net-inst-type;
      description
        "Specifies the network instance type used for the test, distinguishing between default routing instances and
         VRF-based instances.";
    }
    leaf ni-name {
      type string;
      description
        "Provides the name of the network instance used for the test; ignored when the instance type is the default
         routing instance.";
    }
    leaf timeout {
      type uint64;
      units "seconds";
      description
        "Specifies the total duration, in seconds, for which the throughput measurement is performed.";
    }
    leaf wnd-span {
      type uint64;
      units "seconds";
      description
        "Specifies the duration, in seconds, of each throughput measurement window used during the test execution.";
    }
    leaf num-wnds {
      type uint32;
      description
        "Specifies the total number of measurement windows used during the throughput test execution.";
    }
    leaf port {
      type uint16;
      description
        "Specifies the transport layer port number used by the server during throughput measurement.";
    }
    leaf dscp {
      type uint8;
      description
        "Specifies the DSCP value applied to generated traffic packets during throughput measurement execution.";
    }
    leaf client-rcv {
      type boolean;
      description
        "Flag to indicate that client should receive/read data from server instead of the default mode of writing
         data to server for throughput measurement.";
    }
    leaf mode {
      type livetools-ios-xe-oper:thrpt-mode-result;
      description
        "Specifies the mode used for throughput measurement, such as average, full, or peak mode.";
    }
    leaf bytes {
      type uint64;
      units "bytes";
      description
        "Bytes transferred between client and server for the throughput measurement. Data transfer is supported in
         both directions on the client. The direction is 'transmit' by default. 'Receive' is effective only when
         'client-rcv' flag is set.";
    }
    leaf elapsed-time {
      type uint64;
      units "seconds";
      description
        "Specifies the total time elapsed, in seconds, since the beginning of data transmission or reception
         during the throughput measurement.";
    }
    leaf error-type {
      type livetools-ios-xe-oper:thrpt-err-msg;
      description
        "Indicates the specific error encountered during throughput calculation or measurement execution if any
         failure occurs.";
    }
    leaf thrpt {
      type uint64;
      units "bps";
      description
        "Represents the calculated network throughput measured in bits per second during the throughput test
         execution period.";
    }
  }

  grouping thrpt-result {
    description
      "Contains detailed throughput measurement results, including performance metrics, calculated data rates,
       elapsed time, and any errors encountered during testing.";
    leaf job-id {
      type uint32;
      description
        "The ID is a unique identifier generated per successful throughput actions RPC request. It allows us to
         retrieve the operational data associated with a specific ID. This is useful for matching an action
         RPC response ID with the corresponding operational data.";
    }
    container job-info {
      description
        "Contains job execution details for the throughput RPC action, including operation parameters, status,
         and metadata about the initiated test.";
      uses livetools-common-types-ios-xe:job-response;
    }
    container thrpt-info {
      description
        "Holds throughput-specific operational data, including measured performance metrics, test parameters, and
         results returned by the RPC action.";
      uses livetools-ios-xe-oper:thrpt-response;
    }
  }

  grouping ip-tracert-probe {
    description
      "Information collected for each probe packet sent during the traceroute operation, including response result, hop
       address, and measured round-trip time.";
    leaf probe-num {
      type uint32;
      description
        "Sequence number identifying the probe packet within a hop, allowing correlation of probe attempts and their
         corresponding responses.";
    }
    leaf result {
      type livetools-ios-xe-oper:ip-tracert-probe-rslt;
      description
        "Result returned for the probe packet, indicating whether a response, timeout, or specific network condition
         was encountered.";
    }
    leaf ip-addr {
      type inet:ip-address;
      description
        "IP address of the device that generated the response for this probe at the corresponding network hop.";
    }
    leaf rtt {
      type uint32;
      units "milliseconds";
      description
        "Measured round-trip time for the probe packet between the local device and the responding hop.";
    }
  }

  grouping ip-tracert-hop {
    description
      "Represents a single network hop discovered during the traceroute operation, including probe attempts and
       responses from that hop.";
    leaf hop-num {
      type uint32;
      description
        "Sequential identifier of network hop encountered during traceroute request.";
    }
    list probe-info {
      description
        "Collection of probe responses recorded for this hop, providing detailed results for each probe attempt.";
      uses livetools-ios-xe-oper:ip-tracert-probe;
    }
  }

  grouping ip-tracert-req {
    description
      "Defines input parameters used to initiate an IP traceroute operation towards a specified destination within a selected
       network instance.";
    leaf ni-type {
      type common-types-ios-xe:net-inst-type;
      description
        "Specifies the type of network instance used to perform the traceroute operation, such as default routing instance
         or VRF.";
    }
    leaf ni-name {
      type string;
      description
        "Name identifying the specific network instance used for executing the traceroute request. Ignored when instance
         type is net-inst-default.";
    }
    choice src-choice {
      description
        "Specifies the source used to initiate the IP traceroute request. The source can be provided as an interface name
         or as an IP or IPv6 address.";
      case src-if-name {
        leaf src-if {
          type string;
          description
            "Name of the source interface used to initiate the IP traceroute request.";
        }
      }
      case src-ip-addr {
        leaf src-ip {
          type inet:ip-address;
          description
            "Source IP or IPv6 address used to initiate the traceroute request from the local device toward the specified
             destination host.";
        }
      }
    }
    choice host-choice {
      description
        "Specifies the destination target for the IP traceroute request. The destination can be provided either as a
         hostname or as an IPv4 or IPv6 address.";
      case host-name {
        leaf host-name {
          type string;
          description
            "Hostname that identifies the destination device for which the IP traceroute operation will be performed by
             the system.";
        }
      }
      case host-ip-addr {
        leaf host-ip {
          type inet:ip-address;
          description
            "IP or IPv6 address of the destination device toward which the IP traceroute request will be initiated.";
        }
      }
    }
  }

  grouping ip-tracert-resp {
    description
      "Aggregated traceroute response data containing hop-by-hop results that describe the network path from source
       to destination.";
    list hop-info {
      description
        "List of hop entries describing each intermediate router discovered during the traceroute path discovery process.";
      uses livetools-ios-xe-oper:ip-tracert-hop;
    }
  }

  grouping ip-tracert-result {
    description
      "Represents the complete result of a traceroute request execution, including request parameters, execution status,
       errors, and collected hop responses.";
    leaf job-id {
      type uint32;
      description
        "The ID is a unique identifier generated per successful IP
         traceroute actions RPC request. It allows us to retrieve the operational
         data associated with a specific ID. This is useful for matching an action
         RPC response ID with the corresponding operational data";
    }
    container req-info {
      description
        "Stores parameters originally provided in the traceroute request, allowing reference to the input configuration
         used for the operation.";
      uses livetools-ios-xe-oper:ip-tracert-req;
    }
    container job-info {
      description
        "Provides execution status details for the traceroute operation, including progress, completion state, and
         processing information.";
      uses livetools-common-types-ios-xe:job-response;
    }
    leaf error {
      type livetools-ios-xe-oper:ip-tracert-err;
      description
        "Contains the error reason of IP traceroute request processing, if any; otherwise specified as 'no-error'.";
    }
    container resp-info {
      description
        "Contains the hop-by-hop traceroute response data collected during execution of the traceroute operation,
         describing the discovered network path.";
      uses livetools-ios-xe-oper:ip-tracert-resp;
    }
  }

  grouping ip-ping-echo {
    description
      "Specifies the information related to an ICMP echo packet transmitted as part of the ping operation, including sequence
       number, status, and latency measurements.";
    leaf seq-num {
      type uint8;
      description
        "Represents the sequence number assigned to each ICMP echo request, which helps correlate individual ping packets
         with their corresponding responses.";
    }
    leaf status {
      type livetools-ios-xe-oper:echo-status;
      description
        "Indicates the result or state of the ICMP echo request, showing whether the packet was successfully transmitted
         and a reply was received.";
    }
    leaf latency {
      type uint8;
      status obsolete;
      description
        "Deprecated. Represents the measured round-trip time, in milliseconds, for the ICMP echo request and response,
         indicating how long the packet took to travel to the destination and return.";
    }
    leaf latency-msec {
      type uint32;
      units "milliseconds";
      description
        "Specifies the round-trip delay measured in milliseconds for an ICMP echo request, indicating the time taken
         for the packet to reach the destination and return.";
    }
  }

  grouping ip-ping-response {
    description
      "Specifies the structure used to represent the response information generated from processing an IP ping request,
       including details about each echo attempt.";
    list echo-info {
      description
        "Contains the collection of ICMP echo responses generated for the ping request, where each entry represents the
         result of an individual echo attempt.";
      uses livetools-ios-xe-oper:ip-ping-echo;
    }
  }

  grouping ip-ping-request {
    description
      "Defines the parameters and configuration required to initiate an IP ping operation, including destination information,
       network instance context, and optional source details.";
    leaf ni-type {
      type common-types-ios-xe:net-inst-type;
      default "net-inst-default";
      description
        "Specifies the type of network instance in which the ping operation should be executed, distinguishing between the
         default routing instance and configured VRFs.";
    }
    leaf ni-name {
      type string;
      description
        "Network instance name. If the type is net-inst-default, the name is not meaningful.";
    }
    leaf proto-hint {
      type livetools-common-types-ios-xe:dns-proto-hint;
      default "dns-proto-none";
      description
        "Forces the request to use specific DNS resolution protocol type while resolving the destination host name.";
    }
    leaf egress-if-name {
      type string;
      description
        "Forces the ping traffic to use specified egress interface directly bypassing normal routing table based forwarding.";
    }
    leaf next-hop {
      type inet:ip-address;
      description
        "Specifies the next-hop IP address to use when forwarding the generated ping request packets, overriding the normal
         routing table lookup.";
    }
    choice src-choice {
      description
        "Provides options to define the source of the ping request, allowing selection of either a source interface or source
         IP address.";
      case src-if-name {
        leaf src-if {
          type string;
          description
            "Specifies the name of the source interface to be used for sending the ping request.";
        }
      }
      case src-ip-addr {
        leaf src-ip {
          type inet:ip-address;
          description
            "Specifies the source IP address used for sending the ICMP echo request during execution of the ping operation.";
        }
      }
    }
    choice host-choice {
      description
        "Provides options to specify the destination of the ping request either by host name or by direct IP address.";
      case host-name {
        leaf host-name {
          type string;
          description
            "Specifies the destination host name that should be resolved using configured name resolution mechanisms before
             initiating the ping request.";
        }
      }
      case host-ip-addr {
        leaf host-ip {
          type inet:ip-address;
          description
            "Specifies the destination host IP address to be used for the ping request.";
        }
      }
    }
  }

  grouping ip-ping-result {
    description
      "Represents the complete result information generated after processing the requested IP ping operation by the device.";
    leaf job-id {
      type uint32;
      description
        "Unique identifier generated per successful ping action RPC request, used to retrieve the operational data associated
         with that specific request.";
    }
    container req-info {
      description
        "Contains relevant parameters originally supplied in the ping request including destination source and routing instance
         details.";
      uses livetools-ios-xe-oper:ip-ping-request;
    }
    container job-info {
      description
        "Provides status information about processing of the ping request including execution state completion and progress
         details.";
      uses livetools-common-types-ios-xe:job-response;
    }
    leaf error {
      type livetools-ios-xe-oper:ip-ping-error;
      description
        "Specifies the error that occurred during the ping request processing, if any. If no error occurred, 'ip-ping-no-err'
         is specified.";
    }
    container resp-info {
      description
        "Contains detailed response data for the IP ping request, including the results of each ICMP echo sent.";
      uses livetools-ios-xe-oper:ip-ping-response;
    }
  }

  grouping mtr-host {
    description
      "Provides detailed per hop statistics collected during the MTR operation for the destination path analysis.";
    leaf host-num {
      type uint8;
      description
        "Sequential hop number representing the position of the network node along the path toward destination.";
    }
    leaf host-ip {
      type inet:ip-address;
      description
        "IP address of the responding router or node encountered at the corresponding hop during MTR tracing.";
    }
    leaf loss-prcnt {
      type uint8;
      units "percent";
      description
        "Percentage of probe packets lost while communicating with this hop during the MTR measurement process.";
    }
    leaf sent {
      type uint32;
      description
        "Total number of probe packets transmitted from the system to this hop during the MTR test.";
    }
    leaf last {
      type uint32;
      units "milliseconds";
      description
        "Round trip latency measured for the most recent probe packet received from this hop.";
    }
    leaf avg {
      type uint32;
      units "milliseconds";
      description
        "Average round trip latency calculated from all probe responses received from this hop.";
    }
    leaf best {
      type uint32;
      units "milliseconds";
      description
        "The lowest (best) latency of all packets sent to the hop, in milliseconds.";
    }
    leaf worst {
      type uint32;
      units "milliseconds";
      description
        "The highest (worst) latency of all packets sent to the hop, in milliseconds";
    }
    leaf stdev {
      type uint32;
      units "milliseconds";
      description
        "The standard deviation of the latency values for each hop, in milliseconds";
    }
  }

  grouping mtr-req {
    description
      "Specifies parameters required to initiate an MTR operation toward a specified destination host.";
    leaf ni-type {
      type common-types-ios-xe:net-inst-type;
      description
        "Specifies the network instance type distinguishing between default routing context and configured VRF instances.";
    }
    leaf ni-name {
      type string;
      description
        "Name of the selected network instance; ignored when the instance type is net-inst-default.";
    }
    leaf proto-hint {
      type livetools-common-types-ios-xe:dns-proto-hint;
      description
        "Specifies the type of DNS resolution to use for the MTR request, such as forcing IPv4 or IPv6 address resolution.";
    }
    leaf count {
      type uint8;
      description
        "The number of traceroute/ping probes or packets transmitted to each hop during the MTR operation for measuring latency
         and packet loss.";
    }
    leaf port {
      type uint16;
      description
        "UDP destination port used when sending probe packets during the MTR operation to evaluate network path behavior.";
    }
    leaf timeout {
      type uint16;
      units "seconds";
      description
        "Specifies the maximum waiting time, in seconds, for receiving a response to each probe sent during the MTR operation.";
    }
    leaf min-ttl {
      type uint8;
      description
        "The minimum value of the Time To Live (TTL) field for IP packets, which specifies the lowest hop count limit that a
         packet must maintain when traversing through network routers before being discarded to prevent infinite routing loops.";
    }
    leaf max-ttl {
      type uint8;
      description
        "The maximum value of the Time To Live (TTL) field for IP packets, which defines the highest hop count threshold that
         determines the maximum number of network hops an IP packet can traverse before being dropped by intermediate routers
         to ensure network reliability.";
    }
    choice dscp-choice {
      description
        "Allows selection of the DSCP value format used in probe packets, either numeric code or predefined ASCII option.";
      case dscp-num {
        leaf dscp-num {
          type uint8;
          description
            "Numeric value of the DSCP (Differentiated Services Code Point) to be set in probe packets for the MTR operation.";
        }
      }
      case dscp-ascii {
        leaf dscp-ascii {
          type livetools-common-types-ios-xe:dscp-options;
          description
            "Named DSCP value selected from recognized service classes to define packet forwarding behavior and priority treatment.";
        }
      }
    }
    choice src-choice {
      description
        "Defines the source identifier for sending MTR probes, either using an interface name or specific IP address.";
      case src-if-name {
        leaf src-if {
          type string;
          description
            "Specifies the interface whose address will be used as the source when transmitting MTR probe packets.";
        }
      }
      case src-ip-addr {
        leaf src-ip {
          type inet:ip-address;
          description
            "Specifies the explicit IPv4 or IPv6 source address used when sending probe packets for the MTR operation.";
        }
      }
    }
    choice host-choice {
      description
        "Selects the destination for the MTR request, allowing either a hostname or an IP/IPv6 address.";
      case host-name {
        leaf host-name {
          type string;
          description
            "Hostname representing the target system where the MTR operation will be performed after successful DNS resolution.";
        }
      }
      case host-ip-addr {
        leaf host-ip {
          type inet:ip-address;
          description
            "IP or IPv6 address identifying the destination node that will be probed during the MTR path analysis.";
        }
      }
    }
  }

  grouping mtr-resp {
    description
      "Contains detailed response data collected during the MTR operation, including hop statistics and latency measurements.";
    list host-info {
      description
        "Per-hop response statistics collected during the MTR operation, including latency and packet loss for each network node.";
      uses livetools-ios-xe-oper:mtr-host;
    }
  }

  grouping mtr-result {
    description
      "Represents the overall outcome of an MTR request, including request parameters, processing status, errors, and hop responses.";
    leaf job-id {
      type uint32;
      description
        "Unique identifier generated per successful MTR action RPC request, used to retrieve the operational data associated with
         that specific request and to match an action RPC response with the corresponding result.";
    }
    container req-info {
      description
        "Stores parameters and configuration values originally provided in the MTR request for reference and operational tracking.";
      uses livetools-ios-xe-oper:mtr-req;
    }
    container job-info {
      description
        "Contains status details describing the current processing state and execution progress of the MTR request.";
      uses livetools-common-types-ios-xe:job-response;
    }
    leaf error {
      type livetools-ios-xe-oper:mtr-err;
      description
        "Contains the error reason of the MTR request processing, if any; otherwise specified as 'mtr-err-none'.";
    }
    container resp-info {
      description
        "Contains the final response data produced by the MTR operation, including hop statistics and diagnostic measurements.";
      uses livetools-ios-xe-oper:mtr-resp;
    }
  }

  grouping dns-header {
    description
      "Represents DNS header details containing identifiers, flags, and metadata associated with DNS query responses.";
    leaf id {
      type uint16;
      description
        "Unique identifier used to match DNS responses with their corresponding queries generated by the client.";
    }
    leaf flags {
      type livetools-ios-xe-oper:dns-flags;
      description
        "Contains DNS header flag values describing query type, response behavior, recursion status, and result codes.";
    }
    leaf qdcount {
      type uint16;
      description
        "Number of question entries included in the DNS query section for which the server provides corresponding responses in the DNS
         reply message.";
    }
    leaf ancount {
      type uint16;
      description
        "Total number of answer resource records returned in the DNS response message that directly address the original DNS query
         request.";
    }
    leaf nscount {
      type uint16;
      description
        "Number of authority resource records present in the DNS response, indicating authoritative name servers responsible
         for the queried domain.";
    }
    leaf arcount {
      type uint16;
      description
        "Number of additional resource records included in the DNS response, typically providing supplementary information
         related to the query resolution.";
    }
  }

  grouping dns-query {
    description
      "Represents the DNS query section containing the original query parameters sent by the client
       when requesting domain name resolution.";
    leaf query-name {
      type string;
      description
        "This field repeats the domain name from the original DNS query,
         confirming the response is for the correct domain.";
    }
    leaf class {
      type livetools-ios-xe-oper:dns-class;
      description
        "Specifies the class of the DNS query, such as IN (Internet),
         which indicates the protocol family for the DNS request.";
    }
    leaf type {
      type livetools-common-types-ios-xe:dns-qry-type;
      description
        "Specifies the type of DNS query, such as A (IPv4 address), AAAA (IPv6 address),
         or CNAME (canonical name), indicating the type of resource record requested.";
    }
  }

  grouping dns-rr-a-aaaa {
    description
      "Grouping representing DNS resource records that contain IPv4 or IPv6
       address information returned for A or AAAA queries.";
    leaf ttl {
      type uint32;
      units "seconds";
      description
        "Time To Live (TTL) value, in seconds, indicating how long the DNS
         resource record remains valid before it should be refreshed.";
    }
    leaf addr {
      type inet:ip-address;
      description
        "IP address contained in the DNS resource record (IPv4 for A records or IPv6 for
         AAAA records, where AAAA is the standard DNS record type for IPv6 addresses).";
    }
  }

  grouping dns-rr-cname {
    description
      "Grouping representing DNS canonical name records that map an
       alias domain name to its corresponding canonical domain name.";
    leaf ttl {
      type uint32;
      units "seconds";
      description
        "Time To Live (TTL) value, in seconds, indicating how long
         the DNS CNAME resource record is considered valid.";
    }
    leaf alias-name {
      type string;
      description
        "Canonical domain name associated with the alias provided
         in the CNAME resource record returned in the DNS response.";
    }
  }

  grouping dns-ans-sec {
    description
      "Grouping representing answer resource records returned by the DNS server
       that contain the resolved information for the query.";
    choice rec-type-choice {
      description
        "Choice structure allowing selection of the DNS resource record type present
         in the answer section of the DNS response.";
      case dns-rec-a {
        container a-rec {
          description
            "Container holding details of the DNS A record response that
             provides IPv4 address mapping for the queried domain.";
          uses livetools-ios-xe-oper:dns-rr-a-aaaa;
        }
      }
      case dns-rec-aaaa {
        container aaaa-rec {
          description
            "Container holding details of the DNS AAAA record response
             that provides IPv6 address mapping for the queried domain.";
          uses livetools-ios-xe-oper:dns-rr-a-aaaa;
        }
      }
      case dns-rec-cname {
        container cname-rec {
          description
            "Container containing DNS CNAME record details indicating the
             canonical domain name corresponding to the queried alias.";
          uses livetools-ios-xe-oper:dns-rr-cname;
        }
      }
    }
  }

  grouping dns-query-response {
    description
      "Grouping representing the full DNS query response including header, query details,
       answer records, and timing related information.";
    container header {
      description
        "Container providing DNS response header information including flags, identifiers,
         and counters describing the structure of the response.";
      uses livetools-ios-xe-oper:dns-header;
    }
    container query {
      description
        "Container representing the query section copied from the original
         DNS request included within the DNS response message.";
      uses livetools-ios-xe-oper:dns-query;
    }
    list ans-section {
      description
        "List containing DNS answer resource records returned by the DNS
         server as part of the query resolution process.";
      uses livetools-ios-xe-oper:dns-ans-sec;
    }
    leaf query-time {
      type yang:date-and-time;
      description
        "Timestamp indicating when the DNS query request was sent
         from the system to the configured DNS server.";
    }
    leaf payload-size {
      type uint32;
      units "bytes";
      description
        "Total size, in bytes, of the DNS response payload received from the
         DNS server for the processed query.";
    }
    leaf rtt {
      type uint32;
      units "milliseconds";
      description
        "Round trip time measured in milliseconds between sending the DNS query
         and receiving the corresponding DNS response.";
    }
  }

  grouping dns-lookup-request {
    description
      "Grouping representing parameters used to initiate a DNS lookup request
       including query type, server information, and network instance.";
    leaf ni-type {
      type common-types-ios-xe:net-inst-type;
      description
        "Network instance type. Differentiates between the default routing instance and VRFs.";
    }
    leaf ni-name {
      type string;
      description
        "Network instance name. If the type is net-inst-default, the name is not meaningful.";
    }
    leaf dns-server {
      type inet:ip-address;
      description
        "IP address of the DNS server that will receive and process the DNS lookup
         request for resolving the specified domain name.";
    }
    choice qtype-choice {
      description
        "Specifies the DNS query record type requested for domain name resolution, determining
         whether IPv4 or IPv6 address information should be retrieved.";
      case dns-a-query {
        container a-qry {
          description
            "Container representing a DNS query requesting an IPv4 address mapping for
             the specified domain name using an A record lookup.";
          uses livetools-common-types-ios-xe:dns-a-aaaa-qry;
        }
      }
      case dns-aaaa-query {
        container aaaa-qry {
          description
            "Container representing a DNS query requesting an IPv6 address mapping for
             the specified domain name using an AAAA record lookup.";
          uses livetools-common-types-ios-xe:dns-a-aaaa-qry;
        }
      }
    }
  }

  grouping dns-query-result {
    description
      "Grouping representing the complete result of a DNS lookup request, including
       request parameters, execution status, and received DNS responses.";
    leaf job-id {
      type uint32;
      description
        "Unique identifier generated per successful DNS query action RPC request, used to
         retrieve the operational data associated with that specific request.";
    }
    container job-info {
      description
        "Container providing status information about the DNS query processing, including
         progress, completion state, and execution details.";
      uses livetools-common-types-ios-xe:job-response;
    }
    container request {
      description
        "Container containing the parameters and configuration used to generate the DNS
         lookup request executed by the system.";
      uses livetools-ios-xe-oper:dns-lookup-request;
    }
    leaf error {
      type livetools-ios-xe-oper:dns-error;
      description
        "Contains the error reason of the DNS query request processing, if any; otherwise
         specified as 'dns-lookup-success'.";
    }
    list response {
      description
        "List containing DNS response records returned by the DNS server, including
         resolved addresses, canonical names, and associated metadata.";
      uses livetools-ios-xe-oper:dns-query-response;
    }
  }

  container livetools-oper-data {
    config false;
    description
      "Container for operational data related to live network diagnostic tools, such as
       ping, traceroute, throughput tests, DNS lookups, and WAKE-ON-LAN actions.";
    list tracert-result {
      key "job-id";
      description
        "List of results for IP traceroute operations, including details about each
         traceroute request and its response.";
      uses livetools-ios-xe-oper:ip-tracert-result;
    }
    list thrpt-result {
      key "job-id";
      description
        "Contains the operational data and results of a throughput measurement action,
         including job status and throughput statistics.";
      uses livetools-ios-xe-oper:thrpt-result;
    }
    list ip-ping-result {
      key "job-id";
      description
        "Operational results of the IP ping operation, providing response details and
         packet statistics for the executed connectivity test.";
      uses livetools-ios-xe-oper:ip-ping-result;
    }
    list dns-query-result {
      key "job-id";
      description
        "Contains the operational data and results for a DNS query action, including
         request details, status, errors, and DNS response data.";
      uses livetools-ios-xe-oper:dns-query-result;
    }
    list wol-result {
      key "job-id";
      description
        "Operational result of the WAKE-ON-LAN RPC action indicating the status
         and details of the wake request issued to the specified target device.";
      uses livetools-ios-xe-oper:wol-results;
    }
    list mtr-result {
      key "job-id";
      description
        "Contains the result data for a Multi-Traceroute (MTR) action RPC, including
         request parameters, response details, and any error information.";
      uses livetools-ios-xe-oper:mtr-result;
    }
  }
}
