module Cisco-IOS-XE-http {
  yang-version 1.1;
  namespace "http://cisco.com/ns/yang/Cisco-IOS-XE-http";
  prefix ios-http;

  import cisco-semver {
    prefix cisco-semver;
  }
  import Cisco-IOS-XE-native {
    prefix ios;
  }
  import Cisco-IOS-XE-features {
    prefix ios-features;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Hypertext Transfer Protocol (HTTP) Yang Model.
     Copyright (c) 2016, 2018-2019 by Cisco Systems, Inc.
     All rights reserved.";

  revision 2026-08-01 {
    description
      "- Added support for 'ip http secure-ecdhe-curve'
       - Updated Max range for 'ip http session-idle-timeout'
       - Added yang model for 'ip http secure-pqc-type' CLI
       - Updated ip http server to be set as disabled by default
       - Updated default value for 'ip http secure-server'";
    cisco-semver:module-version "5.0.0";
  }
  revision 2026-02-01 {
    description
      "- Added support for ip http session-module-list configuration capabilities
       - Removed deprecated leaf 'ip http access-class'
       - Deprecated TLS version 1.0 and 1.1 for http secure server
       - Deprecated ip http server and other weak ciphers";
    cisco-semver:module-version "4.0.0";
  }
  revision 2025-07-01 {
    description
      "- Added support for 'ip http accounting commands'";
    cisco-semver:module-version "3.1.0";
  }
  revision 2024-11-01 {
    description
      "- Added support for 'ip http access class ipv6'
       - Added deletion support for 'ip http server'
       - Added deletion support for 'ip http secure-server'
       - Corrected the range and default values for 'ip http max-connections'
       - Added new model for ip http secure personal identity verification CLI
       - Added deletion support for idle and default values at timeout-policy";
    cisco-semver:module-version "3.0.0";
  }
  revision 2024-07-01 {
    description
      "- Added support for 'ip http secure-port'
       - Added support for 'ip http client cache'
       - Added support for 'ip http client connection retry'
       - Added support for 'ip http client connection pipeline-length'
       - Added support for 'ip http client connection idle timeout'
       - Added support for 'ip http client response timeout'
       - Corrected the range and default values for 'ip http session-idle-timeout' and 'ip http port'";
    cisco-semver:module-version "2.4.0";
  }
  revision 2024-03-01 {
    description
      "- Added support for 'ip http access class ipv4'
       - Added support for 'ip http client connection timeout'";
    cisco-semver:module-version "2.3.0";
  }
  revision 2023-11-01 {
    description
      "- Updated default vales for http server and secure-server
       - Corrected max characters supported for secure-trustpoint leaf";
    cisco-semver:module-version "2.2.0";
  }
  revision 2022-11-01 {
    description
      "- Update yang-version to 1.1
       - Added support for http tls-version secure-cipher";
    cisco-semver:module-version "2.1.0";
  }
  revision 2022-07-01 {
    description
      "- Added UEA platform specific feature";
    cisco-semver:module-version "2.0.0";
  }
  revision 2021-11-01 {
    description
      "- Added constraint for http-secure-trustpoint
       - Added constraint for http-client-secure-trustpoint";
    cisco-semver:module-version "1.1.0";
  }
  revision 2019-07-01 {
    description
      "- Establish semantic version baseline
       - Added support for session-idle-timeout
       - Added support for ctc authentication";
    cisco-semver:module-version "1.0.0";
  }
  revision 2018-10-26 {
    description
      "Added support for 'ip http tls-version'";
  }
  revision 2018-09-26 {
    description
      "Added support for 'ip http authentication aaa'";
  }
  revision 2018-01-24 {
    description
      "Updated ip http configurations to prevent full sync";
  }
  revision 2017-12-04 {
    description
      "Added ip http configurations to prevent full sync";
  }
  revision 2017-02-07 {
    description
      "Initial revision";
  }

  grouping config-ip-http-grouping {
    container http {
      description
        "HTTP server configuration";
      container access-class-group {
        description
          "Restrict http server access by access-class";
        choice access-list-choice {
          leaf access-list-number {
            description
              "Access list number";
            type uint8 {
              range "1..99";
            }
          }
          container ipv4 {
            description
              "Restrict http server access by ipv4 access-class";
            choice ipv4-choice {
              leaf ipv4-access-list-number {
                description
                  "IPV4 Access list number";
                type uint8 {
                  range "1..99";
                }
              }
              leaf word {
                description
                  "IPv4 Access list name";
                type string;
              }
            }
          }
          container ipv6 {
            description
              "Restrict http server access by ipv6 access-class";
            leaf word {
              description
                "IPv6 Access list name";
              type string;
            }
          }
        }
      }
      leaf access-class {
        status obsolete;
        description
          "Restrict http server access by access-class (OBSOLETE)";
        type uint8 {
          range "1..99";
        }
      }
      container authentication {
        description
          "Set http server authentication method";
        choice authentication-choice {
          container aaa {
            description
              "Use AAA access control methods";
            presence "true";
            list command-authorization {
              description
                "Set method list for command authorization";
              key "level";
              leaf level {
                description
                  "Enable level";
                type uint8 {
                  range "0..15";
                }
              }
              leaf name {
                description
                  "Use an authorization list with this name";
                mandatory true;
                type string;
              }
            }
            leaf exec-authorization {
              description
                "Set method list for exec authorization";
              type string;
            }
            leaf login-authentication {
              description
                "Set method list for login authentication";
              type string;
            }
          }
          leaf local {
            description
              "Use local username and passwords";
            type empty;
          }
        }
      }
      leaf server {
        status deprecated;
        description
          "Enable http server";
        type boolean;
        default "false";
      }
      leaf secure-server {
        description
          "Enable HTTP secure server";
        type boolean;
        default "false";
      }
      leaf secure-port {
        description
          "HTTP secure server port number for listening.";
        type uint16 {
          range "443 | 1025..65535";
        }
        default "443";
      }
      leaf secure-trustpoint {
        description
          "Set http secure server certificate trustpoint";
        type string {
          length "1..226";
        }
      }
      leaf tls-version {
        description
          "Set TLS version for HTTP secure server";
        type enumeration {
          enum TLSv1.0 {
            status deprecated;
          }
          enum TLSv1.1 {
            status deprecated;
          }
          enum TLSv1.2 {
            value 2;
          }
          enum TLSv1.3 {
            value 3;
          }
        }
      }
      leaf secure-pqc-type {
        description
          "Set PQC algorithm types for HTTP secure server";
        type enumeration {
          enum all;
          enum hybrid;
          enum non-pqc;
          enum pqc;
        }
        default "all";
      }
      leaf secure-ecdhe-curve {
        description
          "Set ECDHE curve for HTTP secure server";
        type enumeration {
          enum secp256r1 {
            description
              "Set NIST curve secp256r1";
          }
          enum secp384r1 {
            description
              "Default NIST curve secp384r1";
          }
          enum secp521r1 {
            description
              "Set NIST curve secp521r1";
          }
        }
        default "secp384r1";
      }
      container timeout-policy {
        description
          "Set http server time-out policy parameters";
        leaf idle {
          description
            "Idle time-out of a http server connection in seconds";
          type uint16 {
            range "1..600";
          }
          default "180";
        }
        leaf life {
          description
            "Life time of a http server connection in seconds";
          type uint32 {
            range "1..86400";
          }
          default "180";
        }
        leaf requests {
          description
            "Maximum number of requests allowed on a http server connection";
          type uint32 {
            range "1..86400";
          }
          default "25";
        }
      }
      container client {
        description
          "Set http client parameters";
        container secure-ciphersuite {
          description
            "Set http secure server ciphersuite";
          leaf aes-128-cbc-sha {
            status deprecated;
            description
              "Encryption type tls_rsa_with_aes_cbc_128_sha ciphersuite";
            type empty;
          }
          leaf aes-256-cbc-sha {
            status deprecated;
            description
              "Encryption type tls_rsa_with_aes_cbc_256_sha ciphersuite";
            type empty;
          }
          leaf dhe-aes-cbc-sha2 {
            description
              "Encryption type tls_dhe_rsa_with_aes_cbc_sha2
               (TLS 1.2) ciphersuite";
            type empty;
          }
          leaf dhe-aes-gcm-sha2 {
            description
              "Encryption type tls_dhe_rsa_with_aes_gcm_sha2(TLS 1.2)
               ciphersuite";
            type empty;
          }
          leaf ecdhe-ecdsa-aes-gcm-sha2 {
            description
              "Encryption type tls_ecdhe_ecdsa_aes_gcm_sha2
               (TLS 1.2)  SuiteB ciphersuite";
            type empty;
          }
          leaf ecdhe-rsa-aes-cbc-sha2 {
            description
              "Encryption type tls_ecdhe_rsa_aes_cbc_sha2(TLS 1.2)
               ciphersuite";
            type empty;
          }
          leaf ecdhe-rsa-aes-gcm-sha2 {
            description
              "Encryption type tls_ecdhe_rsa_aes_gcm_sha2(TLS 1.2)
               ciphersuite";
            type empty;
          }
          leaf rsa-aes-cbc-sha2 {
            description
              "Encryption type tls_rsa_with_aes_cbc_sha2(TLS 1.2)
               ciphersuite";
            type empty;
          }
          leaf rsa-aes-gcm-sha2 {
            description
              "Encryption type tls_rsa_with_aes_gcm_sha2(TLS 1.2)
               ciphersuite";
            type empty;
          }
          leaf tls13-aes128-gcm-sha256 {
            description
              "Encryption type tls13_aes128_gcm_sha256(TLS 1.3)
               ciphersuite";
            type empty;
          }
          leaf tls13-aes256-gcm-sha384 {
            description
              "Encryption type tls13_aes256_gcm_sha384(TLS 1.3)
               ciphersuite";
            type empty;
          }
          leaf tls13-chacha20-poly1305-sha256 {
            description
              "Encryption type tls13_chacha20_poly1305_sha256
               (TLS 1.3) ciphersuite";
            type empty;
          }
        }
        leaf secure-trustpoint {
          description
            "Set http client certificate secure trustpoint";
          type string {
            length "1..219";
          }
        }
        leaf source-interface {
          description
            "Specify interface for source address in all HTTP(S) client connections";
          type string;
        }
        container proxy-server {
          description
            "Specify proxy server name for HTTP file system client connections";
          leaf proxy-server-name {
            description
              "Proxy server name";
            type string;
          }
          leaf proxy-port {
            description
              "Proxy port number";
            type uint16 {
              range "1..65535";
            }
          }
        }
        leaf tls-version {
          description
            "Set TLS version for HTTP secure server";
          type enumeration {
            enum TLSv1.0 {
              status deprecated;
            }
            enum TLSv1.1 {
              status deprecated;
            }
            enum TLSv1.2 {
              value 2;
            }
            enum TLSv1.3 {
              value 3;
            }
          }
        }
        container connection {
          description
            "Configure HTTP Client connection";
          leaf timeout {
            description
              "HTTP connection time-out value (1-60) in seconds";
            type uint8 {
              range "1..60";
            }
          }
          leaf retry {
            description
              "HTTP connection retry value (1-5)";
            type uint8 {
              range "1..5";
            }
            default "1";
          }
          leaf pipeline-length {
            description
              "HTTP connection pipeline length (2-100) (Unit - No. of messages)";
            type uint8 {
              range "2..100";
            }
            default "5";
          }
          container idle {
            description
              "Configure HTTP client connection idle";
            leaf timeout {
              description
                "HTTP connection idle timeout value (1-60) in seconds";
              type uint8 {
                range "1..60";
              }
              default "30";
            }
          }
        }
        container response {
          description
            "Configure HTTP client response timeout";
          leaf timeout {
            description
              "HTTP response timeout value (1-60) in seconds";
            type uint8 {
              range "1..60";
            }
            default "30";
          }
        }
        container cache {
          description
            "HTTP client cache";
          container ager {
            description
              "Cache Interval Time";
            leaf interval {
              description
                "Interval in Minutes <0-60>, default is 5";
              type uint8 {
                range "0..60";
              }
              default "5";
            }
          }
          container memory {
            description
              "Maximum memory allowed for HTTP Client Cache";
            leaf file {
              description
                "Size of cache memory file in kbytes <1-10>, default is 2";
              type uint8 {
                range "1..10";
              }
              default "2";
            }
            leaf pool {
              description
                "Size of cache memory pool in kbytes <0-100>, default is 100";
              type uint8 {
                range "0..100";
              }
              default "100";
            }
          }
        }
        container password {
          description
            "HTTP client password";
          leaf encryption {
            description
              "0 - Specifies an UNENCRYPTED key will follow
               6 - Specifies an ENCRYPTED key will follow
               7 - Specifies HIDDEN key will follow";
            type enumeration {
              enum 0;
              enum 7;
              enum 6;
            }
          }
          leaf key {
            description
              "password line incorporation";
            type string {
              pattern '.*';
            }
          }
        }
      }
      leaf port {
        description
          "http port number";
        type uint16 {
          range "80 | 1024..65535";
        }
        default "80";
      }
      container secure-ciphersuite {
        description
          "Set http secure server ciphersuite";
        leaf aes-128-cbc-sha {
          status deprecated;
          description
            "Encryption type tls_rsa_with_aes_cbc_128_sha ciphersuite";
          type empty;
        }
        leaf aes-256-cbc-sha {
          status deprecated;
          description
            "Encryption type tls_rsa_with_aes_cbc_256_sha ciphersuite";
          type empty;
        }
        leaf dhe-aes-cbc-sha2 {
          description
            "Encryption type tls_dhe_rsa_with_aes_cbc_sha2
             (TLS 1.2) ciphersuite";
          type empty;
        }
        leaf dhe-aes-gcm-sha2 {
          description
            "Encryption type tls_dhe_rsa_with_aes_gcm_sha2(TLS 1.2)
             ciphersuite";
          type empty;
        }
        leaf ecdhe-ecdsa-aes-gcm-sha2 {
          description
            "Encryption type tls_ecdhe_ecdsa_aes_gcm_sha2
             (TLS 1.2)  SuiteB ciphersuite";
          type empty;
        }
        leaf ecdhe-rsa-aes-128-cbc-sha {
          status deprecated;
          description
            "Encryption type tls_ecdhe_rsa_with_aes_128_cbc_sha
             ciphersuite";
          type empty;
        }
        leaf ecdhe-rsa-aes-cbc-sha2 {
          description
            "Encryption type tls_ecdhe_rsa_aes_cbc_sha2(TLS 1.2)
             ciphersuite";
          type empty;
        }
        leaf ecdhe-rsa-aes-gcm-sha2 {
          description
            "Encryption type tls_ecdhe_rsa_aes_gcm_sha2(TLS 1.2)
             ciphersuite";
          type empty;
        }
        leaf rsa-aes-cbc-sha2 {
          description
            "Encryption type tls_rsa_with_aes_cbc_sha2(TLS 1.2 &)
             ciphersuite";
          type empty;
        }
        leaf rsa-aes-gcm-sha2 {
          description
            "Encryption type tls_rsa_with_aes_gcm_sha2(TLS 1.2)
             ciphersuite";
          type empty;
        }
        leaf tls13-aes128-gcm-sha256 {
          description
            "Encryption type tls13_aes128_gcm_sha256(TLS 1.3)
             ciphersuite";
          type empty;
        }
        leaf tls13-aes256-gcm-sha384 {
          description
            "Encryption type tls13_aes256_gcm_sha384(TLS 1.3)
             ciphersuite";
          type empty;
        }
        leaf tls13-chacha20-poly1305-sha256 {
          description
            "Encryption type tls13_chacha20_poly1305_sha256
             (TLS 1.3) ciphersuite";
          type empty;
        }
      }
      leaf max-connections {
        description
          "max http connections";
        type uint16 {
          range "1..300";
        }
        default "300";
      }
      leaf active-session-modules {
        description
          "Set active session modules";
        type union {
          type enumeration {
            enum none;
            enum all;
          }
          type string;
        }
        default "all";
      }
      leaf secure-active-session-modules {
        description
          "Set secure active session modules";
        type union {
          type enumeration {
            enum none;
            enum all;
          }
          type string;
        }
        default "all";
      }
      leaf secure-client-auth {
        description
          "Set http secure server with client authentication";
        type empty;
      }
      leaf path {
        description
          "Set http path name";
        type string;
      }
      leaf session-idle-timeout {
        description
          "Set http server session idle timeout";
        type uint16 {
          range "180..14400";
        }
        default "600";
      }
      container ctc {
        description
          "Set http ctc configuration";
        if-feature "ios-features:ctc-http-app";
        leaf authentication {
          description
            "Enable ctc authentication";
          type empty;
        }
      }
      container accounting {
        description
          "Set http server accounting parameters";
        list commands {
          description
            "Set method list for command accounting";
          key "level";
          leaf level {
            description
              "Enable level";
            type uint8 {
              range "0..15";
            }
          }
          leaf name {
            description
              "Use an accounting list with this name";
            must "not(.='default')" {
              error-message "Configuration of default is not allowed. To move to default accounting command, remove this configuration";
            }
            type string;
          }
        }
      }
      container secure-piv-based-auth {
        description
          "Set Personal Identity Verification for Web UI";
        presence "true";
        leaf secure-piv-based-author-only {
          description
            "Set Personal Identity Verification authorization only for Web UI";
          type empty;
        }
      }
      list session-module-list {
        key "list-id";
        description
          "Set up a http(s) server session module list";
        leaf list-id {
          description
            "Session module list name";
          type string;
        }
        leaf values {
          description
            "List of comma separated http server session name prefixes";
          type string {
            pattern '[a-zA-Z0-9-_,]+';
          }
        }
      }
    }
  }

  augment "/ios:native/ios:ip" {
    uses config-ip-http-grouping;
  }
}
