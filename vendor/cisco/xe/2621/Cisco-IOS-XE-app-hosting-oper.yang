module Cisco-IOS-XE-app-hosting-oper {
  yang-version 1.1;
  namespace "http://cisco.com/ns/yang/Cisco-IOS-XE-app-hosting-oper";
  prefix app-hosting-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     monitoring app-hosting in a Network Element.
     Copyright (c) 2016-2020, 2022, 2026 by Cisco Systems, Inc.
     All rights reserved.";

  revision 2026-08-01 {
    description
      "- Updated descriptions of several model elements across the model from terse labels to complete English sentences, improving documentation clarity for model consumers.
       - Added application memory utilization support in the memory utilization container.";
    reference
      "3.10.0";
    cisco-semver:module-version "3.10.0";
  }
  revision 2026-02-01 {
    description
      "- Added disk utilization information to the utilization container.
       - Added IOX service status, health, and version details to app-global, including new enumerations for IOX status, health, and synchronization.";
    reference
      "3.9.0";
    cisco-semver:module-version "3.9.0";
  }
  revision 2023-03-01 {
    description
      "- Added CPU percent support for platform resource profiles.
       - Added support for multicast and mirroring in interfaces.";
    reference
      "3.8.0";
    cisco-semver:module-version "3.8.0";
  }
  revision 2022-11-01 {
    description
      "Update yang-version to 1.1";
    reference
      "3.7.0";
    cisco-semver:module-version "3.7.0";
  }
  revision 2022-07-01 {
    description
      "- Added support for multicast traffic to be forwarded to application through AppGigabitEthernet and management interfaces.";
    reference
      "3.6.0";
    cisco-semver:module-version "3.6.0";
  }
  revision 2021-07-01 {
    description
      "- Added support for platform resource profiles.
       - Added MAC address of Internal Ethernet Out-of-band Channel interface.
       - Added the reserved CPU resource shown in 'unit'.";
    reference
      "3.5.0";
    cisco-semver:module-version "3.5.0";
  }
  revision 2021-03-01 {
    description
      "- Added support for IOX enablement.";
    reference
      "3.4.0";
    cisco-semver:module-version "3.4.0";
  }
  revision 2020-11-01 {
    description
      "- Added static IPV6 support.
       - Added CPU percent that is relative to IOX total CPU units.
       - Added URL package path
       - Added support for docker package runtime options";
    reference
      "3.3.0";
    cisco-semver:module-version "3.3.0";
  }
  revision 2019-05-01 {
    description
      "- Add network-name and some docker-related operational details.
       - Added semantic version";
    reference
      "3.2.0";
    cisco-semver:module-version "3.2.0";
  }
  revision 2018-11-29 {
    description
      "- Add option to indicate if activation of an application is allowed or not
       - Cleaned up spelling errors in descriptions.
       - Add global resources.
       - Add DMI notification event.";
    reference
      "3.1.0";
    cisco-semver:module-version "3.1.0";
  }
  revision 2018-06-14 {
    description
      "Rename virtual service to app-hosting";
    reference
      "3.0.0";
    cisco-semver:module-version "3.0.0";
  }
  revision 2018-02-01 {
    description
      "Add owner details to application";
    reference
      "2.1.0";
    cisco-semver:module-version "2.1.0";
  }
  revision 2017-09-25 {
    description
      "Add process details and change network utilization and storage utilization lists";
    reference
      "2.0.0";
    cisco-semver:module-version "2.0.0";
  }
  revision 2017-02-07 {
    description
      "Initial revision";
    reference
      "1.0.0";
    cisco-semver:module-version "1.0.0";
  }

  typedef ioxman-run-status {
    type enumeration {
      enum ioxm-stat-run {
        value 0;
        description
          "IOXMAN is running";
      }
      enum ioxm-stat-no-run {
        value 1;
        description
          "IOXMAN is not running";
      }
      enum ioxm-stat-not-ready {
        value 2;
        description
          "IOXMAN is not ready";
      }
      enum ioxm-stat-na {
        value 3;
        description
          "IOXMAN is not supported";
      }
    }
    description
      "IOXMAN run status";
  }

  typedef iox-run-status {
    type enumeration {
      enum iox-stat-run {
        value 0;
        description
          "IOX is running";
      }
      enum iox-stat-no-run {
        value 1;
        description
          "IOX is not running";
      }
      enum iox-stat-na {
        value 2;
        description
          "IOX is not supported";
      }
    }
    description
      "IOX run status";
  }

  typedef iox-health-status {
    type enumeration {
      enum ioxcaf-stat-stbl {
        value 0;
        description
          "IOX CAF is stable";
      }
      enum ioxcaf-stat-unstb {
        value 1;
        description
          "IOX CAF is unstable";
      }
      enum ioxcaf-stat-na {
        value 2;
        description
          "IOX CAF is not set";
      }
    }
    description
      "IOX health status";
  }

  typedef iox-app-sign-status {
    type enumeration {
      enum iox-app-sign-stat-en {
        value 0;
        description
          "IOX App Signature Verification is enabled";
      }
      enum iox-app-sign-stat-dis {
        value 1;
        description
          "IOX App Signature Verification is disabled";
      }
      enum iox-app-sign-stat-na {
        value 2;
        description
          "IOX App Signature Verification is not set";
      }
    }
    description
      "IOX app signature verification status";
  }

  typedef iox-ha-sync-status {
    type enumeration {
      enum iox-ha-sync-stat-succ {
        value 0;
        description
          "IOX HA sync is successful";
      }
      enum iox-ha-sync-stat-fail {
        value 1;
        description
          "IOX HA sync failed";
      }
      enum iox-ha-sync-stat-stby-unav {
        value 2;
        description
          "IOX HA sync standby is unavailable";
      }
      enum iox-ha-sync-stat-inprog {
        value 3;
        description
          "IOX HA sync is in progress";
      }
      enum iox-ha-sync-stat-dis {
        value 4;
        description
          "IOX HA sync is disabled";
      }
    }
    description
      "IOX HA sync status";
  }

  typedef iox-pkg-policy {
    type enumeration {
      enum iox-pkg-policy-invalid {
        value 0;
        description
          "Package policy is invalid";
      }
      enum iox-pkg-policy-none {
        value 1;
        description
          "Package policy does not set";
      }
      enum iox-pkg-policy-cisco {
        value 2;
        description
          "Package policy is signed by Cisco";
      }
      enum iox-pkg-policy-third-party {
        value 3;
        description
          "Package policy is signed by third party";
      }
      enum iox-pkg-policy-unsigned {
        value 4;
        description
          "Package policy is unsigned";
      }
    }
    description
      "IOX package policy";
  }

  typedef notification-event-severity {
    type enumeration {
      enum critical {
        value 0;
        description
          "Severity critical";
      }
      enum major {
        value 1;
        description
          "Severity major";
      }
      enum minor {
        value 2;
        description
          "Severity minor";
      }
    }
    description
      "Notification event severity";
  }

  typedef notification-event-type {
    type enumeration {
      enum im-iox-enable {
        value 0;
        description
          "IOX is enabled";
      }
      enum im-app-install {
        value 1;
        description
          "Application is installed";
      }
      enum im-app-uninstall {
        value 2;
        description
          "Application is uninstalled";
      }
      enum im-app-start {
        value 3;
        description
          "Application is started";
      }
      enum im-app-no-start {
        value 4;
        description
          "Application is stopped";
      }
      enum im-app-unsolicited {
        value 5;
        description
          "Application is unsolicited";
      }
      enum im-app-activate {
        value 6;
        description
          "Application is activated";
      }
      enum im-app-deactivate {
        value 7;
        description
          "Application is deactivated";
      }
    }
    description
      "Notification event type";
  }

  typedef notification-app-status {
    type enumeration {
      enum im-app-pass {
        value 0;
        description
          "Status pass";
      }
      enum im-app-fail {
        value 1;
        description
          "Status failed";
      }
    }
    description
      "Notification application status";
  }

  typedef notification-app-state {
    type enumeration {
      enum im-state-deployed {
        value 0;
        description
          "Application is in deployed state";
      }
      enum im-state-activated {
        value 1;
        description
          "Application is in activated state";
      }
      enum im-state-running {
        value 2;
        description
          "Application is in running state";
      }
      enum im-state-stopped {
        value 3;
        description
          "Application is in stopped state";
      }
      enum im-state-uninstalled {
        value 4;
        description
          "Application is in uninstalled state";
      }
    }
    description
      "Notification application state";
  }

  grouping application {
    description
      "This object represents a hosted application";
    leaf name {
      type string;
      description
        "Application name";
    }
    leaf installed-version {
      type string;
      description
        "Specifies the version of the installed application package.";
    }
    leaf description {
      type string;
      description
        "Provides a textual description of the application.";
    }
    leaf type {
      type string;
      description
        "Indicates the type or category of the application.";
    }
    leaf owner {
      type string;
      description
        "Which process creates the application";
    }
    leaf activation-allowed {
      type boolean;
      description
        "Does platform allow the activation of the application";
    }
    leaf author {
      type string;
      description
        "Specifies the author or creator of the application.";
    }
  }

  grouping signing {
    description
      "Application signing information";
    leaf key-type {
      type string;
      description
        "Specifies the type of key used to sign the application package.";
    }
    leaf method {
      type string;
      description
        "Method the key was signed";
    }
  }

  grouping licensing {
    description
      "Application licensing information";
    leaf name {
      type string;
      description
        "Specifies the name of the license associated with the application package.";
    }
    leaf version {
      type string;
      description
        "License version";
    }
  }

  grouping package-information {
    description
      "Application packaging information";
    leaf name {
      type string;
      description
        "Package name";
    }
    leaf path {
      type string;
      description
        "Package path";
    }
    container application {
      description
        "Application details";
      uses app-hosting-ios-xe-oper:application;
    }
    container signing {
      description
        "Contains details about the application's signing key and signature method.";
      uses app-hosting-ios-xe-oper:signing;
    }
    container licensing {
      description
        "Contains details about the application's licensing information, such as license name and version.";
      uses app-hosting-ios-xe-oper:licensing;
    }
    leaf url-path {
      type string;
      description
        "URL package path";
    }
    leaf mcast-enabled {
      type boolean;
      description
        "Indicates whether multicast is enabled for the application package.";
    }
  }

  grouping vs-process {
    description
      "Virtual service process information";
    leaf name {
      type string;
      description
        "Specifies the name of the process running within the hosted application.";
    }
    leaf status {
      type string;
      description
        "Specifies the process status string reported for the process running within
         the hosted application. Valid values are:
         'running' (active);
         'stopped' (not running);
         'crashed' (terminated unexpectedly);
         'starting' (being started);
         'unknown' (state cannot be determined).";
    }
    leaf pid {
      type string;
      description
        "Specifies the process identifier (PID) for the process running within the hosted application.";
    }
    leaf uptime {
      type string;
      units "seconds";
      description
        "Specifies the amount of time the process has been running within the hosted application, in seconds.";
    }
    leaf memory {
      type string;
      description
        "Amount of process memory";
    }
  }

  grouping detailed-guest-status {
    description
      "Detailed guest status detail information";
    container processes {
      description
        "Contains process details for the guest application, including the processes child table with one entry per process.";
      uses app-hosting-ios-xe-oper:vs-process;
    }
  }

  grouping resource-reservation {
    description
      "Resource reservation information";
    leaf disk {
      type uint64;
      description
        "Amount of reserved disk space in MB";
    }
    leaf memory {
      type uint64;
      description
        "Amount of reserved memory in MB";
    }
    leaf cpu {
      type uint64;
      description
        "Amount of reserved CPU in unit";
    }
    leaf vcpu {
      type uint64;
      description
        "Amount of reserved VCPU in unit";
    }
    leaf cpu-percent {
      type uint8;
      description
        "Amount of reserved CPU in percent";
    }
  }

  grouping attached-device {
    description
      "Attached device information";
    leaf name {
      type string;
      description
        "Attached device name";
    }
    leaf type {
      type string;
      description
        "Attached device type";
    }
    leaf alias {
      type string;
      description
        "Attached device alias";
    }
  }

  grouping network-interface {
    description
      "Network interface information";
    leaf mac-address {
      type yang:mac-address;
      description
        "MAC address for the network interface";
    }
    leaf attached-interface {
      type string;
      description
        "Attached interface name";
    }
    leaf ipv4-address {
      type inet:ipv4-address;
      description
        "IPv4 address for the network interface";
    }
    leaf network-name {
      type string;
      description
        "Name of the network";
    }
    leaf ipv6-address {
      type inet:ipv6-address;
      description
        "IPv6 address for the network interface";
    }
    leaf intf-mcast {
      type boolean;
      description
        "Status of multicast on network interface";
    }
    leaf intf-mirroring {
      type boolean;
      description
        "Status of mirroring on network interface";
    }
  }

  grouping guest-route {
    description
      "Guest routing information";
    leaf route {
      type string;
      description
        "Guest route of the guest interface";
    }
  }

  grouping resource-admission {
    description
      "Resource admission information";
    leaf state {
      type string;
      description
        "Status of the resource allocation";
    }
    leaf disk-space {
      type string;
      description
        "Amount of disk space allocated for the virtual service in MB";
    }
    leaf memory {
      type string;
      description
        "Amount of memory allocated for the virtual service in MB";
    }
    leaf cpu {
      type uint64;
      description
        "Percentage of CPU allocated for the virtual-service in unit";
    }
    leaf vcpus {
      type string;
      description
        "Amount of VCPUs allocated for the virtual service";
    }
  }

  grouping details {
    description
      "Detailed virtual service information";
    leaf state {
      type string;
      description
        "State of the virtual service";
    }
    container package-information {
      description
        "Virtual service packaging information";
      uses app-hosting-ios-xe-oper:package-information;
    }
    container detailed-guest-status {
      description
        "Contains detailed status information about the guest application.";
      uses app-hosting-ios-xe-oper:detailed-guest-status;
    }
    leaf activated-profile-name {
      type string;
      description
        "Activated resource profile name";
    }
    container resource-reservation {
      description
        "Resource reservation details";
      uses app-hosting-ios-xe-oper:resource-reservation;
    }
    leaf guest-interface {
      type string;
      description
        "Guest interface name";
    }
    container resource-admission {
      description
        "Resources allocated for the virtual service";
      uses app-hosting-ios-xe-oper:resource-admission;
    }
    leaf docker-run-opts {
      type string;
      description
        "Activated Docker Run-Time Options";
    }
    leaf command {
      type string;
      description
        "Docker Run-time command";
    }
    leaf entry-point {
      type string;
      description
        "Docker Run-Time entry point";
    }
    leaf health-status {
      type uint32;
      description
        "Docker container health status";
    }
    leaf last-health-probe-error {
      type string;
      description
        "Specifies the last error encountered during the Docker container health probe for the virtual service.";
    }
    leaf last-health-probe-output {
      type string;
      description
        "Docker Last Health probe Output";
    }
    leaf pkg-run-opt {
      type string;
      description
        "Specifies the runtime options configured for the Docker package associated with the application.";
    }
    leaf ieobc-mac-addr {
      type yang:mac-address;
      description
        "MAC address of Internal Ethernet Out-of-band Channel interface";
    }
  }

  grouping cpu-util {
    description
      "CPU utilization information";
    leaf requested-application-util {
      type uint64;
      description
        "Amount of requested CPU utilization by the virtual service";
    }
    leaf actual-application-util {
      type uint64;
      description
        "Percentage of CPU actual utilization for the virtual service";
    }
    leaf cpu-state {
      type string;
      description
        "State of the CPU utilization for the virtual-service";
    }
  }

  grouping memory-util {
    description
      "Memory utilization information";
    leaf memory-allocation {
      type string;
      description
        "Amount of memory allocated for the virtual service in MB";
    }
    leaf memory-used {
      type string;
      description
        "Amount of used memory for the virtual service in KB";
    }
    leaf app-mem-used {
      type uint64;
      units "kilobytes";
      description
        "Application memory used by the virtual service in KB";
    }
  }

  grouping disk-util-val {
    description
      "Provides detailed information about disk utilization for the virtual service, including allocated and used disk space.";
    leaf disk-alloc {
      type uint64;
      units "Megabytes";
      description
        "Amount of disk allocated for the virtual service in MB";
    }
    leaf disk-used {
      type decimal64 {
        fraction-digits 2;
      }
      units "Megabytes";
      description
        "Amount of used disk for the virtual service in MB";
    }
  }

  grouping network-util {
    description
      "Network utilization information";
    leaf name {
      type string;
      description
        "Name of the network used for the virtual service";
    }
    leaf alias {
      type string;
      description
        "Alias of the network used by the virtual service";
    }
    leaf rx-packets {
      type uint64;
      description
        "Number of packets received by the virtual service";
    }
    leaf rx-bytes {
      type uint64;
      description
        "Number of octets received by the virtual service";
    }
    leaf rx-errors {
      type uint64;
      description
        "Number of RX errors by the virtual service";
    }
    leaf tx-packets {
      type uint64;
      description
        "Number of packets transmitted by the virtual service";
    }
    leaf tx-bytes {
      type uint64;
      description
        "Number of octets transmitted by the virtual service";
    }
    leaf tx-errors {
      type uint64;
      description
        "Number of TX errors by the virtual service";
    }
  }

  grouping storage-util {
    description
      "Storage utilization information";
    leaf name {
      type string;
      description
        "Name of the storage device used for the virtual service";
    }
    leaf alias {
      type string;
      description
        "Alias of the storage device used by the virtual service";
    }
    leaf rd-bytes {
      type uint64;
      description
        "Number of bytes read by the virtual service";
    }
    leaf rd-requests {
      type uint64;
      description
        "Number of read requests made by the virtual service";
    }
    leaf errors {
      type uint64;
      description
        "Number of storage error seen by the virtual service";
    }
    leaf wr-bytes {
      type uint64;
      description
        "Number of bytes written by the virtual service";
    }
    leaf wr-requests {
      type uint64;
      description
        "Number of write requests made by the virtual service";
    }
    leaf capacity {
      type uint64;
      description
        "Storage capacity in 1000 blocks";
    }
    leaf available {
      type string;
      description
        "Available storage in 1000 blocks";
    }
    leaf used {
      type uint64;
      description
        "Used storage in 1000 blocks";
    }
    leaf usage {
      type string;
      description
        "Percentage of storage capacity used by the virtual service";
    }
  }

  grouping utilization {
    description
      "Resource utilization details";
    leaf name {
      type string;
      description
        "Name of the virtual service";
    }
    container cpu-util {
      description
        "CPU utilization information";
      uses app-hosting-ios-xe-oper:cpu-util;
    }
    container memory-util {
      description
        "Memory utilization information";
      uses app-hosting-ios-xe-oper:memory-util;
    }
    container disk-util {
      description
        "Disk utilization information";
      uses app-hosting-ios-xe-oper:disk-util-val;
    }
  }

  grouping plfm-res-prof {
    description
      "Platform resource profiles";
    leaf name {
      type string;
      description
        "Profile name";
    }
    leaf cpu {
      type uint64;
      units "CPU unit";
      description
        "Amount of reserved CPU units for resource profile";
    }
    leaf memory {
      type uint64;
      units "megabytes";
      description
        "Amount of reserved memory";
    }
    leaf disk {
      type uint64;
      units "megabytes";
      description
        "Amount of reserved disk space";
    }
    leaf cpu-percent {
      type uint8;
      units "percentage";
      description
        "Amount of reserved CPU percentage for resource profile";
    }
  }

  grouping virtual-service {
    description
      "Virtual service information";
    leaf name {
      type string;
      description
        "Virtual service name";
    }
    container details {
      description
        "Virtual service details";
      uses app-hosting-ios-xe-oper:details;
    }
    container utilization {
      description
        "Virtual service resource utilization details";
      uses app-hosting-ios-xe-oper:utilization;
    }
    container network-utils {
      description
        "Virtual service network utilization details";
      list network-util {
        key "name";
        description
          "List of network utilization statistics for the virtual service, including metrics such as packets, bytes, and errors for each network interface.";
        uses app-hosting-ios-xe-oper:network-util;
      }
    }
    container storage-utils {
      description
        "Virtual service storage utilization details";
      list storage-util {
        key "name";
        description
          "List of storage utilization details";
        uses app-hosting-ios-xe-oper:storage-util;
      }
    }
    container processes {
      description
        "Virtual service process details";
      list process {
        key "name";
        description
          "List of process details";
        uses app-hosting-ios-xe-oper:vs-process;
      }
    }
    container attached-devices {
      description
        "Virtual service attached device details";
      list attached-device {
        key "name";
        description
          "A list of attached device details";
        uses app-hosting-ios-xe-oper:attached-device;
      }
    }
    container network-interfaces {
      description
        "Virtual service network interface details";
      list network-interface {
        key "mac-address";
        description
          "A list of network interface details";
        uses app-hosting-ios-xe-oper:network-interface;
      }
    }
    container guest-routes {
      description
        "Virtual service guest route details";
      list guest-route {
        key "route";
        description
          "List of guest routes for a guest interface";
        uses app-hosting-ios-xe-oper:guest-route;
      }
    }
    list plfm-res-prof {
      key "name";
      description
        "Platform resource profiles";
      uses app-hosting-ios-xe-oper:plfm-res-prof;
    }
    leaf pkg-policy {
      type app-hosting-ios-xe-oper:iox-pkg-policy;
      description
        "Application package policy type";
    }
  }

  grouping cpu {
    description
      "CPU information";
    leaf name {
      type string;
      description
        "Specifies the CPU resource name reported for the application hosting resource entry.";
    }
    leaf quota {
      type uint32;
      units "percentage";
      description
        "Amount of total system reserved CPU";
    }
    leaf available {
      type uint32;
      units "percentage";
      description
        "Amount of total system available CPU";
    }
    leaf quota-unit {
      type uint64;
      units "unit";
      description
        "Amount of total system reserved CPU units";
    }
    leaf available-unit {
      type uint64;
      units "unit";
      description
        "Amount of total system available CPU units";
    }
  }

  grouping memory {
    description
      "Memory information";
    leaf name {
      type string;
      description
        "Specifies the memory resource name reported for the application hosting resource entry.";
    }
    leaf quota {
      type uint32;
      units "MB";
      description
        "Amount of reserved memory in MB";
    }
    leaf available {
      type uint32;
      units "MB";
      description
        "Amount of available memory in MB";
    }
  }

  grouping storage-device {
    description
      "Storage device information";
    leaf name {
      type string;
      description
        "Storage device name";
    }
    leaf quota {
      type uint32;
      units "MB";
      description
        "Amount of reserved storage space";
    }
    leaf available {
      type uint32;
      units "MB";
      description
        "Amount of available storage space";
    }
  }

  grouping app-resource {
    description
      "Global resources information";
    leaf name {
      type string;
      description
        "Specifies the name of the global resource group for application hosting on the device.";
    }
    list cpu {
      key "name";
      description
        "A list of CPU types";
      uses app-hosting-ios-xe-oper:cpu;
    }
    list memory {
      key "name";
      description
        "A list of memory types";
      uses app-hosting-ios-xe-oper:memory;
    }
    list storage-device {
      key "name";
      description
        "A list of storage device types";
      uses app-hosting-ios-xe-oper:storage-device;
    }
  }

  grouping app-notification {
    description
      "Application event notification";
    leaf name {
      type string;
      description
        "Event name";
    }
    leaf timestamp {
      type yang:date-and-time;
      description
        "Event timestamp";
    }
    leaf severity-level {
      type app-hosting-ios-xe-oper:notification-event-severity;
      description
        "Event severity";
    }
    leaf host-name {
      type string;
      description
        "Host name";
    }
    leaf vrf-name {
      type string;
      description
        "Specifies the name of the Virtual Routing and Forwarding (VRF) instance associated with the interface for this event notification.";
    }
    leaf app-id {
      type string;
      description
        "Specifies the name of the application associated with this event notification.";
    }
    leaf system-ip {
      type inet:ip-address;
      description
        "Specifies the IP address of the host system where the event notification was generated.";
    }
    leaf ev-type {
      type app-hosting-ios-xe-oper:notification-event-type;
      description
        "Indicates the type of event that triggered this notification.";
    }
    leaf status {
      type app-hosting-ios-xe-oper:notification-app-status;
      description
        "Indicates the status of the event, such as whether the event was successful or failed.";
    }
    leaf message {
      type string;
      description
        "Provides a human-readable message with additional details about the event notification.";
    }
    leaf app-state {
      type app-hosting-ios-xe-oper:notification-app-state;
      description
        "Indicates the state of the application at the time of the event.";
    }
  }

  grouping app-global {
    description
      "Global app-hosting information";
    leaf iox-enabled {
      type boolean;
      description
        "IOX enabled or disabled";
    }
    leaf iox-version {
      type string;
      description
        "Specifies the version of IOX running on the device.";
    }
    leaf iox-dir {
      type string;
      description
        "Indicates the working directory used by IOX on the device.";
    }
    leaf iox-app-sign-verify {
      type app-hosting-ios-xe-oper:iox-app-sign-status;
      description
        "Specifies whether IOX application signature verification is enabled on the device.";
    }
    leaf iox-caf-status {
      type app-hosting-ios-xe-oper:iox-run-status;
      description
        "Represents the operational status of the Cisco Application Framework (CAF) on the device.";
    }
    leaf iox-caf-health {
      type app-hosting-ios-xe-oper:iox-health-status;
      description
        "Represents the health of the Cisco Application Framework (CAF) on the device.";
    }
    leaf iox-ha-status {
      type app-hosting-ios-xe-oper:iox-run-status;
      description
        "Represents the operational status of the High Availability (HA) on the device.";
    }
    leaf iox-ioxman-status {
      type app-hosting-ios-xe-oper:ioxman-run-status;
      description
        "Represents the operational status of IOX Management (IOXMAN) on the device.";
    }
    leaf iox-sec-storage-status {
      type app-hosting-ios-xe-oper:iox-run-status;
      description
        "Represents the operational status of IOX Secondary Storage on the device.";
    }
    leaf iox-libvirtd-status {
      type app-hosting-ios-xe-oper:iox-run-status;
      description
        "Represents the operational status of IOX libvirtd on the device.";
    }
    leaf iox-libvirtd-version {
      type string;
      description
        "Specifies the version of the libvirtd infrastructure used by IOX.";
    }
    leaf iox-dockerd-status {
      type app-hosting-ios-xe-oper:iox-run-status;
      description
        "Represents the operational status of IOX dockerd on the device.";
    }
    leaf iox-dockerd-version {
      type string;
      description
        "Specifies the version of the Docker daemon (dockerd) infrastructure used by IOX.";
    }
    leaf iox-ha-sync-status {
      type app-hosting-ios-xe-oper:iox-ha-sync-status;
      description
        "Specifies the IOX High Availability (HA) synchronization status on the device.";
    }
  }

  container app-hosting-oper-data {
    config false;
    description
      "Information on all applications";
    list app {
      key "name";
      description
        "List of applications";
      uses app-hosting-ios-xe-oper:virtual-service;
    }
    list app-resources {
      key "name";
      description
        "Lists the global resources available for application hosting on the device; each entry represents one resource group.";
      uses app-hosting-ios-xe-oper:app-resource;
    }
    list app-notifications {
      key "name";
      description
        "Contains a list of event notifications generated by applications hosted on the device.";
      uses app-hosting-ios-xe-oper:app-notification;
    }
    container app-globals {
      presence "app-globals";
      description
        "Global app-hosting information";
      uses app-hosting-ios-xe-oper:app-global;
    }
  }
}
