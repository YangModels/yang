module Cisco-IOS-XE-wireless-mesh-global-oper {
  yang-version 1.1;
  namespace "http://cisco.com/ns/yang/Cisco-IOS-XE-wireless-mesh-global-oper";
  prefix wireless-mesh-global-oper;

  import Cisco-IOS-XE-wireless-types {
    prefix wireless-types;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains mesh operational data aggregated across wireless processes.
     Copyright (c) 2021-2022,2026 by Cisco Systems, Inc.
     All rights reserved.";

  revision 2026-08-01 {
    description
      "Updated descriptions of several model elements to clarify their meaning and purpose";
    reference
      "2.0.0";
    cisco-semver:module-version "2.0.0";
  }
  revision 2022-11-01 {
    description
      "Update yang-version to 1.1";
    reference
      "1.1.0";
    cisco-semver:module-version "1.1.0";
  }
  revision 2022-03-01 {
    description
      "Initial revision";
    reference
      "1.0.0";
    cisco-semver:module-version "1.0.0";
  }

  grouping st-mesh-global-stats {
    description
      "Statistics of mesh AP's joined to the controller";
    leaf num-of-bridge-aps {
      type uint32;
      description
        "Total number of bridge mode Access Points joined to the controller";
    }
    leaf num-of-maps {
      type uint32;
      description
        "Total number of mesh Access Points (MAPs) joined to the controller";
    }
    leaf num-of-raps {
      type uint32;
      description
        "Total number of root Access Points (RAPs) joined to the controller";
    }
    leaf num-of-flex-bridge-aps {
      type uint32;
      description
        "Total number of Access Points operating in flex bridge mode joined to the controller";
    }
    leaf num-of-flex-bridge-maps {
      type uint32;
      description
        "Total number of mesh Access Points (MAPs) operating in flex bridge mode joined to the controller";
    }
    leaf num-of-flex-bridge-raps {
      type uint32;
      description
        "Total number of root Access Points (RAPs) operating in flex bridge mode joined to the controller";
    }
  }

  grouping st-emltd-mesh-ap-info {
    description
      "Mesh AP tree info";
    leaf ap-name {
      type string;
      description
        "Name of the mesh Access Point";
    }
    leaf ap-role {
      type wireless-types:ap-role;
      description
        "Role of the bridge mode Access Point, either root or mesh";
    }
    leaf bridge-group-name {
      type string;
      description
        "Bridge group name configured on this Access Point";
    }
    leaf pref-parent-ap-name {
      type string;
      description
        "Name of the configured preferred parent Access Point for this AP in the mesh tree";
    }
    leaf depth {
      type uint8;
      description
        "Depth of mesh AP in the mesh tree";
    }
    leaf link-snr {
      type uint8;
      units "dB";
      description
        "Calculated SNR of the link";
    }
    leaf curr-freq {
      type uint16;
      description
        "Current operating channel on the AP radio";
    }
    leaf chan-util {
      type uint16;
      units "percentage";
      description
        "Percentage of channel bandwidth currently utilized by the mesh Access Point radio";
    }
    leaf clients-count {
      type uint16;
      description
        "Total number of clients connected to the mesh AP";
    }
    leaf not-in-this-wlc {
      type boolean;
      description
        "Indicates mesh AP connected to other controller";
    }
    leaf parent-info-not-avail {
      type boolean;
      description
        "Indicates whether parent Access Point information is unavailable for this mesh Access Point; true if information is not available, false otherwise";
    }
  }

  grouping st-emltd-mesh-ap-tree-data {
    description
      "Mesh tree info";
    leaf mesh-ap-count {
      type uint32;
      description
        "Number of Bridge AP's";
    }
    leaf rap-count {
      type uint32;
      description
        "Number of root AP's";
    }
    leaf map-count {
      type uint32;
      description
        "Total number of mesh Access Points (MAPs) joined to the controller";
    }
    list mesh-ap-list {
      description
        "List of Mesh AP's with path info";
      uses wireless-mesh-global-oper:st-emltd-mesh-ap-info;
    }
  }

  grouping st-emltd-mesh-path-info {
    description
      "Path info of a mesh AP";
    leaf ap-name {
      type string;
      description
        "Name of the mesh Access Point";
    }
    leaf ap-role {
      type wireless-types:ap-role;
      description
        "Role of the bridge mode Access Point, either root or mesh";
    }
    leaf depth {
      type uint8;
      description
        "Depth of mesh AP in the mesh tree";
    }
    leaf link-snr {
      type uint8;
      units "dB";
      description
        "Calculated SNR of the link";
    }
    leaf curr-freq {
      type uint16;
      description
        "Current operating channel on the AP radio";
    }
    leaf rate {
      type string;
      description
        "Mesh backhaul data rate represented as a format string; for legacy 802.11a/b/g, the value is a numeric rate in Mbps.
         The format depends on the 802.11 standard in use:
         802.11ax (HE) - Format m<MCS>ss<SS> where MCS is 0-11
           and SS is the number of spatial streams (1-8).
           Examples: m0ss1, m9ss2, m11ss4.
         802.11ac (VHT) - Format m<MCS>ss<SS> where MCS is 0-9
           and SS is the number of spatial streams (1-8).
           Examples: m0ss1, m9ss2, m7ss4.
         802.11n (HT) - Format m<MCS> where MCS is the MCS
           index (0-31).
           Examples: m0, m7, m15, m31.
         Legacy 802.11a/b/g - Raw data rate as a numeric string
           in Mbps.
           Examples: 1, 6, 12, 24, 54.
         Auto - The string auto when the rate is not set
           or set to automatic rate selection.";
    }
    leaf flags {
      type uint32;
      description
        "Indicates mesh node status as a bitmap.
         Bit 0  - received an update for this adjacency
         Bit 1  - node is the parent
         Bit 2  - node is updated in seek state as tentative parent
         Bit 3  - node is a neighbor
         Bit 4  - node is excluded from parent selection
         Bit 5  - node is on the hash table
         Bit 6  - node is allocated
         Bit 7  - SNR value set by the controller is used for parent selection
         Bit 8  - node is a child
         Bit 9  - needs a fresh update before being considered for parent selection
         Bit 10 - topology update notification is pending to the parent node
         Bit 11 - this is a beacon entry
         Bit 12 - entry connected with default network name
         Bit 13 - node was previously blocked
         Bit 14 - node block backoff exponent can be incremented
         Bit 15 - sibling information is available
         Bit 16 - sibling information template is available
         Bit 17 - node is forced as the parent
         Bit 18 - adjacency is learned via wired Ethernet link
         Bit 19 - a stale timed out entry
         Bit 20 - channel width has changed";
    }
    leaf state {
      type string;
      description
        "Space-separated combination of mesh node adjacency state flags derived from the flags bitmask.
         Possible values are:
         UPDATED     - received an update for this adjacency
         PARENT      - node is the parent
         SEEKED      - node is updated in seek state as tentative parent
         NEIGH       - node is a neighbor
         EXCLUDED    - node is excluded from parent selection
         HASH        - node is on the hash table
         ALLOC       - node is allocated
         PERMSNR     - SNR value set by the controller is used for parent selection
         CHILD       - node is a child
         NEEDUPDATE  - needs a fresh update before being considered for parent selection
         TRIGGER     - topology update notification is pending to the parent node
         BEACON      - this is a beacon entry
         DEFAULT     - entry connected with default network name
         WASBLOCK    - node was previously blocked
         INCRBLEXP   - node block backoff exponent can be incremented
         SIBINFO     - sibling information is available
         SIBINFOTEMP - sibling information template is available
         PARENTFORCE - node is forced as the parent
         ETHERNET    - adjacency is learned via wired Ethernet link
         STALE       - a stale timed out entry
         CHANWIDTH   - channel width has changed";
    }
    leaf not-in-this-wlc {
      type boolean;
      description
        "Indicates mesh AP connected to other controller";
    }
  }

  grouping st-emltd-mesh-ap-path-info {
    description
      "List of mesh AP's path info";
    leaf wtp-name {
      type string;
      description
        "Name of the mesh Access Point";
    }
    list mesh-ap-list {
      description
        "Mesh AP's with path info";
      uses wireless-mesh-global-oper:st-emltd-mesh-path-info;
    }
  }

  grouping st-emltd-mesh-cac-info {
    description
      "Call admission control information of the mesh AP";
    leaf ap-name {
      type string;
      description
        "Name of the mesh Access Point associated with this call admission control (CAC) information";
    }
    leaf depth {
      type uint8;
      description
        "Depth of mesh AP in the mesh tree";
    }
    leaf radio-type-slot-id-0 {
      type uint8;
      description
        "Radio identifier for slot 0 on the mesh Access Point";
    }
    leaf radio-type-slot-id-1 {
      type uint8;
      description
        "Radio identifier for slot 1 on the mesh Access Point";
    }
    leaf access-call-bw-24ghz {
      type uint16;
      units "MHz";
      description
        "Access call bandwidth at 24 ghz";
    }
    leaf access-call-bw-5ghz {
      type uint16;
      units "MHz";
      description
        "Access call bandwidth at 5 ghz";
    }
    leaf voice-bw-allocated-24ghz {
      type uint32;
      units "MHz";
      description
        "Voice bandwidth being allocated for 24 ghz radio";
    }
    leaf voice-bw-allocated-5ghz {
      type uint32;
      units "MHz";
      description
        "Voice bandwidth being allocated for 5 ghz radio";
    }
    leaf mesh-call-in-progress-5ghz {
      type uint16;
      description
        "Number of access and mesh calls in progress on radio 5 ghz";
    }
    leaf mesh-call-rejected-24ghz {
      type uint16;
      description
        "Number of mesh calls rejected on radio 24 ghz";
    }
    leaf mesh-call-rejected-5ghz {
      type uint16;
      description
        "Number of mesh calls rejected on radio 5 ghz";
    }
    leaf total-active-calls-24ghz {
      type uint16;
      description
        "Number of active calls on radio 24 ghz";
    }
    leaf total-active-calls-5ghz {
      type uint16;
      description
        "Number of active calls on radio 5 ghz";
    }
    leaf call-in-progress-24ghz {
      type uint16;
      description
        "Number of access and mesh calls in progress on radio 24 ghz";
    }
  }

  grouping st-emltd-mesh-ap-cac-info {
    description
      "List mesh AP's Call admission control information";
    leaf wtp-name {
      type string;
      description
        "Name of the mesh Access Point for which call admission control (CAC) statistics are reported";
    }
    list cac-info-list {
      description
        "Mesh AP's with cac info";
      uses wireless-mesh-global-oper:st-emltd-mesh-cac-info;
    }
  }

  container mesh-global-oper-data {
    config false;
    description
      "Root container for mesh operational data aggregated across wireless processes";
    container mesh-global-stats {
      presence "mesh-global-stats";
      description
        "Summary of mesh AP statistics";
      uses wireless-mesh-global-oper:st-mesh-global-stats;
    }
    list mesh-ap-cac-info {
      key "wtp-name";
      description
        "Summary of mesh voice call statistics";
      uses wireless-mesh-global-oper:st-emltd-mesh-ap-cac-info;
    }
    list mesh-ap-path-info {
      key "wtp-name";
      description
        "Mesh AP path from root AP to mesh AP";
      uses wireless-mesh-global-oper:st-emltd-mesh-ap-path-info;
    }
    list mesh-ap-tree-data {
      key "sector-number wtp-mac";
      description
        "Mesh AP tree view";
      uses wireless-types:ewlc-mesh-sector-root-key;
      uses wireless-mesh-global-oper:st-emltd-mesh-ap-tree-data;
    }
  }
}
