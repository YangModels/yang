module cisco-xe-switching-openconfig-platform-deviation {
  namespace "http://cisco.com/ns/yang/cisco-xe-switching-openconfig-platform-deviation";
  prefix cisco-xe-switching-oc-platform-devs;

  import openconfig-platform {
    prefix oc-platform;
  }
  import openconfig-platform-transceiver {
    prefix oc-transceiver;
  }
  import openconfig-platform-port {
    prefix oc-port;
  }

  organization
    "Cisco Systems, Inc.";
  contact
    " Cisco Systems, Inc.
     Customer Service

     Postal: 170 W Tasman Drive
     San Jose, CA 95134

     Tel: +1 1800 553-NETS

     E-mail: cs-yang@cisco.com";
  description
    "This module defines deviation statements for openconfig-platform module for IOS XE Cat9K Switching devices.";

  revision 2021-09-20 {
    description
      "Deviated unsupported leaves for oc-state mfg-name and mfg-date";
  }
  revision 2021-03-22 {
    description
      "Removed deviations for temperature/oc-platform:average/min/max xpaths";
  }
  revision 2018-08-28 {
    description
      "Deviations for component/breakout-mode config and oper";
  }
  revision 2018-01-25 {
    description
      "Deviated unsupported leaves for oc-port and oc-transceiver";
  }
  revision 2017-09-01 {
    description
      "Hided avg/min/max temperature because we do not support them";
  }
  revision 2017-03-21 {
    description
      "Initial Revision";
    reference
      "RFC 6020: YANG - A Data Modeling Language for the
       Network Configuration Protocol (NETCONF)";
  }

  deviation "/oc-platform:components/oc-platform:component/oc-platform:properties/oc-platform:property/oc-platform:name" {
    deviate replace {
      type string;
    }
    description
      "platform is oper only in Cisco XE device.";
  }

  deviation "/oc-platform:components/oc-platform:component/oc-platform:subcomponents/oc-platform:subcomponent/oc-platform:name" {
    deviate replace {
      type string;
    }
    description
      "platform is oper only in Cisco XE device.";
  }

  deviation "/oc-platform:components/oc-platform:component/oc-platform:subcomponents/oc-platform:subcomponent/oc-platform:state/oc-platform:name" {
    deviate replace {
      type string;
    }
    description
      "platform is oper only in Cisco XE device.";
  }

  deviation "/oc-platform:components/oc-platform:component/oc-platform:name" {
    deviate replace {
      type string;
    }
    description
      "platform is oper only in Cisco XE device.";
  }

  deviation "/oc-platform:components/oc-platform:component/oc-platform:properties/oc-platform:property/oc-platform:name" {
    deviate replace {
      config false;
    }
    description
      "platform is oper only in Cisco XE device.";
  }

  deviation "/oc-platform:components/oc-platform:component/oc-platform:subcomponents/oc-platform:subcomponent/oc-platform:name" {
    deviate replace {
      config false;
    }
    description
      "platform is oper only in Cisco XE device.";
  }

  deviation "/oc-platform:components/oc-platform:component/oc-platform:properties" {
    deviate replace {
      config false;
    }
    description
      "platform is oper only in Cisco XE device.";
  }

  deviation "/oc-platform:components/oc-platform:component/oc-platform:properties/oc-platform:property" {
    deviate replace {
      config false;
    }
    description
      "platform is oper only in Cisco XE device.";
  }

  deviation "/oc-platform:components/oc-platform:component/oc-platform:subcomponents" {
    deviate replace {
      config false;
    }
    description
      "platform is oper only in Cisco XE device.";
  }

  deviation "/oc-platform:components/oc-platform:component/oc-platform:subcomponents/oc-platform:subcomponent" {
    deviate replace {
      config false;
    }
    description
      "platform is oper only in Cisco XE device.";
  }

  deviation "/oc-platform:components/oc-platform:component/oc-transceiver:transceiver/oc-transceiver:config" {
    deviate not-supported;
  }

  deviation "/oc-platform:components/oc-platform:component/oc-transceiver:transceiver/oc-transceiver:state/oc-transceiver:fault-condition" {
    deviate not-supported;
  }

  deviation "/oc-platform:components/oc-platform:component/oc-transceiver:transceiver/oc-transceiver:state/oc-transceiver:vendor-rev" {
    deviate replace {
      type string;
    }
  }

  deviation "/oc-platform:components/oc-platform:component/oc-transceiver:transceiver/oc-transceiver:state/oc-transceiver:date-code" {
    deviate replace {
      type string;
    }
  }

  deviation "/oc-platform:components/oc-platform:component/oc-transceiver:transceiver/oc-transceiver:physical-channels/oc-transceiver:channel/oc-transceiver:index" {
    deviate replace {
      type uint16;
      config false;
    }
  }

  deviation "/oc-platform:components/oc-platform:component/oc-transceiver:transceiver/oc-transceiver:physical-channels/oc-transceiver:channel/oc-transceiver:config" {
    deviate not-supported;
  }

  deviation "/oc-platform:components/oc-platform:component/oc-transceiver:transceiver/oc-transceiver:physical-channels/oc-transceiver:channel/oc-transceiver:state/oc-transceiver:description" {
    deviate not-supported;
  }

  deviation "/oc-platform:components/oc-platform:component/oc-transceiver:transceiver/oc-transceiver:physical-channels/oc-transceiver:channel/oc-transceiver:state/oc-transceiver:target-output-power" {
    deviate not-supported;
  }

  deviation "/oc-platform:components/oc-platform:component/oc-transceiver:transceiver/oc-transceiver:physical-channels/oc-transceiver:channel/oc-transceiver:state/oc-transceiver:tx-laser" {
    deviate not-supported;
  }

  deviation "/oc-platform:components/oc-platform:component/oc-transceiver:transceiver/oc-transceiver:physical-channels/oc-transceiver:channel/oc-transceiver:state/oc-transceiver:output-frequency" {
    deviate not-supported;
  }

  deviation "/oc-platform:components/oc-platform:component/oc-transceiver:transceiver/oc-transceiver:physical-channels/oc-transceiver:channel/oc-transceiver:state/oc-transceiver:input-power/oc-transceiver:avg" {
    deviate not-supported;
  }

  deviation "/oc-platform:components/oc-platform:component/oc-transceiver:transceiver/oc-transceiver:physical-channels/oc-transceiver:channel/oc-transceiver:state/oc-transceiver:input-power/oc-transceiver:min" {
    deviate not-supported;
  }

  deviation "/oc-platform:components/oc-platform:component/oc-transceiver:transceiver/oc-transceiver:physical-channels/oc-transceiver:channel/oc-transceiver:state/oc-transceiver:input-power/oc-transceiver:max" {
    deviate not-supported;
  }

  deviation "/oc-platform:components/oc-platform:component/oc-transceiver:transceiver/oc-transceiver:physical-channels/oc-transceiver:channel/oc-transceiver:state/oc-transceiver:output-power/oc-transceiver:avg" {
    deviate not-supported;
  }

  deviation "/oc-platform:components/oc-platform:component/oc-transceiver:transceiver/oc-transceiver:physical-channels/oc-transceiver:channel/oc-transceiver:state/oc-transceiver:output-power/oc-transceiver:min" {
    deviate not-supported;
  }

  deviation "/oc-platform:components/oc-platform:component/oc-transceiver:transceiver/oc-transceiver:physical-channels/oc-transceiver:channel/oc-transceiver:state/oc-transceiver:output-power/oc-transceiver:max" {
    deviate not-supported;
  }

  deviation "/oc-platform:components/oc-platform:component/oc-transceiver:transceiver/oc-transceiver:physical-channels/oc-transceiver:channel/oc-transceiver:state/oc-transceiver:laser-bias-current/oc-transceiver:avg" {
    deviate not-supported;
  }

  deviation "/oc-platform:components/oc-platform:component/oc-transceiver:transceiver/oc-transceiver:physical-channels/oc-transceiver:channel/oc-transceiver:state/oc-transceiver:laser-bias-current/oc-transceiver:min" {
    deviate not-supported;
  }

  deviation "/oc-platform:components/oc-platform:component/oc-transceiver:transceiver/oc-transceiver:physical-channels/oc-transceiver:channel/oc-transceiver:state/oc-transceiver:laser-bias-current/oc-transceiver:max" {
    deviate not-supported;
  }

  deviation "/oc-platform:components/oc-platform:component/oc-platform:state/oc-platform:mfg-date" {
    deviate not-supported;
    description
      "oc-platform mfg-date is not supported in 17.7.";
  }

  deviation "/oc-platform:components/oc-platform:component/oc-platform:state/oc-platform:mfg-name" {
    deviate not-supported;
    description
      "oc-platform mfg-name is not supported in 17.7.";
  }

  deviation "/oc-platform:components/oc-platform:component/oc-platform:port/oc-port:breakout-mode/oc-port:config/oc-port:num-channels" {
    deviate add {
      must '.=4' {
        error-message "num-channels must be set to 4";
      }
    }
  }

  deviation "/oc-platform:components/oc-platform:component/oc-platform:port/oc-port:breakout-mode/oc-port:config/oc-port:channel-speed" {
    deviate not-supported;
  }
}
