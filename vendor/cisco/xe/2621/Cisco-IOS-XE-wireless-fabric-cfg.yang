module Cisco-IOS-XE-wireless-fabric-cfg {
  yang-version 1.1;
  namespace "http://cisco.com/ns/yang/Cisco-IOS-XE-wireless-fabric-cfg";
  prefix wireless-fabric-cfg;

  import Cisco-IOS-XE-wireless-enum-types {
    prefix wireless-enum-types;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Model for managing fabric mode configuration.
     Copyright (c) 2016-2022, 2026 by Cisco Systems, Inc.
     All rights reserved.";

  revision 2026-08-01 {
    description
      "Updated descriptions for fabric profiles, VNID mappings, and control plane YANG model elements";
    reference
      "6.0.1";
    cisco-semver:module-version "6.0.1";
  }
  revision 2024-03-01 {
    description
      "Add fabric control plane ip and fabric name network ip check";
    reference
      "6.0.0";
    cisco-semver:module-version "6.0.0";
  }
  revision 2023-03-01 {
    description
      "Add fabric control plane description length check";
    reference
      "5.0.0";
    cisco-semver:module-version "5.0.0";
  }
  revision 2022-11-01 {
    description
      "- Update yang-version to 1.1
       - Add fabric control plane authentication key length check";
    reference
      "4.1.0";
    cisco-semver:module-version "4.1.0";
  }
  revision 2021-03-01 {
    description
      "- Add ASCII 32-126 and leading/trailing spaces restriction for fabric profile name,
       - Support 32 character length for control plane and fabric profile name";
    reference
      "4.0.0";
    cisco-semver:module-version "4.0.0";
  }
  revision 2020-07-01 {
    description
      "Add constraints to allow only ASCII 32-126 in fabric profile name, fabric name and control plane name";
    reference
      "3.3.0";
    cisco-semver:module-version "3.3.0";
  }
  revision 2019-05-01 {
    description
      "Added semantic version";
    reference
      "3.2.0";
    cisco-semver:module-version "3.2.0";
  }
  revision 2018-12-15 {
    description
      "Modifying ordering of elements in fabric VNID config";
    reference
      "3.1.0";
    cisco-semver:module-version "3.1.0";
  }
  revision 2018-03-08 {
    description
      "Add constraints to fabric profile and control plane";
    reference
      "3.0.0";
    cisco-semver:module-version "3.0.0";
  }
  revision 2018-01-24 {
    description
      "The first generally available version";
    reference
      "2.0.0";
    cisco-semver:module-version "2.0.0";
  }
  revision 2017-05-05 {
    description
      "Initial revision";
    reference
      "1.0.0";
    cisco-semver:module-version "1.0.0";
  }

  typedef enm-fabric-profile-encap-type {
    type enumeration {
      enum dont-use {
        value 0;
        description
          "Not a Valid Type";
      }
      enum fabric-encap-type-vxlan {
        value 1;
        description
          "VXLAN Encapsulation Type for Fabric data path";
      }
    }
    description
      "Enumeration of Encapsulation Types for Fabric Data Path";
  }

  grouping fabric {
    description
      "Fabric Profile details";
    leaf fabric-profile-name {
      type string {
        length "0..32";
        pattern '[!-~]([ -~]*[!-~])?';
      }
      description
        "Fabric Profile name";
    }
    leaf description {
      type string;
      default "";
      description
        "Fabric profile description";
    }
    leaf encap-type {
      type wireless-fabric-cfg:enm-fabric-profile-encap-type;
      default "fabric-encap-type-vxlan";
      description
        "Encapsulation type used in this profile";
    }
    leaf sgt-tag {
      type uint16 {
        range "2 .. 65519";
      }
      description
        "Group tag associated with the fabric profile";
    }
    leaf client-l2-vnid {
      type uint32 {
        range "0 .. 16777215";
      }
      default "0";
      description
        "Client Virtual Network ID";
    }
  }

  grouping fabric-name-vnid {
    description
      "Fabric Name Identifier";
    leaf name {
      type string {
        length "0..32";
        pattern '[ -~]+';
      }
      description
        "Fabric name for AP Join and VNID override";
    }
    leaf l2-vnid {
      type uint32 {
        range "0 .. 16777215";
      }
      description
        "VNID for Client subnet";
    }
    leaf l3-vnid {
      type uint32 {
        range "0 .. 16777215";
      }
      default "0";
      description
        "VNID for AP Subnet";
    }
    leaf netmask {
      type inet:ip-address;
      default "0.0.0.0";
      description
        "Network mask of AP subnet";
    }
    leaf network-ip {
      type inet:ip-address;
      must "../network-ip != '0.0.0.0'" {
        error-message "Null IPv4 address is invalid";
        error-app-tag "must-violation";
      }
      must "(../network-ip != '255.255.255.0') and (../network-ip != '255.255.0.0') and (../network-ip != '255.0.0.0')" {
        error-message "Invalid IPv4 AP address provided";
        error-app-tag "must-violation";
      }
      must "../network-ip != '255.255.255.255'" {
        error-message "Broadcast IPv4 address is invalid";
        error-app-tag "must-violation";
      }
      must "not(starts-with(../network-ip, '127.'))" {
        error-message "Loopback IPv4 address is invalid";
        error-app-tag "must-violation";
      }
      must "not(starts-with(../network-ip, '224.')) and not(starts-with(../network-ip, '225.')) and not(starts-with(../network-ip, '226.')) and not(starts-with(../network-ip, '227.')) and not(starts-with(../network-ip, '228.')) and not(starts-with(../network-ip, '229.')) and not(starts-with(../network-ip, '230.')) and not(starts-with(../network-ip, '231.')) and not(starts-with(../network-ip, '232.')) and not(starts-with(../network-ip, '233.')) and not(starts-with(../network-ip, '234.')) and not(starts-with(../network-ip, '235.')) and not(starts-with(../network-ip, '236.')) and not(starts-with(../network-ip, '237.')) and not(starts-with(../network-ip, '238.')) and not(starts-with(../network-ip, '239.'))" {
        error-message "Multicast IPv4 address is invalid";
        error-app-tag "must-violation";
      }
      must "../network-ip != '0::0'" {
        error-message "Null IPv6 address is invalid";
        error-app-tag "must-violation";
      }
      must "../network-ip != 'ffff:ffff:ffff:ffff:ffff:ffff:ffff:ffff'" {
        error-message "Subnet mask IPv6 address is invalid";
        error-app-tag "must-violation";
      }
      must "../network-ip != '0::1'" {
        error-message "Loopback IPv6 address is invalid";
        error-app-tag "must-violation";
      }
      must "not(contains(substring(../network-ip, 1, 4), 'fe80'))" {
        error-message "Link-local IPv6 address is invalid";
        error-app-tag "must-violation";
      }
      must "not(contains(substring(../network-ip, 1, 4), 'fec0'))" {
        error-message "Site-local IPv6 address is invalid";
        error-app-tag "must-violation";
      }
      must "not(contains(substring(../network-ip, 1, 4), 'ff00'))" {
        error-message "Multicast IPv6 address is invalid";
        error-app-tag "must-violation";
      }
      description
        "IP address of AP Subnet";
    }
    leaf control-plane-name {
      type string {
        pattern '[ -~]+';
      }
      description
        "Fabric Control Plane name";
    }
  }

  grouping fabric-control-plane {
    description
      "Fabric Control Plane information";
    leaf control-plane-ip {
      type inet:ip-address;
      must "../control-plane-ip != '0.0.0.0'" {
        error-message "Null IPv4 address is invalid for control plane address";
        error-app-tag "must-violation";
      }
      must "(../control-plane-ip != '255.255.255.0') and (../control-plane-ip != '255.255.0.0') and (../control-plane-ip != '255.0.0.0')" {
        error-message "Invalid IPv4 control plane address provided";
        error-app-tag "must-violation";
      }
      must "../control-plane-ip != '255.255.255.255'" {
        error-message "Broadcast IPv4 address is invalid for control plane address";
        error-app-tag "must-violation";
      }
      must "not(starts-with(../control-plane-ip, '127.'))" {
        error-message "Loopback IPv4 address is invalid for control plane address";
        error-app-tag "must-violation";
      }
      must "not(starts-with(../control-plane-ip, '224.')) and not(starts-with(../control-plane-ip, '225.')) and not(starts-with(../control-plane-ip, '226.')) and not(starts-with(../control-plane-ip, '227.')) and not(starts-with(../control-plane-ip, '228.')) and not(starts-with(../control-plane-ip, '229.')) and not(starts-with(../control-plane-ip, '230.')) and not(starts-with(../control-plane-ip, '231.')) and not(starts-with(../control-plane-ip, '232.')) and not(starts-with(../control-plane-ip, '233.')) and not(starts-with(../control-plane-ip, '234.')) and not(starts-with(../control-plane-ip, '235.')) and not(starts-with(../control-plane-ip, '236.')) and not(starts-with(../control-plane-ip, '237.')) and not(starts-with(../control-plane-ip, '238.')) and not(starts-with(../control-plane-ip, '239.'))" {
        error-message "Multicast IPv4 address is invalid for control plane address";
        error-app-tag "must-violation";
      }
      must "../control-plane-ip != '0::0'" {
        error-message "Null IPv6 address is invalid for control plane address";
        error-app-tag "must-violation";
      }
      must "../control-plane-ip != 'ffff:ffff:ffff:ffff:ffff:ffff:ffff:ffff'" {
        error-message "Subnet mask IPv6 address is invalid for control plane address";
        error-app-tag "must-violation";
      }
      must "../control-plane-ip != '0::1'" {
        error-message "Loopback IPv6 address is invalid for control plane address";
        error-app-tag "must-violation";
      }
      must "not(contains(substring(../control-plane-ip, 1, 4), 'fe80'))" {
        error-message "Link-local IPv6 address is invalid for control plane address";
        error-app-tag "must-violation";
      }
      must "not(contains(substring(../control-plane-ip, 1, 4), 'fec0'))" {
        error-message "Site-local IPv6 address is invalid for control plane address";
        error-app-tag "must-violation";
      }
      must "not(contains(substring(../control-plane-ip, 1, 4), 'ff00'))" {
        error-message "Multicast IPv6 address is invalid for control plane address";
        error-app-tag "must-violation";
      }
      description
        "IP address of the Control Plane";
    }
    leaf psk-key {
      type string;
      must "((../psk-key-type = 'clear') and (string-length(../psk-key) >= 1) and (string-length(../psk-key) <= 64)) or ((../psk-key-type != 'clear') and (string-length(../psk-key) <= 227))" {
        error-message "ASCII PSK must be in the range of 1-64 characters and non-ASCII PSK must not exceed 227 characters";
        error-app-tag "must-violation";
      }
      default "";
      description
        "PSK associated with the Control Plane entity";
    }
    leaf psk-key-type {
      type wireless-enum-types:crypt-type;
      default "clear";
      description
        "PSK type for the Control Plane";
    }
  }

  grouping fabric-control-plane-name {
    description
      "Fabric Control Plane Name Configuration";
    leaf control-plane-name {
      type string {
        length "0..32";
        pattern '[ -~]+';
      }
      description
        "Specifies the name assigned to the Fabric Control Plane,
         used to identify and reference the control plane entity within the fabric configuration";
    }
    leaf description {
      type string;
      must '(string-length(../description) <= 64)' {
        error-message "Description should not exceed 64 characters";
        error-app-tag "must-violation";
      }
      description
        "Provides a user-defined description for the Fabric Control Plane,
         allowing administrators to add contextual information or notes about the control plane entity";
    }
    container fabric-control-plane-ip-configs {
      description
        "Container for the list of Fabric Control Plane IP configuration objects,
         defining the IP addresses and related settings for the control plane";
      list fabric-control-plane-ip-config {
        key "control-plane-ip";
        max-elements 2;
        description
          "List of Fabric Control Plane Configuration objects";
        uses wireless-fabric-cfg:fabric-control-plane;
      }
    }
  }

  grouping fabric-cfg {
    description
      "Global Fabric Configuration";
    leaf fabric-enabled {
      type boolean;
      default "false";
      description
        "Global Fabric Enable";
    }
    container fabric-name-vnid-entries {
      description
        "Container for global Virtual Network Identifier (VNID)
         name mappings, used to associate fabric names with their corresponding
         Virtual Network Identifiers for AP join and subnet configuration";
      list fabric-name-vnid-entry {
        key "name";
        unique "l2-vnid";
        description
          "Entry mapping a fabric name to its associated Layer 2
           and Layer 3 Virtual Network Identifiers, network IP, and control plane name
           for global fabric configuration";
        uses wireless-fabric-cfg:fabric-name-vnid {
          refine "l2-vnid" {
            mandatory true;
          }
        }
      }
    }
  }

  container fabric-cfg-data {
    description
      "SDA Wireless Configuration Data";
    container fabric-profiles {
      description
        "Container for the list of fabric profiles, which define
         encapsulation and group tag settings for fabric networks";
      list fabric-profile {
        key "fabric-profile-name";
        max-elements 1024;
        description
          "List of Fabric Profiles";
        uses wireless-fabric-cfg:fabric;
      }
    }
    container fabric {
      presence "fabric";
      description
        "Container for global fabric-specific configuration settings";
      uses wireless-fabric-cfg:fabric-cfg;
    }
    container fabric-controlplane-names {
      description
        "Fabric Control Plane Name configuration";
      list fabric-controlplane-name {
        key "control-plane-name";
        max-elements 16;
        description
          "List of Fabric Control Plane Name configuration objects";
        uses wireless-fabric-cfg:fabric-control-plane-name;
      }
    }
  }
}
