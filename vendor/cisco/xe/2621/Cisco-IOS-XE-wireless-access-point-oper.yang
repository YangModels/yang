module Cisco-IOS-XE-wireless-access-point-oper {
  yang-version 1.1;
  namespace "http://cisco.com/ns/yang/Cisco-IOS-XE-wireless-access-point-oper";
  prefix wireless-access-point-oper;

  import Cisco-IOS-XE-event-history-types {
    prefix event-history-types;
  }
  import Cisco-IOS-XE-wireless-ap-types {
    prefix ap-types;
  }
  import Cisco-IOS-XE-wireless-enum-types {
    prefix wireless-enum-types;
  }
  import Cisco-IOS-XE-wireless-rrm-types {
    prefix wireless-rrm-types;
  }
  import Cisco-IOS-XE-wireless-types {
    prefix wireless-types;
  }
  import Cisco-IOS-XE-wireless-urwb-common-types {
    prefix wireless-urwb-common-types;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for access point operational data.
     Copyright (c) 2016-2026 by Cisco Systems, Inc.
     All rights reserved.";

  revision 2026-08-01 {
    description
      "- Added support for proximity method
       - Added support for the Local-MAC capability flag on AP stacks
       - Added support for auto-MACsec
       - Added support for SIA serial number
       - Added AP capability flag ap-idr-capable
       - Added WAT Wired Testing capability flag
       - Added AP auto-MACsec capability flag";
    reference
      "8.6.0";
    cisco-semver:module-version "8.6.0";
  }
  revision 2026-02-01 {
    description
      "- Added MACsec status enum
       - Added Ciphersuite enum
       - Added AP Spaces telemetry channel operational data
       - Added GRPC related statistics
       - Added WiFi-IOT Coexistence data
       - Added reboot stats for AP
       - Added per wncd level stats for iapp messages
       - Added AP height above the floor configuration
       - Added JWT token stats for AP Spaces telemetry channel
       - Added AP kernel coredump capability flags
       - Added boolean to indicate if AP name is statically configured
       - Added support for the Local-MAC-Dot11-kv capability flag on AP stacks
       - Added support for AP console speed configuration
       - Added radio operational information including Ultra Reliable Wireless Backhaul (URWB) configuration
       - Added estimated beacon EIRP of the radio
       - Added IOT BLE GRPC endpoint connection details
       - Added radio capability flag bridge-mode-support";
    reference
      "8.5.0";
    cisco-semver:module-version "8.5.0";
  }
  revision 2025-07-01 {
    description
      "- Added AP beam state configuration
       - Added Ultra Reliable Wireless Backhaul(URWB) capability flag
       - Added user configured channel, width and transmit power for standard power mode of operation
       - Deprecated the leaf node ack-failure-count
       - Added beacon-protection status in VAP operational config
       - Added serial AP upgrade
       - Marked upgraded AP list in AP upgrade report as obsolete and introduced new list for completed APs to replace upgraded APs
       - Added new enum for AP license non-compliance
       - Added Ultra Reliable Wireless Backhaul(URWB) AP config status
       - Added per radio stats for 802.11k and 802.11v requests";
    reference
      "8.4.0";
    cisco-semver:module-version "8.4.0";
  }
  revision 2025-03-01 {
    description
      "- Added AP Nextunnel operational information
       - Added staggered rollover AP upgrade feature type
       - Added capability flag ap-hybrid-sku-capable
       - Added radio capability flag static-channel-power
       - Added AP capability flag unii-3-channels-capable
       - Added new AP radio operational stats
       - Added AP unified license information
       - Added failed AP data in staggered rollover upgrade
       - Added AP dual port authentication information
       - Added AP nextunnel state information";
    reference
      "8.3.0";
    cisco-semver:module-version "8.3.0";
  }
  revision 2024-11-01 {
    description
      "- Added the enum installed-via-meraki-dashboard
       - Added new enum for AP image pre downloading
       - Added capability flag antenna-mode-switch
       - Added CAPWAP Discovery Meraki packet counters";
    reference
      "8.2.0";
    cisco-semver:module-version "8.2.0";
  }
  revision 2024-07-01 {
    description
      "- Added AP Multi Link capability
       - Added radio capabilities, MLD MAC, preamble puncturing and multi-link operation status
       - Added GNSS antenna serial number
       - Added radio band to Radio Neighbor table
       - Added multi link BSSID statistics
       - Added multi link radio statistics
       - Added AP capability for client FTM and dot11az";
    reference
      "8.1.0";
    cisco-semver:module-version "8.1.0";
  }
  revision 2024-03-01 {
    description
      "- Adding proxy username and password for AP
       - Added sniffer operational data for AP radio
       - Added Accelerometer sensor information";
    reference
      "8.0.0";
    cisco-semver:module-version "8.0.0";
  }
  revision 2023-11-01 {
    description
      "- Added AP indoor default mode
       - Added new leaf packet-expiration-time
       - Added Meraki monitor capability and connect status
       - Added AP uplink interface statistics
       - Added AP image and file system status";
    reference
      "7.9.0";
    cisco-semver:module-version "7.9.0";
  }
  revision 2023-07-01 {
    description
      "- Added AP Power policy enum to handle the case when power policy is not applied due to clients
       - Added power profile type operational data
       - Added AP kernel coredump configuration
       - Changed description of ewlc-wncd-stats to specify it is only valid for EWC on AP platforms
       - Added AP spectral-capture operational data
       - Added RF based AP neighborhood algorithm output information and stats
       - Added ranging mode
       - Added AP regulatory domain information
       - Added GNSS antenna product id
       - Added Zero wait DFS statistics";
    reference
      "7.8.0";
    cisco-semver:module-version "7.8.0";
  }
  revision 2023-03-01 {
    description
      "- Added AP transmit data retransmit interval
       - Added Radio-Authority IDs
       - Added AP 6GHz power mode information
       - Added AP WLAN stats and AP mode data
       - Added ICAP sniffer capable flag
       - Added RAP ethernet daisy-chain support
       - Added AP upgrade client de-auth and tx-power reduction field
       - Added two new leaf for AP image download start and download end timestamps and deprecated old leaf for download start and download end timestamp
       - Added when condition to current operating channel and frequency string attributes to check for AP radio mode
       - Added when condition to radio oper data to check for radio type
       - Added when constraint to radio subband";
    reference
      "7.7.0";
    cisco-semver:module-version "7.7.0";
  }
  revision 2022-11-01 {
    description
      "- Added coverage overlap factor for Open RRM FRA features
       - Added AP power-save mode and power policy entry skipped enum
       - Added AP client tracing information
       - Update yang-version to 1.1
       - Added country specific regulatory information for all bands as regulatory domain, supported channels, DCA channels and DFS channels
       - Added information as ^ indicating ROW domain support
       - Added AP priming profile details
       - Deprecated DART connection status boolean and replaced with a tri-state enum
       - Added AP pressure sensor support
       - Added AP pressure sensor capability flag
       - Added AP GNSS support
       - Added wireless management trustpoint data
       - Added AP image download statistics
       - Added DHCP ipv4 pool data
       - Added USB external module data
       - Added supported country specific regulatory information for all bands";
    reference
      "7.6.0";
    cisco-semver:module-version "7.6.0";
  }
  revision 2022-07-01 {
    description
      "- Added number of slots in use in AP
       - Added AP Meraki data and conversion information
       - Added Zero wait DFS capability data
       - Added MDNS rule group method
       - Added 802.11ax capabilities for XOR 5/6 GHz radio
       - Added new configuration for AP upgrade
       - Added support for AAA Location information attributes
       - Added serial console under device management configuration
       - Added antenna labels 7 and 8
       - Added led flash expiry time
       - Added TX power level indices for AP radios
       - Added LSC expiry time
       - Added configured channel list.
       - Added data pertaining to hyperlocation, resolved tags, and other miscellaneous fields
       - Added supported antenna modes 5, 6, 7 and 8";
    reference
      "7.5.0";
    cisco-semver:module-version "7.5.0";
  }
  revision 2022-03-01 {
    description
      "- Added multi domain dot11n capabilities and station configuration data
       - Added sniffer configuration parameters
       - Added additional 802.11ax capability data
       - Added additional AP Ethernet interface information
       - Added PMK Propagation sender and receiver AP MAC
       - Added a counter for the number of radios in sniffer role
       - Added AP sensor support
       - Added AP power profile information, associated calendar profile and AP de-rating capability flag
       - Added a limit for the maximum number of clients allowed on an AP
       - Added flag for AP Zero wait Dynamic Frequency Selection (DFS) capability
       - Added WTP extension module information
       - Added AP convert to Meraki capability flag";
    reference
      "7.4.0";
    cisco-semver:module-version "7.4.0";
  }
  revision 2021-11-01 {
    description
      "- Added support for AP OOB (out-of-band) image download
       - Added action for high memory or high CPU usage of the AP
       - Added radio reset count flag
       - Added radio statistics monitor data
       - Added AP certificate issuer common name
       - Added mesh parameters for serial backhaul
       - Added CDP cache related fields
       - Added IoT Radio firmware information
       - Added Spatial Reuse Group (SRG) capability for Overlapping Basic Service Set Packet Detect (OBSS PD)
       - Added PMK distribution capability and AP role
       - Added per radio maximum client limit
       - Added additional radio oper stats";
    reference
      "7.3.0";
    cisco-semver:module-version "7.3.0";
  }
  revision 2021-07-01 {
    description
      "- Added support NTP AP authentication and status
       - Added support for image direct download under AP capability
       - Added support for AP timezone
       - Added flag for AID managing capability of the AP
       - Updated SIA parameters for Marlin 4 antenna
       - Added 6 GHz radio type enum
       - Added 802.11ax transmitted BSSID
       - Added antenna configuration parameters
       - Added DTLS LSC fallback state of AP
       - Added per AP CAPWAP packet counters
       - Added supported channels and transmit power for AP radio
       - Added antenna label parameter";
    reference
      "7.2.0";
    cisco-semver:module-version "7.2.0";
  }
  revision 2021-03-01 {
    description
      "- Added support for LLDP neighbor
       - Added support for AP stats
       - Added neighbor discovery capability and mode for AP
       - Added support for on-demand Office Extended AP link test
       - Added QoS client values
       - Added support for staggered AP upgrade stats
       - Added AP LSC status, AP cert expiry time and DTLS certificate policy information
       - Added flags ant-1-2-3-no-config and dual-radio-enable under AP capability
       - Added static address details for AP and deprecated ip addr";
    reference
      "7.1.0";
    cisco-semver:module-version "7.1.0";
  }
  revision 2020-11-01 {
    description
      "- Added support for antenna monitoring configuration
       - Added 802.11ax OBSS PD radio capability
       - Added support for AP disconnect reason
       - Added AP image file information for installed images
       - Added RPC support for ap image predownload and abort
       - Added USB data and obsolete status for is-ext-module-enabled under CAPWAP data
       - Added RX/TX radio operational stats
       - Added support for per AP SSID operational information
       - Deprecated Rogue RLDP capability
       - Added Channel availability check status";
    reference
      "7.0.0";
    cisco-semver:module-version "7.0.0";
  }
  revision 2020-07-01 {
    description
      "- Added MDNS group ID
       - Added mesh daisy chain STP redundancy support
       - Added support for AP image predownload information
       - Added support for monitoring gRPC channel from AP to Cisco-DNA
       - Added MDNS rule name
       - Added external module capability flag to indicate whether AP has support for an external module
       - Updated description for rlan-port-id leaf node
       - Added support bundle file transfer information
       - Added support for AP Audit Report
       - Added support for AP temperature
       - Added support for AP 6300 with two antennas
       - Added support for AP click OS feature set
       - Added support for Controller image predownload information
       - Added support for AP Single Band Antenna Mode
       - Added support for AP system info including CPU type and memory type
       - Added support for noise floor and FCS error count
       - Added Traffic Distribution Statistics Capability and Dual DFS Statistics Capability to AP capability flag
       - Added antenna-gain
       - Added new states for GRPC connection from AP to Cisco DNA
       - Added BSS channel utilisation and control stats
       - Added EWC predownload state
       - Added USB or PSE supported flag under AP capability";
    reference
      "6.5.0";
    cisco-semver:module-version "6.5.0";
  }
  revision 2020-03-01 {
    description
      "- Added download image size percentage and ETA
       - Added window size for CAPWAP multiwindow
       - Added image name for CAPWAP WTP data
       - Added support for RADIUS counters
       - Added support for persistent SSID broadcast
       - Added support for AP proxy
       - Added IPv6 static address details for APs
       - Added two new flags for AP capability ap-min-two-antennas-to-be-enabled and ap-antennas-5-6-7-not-configurable";
    reference
      "6.4.0";
    cisco-semver:module-version "6.4.0";
  }
  revision 2019-11-01 {
    description
      "- Added AP AWIPS Capability
       - Added AP power type
       - Added UDP-Lite operational information
       - Added multi-lan-port-capable flag under AP capability
       - Added AP LAN operational information
       - Added support for IOX application hosting on APs
       - Added support for Auxiliary Client Interface on APs
       - Added radio enable time for AP
       - Added 802.11ax BSS color configuration and capability
       - Added strict-wired-uplink-capable flag under AP capability
       - Added dual radio mode and FRA capable parameters
       - Added AP LED flash state and duration timer
       - Added highest throughput supported by radio";
    reference
      "6.3.0";
    cisco-semver:module-version "6.3.0";
  }
  revision 2019-08-26 {
    description
      "- Added radio enable time for AP
       - Added flag definition for MCS rates
       - Added antenna-band-mode-capable flag under AP capability
       - Added SIA parameters for AP radio";
    reference
      "6.2.0";
    cisco-semver:module-version "6.2.0";
  }
  revision 2019-06-18 {
    description
      "- Added NTP server information to be used by AP
       - Added Various statistics counter for SSID
       - Added ap-mac-ssid-info to keep the list of clients MAC address for each SSID
       - Updated description for leaf node ht-enable
       - Added rrm-channel-change-reason
       - Added monitor mode optimization information
       - Added semantic version
       - Added slot-antenna-type
       - Added AP filter name";
    reference
      "6.1.0";
    cisco-semver:module-version "6.1.0";
  }
  revision 2019-02-24 {
    description
      "- Renamed QoS enum type
       - Removal of unused leaves from QoS enum
       - Added new enum for cac state type
       - Removal of unused leaves from qos client data
       - Added description of AP capabilities
       - Added new leaf AP stationing type to identify AP type
         indoor or outdoor
       - Added secondary 80 channel of 80+80 channel width
       - Added me-internal-ap
       - Removal of unused leaves
       - Added fallback wait status in AP upgrade status
       - Added fallback type in AP upgrade report
       - Added new enum for AP upgrade fallback type
       - Added current-band-id for radio-oper-stats
       - Cleaned up spelling errors in descriptions
       - Removed CAC counters from Radio statistics information
       - Added rrm-channel-change-reason
       - Removal of unused leaves
       - Added upgrade failure type in AP upgrade report
       - Added new enum for AP upgrade failure reason
       - Added lists for AP software related information
       - Updated description for leaf nodes leg-tx-bf-enabled, current-band-id and he-stbc-mode
       - Added leaf node current-active-band
       - Removed redundant leaves under capwap-data
       - Categorized attributes into AP static and dynamic information,
         clubbed the various version of the AP together and changed few
         of the leaf descriptions to make them more appropriate/precise
       - Added wtp-serial-num for capwap-data
       - Added additional AirTime Fairness Statistics
       - Added sensor-mode-capable and only-local-mode-capable flags under AP capability
       - Removal of less important leaf nodes from AP and Radio operational data
       - Removed radio-uptime from radio-oper-stats";
    reference
      "6.0.0";
    cisco-semver:module-version "6.0.0";
  }
  revision 2018-06-28 {
    description
      "- Add AP name for which bandwidth is allocated, number of active TSPEC and SIP calls
       - Remove voice client from qos client data
       - Add SIP active and rejected call counters
       - Add SIP call-control metrics";
    reference
      "5.0.0";
    cisco-semver:module-version "5.0.0";
  }
  revision 2018-04-02 {
    description
      "Replaced an existing attribute lookup_neigh_mac with
       neighbor_ap_name";
    reference
      "4.0.0";
    cisco-semver:module-version "4.0.0";
  }
  revision 2018-03-22 {
    description
      "Enum value change";
    reference
      "3.0.0";
    cisco-semver:module-version "3.0.0";
  }
  revision 2018-01-24 {
    description
      "The first generally available version";
    reference
      "2.0.0";
    cisco-semver:module-version "2.0.0";
  }
  revision 2017-05-05 {
    description
      "Initial revision";
    reference
      "1.0.0";
    cisco-semver:module-version "1.0.0";
  }

  typedef enum-ap-state {
    type enumeration {
      enum ap-down {
        value 1;
        description
          "AP state is Down";
      }
      enum ap-up {
        value 2;
        description
          "AP state is Up";
      }
      enum unregistered {
        value 3;
        description
          "AP state is un-registered";
      }
      enum registered {
        value 4;
        description
          "AP state is Registered";
      }
      enum downloading {
        value 5;
        description
          "AP state is Image Download";
      }
      enum pre-downloading {
        value 6;
        description
          "AP state is Image pre-download";
      }
    }
    description
      "Operational state of AP";
  }

  typedef enum-ap-stationing-type {
    type enumeration {
      enum indoor-ap {
        value 0;
        description
          "AP stationing type INDOOR";
      }
      enum outdoor-ap {
        value 1;
        description
          "AP stationing type OUTDOOR";
      }
    }
    description
      "AP stationing type, indoor or outdoor";
  }

  typedef enm-cert-type {
    type enumeration {
      enum wireless-cert-mic {
        value 1;
        description
          "Cert type: Manufacturer Installed Certificate";
      }
      enum wireless-cert-ssc {
        value 2;
        description
          "Cert type: Self Signed Certificate";
      }
      enum wireless-cert-lsc {
        value 3;
        description
          "Cert type: Locally Significant Certificate";
      }
    }
    description
      "enumeration to define certificate types with which
       AP can join";
  }

  typedef enm-vlan-state {
    type enumeration {
      enum vlan-tagging-disabled {
        value 0;
        description
          "VLAN tagging disabled";
      }
      enum vlan-tagging-enabled {
        value 1;
        description
          "VLAN tagging enabled";
      }
      enum vlan-tagging-failover {
        value 2;
        description
          "VLAN tagging failover";
      }
    }
    description
      "AP VLAN tagging state";
  }

  typedef enum-iotgwd-e2e-cli-exec-state {
    type enumeration {
      enum cli-idle {
        value 0;
        description
          "CLI execution is idle";
      }
      enum cli-in-prog {
        value 1;
        description
          "CLI execution is in progress";
      }
      enum cli-done {
        value 2;
        description
          "CLI execution is completed";
      }
      enum cli-failed {
        value 3;
        description
          "CLI execution has failed";
      }
    }
    description
      "Status of End to End GRPC CLI execution";
  }

  typedef enum-ap-dna-grpc-status-code {
    type enumeration {
      enum cisco-dna-grpc-status-unknown {
        value 0;
        description
          "gRPC status is unknown";
      }
      enum cisco-dna-grpc-status-up {
        value 1;
        description
          "gRPC status is up";
      }
      enum cisco-dna-grpc-status-down-disabled {
        value 2;
        description
          "gRPC status is down because disabled";
      }
      enum cisco-dna-grpc-status-down-wrong-token {
        value 3;
        description
          "gRPC status is down because of wrong token";
      }
      enum cisco-dna-grpc-status-down-wrong-certificate {
        value 4;
        description
          "gRPC status is down because of wrong certificate";
      }
      enum cisco-dna-grpc-status-down-server-unreachable {
        value 5;
        description
          "gRPC status is down because of server unreachable";
      }
      enum cisco-dna-grpc-status-down-service-down {
        value 6;
        description
          "gRPC status is down because of service being down";
      }
      enum cisco-dna-grpc-status-down-unknown-error {
        value 7;
        description
          "gRPC status is down because of unknown error";
      }
    }
    description
      "enumeration to define the possible states of the gRPC connection from AP to Cisco-DNA";
  }

  typedef enum-ap-temp-heater-status {
    type enumeration {
      enum heater1-off-heater2-off {
        value 0;
        description
          "Both heater 1 and heater 2 are off";
      }
      enum heater1-on-heater2-off {
        value 4;
        description
          "Heater 1 is on and heater 2 is off";
      }
      enum heater1-off-heater2-on {
        value 8;
        description
          "Heater 1 is off and heater 2 is on";
      }
      enum heater1-on-heater2-on {
        value 12;
        description
          "Both heater 1 and heater 2 are on";
      }
    }
    description
      "Enumeration to define possible states of AP heater status";
  }

  typedef enum-ap-temp-status {
    type enumeration {
      enum normal {
        value 1;
        description
          "AP temperature status is normal";
      }
      enum abnormal {
        value 3;
        description
          "AP temperature status is abnormal";
      }
    }
    description
      "Enumeration to define possible states of AP temperature status";
  }

  typedef ewlc-ntp-server-status {
    type enumeration {
      enum ntp-server-notconfig {
        value 0;
        description
          "There is no configuration for NTP";
      }
      enum ntp-server-nostatus {
        value 1;
        description
          "There is no status currently for NTP";
      }
      enum ntp-server-unreachable {
        value 2;
        description
          "The NTP server is unreachable";
      }
      enum ntp-server-sync {
        value 3;
        description
          "The NTP server is in sync with device";
      }
      enum ntp-server-notsync {
        value 4;
        description
          "The device is not in sync with the NTP server";
      }
      enum ntp-server-waitsync {
        value 5;
        description
          "The NTP server is waiting for sync with device";
      }
      enum ntp-server-authfailed {
        value 6;
        description
          "The NTP server authentication failed";
      }
      enum ntp-server-notsuitable {
        value 7;
        description
          "The NTP server is not suitable";
      }
    }
    description
      "enumeration to define the NTP server status";
  }

  typedef enm-ap-priming-source {
    type enumeration {
      enum ap-priming-source-none {
        value 0;
        description
          "Unknown AP priming profile source";
      }
      enum ap-priming-source-ap-mac {
        value 1;
        description
          "AP priming profile configured under AP MAC";
      }
      enum ap-priming-source-ap-filter {
        value 2;
        description
          "AP priming profile configured under AP filter";
      }
    }
    description
      "AP priming profile source";
  }

  typedef ap-misconfig {
    type enumeration {
      enum apmgr-no-misconfig {
        value 0;
        description
          "No misconfiguration";
      }
      enum country-misconfig {
        value 1;
        description
          "AP country misconfiguration";
      }
      enum world-wide-mode {
        value 2;
        description
          "AP is in world wide mode";
      }
      enum lic-no-comp {
        value 3;
        description
          "AP is in world wide mode due to license compliance failure";
      }
    }
    description
      "AP misconfiguration reasons";
  }

  typedef reg-domain-resoultion-method {
    type enumeration {
      enum invalid-method {
        value 0;
        description
          "Invalid method";
      }
      enum gps {
        value 1;
        description
          "GPS location";
      }
      enum proximity {
        value 2;
        description
          "Proximity";
      }
      enum regulatory-file {
        value 3;
        description
          "Regulatory domain file";
      }
      enum ip-address {
        value 4;
        description
          "IP address";
      }
      enum installed-via-meraki-dashboard {
        value 5;
        description
          "Installed via Meraki dashboard";
      }
    }
    description
      "AP Regulatory domain resolution method";
  }

  typedef proximity-resolution-method {
    type enumeration {
      enum prm-none {
        value 0;
        description
          "No proximity resolution method was used or the method is unknown.";
      }
      enum prm-ndp {
        value 1;
        description
          "Neighbor Discovery Protocol (NDP) was used to determine its regulatory domain via proximity.";
      }
      enum prm-cdp {
        value 2;
        description
          "Cisco Discovery Protocol (CDP) was used to determine its regulatory domain via proximity.";
      }
      enum prm-lldp {
        value 3;
        description
          "Link Layer Discovery Protocol (LLDP) was used to determine its regulatory domain via proximity.";
      }
    }
    description
      "AP Regulatory domain proximity resolution method";
  }

  typedef enm-ap-env-mode {
    type enumeration {
      enum ap-environment-indoor {
        value 0;
        description
          "AP environment mode indoor";
      }
      enum ap-environment-outdoor {
        value 1;
        description
          "AP environment mode outdoor";
      }
      enum ap-environment-error {
        value 2;
        description
          "AP environment mode detection error";
      }
      enum ap-environment-none {
        value 3;
        description
          "AP environment mode none";
      }
    }
    description
      "Enumeration for AP environment mode";
  }

  typedef oeap-link-test-state {
    type enumeration {
      enum never-started {
        value 0;
        description
          "Link test was never started";
      }
      enum running {
        value 1;
        description
          "Link test is running";
      }
      enum success {
        value 2;
        description
          "Link test is terminated with success";
      }
      enum failure {
        value 3;
        description
          "Link test is terminated with failure";
      }
    }
    description
      "State of the Office Extended AP link test";
  }

  typedef ap-sys-alarm-status {
    type enumeration {
      enum alarm-inactive {
        value 0;
        description
          "Alarm inactive";
      }
      enum alarm-active-soaking {
        value 1;
        description
          "Alarm active soaking";
      }
      enum alarm-active {
        value 2;
        description
          "Alarm active";
      }
      enum alarm-inactive-soaking {
        value 3;
        description
          "Alarm inactive soaking";
      }
    }
    description
      "enumeration to define the AP system stats alarm status";
  }

  typedef ap-sys-alarm-type {
    type enumeration {
      enum alarm-cpu {
        value 0;
        description
          "Alarm CPU";
      }
      enum alarm-memory {
        value 1;
        description
          "Alarm memory";
      }
    }
    description
      "enumeration to define the AP system stats alarm type";
  }

  typedef meraki-pre-conv-status {
    type enumeration {
      enum mk-cv-validation-success {
        value 0;
        description
          "Validation success";
      }
      enum mk-cv-err-miscfg-country {
        value 1;
        description
          "Country-code misconfigured";
      }
      enum mk-cv-err-no-reg-domain {
        value 2;
        description
          "Regulatory domain not set";
      }
      enum mk-cv-err-ap-disjoined {
        value 3;
        description
          "AP is not responsive and disjoined";
      }
      enum mk-cv-err-no-ap-ack {
        value 4;
        description
          "No acknowledgement from AP";
      }
      enum mk-cv-err-set-ap-env {
        value 5;
        description
          "Set Meraki environment failure at AP";
      }
      enum mk-cv-err-internal {
        value 6;
        description
          "Internal error";
      }
      enum mk-cv-err-unknown {
        value 7;
        description
          "Unknown failure";
      }
    }
    description
      "Meraki mode pre conversion status";
  }

  typedef ap-meraki-connect-status {
    type enumeration {
      enum am-status-unknown {
        value 0;
        description
          "Status unknown";
      }
      enum am-status-reg-success {
        value 1;
        description
          "Registration successful for Meraki connect";
      }
      enum am-status-reg-failed {
        value 2;
        description
          "Registration failed for Meraki connect";
      }
      enum am-status-not-reg {
        value 3;
        description
          "AP not yet registered for Meraki connect";
      }
      enum am-status-disabled {
        value 4;
        description
          "Meraki connect is disabled";
      }
      enum am-status-unsupported {
        value 5;
        description
          "Meraki monitoring not supported on AP";
      }
    }
    description
      "AP Meraki connect status";
  }

  typedef enum-ap-image-type {
    type enumeration {
      enum undefined-image {
        value 0;
        description
          "Undefined image on AP";
      }
      enum primary-image {
        value 1;
        description
          "AP primary image";
      }
      enum backup-image {
        value 2;
        description
          "AP backup image";
      }
    }
    description
      "AP image type";
  }

  typedef enum-ap-file-status {
    type enumeration {
      enum good {
        value 0;
        description
          "File is not corrupted";
      }
      enum corrupted {
        value 1;
        description
          "File is corrupted";
      }
    }
    description
      "AP file Status";
  }

  typedef enum-ap-partition {
    type enumeration {
      enum part1 {
        value 0;
        description
          "Image is stored on partition 1";
      }
      enum part2 {
        value 1;
        description
          "Image is stored on partition 2";
      }
    }
    description
      "AP partition";
  }

  typedef enm-cw-compliance-state {
    type enumeration {
      enum cw-non-compliant {
        value 0;
        description
          "AP is non-compliant with the cisco wireless license";
      }
      enum cw-compliant {
        value 1;
        description
          "AP is compliant with the cisco wireless license";
      }
      enum cw-pre-allowed {
        value 2;
        description
          "AP is not using cisco wireless license";
      }
      enum cw-policy-allowed {
        value 3;
        description
          "AP is compliant with license through policy";
      }
    }
    description
      "AP cisco wireless license state";
  }

  typedef enm-cw-non-compliance-reason {
    type enumeration {
      enum cw-never-licensed {
        value 0;
        description
          "AP has no cisco wireless license";
      }
      enum cw-not-applicable {
        value 1;
        description
          "AP has license";
      }
      enum cw-license-expiration {
        value 2;
        description
          "AP cisco wireless license has expired";
      }
    }
    description
      "AP cisco wireless license non compliance reason";
  }

  typedef ap-ppe-status {
    type enumeration {
      enum ap-pwr-pol-entry-success {
        value 0;
        description
          "Power policy entry is successfully applied";
      }
      enum ap-pwr-pol-entry-na {
        value 1;
        description
          "Power policy entry is not applicable";
      }
      enum ap-pwr-pol-entry-not-eval {
        value 2;
        description
          "Power policy entry is not evaluated";
      }
      enum ap-pwr-pol-entry-fixed-pol {
        value 3;
        description
          "Power policy entry has fixed power policy applied";
      }
      enum ap-pwr-pol-entry-unknown {
        value 4;
        description
          "Power policy entry status unknown";
      }
      enum ap-pwr-pol-entry-skipped {
        value 5;
        description
          "Power policy entry is skipped";
      }
      enum ap-pwr-pol-not-applied {
        value 6;
        description
          "Power policy entry is not applied due to clients";
      }
    }
    description
      "Power policy entry status of AP";
  }

  typedef ap-power-status {
    type enumeration {
      enum ap-pwr-pol-success {
        value 0;
        description
          "Power policy is successfully applied";
      }
      enum ap-pwr-pol-less-derating {
        value 1;
        description
          "Power policy de-rating is insufficient";
      }
      enum ap-pwr-pol-fixed {
        value 2;
        description
          "AP applied a fixed policy as power policy is absent";
      }
      enum ap-pwr-pol-unknown {
        value 3;
        description
          "Power policy status unknown";
      }
    }
    description
      "Power policy status of AP";
  }

  typedef ap-debug-bundle-event-type {
    type enumeration {
      enum debug-bundle-client {
        value 0;
        description
          "Client debug bundle";
      }
      enum debug-bundle-spectral {
        value 1;
        description
          "Spectral debug bundle";
      }
    }
    description
      "Event type for AP debug bundle";
  }

  typedef ap-spectral-capture-event {
    type enumeration {
      enum unknown-event {
        value 0;
        description
          "Spectral-capture event unknown";
      }
      enum start-request {
        value 1;
        description
          "Spectral-capture event start-request";
      }
      enum start-request-timeout {
        value 2;
        description
          "Spectral-capture event start request timed-out";
      }
      enum start-response-failed {
        value 3;
        description
          "Spectral-capture event start response failed";
      }
      enum stop-request {
        value 4;
        description
          "Spectral-capture event stop request";
      }
      enum stop-request-timeout {
        value 5;
        description
          "Spectral-capture event stop request timed-out";
      }
      enum stop-response-failed {
        value 6;
        description
          "Spectral-capture event stop response failed";
      }
      enum stop-response-success {
        value 7;
        description
          "Spectral-capture event stop response success";
      }
      enum abort-request {
        value 8;
        description
          "Spectral-capture event abort request";
      }
      enum capture-response-in-progress {
        value 9;
        description
          "Spectral-capture event capture response in-progress";
      }
      enum capture-response-failed {
        value 10;
        description
          "Spectral-capture event capture response failed";
      }
      enum capture-response-success {
        value 11;
        description
          "Spectral-capture event capture response success";
      }
      enum jwt-token-request-timeout {
        value 12;
        description
          "Spectral-capture event JWT request timed-out";
      }
      enum upload-request {
        value 13;
        description
          "Spectral-capture event upload request";
      }
      enum upload-request-timeout {
        value 14;
        description
          "Spectral-capture event upload request timed-out";
      }
      enum upload-response-failed {
        value 15;
        description
          "Spectral-capture event upload response failed";
      }
      enum upload-response-in-progress {
        value 16;
        description
          "Spectral-capture event upload response in-progress";
      }
      enum upload-response-success {
        value 17;
        description
          "Spectral-capture event upload response success";
      }
    }
    description
      "Spectral-capture event";
  }

  typedef ap-spectral-capture-state {
    type enumeration {
      enum state-unknown {
        value 0;
        description
          "Spectral-capture state unknown";
      }
      enum state-init {
        value 1;
        description
          "Spectral-capture state initial";
      }
      enum state-starting {
        value 2;
        description
          "Spectral-capture state starting";
      }
      enum state-stopping {
        value 3;
        description
          "Spectral-capture state stopping";
      }
      enum state-stopped {
        value 4;
        description
          "Spectral-capture state stopped";
      }
      enum state-capture-in-progress {
        value 5;
        description
          "Spectral-capture state capture-in-progress";
      }
      enum state-uploading {
        value 6;
        description
          "Spectral-capture state up-loading";
      }
      enum state-upload-in-progress {
        value 7;
        description
          "Spectral-capture state upload-in-progress";
      }
    }
    description
      "Spectral-capture state";
  }

  typedef ap-lsc-prov-workflow {
    type enumeration {
      enum wlc-proxy {
        value 0;
        description
          "WLC proxy enrollment";
      }
      enum pnp-secure-onboarding {
        value 1;
        description
          "PNP secure onboarding";
      }
    }
    description
      "Certificate provision workflow";
  }

  typedef ap-lsc-renew-failure-rc {
    type enumeration {
      enum renew-none {
        value 0;
        description
          "renew None";
      }
      enum renew-success {
        value 1;
        description
          "renew success";
      }
      enum renew-error {
        value 2;
        description
          "renew error";
      }
      enum not-yet-valid {
        value 3;
        description
          "Renewed certificate not valid yet";
      }
      enum failed-to-install {
        value 4;
        description
          "AP failed to install renewed certificate";
      }
      enum failed-ca-signing {
        value 5;
        description
          "Failed to get signed certificate from CA";
      }
      enum no-response {
        value 6;
        description
          "no response";
      }
      enum timeout-ca-signing {
        value 7;
        description
          "CA signing response timeout";
      }
    }
    description
      "Last certificate renewal failure reason code";
  }

  typedef enm-tunnel-cfg-fetch-state {
    type enumeration {
      enum fetch-state-invalid {
        value 0;
        description
          "Invalid config fetch state";
      }
      enum fetch-init {
        value 1;
        description
          "Config fetch initiated";
      }
      enum fetch-init-retry {
        value 2;
        description
          "Config fetch retry";
      }
      enum fetch-failed {
        value 3;
        description
          "Config fetch failed";
      }
      enum fetch-succeeded {
        value 4;
        description
          "Config fetch succeeded";
      }
    }
    description
      "AP Nextunnel config fetch state";
  }

  typedef enm-tunnel-state {
    type enumeration {
      enum nextunnel-state-invalid {
        value 0;
        description
          "Invalid tunnel";
      }
      enum nextunnel-down {
        value 1;
        description
          "Tunnel down";
      }
      enum nextunnel-up {
        value 2;
        description
          "Tunnel up";
      }
    }
    description
      "AP Nextunnel interface state";
  }

  typedef enum-radio-admin-state {
    type enumeration {
      enum enabled {
        value 1;
        description
          "Radio Admin State is Enabled";
      }
      enum disabled {
        value 2;
        description
          "Radio Admin State is Disabled";
      }
    }
    description
      "Radio Admin state";
  }

  typedef enum-radio-oper-state {
    type enumeration {
      enum radio-up {
        value 0;
        description
          "Radio Operational State Enabled";
      }
      enum radio-down {
        value 1;
        description
          "Radio Operational State Disabled";
      }
    }
    description
      "Radio Operational state";
  }

  typedef radio-sniff-dis-rson-code {
    type enumeration {
      enum sniffer-reason-none {
        value 0;
        description
          "Sniffer enabled";
      }
      enum dual-5ghz-radio-disabled {
        value 1;
        description
          "Sniffer disabled, dual 5GHz disabled";
      }
      enum ap-mode-non-client-serv {
        value 2;
        description
          "Sniffer disabled, AP not in client serving mode";
      }
      enum reg-domain-mismatch {
        value 3;
        description
          "Sniffer disabled, regulatory domain mismatch";
      }
      enum dual-5ghz-radios-up {
        value 4;
        description
          "Sniffer disabled, dual 5GHz radios UP";
      }
      enum ranging-mode-disruptive {
        value 5;
        description
          "Sniffer disabled, ranging mode disruptive in progress";
      }
    }
    description
      "Sniffer disable reason code for the AP radio";
  }

  typedef enm-antenna-label {
    type enumeration {
      enum ap-ant-invalid {
        value 0;
        description
          "Invalid antenna label";
      }
      enum ap-ant-a {
        value 1;
        description
          "Antenna label A";
      }
      enum ap-ant-b {
        value 2;
        description
          "Antenna label B";
      }
      enum ap-ant-c {
        value 3;
        description
          "Antenna label C";
      }
      enum ap-ant-d {
        value 4;
        description
          "Antenna label D";
      }
      enum ap-ant-e {
        value 5;
        description
          "Antenna label E";
      }
      enum ap-ant-f {
        value 6;
        description
          "Antenna label F";
      }
      enum ap-ant-g {
        value 7;
        description
          "Antenna label G";
      }
      enum ap-ant-h {
        value 8;
        description
          "Antenna label H";
      }
      enum ap-ant-1 {
        value 9;
        description
          "Antenna label 1";
      }
      enum ap-ant-2 {
        value 10;
        description
          "Antenna label 2";
      }
      enum ap-ant-3 {
        value 11;
        description
          "Antenna label 3";
      }
      enum ap-ant-4 {
        value 12;
        description
          "Antenna label 4";
      }
      enum ap-ant-5 {
        value 13;
        description
          "Antenna label 5";
      }
      enum ap-ant-6 {
        value 14;
        description
          "Antenna label 6";
      }
      enum ap-ant-7 {
        value 15;
        description
          "Antenna label 7";
      }
      enum ap-ant-8 {
        value 16;
        description
          "Antenna label 8";
      }
    }
    description
      "Enumeration defining antenna labels";
  }

  typedef enm-radio-op-stats-type {
    type enumeration {
      enum radio-stats-multi-link {
        value 0;
        description
          "Multi link type radio";
      }
    }
    description
      "Radio statistics type";
  }

  typedef enm-ssid-counter-type {
    type enumeration {
      enum ssid-counter-multi-link {
        value 0;
        description
          "Multi link type";
      }
    }
    description
      "Enumeration defining SSID counter type";
  }

  typedef ewlc-rlan-poe-state {
    type enumeration {
      enum poe-disabled {
        value 0;
        description
          "PoE is disabled";
      }
      enum poe-enabled {
        value 1;
        description
          "PoE is enabled";
      }
      enum poe-not-applicable {
        value 2;
        description
          "PoE is not applicable on AP LAN port";
      }
    }
    description
      "PoE state of AP LAN port";
  }

  typedef enm-apphost-state {
    type enumeration {
      enum apphost-disabled {
        value 0;
        description
          "Application hosting is disabled";
      }
      enum apphost-enabled {
        value 1;
        description
          "Application hosting is enabled";
      }
      enum apphost-libvrt-failure {
        value 2;
        description
          "Application hosting failure because of Virtualization Library";
      }
      enum apphost-caf-failure {
        value 3;
        description
          "Application hosting failure because of Cisco Application hosting Framework";
      }
    }
    description
      "enumeration to define the possible states of the application hosting of the AP";
  }

  typedef enum-trustpoint-fips-suitability {
    type enumeration {
      enum fips-na {
        value 0;
        description
          "FIPS not applicable";
      }
      enum fips-suitable {
        value 1;
        description
          "FIPS suitable";
      }
      enum fips-not-suitable {
        value 2;
        description
          "FIPS not suitable";
      }
    }
    description
      "FIPS suitability";
  }

  typedef ap-img-site-status {
    type enumeration {
      enum ap-img-site-map-false {
        value 0;
        description
          "Operation not started";
      }
      enum ap-img-site-ongoing {
        value 1;
        description
          "Operation ongoing";
      }
      enum ap-img-site-map-true {
        value 2;
        description
          "Operation completed";
      }
    }
    description
      "Install operation status of site in AP upgrade";
  }

  typedef flag-ap-capability {
    type bits {
      bit bridge-mode-capable {
        position 0;
        description
          "Ap capability for bridge mode";
      }
      bit mesh-daisy-chaining-capable {
        position 1;
        description
          "AP capability for daisy chaining mode";
      }
      bit cap-three-spatial-streams-capable {
        position 2;
        description
          "AP capability for spatial streams mode";
      }
      bit antenna-selection-restricted-capable {
        position 3;
        description
          "AP capability for antenna selection mode";
      }
      bit avc-cnf-capable {
        position 4;
        description
          "AP capability for avc fnf mode";
      }
      bit rxsop-threshold-capable {
        position 5;
        description
          "AP capability for rxsop threshold mode";
      }
      bit fabric-capability {
        position 6;
        description
          "AP capability for fabric mode";
      }
      bit rogue-rldp-capable {
        position 7;
        status deprecated;
        description
          "AP capability for rogue rldp mode";
      }
      bit barbados-external-antenna-sku-capable {
        position 8;
        description
          "Barbados AP capability for external antenna mode";
      }
      bit barbados-internal-antenna-sku-capable {
        position 9;
        description
          "Barbados AP capability for internal antenna mode";
      }
      bit barbados-location-antenna-sku-capable {
        position 10;
        description
          "Barbados AP capability for location antenna mode";
      }
      bit remote-lan-capable {
        position 11;
        description
          "AP capability for remote lan mode";
      }
      bit dot11ac-160mhz-channel-width-capable {
        position 12;
        description
          "AP capability for dot11 channel width mode";
      }
      bit location-optimized-monitor-mode-capable {
        position 13;
        description
          "AP capability for optimized monitor  mode";
      }
      bit avc-fnf-fabric-capable {
        position 14;
        description
          "AP capability for avc fabric mode";
      }
      bit telent-capable {
        position 15;
        description
          "AP capability for telnet mode";
      }
      bit ap-packet-capture-capable {
        position 16;
        description
          "AP capability for packet capture mode";
      }
      bit ap-cts-capable {
        position 17;
        description
          "AP capability for cts mode";
      }
      bit ap-qca-spectrum-intelligence-capable {
        position 18;
        description
          "AP capability for spectrum intelligence mode";
      }
      bit fips-capable {
        position 19;
        description
          "AP capability for fips mode";
      }
      bit is-dot1x-port-auth-capable {
        position 20;
        description
          "AP capability for dot1x port authentication mode";
      }
      bit ap-tracing-capable {
        position 21;
        description
          "AP capability for tracing enable from Controller";
      }
      bit ap-wpa3-capable {
        position 22;
        description
          "AP capability for WPA3 authentication";
      }
      bit is-lag-capable {
        position 23;
        description
          "AP capability for lag mode";
      }
      bit ap-eta-capable {
        position 24;
        description
          "AP capability for Encrypted Traffic Analytics";
      }
      bit is-li-capable {
        position 25;
        description
          "AP capability for LI";
      }
      bit office-extend-capable {
        position 26;
        description
          "AP capability for office extend mode";
      }
      bit eth2-rlan-capable {
        position 27;
        description
          "AP capability for Ethernet2 as RLAN port, when LAG is disabled";
      }
      bit nbn-capable {
        position 28;
        description
          "AP capability for NBN features";
      }
      bit ap-mewlc-capable {
        position 29;
        description
          "AP capability for AP MEWLC features";
      }
      bit sniffer-mode-capable {
        position 30;
        description
          "AP capability for sniffer mode";
      }
      bit icap-full-packet-trace-capable {
        position 31;
        description
          "AP capability for icap full packet trace";
      }
      bit icap-partial-capable {
        position 32;
        description
          "AP capability for icap partial packet trace";
      }
      bit icap-anomaly-detection-capable {
        position 33;
        description
          "AP capability for icap anomaly detection";
      }
      bit icp-statistics-capable {
        position 34;
        description
          "AP capability for icap statistics";
      }
      bit icap-rf-spectrum-capable {
        position 35;
        description
          "AP capability for icap RF spectrum";
      }
      bit icap-feature-capable {
        position 36;
        description
          "AP capability for icap features";
      }
      bit sensor-mode-capable {
        position 37;
        description
          "AP capability for sensor mode";
      }
      bit only-local-mode-capable {
        position 38;
        description
          "AP capability for only local mode";
      }
      bit antenna-band-mode-capable {
        position 39;
        description
          "AP capability for antenna band mode";
      }
      bit sia-capable {
        position 40;
        description
          "AP capability for Self Identifying Antenna";
      }
      bit ap-awips-capable {
        position 41;
        description
          "AP capability for AWIPS";
      }
      bit multi-lan-port-poe-capable {
        position 42;
        description
          "AP capability for multiple PoE ports support";
      }
      bit iox-hardware-capable {
        position 43;
        description
          "AP hardware capability for IOX feature";
      }
      bit auxiliary-client-interface-capable {
        position 44;
        description
          "AP Auxiliary Client Interface capability";
      }
      bit strict-wired-uplink-capable {
        position 45;
        description
          "AP capability for strict wired uplink";
      }
      bit ap-min-two-antennas-to-be-enabled {
        position 46;
        description
          "AP capability for minimum of two Antennas to be enabled";
      }
      bit ap-antennas-5-6-7-not-configurable {
        position 47;
        description
          "AP capability for Antenna ID 5, 6, 7 not configurable";
      }
      bit ap-indoor-mode-capable {
        position 48;
        description
          "AP capability for Indoor Mode";
      }
      bit ext-module-capable {
        position 49;
        description
          "AP capability for for external module support";
      }
      bit ap-heaters-capable {
        position 50;
        description
          "AP capability for heater support";
      }
      bit ap-6300-with-two-antenna-capable {
        position 51;
        description
          "AP capability for 6300 AP with two Antennas";
      }
      bit click-os-feature-set {
        position 52;
        description
          "AP capability for click OS feature set support";
      }
      bit single-band-antenna-mode {
        position 53;
        description
          "AP capability for single band antenna mode";
      }
      bit mesh-daisychain-stp-redundancy-capable {
        position 54;
        description
          "AP capability for daisy chain STP redundancy support";
      }
      bit td-stats {
        position 55;
        description
          "AP capability for traffic distribution stats support";
      }
      bit dual-dfs-stats {
        position 56;
        description
          "AP capability for dual dfs stats support";
      }
      bit usb-or-pse-capable {
        position 57;
        description
          "AP capability for either USB or PSE supported";
      }
      bit ant-1-2-3-no-config {
        position 58;
        description
          "AP capability for Antenna IDs 1(A),2(B),3(C) not configurable";
      }
      bit dual-radio-enable {
        position 59;
        description
          "AP capability for enabling dual-radio in the absence of external antenna";
      }
      bit image-direct-download {
        position 60;
        description
          "AP capability for efficient direct download URI";
      }
      bit aid-manage-capable {
        position 61;
        description
          "AP capability for Managing AID";
      }
      bit oob-img-dwnld-capable {
        position 62;
        description
          "AP capability for OOB(out-of-band, outside CAPWAP control path) image download";
      }
      bit mesh-serial-bhaul-capable {
        position 63;
        description
          "AP capability for Mesh Serial backhaul";
      }
      bit ap-pmk-push-capable {
        position 64;
        description
          "AP capability for PMK distribution";
      }
      bit ap-sensor-air-qlty-capable {
        position 65;
        description
          "AP capability for air-quality environmental sensor hardware support";
      }
      bit ap-sensor-temp-capable {
        position 66;
        description
          "AP capability for temperature environmental sensor hardware support";
      }
      bit ap-power-derate-capable {
        position 67;
        description
          "AP capability for power profile de-rated support";
      }
      bit ap-meraki-capable {
        position 68;
        description
          "AP capability for Meraki conversion";
      }
      bit zero-wait-dfs-capable {
        position 69;
        description
          "AP capability for zero wait DFS";
      }
      bit ap-sensor-press-capable {
        position 70;
        description
          "AP capability for pressure sensor hardware support";
      }
      bit ap-geoloc-capable {
        position 71;
        description
          "AP capability for geolocation hardware support";
      }
      bit icap-sniffer-capable {
        position 72;
        description
          "AP capability for icap-driven sniffer";
      }
      bit ap-mesh-rap-eth-daisy-chain {
        position 73;
        description
          "AP capability for rap ethernet daisy-chain support";
      }
      bit ftm-responder-mode-capable {
        position 74;
        description
          "AP capability for Fine Timing Measurement responder mode support";
      }
      bit ftm-initiator-mode-capable {
        position 75;
        description
          "AP capability for Fine Timing Measurement initiator support";
      }
      bit uwb-responder-mode-capable {
        position 76;
        description
          "AP capability for Ultra-Wideband responder mode support";
      }
      bit uwb-initiator-mode-capable {
        position 77;
        description
          "AP capability for Ultra-Wideband initiator support";
      }
      bit ap-outdoor-mode-capable {
        position 78;
        description
          "AP capability for Outdoor Mode";
      }
      bit ap-sensor-accelerator-capable {
        position 79;
        description
          "AP capability for accelerometer environmental sensor hardware support";
      }
      bit ap-mlo-capable {
        position 80;
        description
          "AP capability for multi-link operation";
      }
      bit cipher-support-gcmp256 {
        position 81;
        description
          "AP capability for GCMP256 Cipher";
      }
      bit ap-single-pid-capable {
        position 82;
        description
          "AP single PID capability";
      }
    }
    description
      "AP Capabilities";
  }

  typedef flag-ap-capability-ext {
    type bits {
      bit ap-client-ftm-capable {
        position 0;
        description
          "AP capability for client FTM(Fine Time Measurement)";
      }
      bit ap-dot11az-capable {
        position 1;
        description
          "AP capability for dot11az";
      }
      bit ap-hybrid-sku-capable {
        position 2;
        description
          "AP hybrid SKU capability";
      }
      bit unii-3-channels-capable {
        position 3;
        description
          "AP UNII-3 low power channels capability";
      }
      bit ap-dual-port-dot1x {
        position 4;
        description
          "AP dual port dot1x capability";
      }
      bit ap-urwb-cap {
        position 5;
        description
          "AP URWB capability";
      }
      bit ap-wat-cap {
        position 6;
        description
          "AP Wireless Active Testing (WAT) capability";
      }
      bit ap-fulldump-capable {
        position 7;
        description
          "AP capability for full kernel coredump support";
      }
      bit ap-minidump-capable {
        position 8;
        description
          "AP capability for mini kernel coredump support";
      }
      bit ap-local-mac-dot11-kv-capable {
        position 9;
        description
          "AP enablement of local-mac stack for Dot11 kv frames";
      }
      bit ap-macsec-cap {
        position 10;
        description
          "AP MACSEC capability";
      }
      bit ap-local-mac-capable {
        position 11;
        description
          "AP enablement of local-mac stack";
      }
      bit ap-idr-capable {
        position 12;
        description
          "Indicates that the AP supports Infrastructure Detection and Response (IDR) functionality";
      }
      bit ap-wat-wired-cap {
        position 13;
        description
          "AP WAT Wired Testing capability";
      }
      bit ap-auto-macsec-cap {
        position 14;
        description
          "AP auto-MACsec capability";
      }
    }
    description
      "AP Capabilities";
  }

  typedef cdp-device-security {
    type bits {
      bit cdp-device-auto-secure {
        position 0;
        description
          "Indicates whether CDP neighbor device supports auto-secure functionality.";
      }
    }
    description
      "CDP device security flags";
  }

  typedef lldp-device-capability {
    type bits {
      bit lldp-device-other-capable {
        position 0;
        description
          "LLDP device other capable";
      }
      bit lldp-device-repeater-capable {
        position 1;
        description
          "LLDP device repeater capable";
      }
      bit lldp-device-bridge-capable {
        position 2;
        description
          "LLDP device bridge capable";
      }
      bit lldp-device-wlan-ap-capable {
        position 3;
        description
          "LLDP device WLAN AP capable";
      }
      bit lldp-device-router-capable {
        position 4;
        description
          "LLDP device router capable";
      }
      bit lldp-device-telephone-capable {
        position 5;
        description
          "LLDP device telephone capable";
      }
      bit lldp-device-docsis-capable {
        position 6;
        description
          "LLDP device DOCSIS cable capable";
      }
      bit lldp-device-station-capable {
        position 7;
        description
          "LLDP device station capable";
      }
    }
    description
      "LLDP neighbor device capabilities";
  }

  typedef ap-lsc-usage {
    type bits {
      bit capwap-dtls {
        position 0;
        description
          "CAPWAP DTLS";
      }
      bit dot1x-port-auth {
        position 1;
        description
          "802.1x authentication with switch port";
      }
    }
    description
      "Certificate usage for different services";
  }

  typedef flag-dot11n-mcs-rates {
    type bits {
      bit dot11n-mcs-rate-zero {
        position 0;
        description
          "802.11n MCS Rate Index 0";
      }
      bit dot11n-mcs-rate-one {
        position 1;
        description
          "802.11n MCS Rate Index 1";
      }
      bit dot11n-mcs-rate-two {
        position 2;
        description
          "802.11n MCS Rate Index 2";
      }
      bit dot11n-mcs-rate-three {
        position 3;
        description
          "802.11n MCS Rate Index 3";
      }
      bit dot11n-mcs-rate-four {
        position 4;
        description
          "802.11n MCS Rate Index 4";
      }
      bit dot11n-mcs-rate-five {
        position 5;
        description
          "802.11n MCS Rate Index 5";
      }
      bit dot11n-mcs-rate-six {
        position 6;
        description
          "802.11n MCS Rate Index 6";
      }
      bit dot11n-mcs-rate-seven {
        position 7;
        description
          "802.11n MCS Rate Index 7";
      }
      bit dot11n-mcs-rate-eight {
        position 8;
        description
          "802.11n MCS Rate Index 8";
      }
      bit dot11n-mcs-rate-nine {
        position 9;
        description
          "802.11n MCS Rate Index 9";
      }
      bit dot11n-mcs-rate-ten {
        position 10;
        description
          "802.11n MCS Rate Index 10";
      }
      bit dot11n-mcs-rate-eleven {
        position 11;
        description
          "802.11n MCS Rate Index 11";
      }
      bit dot11n-mcs-rate-twelve {
        position 12;
        description
          "802.11n MCS Rate Index 12";
      }
      bit dot11n-mcs-rate-thirteen {
        position 13;
        description
          "802.11n MCS Rate Index 13";
      }
      bit dot11n-mcs-rate-fourteen {
        position 14;
        description
          "802.11n MCS Rate Index 14";
      }
      bit dot11n-mcs-rate-fifteen {
        position 15;
        description
          "802.11n MCS Rate Index 15";
      }
      bit dot11n-mcs-rate-sixteen {
        position 16;
        description
          "802.11n MCS Rate Index 16";
      }
      bit dot11n-mcs-rate-seventeen {
        position 17;
        description
          "802.11n MCS Rate Index 17";
      }
      bit dot11n-mcs-rate-eighteen {
        position 18;
        description
          "802.11n MCS Rate Index 18";
      }
      bit dot11n-mcs-rate-nineteen {
        position 19;
        description
          "802.11n MCS Rate Index 19";
      }
      bit dot11n-mcs-rate-twenty {
        position 20;
        description
          "802.11n MCS Rate Index 20";
      }
      bit dot11n-mcs-rate-twenty-one {
        position 21;
        description
          "802.11n MCS Rate Index 21";
      }
      bit dot11n-mcs-rate-twenty-two {
        position 22;
        description
          "802.11n MCS Rate Index 22";
      }
      bit dot11n-mcs-rate-twenty-three {
        position 23;
        description
          "802.11n MCS Rate Index 23";
      }
      bit dot11n-mcs-rate-twenty-four {
        position 24;
        description
          "802.11n MCS Rate Index 24";
      }
      bit dot11n-mcs-rate-twenty-five {
        position 25;
        description
          "802.11n MCS Rate Index 25";
      }
      bit dot11n-mcs-rate-twenty-six {
        position 26;
        description
          "802.11n MCS Rate Index 26";
      }
      bit dot11n-mcs-rate-twenty-seven {
        position 27;
        description
          "802.11n MCS Rate Index 27";
      }
      bit dot11n-mcs-rate-twenty-eight {
        position 28;
        description
          "802.11n MCS Rate Index 28";
      }
      bit dot11n-mcs-rate-twenty-nine {
        position 29;
        description
          "802.11n MCS Rate Index 29";
      }
      bit dot11n-mcs-rate-thirty {
        position 30;
        description
          "802.11n MCS Rate Index 30";
      }
      bit dot11n-mcs-rate-thirty-one {
        position 31;
        description
          "802.11n MCS Rate Index 31";
      }
    }
    description
      "802.11n MCS Rates";
  }

  typedef flag-ant-bitmap {
    type bits {
      bit ap-ant-mode-1x1 {
        position 0;
        description
          "Antenna mode 1 x 1";
      }
      bit ap-ant-mode-2x2 {
        position 1;
        description
          "Antenna mode 2 x 2";
      }
      bit ap-ant-mode-3x3 {
        position 2;
        description
          "Antenna mode 3 x 3";
      }
      bit ap-ant-mode-4x4 {
        position 3;
        description
          "Antenna mode 4 x 4";
      }
      bit ap-ant-mode-5x5 {
        position 4;
        description
          "Antenna mode 5 x 5";
      }
      bit ap-ant-mode-6x6 {
        position 5;
        description
          "Antenna mode 6 x 6";
      }
      bit ap-ant-mode-7x7 {
        position 6;
        description
          "Antenna mode 7 x 7";
      }
      bit ap-ant-mode-8x8 {
        position 7;
        description
          "Antenna mode 8 x 8";
      }
    }
    description
      "Antenna bitmap";
  }

  typedef flag-radio-capabilities {
    type bits {
      bit width-320mhz-capable {
        position 0;
        description
          "Radio capability for 320 MHz channel width";
      }
      bit preamble-puncture-capable {
        position 1;
        description
          "Radio capability for preamble puncturing";
      }
      bit dual-5ghz-band-lock-capable {
        position 2;
        description
          "Radio capability for Dual 5GHz band locked mode";
      }
      bit antenna-mode-switch {
        position 3;
        description
          "Radio capability for antenna mode switch";
      }
      bit static-channel-power {
        position 4;
        description
          "Radio capability for static channel and power";
      }
      bit bridge-mode-support {
        position 5;
        description
          "Radio capability for bridge mode support.
           If this capability is not set, both mesh backhaul and client access not be allowed on this radio
           and it will remain in disabled state when in bridge mode.";
      }
    }
    description
      "AP radio Capabilities";
  }

  grouping ap-gnss-info {
    description
      "AP GNSS information";
    leaf ant-type {
      type wireless-enum-types:enm-ap-geolocation-gnss-ant-type;
      description
        "AP GNSS antenna type";
    }
    leaf ant-cable-length {
      type uint16;
      units "meters";
      description
        "AP GNSS external antenna cable length";
    }
    leaf antenna-product-id {
      type string;
      description
        "AP global navigation satellite system antenna product id";
    }
    leaf antenna-sn {
      type string;
      description
        "AP global navigation satellite system antenna serial number";
    }
  }

  grouping st-ap-sys-info {
    description
      "AP System information";
    leaf mem-type {
      type string;
      description
        "AP memory type";
    }
    leaf cpu-type {
      type string;
      description
        "AP CPU type";
    }
    leaf mem-size {
      type uint32;
      description
        "AP memory size";
    }
  }

  grouping reboot-statistics {
    description
      "AP reboot Statistics";
    leaf reboot-reason {
      type wireless-types:spam-ap-reboot-reason;
      description
        "Reason for last AP reboot";
    }
    leaf reboot-type {
      type wireless-types:spam-ap-reboot-types;
      description
        "AP specified last reboot type";
    }
  }

  grouping reason-count {
    description
      "Per reboot / crash / process / radio (failure or reset) reason counters.";
    leaf reason {
      type uint16;
      description
        "Value for identifying specific reboot";
    }
    leaf count {
      type uint32;
      description
        "Occurrences within the current statistics window.";
    }
    leaf agg-count {
      type uint32;
      description
        "Aggregate occurrences (lifetime or rolling) of this reason.";
    }
  }

  grouping st-ap-reboot-context {
    description
      "Represents the context and details of an AP reboot event, including cause, time, and related process information.";
    leaf reboot-type {
      type wireless-types:spam-ap-reboot-types;
      description
        "Specifies the type of reboot that occurred for the AP.";
    }
    leaf reboot-reason {
      type wireless-types:spam-ap-reboot-reason;
      description
        "Indicates the specific reason for the AP reboot as initiated by the system.";
    }
    leaf crash-reason {
      type wireless-types:ap-reboot-crash-reasons;
      description
        "Specifies the crash reason that led to the AP reboot, if applicable.";
    }
    leaf signal {
      type wireless-types:enm-linux-signal;
      description
        "Indicates the Linux signal that caused the AP process to restart.";
    }
    leaf id {
      type uint16;
      description
        "Unique index identifying this AP reboot event.";
    }
    leaf func-name {
      type string;
      description
        "Name of the function where the reboot or crash was triggered.";
    }
    leaf module {
      type string;
      description
        "Name of the AP software module involved in the reboot event.";
    }
    leaf reboot-time {
      type yang:date-and-time;
      description
        "Timestamp indicating when the AP boot occurred.";
    }
    leaf reload-time {
      type yang:date-and-time;
      description
        "Timestamp indicating when the AP reload occurred.";
    }
    leaf crash-context {
      type string;
      description
        "Additional information or context about the AP crash, if available.";
    }
    leaf version {
      type string;
      description
        "Software image version running on the AP at the time of reboot.";
    }
  }

  grouping st-ap-radio-reset-context {
    description
      "Represents the context and details of an AP radio reset event.";
    leaf slot-id {
      type uint8;
      description
        "Identifier of the slot that experienced a radio failure leading to reset.";
    }
    leaf detail-cause {
      type wireless-types:radio-failure-detail-cause;
      description
        "Detailed cause of the radio failure that triggered the reset.";
    }
    leaf normal-cause {
      type wireless-types:radio-reset-detail-cause;
      description
        "Detailed cause of the normal radio reset that triggered the reset.";
    }
    leaf reset-cause {
      type wireless-types:radio-reset-cause;
      description
        "Category of radio reset - normal operational or failure-based.";
    }
    leaf failure-time {
      type yang:date-and-time;
      description
        "Timestamp indicating when the radio failure occurred.";
    }
  }

  grouping st-ap-reboot {
    description
      "AP reboot statistics and detailed history.";
    leaf wtp-mac {
      type yang:mac-address;
      description
        "MAC address of the AP radio associated with the reboot statistics.";
    }
    leaf link-fail-count {
      type uint32;
      description
        "Window count of link failure reboot.";
    }
    leaf link-fail-agg-count {
      type uint32;
      description
        "Aggregate count of link failure reboot.";
    }
    list spam-count {
      description
        "Spam initiated reboot reason counters.";
      uses wireless-access-point-oper:reason-count;
    }
    list crash-count {
      description
        "Crash initiated reboot reason counters.";
      uses wireless-access-point-oper:reason-count;
    }
    list proc-count {
      description
        "Process (Linux signal) restart reason counters.";
      uses wireless-access-point-oper:reason-count;
    }
    list radio-fail-count {
      description
        "Radio failure detailed cause counters.";
      uses wireless-access-point-oper:reason-count;
    }
    list radio-rst-count {
      description
        "Normal radio reset detailed cause counters .";
      uses wireless-access-point-oper:reason-count;
    }
    list reboot-context {
      description
        "List of detailed AP reboot event context records.";
      uses wireless-access-point-oper:st-ap-reboot-context;
    }
    list proc-restart {
      description
        "List of detailed AP process restart event context records.";
      uses wireless-access-point-oper:st-ap-reboot-context;
    }
    list radio-reset-context {
      description
        "List of AP radio reset event context records.";
      uses wireless-access-point-oper:st-ap-radio-reset-context;
    }
  }

  grouping st-disconnect-detail {
    description
      "AP disconnect detail";
    leaf disconnect-reason {
      type wireless-types:spam-ap-disconnect-reason;
      description
        "AP specified last disconnect reason";
    }
  }

  grouping wtp-board-data {
    description
      "AP Board details";
    leaf wtp-serial-num {
      type string;
      description
        "AP serial number";
    }
    leaf wtp-enet-mac {
      type yang:mac-address;
      description
        "AP Ethernet MAC address";
    }
    container ap-sys-info {
      description
        "AP system info";
      uses wireless-access-point-oper:st-ap-sys-info;
    }
  }

  grouping st-ap-ip-data {
    description
      "IP address of AP";
    leaf ap-prefix {
      type uint32;
      description
        "Prefix length of the IPv6 Address of the AP.";
    }
    leaf mtu {
      type uint32;
      description
        "Maximum transmission unit size for the client";
    }
    leaf is-static-ap-ipaddr {
      type boolean;
      description
        "Value of True implies
         AP is using static IP Address, value of False
         implies AP is using DHCP IP";
    }
    leaf domain-name {
      type string;
      description
        "AP domain name";
    }
    leaf ap-ip-addr {
      type inet:ipv4-address;
      description
        "Static IPv4 Address configuration for the AP.";
    }
    leaf ap-ipv6-addr {
      type inet:ipv6-address;
      description
        "Static IPv6 Address configuration for the AP.";
    }
    leaf ap-ip-netmask {
      type inet:ipv4-address;
      description
        "Netmask of the IPv4 address of the AP.";
    }
    leaf ap-ip-gateway {
      type inet:ipv4-address;
      description
        "Gateway for the IPv4 Address of the AP.";
    }
    leaf ap-ipv6-gateway {
      type inet:ipv6-address;
      description
        "Gateway for the IPv6 Address of the AP.";
    }
    leaf ap-name-server {
      type inet:ip-address;
      description
        "AP name server IP address";
    }
    leaf ap-name-server-type {
      type wireless-types:enm-ip-address-type;
      description
        "Type of the IP address of the name server";
    }
    leaf ap-ipv6-method {
      type wireless-types:enum-ap-ipv6-addr-method;
      description
        "Method used by AP to join over IPv6.";
    }
    leaf is-v6-static-addr {
      type empty;
      description
        "Static IPv6 address configured on the AP";
    }
    leaf static-ip {
      type inet:ip-address;
      description
        "Static IP address of the AP";
    }
    leaf static-gw-ip {
      type inet:ip-address;
      description
        "Gateway for the static IP address of the AP";
    }
    leaf static-netmask {
      type inet:ip-address;
      description
        "Netmask of the static IP address of the AP";
    }
    leaf static-prefix {
      type uint32;
      description
        "AP prefix length of the static IPv6 address";
    }
  }

  grouping ap-link-audit-data {
    description
      "Link audit data";
    leaf linkaudit-flag {
      type ap-types:enm-link-latency-type;
      description
        "Link auditing configuration for the AP";
    }
    leaf linkaudit-delay-time {
      type uint32;
      description
        "Link latency recorded for this AP";
    }
    leaf linkaudit-max-time {
      type uint32;
      description
        "Maximum link latency recorded for the AP";
    }
    leaf linkaudit-min-time {
      type uint32;
      description
        "Minimum link latency recorded for the AP";
    }
    leaf linkaudit-rcv-time {
      type uint32;
      description
        "Time of last latency heartbeat from AP";
    }
  }

  grouping ap-link-audit-oeap-data {
    description
      "On-demand Office Extended AP link test data";
    leaf last-run {
      type yang:date-and-time;
      description
        "Timestamp of the last link test run";
    }
    leaf state {
      type wireless-access-point-oper:oeap-link-test-state;
      description
        "State of the link test";
    }
    leaf dtls-upload {
      type decimal64 {
        fraction-digits 2;
      }
      units "Mbps";
      description
        "Upload speed for the DTLS link";
    }
    leaf latency {
      type uint32;
      units "ms";
      description
        "Latency of the DTLS link";
    }
    leaf jitter {
      type uint32;
      units "ms";
      description
        "Jitter of the DTLS link";
    }
  }

  grouping ap-tcp-mss-data {
    description
      "Configured TCP MSS value for client";
    leaf tcp-adjust-mss-state {
      type boolean;
      description
        "TCP MSS adjust configuration status for the AP";
    }
    leaf tcp-adjust-mss-size {
      type uint16;
      description
        "TCP Maximum Segment Size for the AP.
         Permissible value are between 536 and 1363.
         This will also enable the TCP MSS flag for this AP
         Value of 0 will disable the TCP MSS flag for this AP";
    }
  }

  grouping ap-universal-provision-data {
    description
      "Universal AP Data";
    leaf is-universal {
      type boolean;
      description
        "Value of True implies AP is Universal AP.
         A value of False implies AP is not universal AP";
    }
    leaf universal-prime-status {
      type string;
      description
        "Priming method of the Universal AP";
    }
  }

  grouping ap-pow-data {
    description
      "AP power related information";
    leaf power-injector-sel {
      type wireless-enum-types:power-injector-selection;
      description
        "Specify power level";
    }
    leaf power-injector-macaddr {
      type yang:mac-address;
      description
        "Mac address of the switch port
         that has a power injector and is valid only when
         'power_injector_sel' is in 'installed' mode.
         If set to 00:00:00:00:00:00, AP will detect the MAC address
         of the current switch port that has a power injector";
    }
    leaf pre-std-switch-enabled {
      type boolean;
      description
        "Pre-standard state of the AP, enabled or disabled.
         Value of 'true' denotes Pre-Standard state is Enabled,
         Value of 'false' denotes Pre-Standard state is Disabled";
    }
    leaf power-injector-enabled {
      type boolean;
      description
        "Power injector state, Enabled or Disabled.
         Value of 'true' denotes power injector state is Enabled,
         Value of 'false' denotes power injector state is Disabled";
    }
    leaf power-type {
      type wireless-enum-types:power-type;
      description
        "AP power type";
    }
    leaf power-mode {
      type wireless-enum-types:power-mode-type;
      description
        "This notification is generated whenever an AP detects low
         power from ethernet";
    }
  }

  grouping ap-sys-stats-alarm {
    description
      "AP system stats alarm";
    leaf alarm-status {
      type wireless-access-point-oper:ap-sys-alarm-status;
      description
        "The alarm status";
    }
    leaf raise-ticks {
      type yang:date-and-time;
      description
        "When the alarm was last raised";
    }
    leaf clear-ticks {
      type yang:date-and-time;
      description
        "When the alarm was cleared";
    }
    leaf last-send-ticks {
      type yang:date-and-time;
      description
        "When a trap related to this alarm was sent";
    }
    leaf type {
      type wireless-access-point-oper:ap-sys-alarm-type;
      description
        "Type of the alarm";
    }
  }

  grouping uplink-if-rates {
    description
      "AP uplink interface rates";
    leaf if-name {
      type string;
      description
        "Interface name";
    }
    leaf if-upstream-rate {
      type uint32;
      units "mega bits per seconds";
      description
        "AP uplink upstream rate";
    }
    leaf if-downstream-rate {
      type uint32;
      units "mega bits per seconds";
      description
        "AP uplink downstream rate";
    }
  }

  grouping ap-sys-uplink-if {
    description
      "Structure for AP uplink interface rates";
    list intf {
      description
        "AP uplink interface rates";
      uses wireless-access-point-oper:uplink-if-rates;
    }
  }

  grouping ap-sys-stats-data {
    description
      "AP system stats for CPU and memory usage";
    leaf cpu-usage {
      type uint8;
      units "percentage";
      description
        "AP CPU usage";
    }
    leaf memory-usage {
      type uint8;
      units "percentage";
      description
        "AP memory usage";
    }
    leaf avg-cpu-usage {
      type uint8;
      units "percentage";
      description
        "Average CPU usage";
    }
    leaf avg-memory-usage {
      type uint8;
      units "percentage";
      description
        "Average memory usage";
    }
    leaf window-size {
      type uint16;
      description
        "Current window size of stats";
    }
    leaf last-ts {
      type yang:date-and-time;
      description
        "Last received stats time";
    }
    container memory {
      description
        "Alarm memory";
      uses wireless-access-point-oper:ap-sys-stats-alarm;
    }
    container cpu {
      description
        "Alarm CPU";
      uses wireless-access-point-oper:ap-sys-stats-alarm;
    }
    container uplink-if {
      description
        "Uplink interface information";
      uses wireless-access-point-oper:ap-sys-uplink-if;
    }
    leaf tmp-usage {
      type uint8;
      units "percentage";
      description
        "AP tmp file system usage";
    }
    leaf storage-usage {
      type uint8;
      units "percentage";
      description
        "AP storage usage";
    }
  }

  grouping ap-ntp-sync-status-data {
    description
      "AP NTP synchronization status";
    leaf enabled {
      type boolean;
      description
        "True when NTP is enabled";
    }
    leaf ip-addr {
      type inet:ip-address;
      description
        "The NTP IP address";
    }
    leaf stratum {
      type uint8;
      description
        "The stratum of the NTP server";
    }
    leaf status {
      type wireless-access-point-oper:ewlc-ntp-server-status;
      description
        "The status of NTP synchronization";
    }
    leaf sec-since-last-sync {
      type uint32;
      units "seconds";
      description
        "Seconds elapsed since last AP synchronization with NTP server, at last update from AP";
    }
    leaf sync-offset {
      type int32;
      units "milliseconds";
      description
        "The offset with NTP server during last synchronization";
    }
    leaf rx-ts {
      type yang:date-and-time;
      description
        "The time the controller received the last NTP update from the AP";
    }
  }

  grouping ap-prime-data {
    description
      "AP priming related information";
    leaf primary-controller-name {
      type string;
      description
        "Name of the primary controller configured for the AP";
    }
    leaf secondary-controller-name {
      type string;
      description
        "Name of the secondary controller configured for the AP";
    }
    leaf primary-controller-ip-addr {
      type inet:ip-address;
      description
        "IP address of the primary controller configured
         for the AP";
    }
    leaf secondary-controller-ip-addr {
      type inet:ip-address;
      description
        "IP address of the secondary controller configured
         for AP";
    }
    leaf tertiary-controller-name {
      type string;
      description
        "Name of the tertiary controller configured for the
         AP";
    }
    leaf tertiary-controller-ip-addr {
      type inet:ip-address;
      description
        "IP address of the tertiary controller configured
         for AP";
    }
    leaf ap-fallback-ip {
      type inet:ip-address;
      description
        "The fallback address: AP will join over this address when it can't join over static-ip.";
    }
    leaf fallback-enabled {
      type boolean;
      description
        "Value of true implies AP fallback is enabled";
    }
  }

  grouping ap-mgmt-data {
    description
      "AP management information";
    leaf is-telnet-enabled {
      type boolean;
      description
        "Value of 'true' indicates telnet session
         can be established to the AP";
    }
    leaf is-ssh-enabled {
      type boolean;
      description
        "Value of 'true' indicates SSH session
         can be established to the AP";
    }
    leaf is-console-enabled {
      type boolean;
      description
        "Serial console of the AP is enabled";
    }
  }

  grouping ap-iot-coex-data {
    description
      "WiFi-IOT Coexistence data";
    container iot-coex-cfg-data {
      description
        "WiFi-IOT Coexistence configuration data";
      uses ap-types:st-iot-coex-cfg;
    }
    leaf iot-coex-oper-state {
      type wireless-enum-types:enm-iot-coex-oper-state;
      description
        "Operational state of the WiFi-IOT Coexistence for the AP";
    }
  }

  grouping ap-aux-client-interface-data {
    description
      "Auxiliary Client Interface data";
    leaf is-enabled {
      type boolean;
      description
        "This indicates whether Auxiliary Client Interface is
         enabled on the Access Point";
    }
    leaf vlan-id {
      when "(../is-enabled = 'true')";
      type uint16;
      description
        "VLAN ID of the Auxiliary Client Interface.";
    }
    leaf ip-addr {
      when "(../is-enabled = 'true')";
      type inet:ip-address;
      description
        "IP address of the Auxiliary Client Interface.";
    }
    leaf ip-netmask {
      when "(../is-enabled = 'true')";
      type inet:ipv4-address;
      description
        "Netmask of the Auxiliary Client Interface.";
    }
  }

  grouping ap-grpc-data {
    description
      "AP GRPC data statistics";
    leaf kpa-tx {
      type uint64;
      description
        "Number of keepalive transmit packets";
    }
    leaf kpa-rx {
      type uint64;
      description
        "Number of keepalive received packets";
    }
    leaf ble-scan-tx {
      type uint64;
      description
        "Number of BLE scan TX records";
    }
    leaf token-valid {
      type boolean;
      description
        "Indicates whether the JWT token is valid";
    }
    leaf token-attempts {
      type uint32;
      description
        "The total number of token attempts made to validate JWT token";
    }
    leaf token-failures {
      type uint32;
      description
        "The total number of failures to validate JWT token";
    }
    leaf token-last-success-ts {
      type yang:date-and-time;
      description
        "The timestamp of last successful JWT token validation";
    }
    leaf token-last-fail-ts {
      type yang:date-and-time;
      description
        "The timestamp of last failed JWT token validation";
    }
    leaf token-exp-ts {
      type yang:date-and-time;
      description
        "JWT token expiration time";
    }
    leaf grpc-endp-url {
      type string;
      description
        "GRPC connection endpoint url";
    }
  }

  grouping grpc-e2e-data {
    description
      "gRPC endpoint connection results";
    leaf is-process-up {
      type boolean;
      description
        "Indicates whether the process is up";
    }
    leaf is-config-present {
      type boolean;
      description
        "Indicates whether the config is present";
    }
    leaf ep-alive {
      type boolean;
      description
        "Indicates whether the endpoint is valid";
    }
    leaf https-is-port-open {
      type boolean;
      description
        "Indicates whether HTTPS port is open";
    }
    leaf is-cacert-valid {
      type boolean;
      description
        "Indicates whether the CA certificate for the endpoint connection is valid";
    }
    leaf https-is-cert-valid {
      type boolean;
      description
        "Indicates whether the HTTPS certificate for the endpoint connection is valid";
    }
    leaf https-is-ep-resp {
      type boolean;
      description
        "Indicates whether the endpoint responds to HTTPS connections";
    }
    leaf grpc-is-cert-valid {
      type boolean;
      description
        "Indicates whether the gRPC certificate for the endpoint connection is valid";
    }
    leaf grpc-is-cert-config {
      type boolean;
      description
        "Indicates whether a security certificate is configured for the gRPC endpoint to enable secure communication";
    }
    leaf cli-state {
      type wireless-access-point-oper:enum-iotgwd-e2e-cli-exec-state;
      description
        "Indicates the current execution state of the CLI command for the gRPC endpoint connection";
    }
    leaf last-update {
      type yang:date-and-time;
      description
        "Indicates the last time the gRPC endpoint connection data was updated";
    }
    leaf grpc-is-port-open {
      type boolean;
      description
        "Indicates whether the gRPC service port on the access point is open and available for remote connections";
    }
  }

  grouping ap-dna-data {
    description
      "Cisco-DNA related data";
    leaf grpc-status {
      type wireless-access-point-oper:enum-ap-dna-grpc-status-code;
      description
        "This indicates the status of the gRPC channel from the
         Access Point to Cisco-DNA.";
    }
    leaf packets-tx-attempts {
      type uint64;
      description
        "Number of packets transmissions attempts on the gRPC channel.";
    }
    leaf packets-tx-failures {
      type uint64;
      description
        "Number of packets transmissions failures on the gRPC channel.";
    }
    leaf packets-rx {
      type uint64;
      description
        "Number of packets received on the gRPC channel.";
    }
    leaf packets-rx-failures {
      type uint64;
      description
        "Number of received packets failures on the gRPC channel.";
    }
    container grpc {
      description
        "GRPC connection related stats";
      uses wireless-access-point-oper:ap-grpc-data;
    }
    container iot-e2e-data {
      description
        "IOT GRPC endpoint data";
      uses wireless-access-point-oper:grpc-e2e-data;
    }
    container spaces-e2e-data {
      description
        "Spaces GRPC endpoint data";
      uses wireless-access-point-oper:grpc-e2e-data;
    }
  }

  grouping ap-spaces-conn-data {
    description
      "AP to Spaces Telemetry Connection stats";
    leaf grpc-status {
      type wireless-access-point-oper:enum-ap-dna-grpc-status-code;
      description
        "Status of the gRPC channel from AP to Spaces.";
    }
    leaf pkts-tx {
      type uint64;
      description
        "Number of packet transmission attempts on the gRPC channel.";
    }
    leaf pkts-tx-fail {
      type uint64;
      description
        "Number of packet transmission failures on the gRPC channel.";
    }
    leaf pkts-rx {
      type uint64;
      description
        "Number of packets received on the gRPC channel.";
    }
    leaf pkts-rx-fail {
      type uint64;
      description
        "Number of received packet failures on the gRPC channel.";
    }
    leaf token-valid {
      type boolean;
      description
        "Indicates whether the spaces JWT token is valid";
    }
    leaf token-attempts {
      type uint32;
      description
        "The total number of token attempts made to validate spaces JWT token";
    }
    leaf token-failures {
      type uint32;
      description
        "The total number of failures to validate spaces JWT token";
    }
    leaf token-last-succ-ts {
      type yang:date-and-time;
      description
        "The timestamp of last successful spaces JWT token validation";
    }
    leaf token-last-fail-ts {
      type yang:date-and-time;
      description
        "The timestamp of last failed spaces JWT token validation";
    }
    leaf token-exp-ts {
      type yang:date-and-time;
      description
        "Spaces JWT token expiration time";
    }
    leaf spaces-endp-url {
      type string;
      description
        "Spaces GRPC connection endpoint url";
    }
  }

  grouping ap-gas-rate-limit-cfg-data {
    description
      "Cisco AP Generic Advertisement Services (GAS) rate configuration details";
    leaf is-gas-rate-limit-enabled {
      type boolean;
      description
        "GAS rate limit enabled status";
    }
    leaf num-req-per-interval {
      type uint8;
      description
        "Number of GAS request per interval ";
    }
    leaf interval-msec {
      type uint16;
      description
        "GAS rate limit interval";
    }
  }

  grouping ap-ntp-server-info-cfg-data {
    description
      "NTP server information on Access Point configuration";
    leaf ntp-server-address {
      type inet:ip-address;
      description
        "Specifies the NTP server address to be used by the Access Point";
    }
    leaf trust-key {
      type string;
      description
        "The trust key to use in NTP authentication";
    }
    leaf key-id {
      type uint32;
      description
        "An integer key id that identifies the NTP authentication key ";
    }
    leaf key-type {
      type ap-types:enm-ap-ntp-key-type;
      description
        "The type of the key digest: md5 or sha1";
    }
    leaf key-format {
      type ap-types:enm-ap-ntp-key-format;
      description
        "The format of the key digest: ascii or hex";
    }
    leaf trust-key-type {
      type wireless-enum-types:crypt-type;
      description
        "The encryption to use when storing the trust key locally";
    }
  }

  grouping ap-persistent-ssid-data {
    description
      "Persistent SSID broadcast operation information";
    leaf is-persistent-ssid-enabled {
      type boolean;
      description
        "True if persistent SSID broadcast is enabled on AP";
    }
  }

  grouping ap-retransmit-data {
    description
      "AP retransmission related parameters";
    leaf count {
      type uint8;
      description
        "Total number of times config data is retransmitted";
    }
    leaf interval {
      type uint8;
      units "seconds";
      description
        "Interval at which config data is retransmitted";
    }
  }

  grouping st-infrastructure-mfp {
    description
      "Cisco AP Management Frame Protection configuration details";
    leaf mfp-validation {
      type boolean;
      description
        "Management Frame Validation status";
    }
    leaf mfp-protection {
      type boolean;
      description
        "Management frame protection status";
    }
  }

  grouping st-ap-stats-timer {
    description
      "Cisco AP stats related timer";
    leaf stat-tmr {
      type uint32;
      description
        "Cisco AP statistics reporting period";
    }
  }

  grouping st-ap-syslog-info {
    description
      "Cisco AP system logging information";
    leaf log-host-ipaddr {
      type inet:ip-address;
      description
        "Cisco AP system logging host IP address";
    }
    leaf log-trap-level {
      type wireless-types:syslog-trap-level;
      description
        "Logging trap severity level";
    }
    leaf log-tls-mode {
      type boolean;
      description
        "Cisco AP secured logging TLS mode";
    }
    leaf log-facility-level {
      type ap-types:syslog-facility-value;
      description
        "Cisco AP syslog facility level";
    }
  }

  grouping ap-timer-data {
    description
      "Cisco access point timer data";
    container stats-timer {
      description
        "Cisco AP statistics report timer data";
      uses wireless-access-point-oper:st-ap-stats-timer;
    }
  }

  grouping st-ap-login-credentials {
    description
      "Cisco AP login credentials";
    leaf dot1x-eap-type {
      type ap-types:enm-ap-dot1x-eap-type;
      description
        "802.1X Extensible Authentication Protocol (EAP) type";
    }
    leaf user-name {
      type string;
      description
        "Cisco AP login username";
    }
    leaf dot1x-username {
      type string;
      description
        "Cisco AP 802.1X username";
    }
  }

  grouping st-ap-vlan {
    description
      "AP VLAN tag details";
    leaf vlan-tag-state {
      type wireless-access-point-oper:enm-vlan-state;
      description
        "AP VLAN tagging state";
    }
    leaf vlan-tag-id {
      type uint16;
      description
        "VLAN ID for the AP";
    }
  }

  grouping support-bundle-info {
    description
      "Support bundle file transfer information";
    leaf ap-mac {
      type yang:mac-address;
      description
        "AP MAC address";
    }
    leaf ap-name {
      type string;
      description
        "AP Name";
    }
    leaf last-filename {
      when "(../status = 'supp-bundle-copied')";
      type string;
      description
        "Support bundle file name";
    }
    leaf last-server-ip {
      when "(../status != 'supp-bundle-none')";
      type inet:ip-address;
      description
        "Destination server IP address";
    }
    leaf last-file-path {
      when "(../status != 'supp-bundle-none')";
      type string;
      description
        "Destination file path";
    }
    leaf last-mode {
      when "(../status != 'supp-bundle-none')";
      type wireless-enum-types:support-bundle-transfer-mode;
      description
        "Support bundle file transfer mode";
    }
    leaf last-success-transfer-time {
      when "(../status = 'supp-bundle-copied')";
      type yang:date-and-time;
      description
        "Support bundle file transfer time";
    }
    leaf status {
      type wireless-enum-types:support-bundle-status;
      description
        "Support bundle file transfer status";
    }
    leaf failure-reason {
      when "(../status = 'supp-bundle-copy-failed')";
      type string;
      description
        "Support bundle file transfer failure reason";
    }
  }

  grouping st-ap-security-oper-data {
    description
      "LSC provisioning details";
    leaf fips-enabled {
      type boolean;
      description
        "Cisco AP FIPS enabled status";
    }
    leaf wlancc-enabled {
      type boolean;
      description
        "Cisco AP CC enabled status";
    }
    leaf cert-type {
      type wireless-access-point-oper:enm-cert-type;
      description
        "Enum values denoting AP Certificate Type.
         1 : manufactureinstalled : Manufacture Installed Certificate type (MIC).
         2 : selfsigned : Self Signed Certificate type (SSC).
         3 : localsignificance : Local Significance";
    }
    leaf lsc-ap-auth-type {
      type ap-types:enm-lsc-ap-auth-state-type;
      description
        "AP LSC authentication state";
    }
    leaf ap-cert-policy {
      type wireless-types:enm-ap-cert-policy;
      description
        "Certificate policy used during AP join";
    }
    leaf ap-cert-expiry-time {
      type yang:date-and-time;
      description
        "AP certificate expiry time";
    }
    leaf ap-cert-issuer-cn {
      type string;
      description
        "AP certificate issuer common name";
    }
  }

  grouping st-ap-oper-data {
    description
      "AP operational data";
    leaf wtp-mac {
      type yang:mac-address;
      description
        "MAC Address of the AP Radio";
    }
    leaf radio-id {
      type uint32;
      description
        "AP radio identifier";
    }
    leaf ap-antenna-band-mode {
      type wireless-enum-types:ant-band-mode;
      description
        "Antenna band mode. For
         AP, in which this variable is not relevant,
         value of 'Not Applicable' will be returned.
         In the dual band mode, only two dual band antennas are used,
         connected to ports 1 and 2. In this case, both bands share these antennas.";
    }
    leaf link-encryption-enabled {
      type boolean;
      description
        "True if  encryption between
         controller and AP is enabled. Encryption
         can only be enabled if ESM card in controller is plugged in.
         Otherwise false.";
    }
    leaf ap-remote-debug-mode {
      type boolean;
      description
        "Remote debugging status for the AP";
    }
    container ap-ip-data {
      description
        "AP IP address configuration";
      uses wireless-access-point-oper:st-ap-ip-data;
    }
    container ap-prime-info {
      description
        "Controller configuration for the AP";
      uses wireless-access-point-oper:ap-prime-data;
    }
    container ap-mgmt {
      description
        "AP management data";
      uses wireless-access-point-oper:ap-mgmt-data;
    }
    container ap-login-credentials {
      description
        "Login credentials configured on an AP";
      uses wireless-access-point-oper:st-ap-login-credentials;
    }
    container ap-pow {
      description
        "AP power related data";
      uses wireless-access-point-oper:ap-pow-data;
    }
    container ap-sys-stats {
      description
        "AP system statistics";
      uses wireless-access-point-oper:ap-sys-stats-data;
    }
    container ipv4-tcp-mss {
      description
        "Configured IPv4 TCP MSS value for client";
      uses wireless-access-point-oper:ap-tcp-mss-data;
    }
    container ipv6-tcp-mss {
      description
        "Configured IPv6 TCP MSS value for client";
      uses wireless-access-point-oper:ap-tcp-mss-data;
    }
    container link-audit {
      description
        "Link audit data";
      uses wireless-access-point-oper:ap-link-audit-data;
    }
    container timer {
      description
        "Cisco access point timer data";
      uses wireless-access-point-oper:ap-timer-data;
    }
    container retransmit {
      description
        "AP retransmission parameters";
      uses wireless-access-point-oper:ap-retransmit-data;
    }
    container syslog {
      description
        "Cisco AP System Logging";
      uses wireless-access-point-oper:st-ap-syslog-info;
    }
    container infrastructure-mfp {
      description
        "Cisco AP Management Frame Protection";
      uses wireless-access-point-oper:st-infrastructure-mfp;
    }
    container persistent-ssid {
      description
        "Persistent SSID broadcast operation information";
      uses wireless-access-point-oper:ap-persistent-ssid-data;
    }
    container ap-gas-rate-limit-cfg {
      description
        "Cisco AP Generic Advertisement Services (GAS) rate configuration";
      uses wireless-access-point-oper:ap-gas-rate-limit-cfg-data;
    }
    container ap-ntp-server-info-cfg {
      description
        "NTP server information to be used by AP";
      uses wireless-access-point-oper:ap-ntp-server-info-cfg-data;
    }
    leaf ap-udplite-info {
      type wireless-enum-types:ipv6-capwap-checksum-type;
      description
        "UDP-Lite operational information. enum values denoting
          0 UDP-Lite checksum not yet configured
          1 UDP-Lite checksum for IPv6 CAPWAP data packets
          2 checksum for IPv6 CAPWAP data packets";
    }
    container accounting {
      description
        "Accounting info to be sent to radius server";
      uses ap-types:st-accounting;
    }
    container aux-client-interface-data {
      description
        "Auxiliary Client Interface data";
      uses wireless-access-point-oper:ap-aux-client-interface-data;
    }
    container ap-dna-data {
      description
        "Cisco-DNA related data";
      uses wireless-access-point-oper:ap-dna-data;
    }
    leaf ap-indoor-mode {
      type boolean;
      description
        "Identifier for indoor AP mode";
    }
    leaf is-local-net {
      type boolean;
      description
        "Identifier for local access in OEAP AP";
    }
    container oeap-audit {
      description
        "On-demand Office Extended AP link test data";
      uses wireless-access-point-oper:ap-link-audit-oeap-data;
    }
    leaf prov-ssid {
      type boolean;
      description
        "Enable/Disable Provisional SSID on Office Extended AP";
    }
    container ap-ntp-sync-status {
      description
        "AP NTP synchronization status";
      uses wireless-access-point-oper:ap-ntp-sync-status-data;
    }
    container ap-tz-config {
      description
        "AP timezone configuration";
      uses ap-types:st-ap-timezone-cfg-data;
    }
    leaf ap-pmk-propagation-status {
      type boolean;
      description
        "AP PMK push propagation status";
    }
    leaf ap-role {
      type wireless-enum-types:enum-ap-pmk-propagation-role;
      description
        "AP role in PMK push";
    }
    leaf pmk-bs-receiver-addr {
      type yang:mac-address;
      description
        "PMK bulk sync receiver AP MAC address";
    }
    leaf pmk-bs-sender-addr {
      type yang:mac-address;
      description
        "PMK bulk sync sender AP MAC address";
    }
    leaf power-profile {
      type string;
      description
        "Power profile applied to the AP";
    }
    leaf pwr-cal-profile {
      type string;
      description
        "Calendar profile associated to power profile";
    }
    leaf max-clients-allowed {
      type uint16;
      description
        "Maximum clients allowed on an AP";
    }
    leaf power-save-mode {
      type empty;
      description
        "AP in power-save mode";
    }
    leaf priming-profile-src {
      type wireless-access-point-oper:enm-ap-priming-source;
      description
        "AP priming profile configuration source";
    }
    leaf priming-profile {
      type string;
      description
        "Applied AP priming profile name";
    }
    leaf priming-filter {
      type string;
      description
        "AP priming filter name";
    }
    leaf ap-priming-override {
      type boolean;
      description
        "AP priming configuration override flag status under applied AP filter";
    }
    container kernel-coredump {
      description
        "Kernel coredump configuration";
      uses ap-types:st-kernel-coredump-cfg;
    }
    leaf ranging-mode {
      type wireless-enum-types:enm-ranging-mode;
      description
        "Ranging mode - normal or accurate";
    }
    leaf pwr-prof-type {
      type string;
      description
        "Power profile type";
    }
    leaf ap-outdoor-mode {
      type boolean;
      description
        "Identifier for outdoor AP mode";
    }
    container spaces-conn-data {
      description
        "AP to Spaces Telemetry Connection related data";
      uses wireless-access-point-oper:ap-spaces-conn-data;
    }
    leaf ap-console-speed {
      type wireless-enum-types:enm-ap-console-speed;
      description
        "Configure AP console speed";
    }
    container iot-coex-data {
      description
        "WiFi-IOT Coexistence data";
      uses wireless-access-point-oper:ap-iot-coex-data;
    }
  }

  grouping wtp-descriptor-data {
    description
      "Structure stores the details about the WTP";
    leaf radio-slots-in-use {
      type uint8;
      description
        "Number of slots in use";
    }
    leaf encryption-capabilities {
      type boolean;
      description
        "Encryption capabilities of the AP";
    }
  }

  grouping board-data-opt {
    description
      "AP Board details";
    leaf join-priority {
      type uint8;
      description
        "AP join priority";
    }
  }

  grouping wtp-policy-tag-info {
    description
      "AP tag relation information";
    leaf policy-tag-name {
      type string;
      description
        "policy tag associated with AP";
    }
  }

  grouping wtp-site-tag-info {
    description
      "Site tag associated with the AP";
    leaf site-tag-name {
      type string;
      description
        "AP site tag name";
    }
    leaf ap-profile {
      type string;
      description
        "AP join profile name";
    }
    leaf flex-profile {
      type string;
      description
        "AP flex profile name";
    }
  }

  grouping wtp-rf-tag-info {
    description
      "RF tag information for the AP";
    leaf rf-tag-name {
      type string;
      description
        "RF tag name associated with the AP";
    }
    leaf ap-beam-state {
      type wireless-enum-types:enm-ap-beam-state;
      description
        "AP Beam state";
    }
  }

  grouping st-resolved-tags-data {
    description
      "Resolved AP tag details";
    leaf resolved-policy-tag {
      type string;
      description
        "Policy tag name";
    }
    leaf resolved-site-tag {
      type string;
      description
        "Site tag name";
    }
    leaf resolved-rf-tag {
      type string;
      description
        "RF tag name";
    }
  }

  grouping ap-filter-info {
    description
      "AP filter information";
    leaf filter-name {
      type string;
      description
        "AP filter name";
    }
  }

  grouping wtp-tags-data {
    description
      "WTP tag associations";
    leaf tag-source {
      type ap-types:enm-ap-tag-source;
      description
        "Tag source";
    }
    leaf is-ap-misconfigured {
      type boolean;
      description
        "Flag for misconfigured access points";
    }
    container resolved-tag-info {
      description
        "Resolved Tag details for an AP";
      uses wireless-access-point-oper:st-resolved-tags-data;
    }
    container policy-tag-info {
      description
        "Policy tag information for the AP";
      uses wireless-access-point-oper:wtp-policy-tag-info;
    }
    container site-tag {
      description
        "Site tag information for the AP";
      uses wireless-access-point-oper:wtp-site-tag-info;
    }
    container rf-tag {
      description
        "RF tag information for the AP";
      uses wireless-access-point-oper:wtp-rf-tag-info;
    }
    container filter-info {
      description
        "AP filter information";
      uses wireless-access-point-oper:ap-filter-info;
    }
    leaf is-dtls-lsc-fbk-ap {
      type boolean;
      description
        "LSC fallback status for the AP";
    }
    leaf ap-misconfig {
      type wireless-access-point-oper:ap-misconfig;
      description
        "AP misconfiguration reason";
    }
  }

  grouping hyperlocation-ap-data {
    description
      "AP Hyperlocation details";
    leaf hyperlocation-method {
      type wireless-types:enm-hyperlocation-method;
      description
        "AP hyperlocation method";
    }
    leaf cmx-ip {
      type inet:ip-address;
      description
        "Connected Mobile Experiences (CMX) IP address";
    }
  }

  grouping xm-info {
    description
      "WTP extension module information";
    leaf numeric-id {
      type uint16;
      description
        "Numeric ID of extension module";
    }
    leaf max-power {
      type uint32;
      units "dBm";
      description
        "WTP extension module maximum power";
    }
    leaf serial-number-string {
      type string;
      description
        "WTP extension module serial number";
    }
    leaf product-id-string {
      type string;
      description
        "WTP extension module product ID string";
    }
    leaf module-type {
      type string;
      description
        "Module type";
    }
    leaf module-description {
      type string;
      description
        "WTP extension module description";
    }
  }

  grouping wtp-xm-info {
    description
      "WTP extension module information";
    leaf is-module-present {
      type boolean;
      description
        "True if an external module is present or not";
    }
    leaf enable {
      when "(../is-module-present = 'true')";
      type boolean;
      description
        "Module operational state";
    }
    container xm {
      description
        "WTP extension module information";
      uses wireless-access-point-oper:xm-info;
    }
  }

  grouping st-sliding-window {
    description
      "CAPWAP multiwindow configuration";
    leaf multi-window-support {
      type boolean;
      description
        "True if CAPWAP multiwindow is enabled on AP";
    }
    leaf window-size {
      type uint16;
      description
        "Window size for CAPWAP multiwindow transport";
    }
  }

  grouping st-external-module-data {
    description
      "External module info used by AP";
    container xm-data {
      description
        "External module data";
      uses wireless-access-point-oper:wtp-xm-info;
    }
    container usb-data {
      description
        "USB module data";
      uses wireless-access-point-oper:wtp-xm-info;
    }
    leaf usb-override {
      type boolean;
      description
        "USB overridden status.
         Value of 'true' indicates USB module operational state can be changed only using AP level configuration.
         Value of 'false' indicates USB module operational state can be changed only using USB configuration under ap-cfg-profile.";
    }
    leaf is-ext-module-enabled {
      type boolean;
      status obsolete;
      description
        "External module state";
    }
  }

  grouping ap-dhcp-server-data {
    description
      "DHCP server details for an AP";
    leaf is-dhcp-server-enabled {
      type boolean;
      description
        "DHCP server status";
    }
  }

  grouping st-aaa-location-attributes {
    description
      "AP AAA Location attribute identifiers";
    leaf civic-id {
      type string;
      description
        "Civic profile identifier for AAA Location information";
    }
    leaf geo-id {
      type string;
      description
        "Geo profile identifier for AAA Location information";
    }
    leaf oper-id {
      type string;
      description
        "Operator identifier for AAA Location information";
    }
  }

  grouping st-ap-location {
    description
      "AP location information";
    leaf floor {
      type uint32;
      description
        "Floor of the AP";
    }
    leaf location {
      type string;
      description
        "User assigned location of the AP";
    }
    container aaa-location {
      description
        "AAA Location attributes of the AP";
      uses wireless-access-point-oper:st-aaa-location-attributes;
    }
    leaf floor-id {
      type int32;
      description
        "Floor id of the AP";
    }
    leaf ranging-capability {
      type uint16;
      description
        "Ranging capability of the AP";
    }
    leaf ap-height-atf {
      type uint16;
      units "centimeters";
      description
        "Specifies the height of the access point above the floor (ATF), measured in
         centimetres. This is distinct from other AP height configurations, such
         as height above ground level (AGL) or height above mean sea level (MSL)";
    }
  }

  grouping st-ap-services {
    description
      "Services used by AP";
    leaf monitor-mode-opt-type {
      type wireless-enum-types:lomm-mode-type;
      description
        "Monitor mode optimization type on the AP
         all      - All optimization is enabled
         tracking - Tracking is optimized
         wips     - WIPS optimization is enabled
         none     - No optimization is enabled";
    }
    container ap-dhcp-server {
      description
        "DHCP server details for an AP";
      uses wireless-access-point-oper:ap-dhcp-server-data;
    }
    leaf tot-sniffer-radio {
      type uint8;
      description
        "Total number of radios on which sniffer role is enabled";
    }
  }

  grouping st-wtp-version {
    description
      "AP software version information";
    container backup-sw-version {
      description
        "Backup software version of the AP";
      uses wireless-types:version-info;
    }
    container mini-ios-version {
      description
        "Cisco AP mini IOS version details";
      uses wireless-types:version-info;
    }
    container sw-ver {
      description
        "Software version of the AP";
      uses wireless-types:version-info;
    }
    container boot-ver {
      description
        "Cisco AP boot version details";
      uses wireless-types:version-info;
    }
    leaf sw-version {
      type string;
      description
        "Cisco AP software version details";
    }
  }

  grouping st-ap-models {
    description
      "AP device model information";
    leaf model {
      type string;
      description
        "Stores the model string of the AP";
    }
  }

  grouping st-static-info {
    description
      "AP device static information";
    container board-data {
      description
        "AP Board Data";
      uses wireless-access-point-oper:wtp-board-data;
    }
    container board-data-opt {
      description
        "AP Additional Board data option";
      uses wireless-access-point-oper:board-data-opt;
    }
    container descriptor-data {
      description
        "AP FW,HW information";
      uses wireless-access-point-oper:wtp-descriptor-data;
    }
    container ap-prov {
      description
        "AP universal provision";
      uses wireless-access-point-oper:ap-universal-provision-data;
    }
    container ap-models {
      description
        "AP device model";
      uses wireless-access-point-oper:st-ap-models;
    }
    leaf num-ports {
      type uint8;
      description
        "Number of ports on AP";
    }
    leaf num-slots {
      type uint8;
      description
        "Number of slots present in the access point";
    }
    leaf wtp-model-type {
      type uint8;
      description
        "AP model type";
    }
    leaf ap-capability {
      type wireless-access-point-oper:flag-ap-capability;
      description
        "AP capabilities";
    }
    leaf is-mm-opt {
      type boolean;
      description
        "AP monitor mode optimization support";
    }
    leaf ap-image-name {
      type string;
      description
        "AP Software image name";
    }
    leaf ap-capability-ext {
      type wireless-access-point-oper:flag-ap-capability-ext;
      description
        "AP capabilities";
    }
  }

  grouping st-ap-crash-data {
    description
      "AP crash data";
    leaf ap-crash-file {
      type string;
      description
        "AP crash file";
    }
    leaf ap-radio-2g-crash-file {
      type string;
      description
        "AP 2 GHz radio crash file";
    }
    leaf ap-radio-5g-crash-file {
      type string;
      description
        "AP 5 GHz radio crash file";
    }
    leaf ap-radio-6g-crash-file {
      type string;
      description
        "AP 6 GHz radio crash file";
    }
    leaf ap-rad-5g-slot2-crash-file {
      type string;
      description
        "AP 5 GHz radio slot 2 crash file";
    }
  }

  grouping st-temperature-info {
    description
      "AP temperature related information";
    leaf degree {
      type int8;
      units "Celsius";
      description
        "AP temperature";
    }
    leaf temp-status {
      type wireless-access-point-oper:enum-ap-temp-status;
      description
        "AP temperature status";
    }
    leaf heater-status {
      type wireless-access-point-oper:enum-ap-temp-heater-status;
      description
        "AP heater status";
    }
  }

  grouping st-dynamic-info {
    description
      "AP device dynamic information";
    container ap-crash-data {
      description
        "AP crash data";
      uses wireless-access-point-oper:st-ap-crash-data;
    }
    leaf led-state-enabled {
      type boolean;
      description
        "True if LED state of AP is enabled.";
    }
    leaf reset-button-state {
      type boolean;
      description
        "True if AP Reset button state is enabled";
    }
    leaf led-flash-enabled {
      type boolean;
      description
        "True if LED Flash state of AP is enabled.";
    }
    leaf flash-sec {
      type uint16;
      units "seconds";
      description
        "LED Flash timer duration for AP.";
    }
    container temp-info {
      description
        "AP temperature info";
      uses wireless-access-point-oper:st-temperature-info;
    }
    leaf led-flash-expiry {
      type yang:date-and-time;
      description
        "Led Flash Expiry Date and Time";
    }
  }

  grouping st-ap-device-info {
    description
      "AP device specific information";
    container static-info {
      description
        "AP device static information";
      uses wireless-access-point-oper:st-static-info;
    }
    container dynamic-info {
      description
        "AP device dynamic information";
      uses wireless-access-point-oper:st-dynamic-info;
    }
    container wtp-version {
      description
        "AP software version";
      uses wireless-access-point-oper:st-wtp-version;
    }
  }

  grouping st-ap-state {
    description
      "The AP state";
    leaf ap-admin-state {
      type wireless-enum-types:admin-state;
      description
        "The AP admin state";
    }
    leaf ap-operation-state {
      type wireless-access-point-oper:enum-ap-state;
      description
        "The AP operation state";
    }
  }

  grouping st-ap-fabric-data {
    description
      "AP fabric related attributes";
    leaf is-fabric-ap {
      type boolean;
      description
        "True if AP is fabric AP";
    }
  }

  grouping st-ap-6ghz-data {
    description
      "AP 6GHz related attributes";
    leaf std-pwr-mode-allowed {
      type empty;
      description
        "AP is allowed to operate in 6GHz standard power mode";
    }
  }

  grouping st-ap-mode-data {
    description
      "AP modes related information";
    leaf home-ap-enabled {
      type boolean;
      description
        "Flag for office extend feature";
    }
    leaf clear-mode {
      type boolean;
      description
        "Clear AP mode to site tag AP mode";
    }
    leaf ap-sub-mode {
      type ap-types:ap-sub-mode-type;
      description
        "value of 'true' indicates this AP is a WIPS AP.
         value of 'false' indicates this AP is not a WIPS AP.
         This applies only when the AP is either in Local or in Monitor mode";
    }
    leaf wtp-mode {
      type wireless-types:enm-ewlc-spam-ap-modes;
      description
        "Mode of the AP to which the Mobile Station is associated.";
    }
    container ap-fabric-data {
      description
        "AP fabric related attributes";
      uses wireless-access-point-oper:st-ap-fabric-data;
    }
    container ap-6ghz-data {
      description
        "AP 6GHz related attributes";
      uses wireless-access-point-oper:st-ap-6ghz-data;
    }
  }

  grouping st-ap-times {
    description
      "AP time related information";
    leaf boot-time {
      type yang:date-and-time;
      description
        "Last AP reboot Date and Time";
    }
    leaf join-time {
      type yang:date-and-time;
      description
        "Date and Time at which AP joined";
    }
    leaf join-time-taken {
      type uint32;
      units "seconds";
      description
        "The amount of time taken by AP to join the wireless controller";
    }
  }

  grouping st-proxy-info {
    description
      "HTTP proxy configuration provisioned to this AP";
    leaf hostname {
      type string;
      description
        "HTTP proxy hostname";
    }
    leaf port {
      type uint16;
      description
        "HTTP proxy port";
    }
    leaf no-proxy-list {
      type string;
      description
        "List of URLs to be excluded from proxying";
    }
    leaf username {
      type string;
      description
        "AP proxy username";
    }
    leaf password-type {
      type wireless-enum-types:crypt-type;
      description
        "Password type for AP proxy";
    }
    leaf password {
      type string;
      description
        "Password for AP proxy";
    }
  }

  grouping st-local-dhcp-pool {
    description
      "DHCP pool";
    leaf network {
      type inet:ipv4-address;
      description
        "DHCP pool start address";
    }
    leaf lease-time {
      type uint16 {
        range "0 .. 365";
      }
      units "days";
      description
        "Total lease time in days";
    }
    leaf netmask {
      type inet:ipv4-address;
      description
        "Subnet mask address";
    }
  }

  grouping st-antenna-monitoring {
    description
      "Operation antenna monitoring configuration sent to the AP";
    leaf support {
      type empty;
      description
        "Support of the antenna monitoring feature by the AP";
    }
    leaf enabled {
      when 'boolean(../support)';
      type empty;
      description
        "Antenna monitoring enabled on the AP";
    }
    leaf rssi-fail-threshold {
      when 'boolean(../support) and boolean(../enabled)';
      type uint8;
      units "dB";
      description
        "RSSI Failure Threshold for antenna monitoring on the AP";
    }
    leaf weak-rssi {
      when 'boolean(../support) and boolean(../enabled)';
      type int16;
      units "dBm";
      description
        "Weak RSSI for antenna monitoring on the AP";
    }
    leaf detection-time {
      when 'boolean(../support) and boolean(../enabled)';
      type uint8;
      units "minutes";
      description
        "Detection time for antenna monitoring on the AP";
    }
  }

  grouping st-ap-stats-mon-cfg {
    description
      "Ap statistics configuration";
    leaf enable {
      type empty;
      description
        "AP stats collection and processing enabled";
    }
    leaf sample-intvl {
      when 'boolean(../enable)';
      type uint16;
      units "seconds";
      description
        "Sampling interval";
    }
    leaf stats-intvl {
      when 'boolean(../enable)';
      type uint16;
      units "seconds";
      description
        "Statistics interval";
    }
    leaf alarm-hold-time {
      when 'boolean(../enable) and boolean(../alarms-enable)';
      type uint16;
      units "seconds";
      description
        "Alarm hold time";
    }
    leaf trap-retx-time {
      when 'boolean(../enable) and boolean(../alarms-enable)';
      type uint16;
      units "seconds";
      description
        "Alarm trap retransmission time";
    }
    leaf alarms-enable {
      when 'boolean(../enable)';
      type empty;
      description
        "AP stats alarms enabled";
    }
    leaf cpu-threshold {
      when 'boolean(../enable) and boolean(../alarms-enable)';
      type uint16;
      units "percentage";
      description
        "CPU threshold";
    }
    leaf mem-threshold {
      when 'boolean(../enable) and boolean(../alarms-enable)';
      type uint16;
      units "percentage";
      description
        "Memory threshold";
    }
    leaf action-ap-reload {
      type boolean;
      description
        "AP reload action on high CPU or high memory usage";
    }
  }

  grouping st-ap-lsc-status {
    description
      "AP LSC information";
    leaf is-dtls-lsc-enabled {
      type boolean;
      description
        "LSC enable status for CAPWAP DTLS handshake";
    }
    leaf dtls-lsc-issuer-hash {
      when "((../is-dtls-lsc-enabled = 'true') or (../is-dtls-lsc-fallback = 'true'))";
      type string;
      description
        "Issuer certificate hash of LSC used for CAPWAP DTLS";
    }
    leaf is-dot1x-lsc-enabled {
      type boolean;
      description
        "LSC enable status for dot1x port authentication";
    }
    leaf dot1x-lsc-issuer-hash {
      when "(../is-dot1x-lsc-enabled = 'true')";
      type string;
      description
        "Issuer certificate hash of LSC used for dot1x port authentication";
    }
    leaf is-dtls-lsc-fallback {
      type boolean;
      description
        "AP fallback state to default certificate instead of LSC";
    }
    leaf dtls-lsc-cert-expiry-time {
      when "((../is-dtls-lsc-enabled = 'true') or (../is-dtls-lsc-fallback = 'true'))";
      type yang:date-and-time;
      description
        "Certificate expiry time of LSC used for CAPWAP DTLS";
    }
    leaf dot1x-lsc-cert-expiry-time {
      when "(../is-dot1x-lsc-enabled = 'true')";
      type yang:date-and-time;
      description
        "Certificate expiry time of LSC used for dot1x port authentication";
    }
  }

  grouping st-channel-list {
    description
      "Channel list";
    leaf-list channel {
      type uint8;
      ordered-by user;
      description
        "Channels";
    }
  }

  grouping st-zerowt-dfs-data {
    description
      "Zero wait DFS parameters";
    container reserve-channel {
      description
        "Reserved channel data";
      uses wireless-types:st-cac-channel-params;
    }
    container dfs-chan-incl-list {
      description
        "DFS inclusion channel list";
      uses wireless-access-point-oper:st-channel-list;
    }
    container dfs-chan-excl-list {
      description
        "DFS exclusion channel list";
      uses wireless-access-point-oper:st-channel-list;
    }
    leaf type {
      type wireless-enum-types:cac-domain-type;
      description
        "CAC domain";
    }
  }

  grouping wtp-meraki-info {
    description
      "AP Meraki information";
    leaf mac {
      type yang:mac-address;
      description
        "MAC address of the Meraki AP";
    }
    leaf serial-num {
      type string;
      description
        "Serial number of the Meraki AP";
    }
  }

  grouping wtp-meraki-conv-result {
    description
      "Meraki mode conversion result of an AP";
    leaf is-meraki-conv-atmptd {
      type boolean;
      description
        "Meraki conversion attempted or not";
    }
    leaf conv-result {
      when "(../is-meraki-conv-atmptd = 'true')";
      type wireless-access-point-oper:meraki-pre-conv-status;
      description
        "Conversion result";
    }
    leaf conv-timestamp {
      when "(../is-meraki-conv-atmptd = 'true')";
      type yang:date-and-time;
      description
        "Timestamp of last conversion attempt";
    }
  }

  grouping st-ap-file-status {
    description
      "AP image and file system operational data";
    leaf part-status {
      type wireless-access-point-oper:enum-ap-file-status;
      description
        "Status of downloaded image";
    }
    leaf file-sys-status {
      type wireless-access-point-oper:enum-ap-file-status;
      description
        "AP Filesystem status";
    }
    leaf iox-status {
      type wireless-access-point-oper:enum-ap-file-status;
      description
        "AP IOX status";
    }
    leaf img-type {
      type wireless-access-point-oper:enum-ap-image-type;
      description
        "Primary or Backup AP image";
    }
    leaf part-type {
      type wireless-access-point-oper:enum-ap-partition;
      description
        "Partition where AP image is stored";
    }
  }

  grouping st-ap-image-status {
    description
      "Status of image on AP";
    list file-system {
      description
        "Integrity of file system on AP";
      uses wireless-access-point-oper:st-ap-file-status;
    }
    leaf image-status-time {
      type yang:date-and-time;
      description
        "Timestamp of last AP image integrity message";
    }
    leaf loaded-alter-image {
      type empty;
      description
        "True if AP is loaded with alternative image";
    }
  }

  grouping cw-license-info {
    description
      "AP cisco wireless license information";
    leaf cw-lic-required {
      type boolean;
      description
        "AP use cisco wireless license";
    }
    leaf cw-lic-state {
      type wireless-access-point-oper:enm-cw-compliance-state;
      description
        "AP cisco wireless license state";
    }
    leaf cw-lic-ooc-reason {
      type wireless-access-point-oper:enm-cw-non-compliance-reason;
      description
        "AP cisco wireless license out of compliance reason";
    }
  }

  grouping capwap-wtp-data {
    description
      "Base AP operational data";
    leaf wtp-mac {
      type yang:mac-address;
      description
        "MAC address of AP radio interface";
    }
    leaf ip-addr {
      type string;
      status deprecated;
      description
        "IP of the AP.
         The leaf is deprecated. Use wtp-ip instead.";
    }
    leaf name {
      type string;
      description
        "AP Name";
    }
    container device-detail {
      description
        "AP device related information";
      uses wireless-access-point-oper:st-ap-device-info;
    }
    leaf ap-lag-enabled {
      type boolean;
      description
        "AP lag status, TRUE indicates the LAG support is enabled, FALSE indicates the LAG support is disabled.";
    }
    container ap-location {
      description
        "AP Location info";
      uses wireless-access-point-oper:st-ap-location;
    }
    container ap-services {
      description
        "AP services info";
      uses wireless-access-point-oper:st-ap-services;
    }
    container tag-info {
      description
        "AP tag info";
      uses wireless-access-point-oper:wtp-tags-data;
    }
    container tunnel {
      description
        "Captures the rogue parameters";
      uses ap-types:st-tunnel;
    }
    container external-module-data {
      description
        "AP external module data info";
      uses wireless-access-point-oper:st-external-module-data;
    }
    leaf ipv6-joined {
      type uint8;
      description
        "True if the AP has joined in IPv6 mode";
    }
    container ap-state {
      description
        "AP state";
      uses wireless-access-point-oper:st-ap-state;
    }
    container ap-mode-data {
      description
        "AP mode related data";
      uses wireless-access-point-oper:st-ap-mode-data;
    }
    container ap-time-info {
      description
        "AP time related information";
      uses wireless-access-point-oper:st-ap-times;
    }
    leaf country-code {
      type string;
      description
        "Country Code configured for the AP";
    }
    container ap-security-data {
      description
        "AP LSC data";
      uses wireless-access-point-oper:st-ap-security-oper-data;
    }
    leaf num-radio-slots {
      type uint8;
      description
        "Number of radio slots used for the AP";
    }
    leaf dart-is-connected {
      type boolean;
      status deprecated;
      description
        "Xor Dart connector status.";
    }
    leaf is-master {
      type boolean;
      description
        "True if the AP is configured as MASTER AP during efficient image download";
    }
    container sliding-window {
      description
        "CAPWAP multiwindow transport info";
      uses wireless-access-point-oper:st-sliding-window;
    }
    container ap-vlan {
      description
        "AP VLAN tagging details";
      uses wireless-access-point-oper:st-ap-vlan;
    }
    container hyperlocation-data {
      description
        "AP Hyperlocation details";
      uses wireless-access-point-oper:hyperlocation-ap-data;
    }
    leaf cdp-enable {
      type boolean;
      description
        "True if CDP is enabled or not on the AP";
    }
    leaf ap-stationing-type {
      type wireless-access-point-oper:enum-ap-stationing-type;
      description
        "Indoor or Outdoor AP";
    }
    container reboot-stats {
      description
        "AP reboot statistics";
      uses wireless-access-point-oper:reboot-statistics;
    }
    container proxy-info {
      description
        "Proxy configuration provisioned to AP";
      uses wireless-access-point-oper:st-proxy-info;
    }
    leaf grpc-enabled {
      type boolean;
      description
        "GRPC server status";
    }
    leaf image-size-eta {
      type yang:timeticks;
      description
        "The estimated amount of time left for the current image download to complete.";
    }
    leaf image-size-start-time {
      type yang:date-and-time;
      description
        "The time the current download started.";
    }
    leaf image-size-percentage {
      type uint32;
      description
        "The percentage of the current image download completed.";
    }
    leaf mdns-group-id {
      type uint32;
      description
        "MDNS group ID to which AP belongs";
    }
    leaf mdns-rule-name {
      type string;
      description
        "MDNS rule name to which AP belongs";
    }
    leaf ap-keepalive-state {
      type boolean;
      description
        "Unencrypted Data Keep Alive status";
    }
    leaf local-dhcp {
      type boolean;
      description
        "Local DHCP Server enabled status";
    }
    container ipv4-pool {
      description
        "DHCP ipv4 pool";
      uses wireless-access-point-oper:st-local-dhcp-pool;
    }
    leaf wlc-image-size-eta {
      type yang:timeticks;
      description
        "The estimated amount of time left for the current controller image download to complete.";
    }
    leaf wlc-image-size-start-time {
      type yang:date-and-time;
      description
        "The time the current controller image download started.";
    }
    leaf wlc-image-size-percentage {
      type uint32;
      description
        "The percentage of the current controller image download completed.";
    }
    container disconnect-detail {
      description
        "AP disconnect detail";
      uses wireless-access-point-oper:st-disconnect-detail;
    }
    container antenna-monitor {
      description
        "AP antenna monitoring current configuration";
      uses wireless-access-point-oper:st-antenna-monitoring;
    }
    leaf wtp-ip {
      type inet:ip-address;
      description
        "IP address of the AP";
    }
    container stats-monitor {
      description
        "AP statistics monitoring";
      uses wireless-access-point-oper:st-ap-stats-mon-cfg;
    }
    leaf lsc-status-pld-supported {
      type empty;
      description
        "AP platform support for sending LSC-status payload to WLC";
    }
    container ap-lsc-status {
      when 'boolean(../lsc-status-pld-supported)';
      description
        "AP LSC status information";
      uses wireless-access-point-oper:st-ap-lsc-status;
    }
    container radio-stats-monitor {
      description
        "AP radio statistics monitoring";
      uses ap-types:ap-radio-mon-cfg;
    }
    leaf oob-img-dwld-method {
      type wireless-enum-types:ewlc-ap-image-oob-method;
      description
        "Image download OOB method type";
    }
    container zero-wt-dfs {
      description
        "Zero wait DFS information of the AP";
      uses wireless-access-point-oper:st-zerowt-dfs-data;
    }
    leaf max-clients-supported {
      type uint16;
      description
        "Maximum number of clients an AP can support";
    }
    container meraki-info {
      when "(../meraki-capable = 'true')";
      description
        "AP Meraki information";
      uses wireless-access-point-oper:wtp-meraki-info;
    }
    container meraki-conv-data {
      when "(../meraki-capable = 'true')";
      description
        "AP Meraki conversion data";
      uses wireless-access-point-oper:wtp-meraki-conv-result;
    }
    leaf meraki-capable {
      type boolean;
      description
        "AP Meraki capability";
    }
    leaf mdns-group-method {
      type wireless-enum-types:enm-group-method;
      description
        "MDNS rule group method";
    }
    container gnss-info {
      description
        "AP GNSS information";
      uses wireless-access-point-oper:ap-gnss-info;
    }
    leaf dart-con-status {
      type wireless-types:enm-dart-con-status;
      description
        "Xor Dart connector status.";
    }
    leaf ap-afc-pre-notification {
      type boolean;
      description
        "AFC license availability on AP";
    }
    leaf-list radio-authority-ids {
      type string;
      ordered-by user;
      description
        "Radio-Authority IDs";
    }
    leaf kernel-coredump-count {
      type uint16;
      description
        "Kernel coredump count on AP";
    }
    leaf reg-domain {
      type string;
      description
        "AP regulatory domain";
    }
    leaf meraki-monitor-capable {
      type boolean;
      description
        "True if AP is Meraki monitoring capable";
    }
    leaf meraki-connect-status {
      type wireless-access-point-oper:ap-meraki-connect-status;
      description
        "AP Meraki connect status";
    }
    leaf err-detail {
      when "(../meraki-connect-status = 'am-status-reg-failed')";
      type string;
      description
        "AP Meraki connect status error";
    }
    container ap-image-status {
      description
        "AP image status";
      uses wireless-access-point-oper:st-ap-image-status;
    }
    leaf reg-domain-resolution {
      type wireless-access-point-oper:reg-domain-resoultion-method;
      description
        "AP regulatory domain resolution method";
    }
    container ap-license {
      description
        "AP cisco wireless license information";
      uses wireless-access-point-oper:cw-license-info;
    }
    list ap-port-auth-info {
      description
        "AP port authentication information";
      uses ap-types:st-ap-port-auth-info;
    }
    leaf ap-nextunnel-state {
      type boolean;
      description
        "AP nextunnel state information";
    }
    leaf ap-env-mode {
      type wireless-access-point-oper:enm-ap-env-mode;
      description
        "AP environment mode ";
    }
    leaf urwb-cfg-status {
      type wireless-enum-types:urwb-cfg-status;
      description
        "URWB Configuration status in the AP";
    }
    leaf static-name {
      type boolean;
      description
        "Indicates that the AP name is statically configured";
    }
    leaf-list macsec-status {
      type wireless-enum-types:enm-macsec-status;
      ordered-by user;
      description
        "Indicates the current MACsec status of the AP.";
    }
    leaf-list ciphersuite {
      type wireless-enum-types:enm-macsec-cipher-suite;
      ordered-by user;
      description
        "Specifies the MACsec ciphersuite used by the AP.";
    }
    leaf prox-res-method {
      type wireless-access-point-oper:proximity-resolution-method;
      description
        "Indicates the method used to determine its regulatory domain via proximity, such as NDP, CDP, LLDP, or none.";
    }
    leaf auto-macsec-enabled {
      type boolean;
      description
        "Indicates whether AP already has automatic MACsec enabled with its peer.";
    }
  }

  grouping meraki-stats-key {
    description
      "Meraki statistics key";
    leaf conv-timestamp {
      type yang:date-and-time;
      description
        "AP Meraki conversion timestamp";
    }
    leaf wtp-mac {
      type yang:mac-address;
      description
        "AP radio MAC address";
    }
  }

  grouping wtp-meraki-info-ext {
    description
      "AP Meraki extended information";
    leaf ap-name {
      type string;
      description
        "AP name";
    }
    leaf model {
      type string;
      description
        "AP model";
    }
    leaf wtp-serial-num {
      type string;
      description
        "AP serial number";
    }
  }

  grouping ap-ethernet-intf-id {
    description
      "AP Ethernet interface info";
    leaf wtp-mac {
      type yang:mac-address;
      description
        "AP Ethernet interface MAC Address";
    }
    leaf if-index {
      type uint16;
      description
        "AP Ethernet interface index";
    }
  }

  grouping ap-ethernet-intf-info {
    description
      "AP Ethernet interface statistics";
    leaf if-name {
      type string;
      description
        "Ethernet interface Name";
    }
    leaf rx-pkts {
      type uint32;
      description
        "Number of packets received from Mobile Station";
    }
    leaf tx-pkts {
      type uint32;
      description
        "Number of packets sent to Mobile Station";
    }
    leaf oper-status {
      type wireless-enum-types:oper-state;
      description
        "Operational state of the Ethernet interface on the AP";
    }
    leaf rx-ucast-pkts {
      type uint32;
      description
        "Total number of unicast packets
         received on the interface";
    }
    leaf rx-non-ucast-pkts {
      type uint32;
      description
        "Total number of non-unicast packets
         received on the interface";
    }
    leaf tx-ucast-pkts {
      type uint32;
      description
        "Total number of unicast packets
         transmitted from the interface";
    }
    leaf tx-non-ucast-pkts {
      type uint32;
      description
        "Total number of non-unicast packets transmitted from the interface";
    }
    leaf duplex {
      type uint32;
      description
        "Interface's duplex mode";
    }
    leaf link-speed {
      type uint32;
      units "Mbps";
      description
        "Speed of the interface in units of 1,000,000 bits per second";
    }
    leaf rx-total-bytes {
      type uint32;
      description
        "Total number of bytes in the error-free packets
         received on the interface";
    }
    leaf tx-total-bytes {
      type uint32;
      description
        "Total number of bytes in the error-free packets
         transmitted from the interface";
    }
    leaf input-crc {
      type uint32;
      description
        "Total number of packets received with CRC error on the interface";
    }
    leaf input-aborts {
      type uint32;
      description
        "Total number of packets aborted while receiving on the interface";
    }
    leaf input-errors {
      type uint32;
      description
        "Sum of all errors in the packets while receiving on the interface";
    }
    leaf input-frames {
      type uint32;
      description
        "Total number of packet received incorrectly having a CRC
         error and a non-integer number of octets on the interface.";
    }
    leaf input-overrun {
      type uint32;
      description
        "Number of times the receiver
         hardware was incapable of handing received data to a
         hardware buffer because the input rate exceeded the
         receiver's capability to handle the data.";
    }
    leaf input-drops {
      type uint32;
      description
        "Total number of packets dropped
         while receiving on the interface";
    }
    leaf input-resource {
      type uint32;
      description
        "Total number of resource errors in packets received on the interface.";
    }
    leaf unknown-protocol {
      type uint32;
      description
        "Total number of packet discarded on
         the interface due to unknown protocol";
    }
    leaf runts {
      type uint32;
      description
        "Number of packets that
         are discarded because they are smaller than the
         medium's minimum packet size";
    }
    leaf giants {
      type uint32;
      description
        "Number of packets that are discarded
         because they exceed the medium's maximum packet size.";
    }
    leaf throttle {
      type uint32;
      description
        "Total number of times the interface advised a sending NIC that it was
         overwhelmed by packets being sent and to slow the pace of delivery.";
    }
    leaf resets {
      type uint32;
      description
        "Number of times that an interface has been completely reset.";
    }
    leaf output-collision {
      type uint32;
      description
        "Total number of packets retransmitted due to an Ethernet collision.";
    }
    leaf output-no-buffer {
      type uint32;
      description
        "Total number of packets discarded because there was no buffer space.";
    }
    leaf output-resource {
      type uint32;
      description
        "Total number of resource errors in packets transmitted from the interface.";
    }
    leaf output-underrun {
      type uint32;
      description
        "Number of times the transmitter has been running
         faster than the router can handle.";
    }
    leaf output-errors {
      type uint32;
      description
        "Sum of all errors that prevented
         the final transmission of packets out of the interface.";
    }
    leaf output-total-drops {
      type uint32;
      description
        "Total number of packets dropped while transmitting
         from the interface";
    }
  }

  grouping ap-name-mac-map {
    description
      "Mapping between AP name and base radio MAC";
    leaf wtp-name {
      type string;
      description
        "AP Name";
    }
    leaf wtp-mac {
      type yang:mac-address;
      description
        "AP radio MAC address";
    }
    leaf eth-mac {
      type yang:mac-address;
      description
        "AP ethernet MAC address";
    }
  }

  grouping ethernet-mac-wtp-mac-map {
    description
      "Mapping between AP ethernet name and base radio MAC";
    leaf ethernet-mac {
      type yang:mac-address;
      description
        "The Ethernet MAC of AP";
    }
    leaf wtp-mac {
      type yang:mac-address;
      description
        "The Radio MAC of AP";
    }
  }

  grouping st-radius-counters {
    description
      "A collection of RADIUS related state objects";
    leaf retried-access-requests {
      type uint64;
      description
        "The count of access request messages that were retried";
    }
    leaf access-accepts {
      type uint64;
      description
        "The count of access accept messages sent by the RADIUS server";
    }
    leaf access-rejects {
      type uint64;
      description
        "The count of access reject messages sent by the RADIUS server";
    }
    leaf timeout-access-requests {
      type uint64;
      description
        "The number of times an access request message timed out without any response from the RADIUS server";
    }
  }

  grouping ewlc-cdp-cache-data-key {
    description
      "Compound key of the table with device id as one of the attributes";
    leaf mac-addr {
      type yang:mac-address;
      description
        "Radio MAC address of the AP";
    }
    leaf cdp-cache-device-id {
      type string;
      description
        "The Device-ID string as reported in the CDP message";
    }
  }

  grouping cdp-cache-data-index-key {
    description
      "Compound key of the table with device index as one of the attributes";
    leaf wtp-mac-addr {
      type yang:mac-address;
      description
        "Radio MAC address of the AP";
    }
    leaf device-index {
      type uint32;
      description
        "A unique value for each device from which CDP messages are being received";
    }
  }

  grouping cdp-cache-neighbour-ip-addr {
    description
      "List of IP address.";
    leaf-list ip-address-value {
      type inet:ip-address;
      max-elements 9;
      ordered-by user;
      description
        "IP address value";
    }
  }

  grouping cdp-cache-data-op {
    description
      "An entry of the CDP cache data table";
    leaf ap-name {
      type string;
      description
        "AP Name";
    }
    leaf last-updated-time {
      type yang:date-and-time;
      description
        "Last updated time";
    }
    leaf version {
      type uint8;
      description
        "Cisco Discovery Protocol version";
    }
    leaf cdp-cache-if-index {
      type int32;
      description
        "CDP cache interface index";
    }
    leaf cdp-cache-version {
      type string;
      description
        "CDP cache version";
    }
    leaf cdp-cache-device-port {
      type string;
      description
        "Device outgoing port";
    }
    leaf cdp-cache-local-port {
      type string;
      description
        "Device interface port";
    }
    leaf cdp-cache-platform {
      type string;
      description
        "CDP cache platform";
    }
    leaf cdp-capabilities-string {
      type string;
      description
        "CDP cache capabilities";
    }
    leaf cdp-cache-ap-address {
      type inet:ip-address;
      description
        "An indication of the type of address contained
         in the corresponding instance of
         clcCdpApCacheAddress for the AP";
    }
    leaf cdp-addr-count {
      type uint8;
      description
        "Neighbor IP count";
    }
    leaf cdp-cache-ip-address-value {
      type inet:ip-address;
      description
        "Entry address(es)";
    }
    container ip-address {
      description
        "All network-layer addresses(IPv4 and IPv6) of the device's
         SNMP-agent as reported in the most recent CDP message.";
      uses wireless-access-point-oper:cdp-cache-neighbour-ip-addr;
    }
    leaf cdp-cache-duplex {
      type wireless-enum-types:cdp-cache-duplex;
      description
        "CDP cache duplex type";
    }
    leaf cdp-cache-interface-speed {
      type uint32;
      units "Mbps";
      description
        "CDP cache interface speed";
    }
    leaf packet-expiration-time {
      type yang:date-and-time;
      description
        "Packet expire time";
    }
    leaf sec {
      type wireless-access-point-oper:cdp-device-security;
      description
        "Security features reported by the CDP neighbor device.";
    }
  }

  grouping lldp-neigh-data-key {
    description
      "LLDP neighbor data table key";
    leaf wtp-mac {
      type yang:mac-address;
      description
        "Radio MAC address of the AP";
    }
    leaf neigh-mac {
      type yang:mac-address;
      description
        "MAC address of the LLDP neighbor device";
    }
  }

  grouping lldp-neigh-data-op {
    description
      "An entry of the LLDP neighbor data table";
    leaf port-id {
      type string;
      description
        "Port name or ID of the LLDP neighbor sending LLDP PDUs";
    }
    leaf local-port {
      type string;
      description
        "AP interface sending/receiving LLDP PDUs";
    }
    leaf system-name {
      type string;
      description
        "LLDP neighbor name";
    }
    leaf port-description {
      type string;
      description
        "Port description of LLDP neighbor sending LLDP PDUs";
    }
    leaf capabilities {
      type wireless-access-point-oper:lldp-device-capability;
      description
        "LLDP device capabilities";
    }
    leaf mgmt-addr {
      type inet:ip-address;
      description
        "Management IPv4 address of LLDP neighbor";
    }
    leaf mgmt-ipv6-addr {
      type inet:ip-address;
      description
        "Management IPv6 address of LLDP neighbor";
    }
    leaf auto-macsec-enabled {
      type boolean;
      description
        "Indicates whether auto-MACsec is enabled on the LLDP neighbor device";
    }
  }

  grouping st-ap-mac-ssid-info {
    description
      "AP MAC and SSID informations";
    list ssid-clients-list-data {
      key "client-mac-address";
      description
        "List of Client MAC address which use this SSID";
      uses wireless-access-point-oper:st-ssid-clients-list-data;
    }
  }

  grouping st-ssid-clients-list-data {
    description
      "Clients MAC address";
    leaf client-mac-address {
      type yang:mac-address;
      description
        "Client MAC address";
    }
  }

  grouping ap-ppe-info {
    description
      "Power policy entry info";
    leaf seq-number {
      type uint32;
      description
        "Interface sequence number";
    }
    leaf ppe-result {
      type wireless-access-point-oper:ap-ppe-status;
      description
        "Power policy entry status";
    }
    choice intf-choice {
      description
        "Interface type";
      case ap-pp-intf-unset {
        leaf intf-unset {
          type empty;
          description
            "Interface is not configured";
        }
      }
      case ap-pp-intf-eth {
        container ethernet {
          description
            "Ethernet interface";
          uses wireless-types:ap-pp-intf-ethernet;
        }
      }
      case ap-pp-intf-radio {
        container radio {
          description
            "Radio interface";
          uses wireless-types:ap-pp-intf-radio;
        }
      }
      case ap-pp-intf-usb {
        container usb {
          description
            "USB interface";
          uses wireless-types:ap-pp-intf-usb;
        }
      }
    }
  }

  grouping ap-power-info {
    description
      "AP power policy info";
    leaf wtp-mac {
      type yang:mac-address;
      description
        "Radio MAC address of the AP";
    }
    leaf status {
      type wireless-access-point-oper:ap-power-status;
      description
        "Power policy status of AP";
    }
    list ppe-info {
      key "seq-number";
      description
        "Power policy entries info";
      uses wireless-access-point-oper:ap-ppe-info;
    }
  }

  grouping ap-radio-wlan-key {
    description
      "AP radio WLAN key";
    leaf wtp-mac {
      type yang:mac-address;
      description
        "AP MAC address";
    }
    leaf slot-id {
      type uint8;
      description
        "AP slot identifier";
    }
    leaf wlan-id {
      type uint32;
      description
        "AP WLAN identifier";
    }
  }

  grouping wtp-slot-wlan-stats {
    description
      "AP slot and WLAN stats";
    leaf bssid-mac {
      type yang:mac-address;
      description
        "AP BSSID MAC address";
    }
    leaf ssid {
      type string;
      description
        "AP SSID name";
    }
    leaf bytes-rx {
      type uint64;
      description
        "Total number of bytes received";
    }
    leaf bytes-tx {
      type uint64;
      description
        "Total number of bytes transfered";
    }
    leaf pkts-rx {
      type uint64;
      description
        "Total number of packets received";
    }
    leaf pkts-tx {
      type uint64;
      description
        "Total number of packets transfered";
    }
    leaf data-retries {
      type uint64;
      description
        "Total number of data retries";
    }
  }

  grouping ap-debug-bundle-key {
    description
      "Key for AP debug bundle";
    leaf wtp-mac {
      type yang:mac-address;
      description
        "Radio MAC address of the AP";
    }
    leaf event {
      type wireless-access-point-oper:ap-debug-bundle-event-type;
      description
        "Event type for the AP debug bundle";
    }
  }

  grouping ap-spectral-debug-bundle {
    description
      "AP spectral debug bundle";
    leaf ap-name {
      type string;
      description
        "Name of the AP";
    }
    leaf last-event {
      type wireless-access-point-oper:ap-spectral-capture-event;
      description
        "AP spectral-capture last-event";
    }
    leaf current-state {
      type wireless-access-point-oper:ap-spectral-capture-state;
      description
        "AP spectral-capture current-state";
    }
    leaf requested-captures {
      type uint16;
      description
        "Number of requested captures";
    }
    leaf received-captures {
      type uint16;
      description
        "Number of received captures";
    }
    leaf filename {
      type string;
      description
        "File-name for the capture file";
    }
    leaf last-timestamp {
      type yang:date-and-time;
      description
        "Last time when spectral-capture data was updated";
    }
  }

  grouping ap-client-debug-bundle {
    description
      "Client debug bundle";
    leaf wtp-mac {
      type yang:mac-address;
      description
        "AP radio MAC address";
    }
  }

  grouping ap-debug-bundle {
    description
      "AP debug bundle";
    choice debug-event-choice {
      description
        "Debug bundle event choice";
      case debug-bundle-client {
        container ap-client-bundle {
          description
            "AP client debug bundle";
          uses wireless-access-point-oper:ap-client-debug-bundle;
        }
      }
      case debug-bundle-spectral {
        container ap-spectral-bundle {
          description
            "AP spectral debug bundle";
          uses wireless-access-point-oper:ap-spectral-debug-bundle;
        }
      }
    }
  }

  grouping st-ap-lsc-key {
    description
      "AP LSC table key";
    leaf expiry-time {
      type yang:date-and-time;
      description
        "Certificate expiry time";
    }
    leaf wtp-mac {
      type yang:mac-address;
      description
        "AP MAC";
    }
    leaf cert-hash {
      type string;
      description
        "Issuer certificate SHA1 hash";
    }
  }

  grouping st-ap-lsc {
    description
      "AP LSC data";
    leaf lsc-usage {
      type wireless-access-point-oper:ap-lsc-usage;
      description
        "Certificate usage for different services";
    }
    leaf lsc-prov-workflow {
      type wireless-access-point-oper:ap-lsc-prov-workflow;
      description
        "Certificate provision workflow";
    }
    leaf last-renew-attempt {
      when "(../last-renew-failure-rc != 'renew-none')";
      type yang:date-and-time;
      description
        "Last certificate renewal attempt";
    }
    leaf last-renew-failure-rc {
      type wireless-access-point-oper:ap-lsc-renew-failure-rc;
      description
        "Last certificate renewal failure reason code";
    }
  }

  grouping st-ap-next-tunnel-cfg {
    description
      "AP Nextunnel configuration data";
    leaf wtp-mac {
      type yang:mac-address;
      description
        "AP radio MAC";
    }
    leaf config-server-url {
      type string;
      description
        "Config server URL";
    }
    leaf primary-url {
      type string;
      description
        "Primary Nextunnel URL";
    }
    leaf secondary-url {
      type string;
      description
        "Secondary Nextunnel URL";
    }
    leaf client-ipv6-addr {
      type inet:ipv6-address;
      description
        "AP Nextunnel client IPv6 address";
    }
    leaf server-ipv6-addr {
      type inet:ipv6-address;
      description
        "AP Nextunnel server IPv6 address";
    }
    leaf last-fetch {
      type yang:date-and-time;
      description
        "Timestamp when last config was fetched";
    }
    leaf next-fetch {
      type yang:date-and-time;
      description
        "Timestamp when next config will be fetched";
    }
    leaf fetch-state {
      type wireless-access-point-oper:enm-tunnel-cfg-fetch-state;
      description
        "Config fetch state";
    }
    leaf fetch-fail-reason {
      type string;
      description
        "Config fetch failure reason";
    }
  }

  grouping st-ap-nextunnel-state-data {
    description
      "AP Nextunnel state information";
    leaf wtp-mac {
      type yang:mac-address;
      description
        "AP radio MAC";
    }
    leaf primary-state {
      type wireless-access-point-oper:enm-tunnel-state;
      description
        "Primary Nextunnel state";
    }
    leaf secondary-state {
      type wireless-access-point-oper:enm-tunnel-state;
      description
        "Secondary Nextunnel state";
    }
    leaf primary-last-change {
      type yang:date-and-time;
      description
        "Timestamp when primary Nextunnel was last changed";
    }
    leaf secondary-last-change {
      type yang:date-and-time;
      description
        "Timestamp when secondary Nextunnel was last changed";
    }
    leaf client-last-restart {
      type yang:date-and-time;
      description
        "Timestamp when Nextunnel client was last restarted";
    }
  }

  grouping st-ap-nextunnel-if-data {
    description
      "AP Nextunnel interface state information";
    leaf wtp-mac {
      type yang:mac-address;
      description
        "AP radio MAC";
    }
    leaf status {
      type boolean;
      description
        "AP Nextunnel interface status";
    }
  }

  grouping st-mewlc-ap-oper-data {
    description
      "Embedded Wireless Controller operational data";
    leaf wtp-mac {
      type yang:mac-address;
      description
        "MAC Address of the AP Radio";
    }
    leaf primary-image-version {
      type string;
      description
        "Primary image software version";
    }
    leaf backup-image-version {
      type string;
      description
        "Backup image software version";
    }
  }

  grouping st-ap-capwap-pkt-info {
    description
      "AP CAPWAP packet counters";
    leaf wtp-mac {
      type yang:mac-address;
      description
        "AP radio interface MAC Address";
    }
    leaf cntrl-pkts {
      type uint64;
      description
        "Number of control packets received from AP";
    }
    leaf data-keep-alive-pkts {
      type uint64;
      description
        "Number of data Keep-alive packets received from AP";
    }
    leaf capwap-error-pkts {
      type uint64;
      description
        "Number of capwap error packets received from AP";
    }
    leaf rfid-pkts {
      type uint64;
      description
        "Number of RFID packets received from AP";
    }
    leaf dot1x-eap-pkts {
      type uint64;
      description
        "Number of dot1x EAP packets received from AP";
    }
    leaf dot1x-mgmt-pkts {
      type uint64;
      description
        "Number of dot1x management packets received from AP";
    }
    leaf dot1x-key-type-pkts {
      type uint64;
      description
        "Number of dot1x key type packets received from AP";
    }
    leaf arp-pkts {
      type uint64;
      description
        "Number of ARP packets received from AP";
    }
    leaf ip-pkts {
      type uint64;
      description
        "Number of IP packets received from AP";
    }
    leaf iapp-pkts {
      type uint64;
      description
        "Number of IAPP packets received from AP";
    }
    leaf dhcp-pkts {
      type uint64;
      description
        "Number of DHCP packets received from AP";
    }
    leaf rrm-pkts {
      type uint64;
      description
        "Number of RRM packets received from AP";
    }
    leaf ipv6-pkts {
      type uint64;
      description
        "Number of IPV6 packets received from AP";
    }
    leaf dot1x-ctrl-pkts {
      type uint64;
      description
        "Number of dot1x control packets received from AP";
    }
  }

  grouping st-capwap-discovery-pkt-info {
    description
      "AP discovery packet counters";
    leaf wtp-mac {
      type yang:mac-address;
      description
        "AP radio interface MAC Address";
    }
    leaf discovery-pkts {
      type uint64;
      description
        "Number of discovery packets received from AP";
    }
    leaf discovery-err-pkts {
      type uint64;
      description
        "Number of discovery error packets received from AP";
    }
    leaf disc-meraki-pkts {
      type uint64;
      description
        "Number of discovery Meraki packets received from AP";
    }
    leaf disc-meraki-l2-pkts {
      type uint64;
      description
        "Number of discovery Meraki L2 packets received from AP";
    }
  }

  grouping wmm-cac-stats {
    description
      "WMM TSPEC call statistics";
    leaf calls-in-progress {
      type uint16;
      description
        "Total number of voice calls in progress";
    }
    leaf roam-calls-in-progress {
      type uint16;
      description
        "Total number of roaming voice calls in progress";
    }
    leaf calls-accepted {
      type uint16;
      description
        "Total number of calls accepted since AP joined";
    }
    leaf roam-calls-accepted {
      type uint16;
      description
        "Total number of roam calls accepted since AP joined";
    }
    leaf calls-rejected {
      type uint16;
      description
        "Total number of calls rejected since AP joined";
    }
    leaf roam-calls-rejected {
      type uint16;
      description
        "Total number of roam calls rejected since AP joined";
    }
    leaf calls-rejected-insuff-bw {
      type uint16;
      description
        "Total number of calls rejected due to insufficient bandwidth";
    }
    leaf calls-rejected-qos {
      type uint16;
      description
        "Total number of calls rejected due to wlan QoS settings";
    }
    leaf calls-rejected-phy-rate {
      type uint16;
      description
        "Total number of calls rejected due to un-acceptable PHY rate";
    }
    leaf calls-rejected-invalid-tspec {
      type uint16;
      description
        "Total number of calls rejected due to invalid TSPEC parameters";
    }
    leaf exp-bw-reqs-received {
      type uint16;
      description
        "Total number of exp bw requests received since AP join";
    }
    leaf exp-bw-reqs-accepted {
      type uint16;
      description
        "Total number of exp bw request calls admitted as
         expbwreqs since AP joined";
    }
  }

  grouping sip-cac-stats {
    description
      "SIP CAC statistics";
    leaf sip-calls-in-progress {
      type uint16;
      description
        "Total number of calls in progress";
    }
    leaf sip-roam-calls-in-progress {
      type uint16;
      description
        "Total number of roam calls in progress";
    }
    leaf sip-calls-accepted {
      type uint16;
      description
        "Total number of calls accepted since AP join";
    }
    leaf sip-roam-calls-accepted {
      type uint16;
      description
        "Total number of roam calls accepted since AP join";
    }
    leaf sip-preferred-calls-received {
      type uint16;
      description
        "Total number of Preferred calls received";
    }
    leaf sip-preferred-calls-accepted {
      type uint16;
      description
        "Total number of Preferred calls accepted";
    }
    leaf sip-preferred-calls-ongoing {
      type uint16;
      description
        "Total number of ongoing preferred calls";
    }
    leaf sip-calls-rejected-insuf-bw {
      type uint16;
      description
        "Total number of calls rejected insufficient bandwidth";
    }
    leaf sip-roam-calls-rejected-insuf-bw {
      type uint16;
      description
        "Total number of roam calls rejected insufficient bandwidth";
    }
  }

  grouping qos-ap-radio-key {
    description
      "Composite key structure for AP Radio record in DB";
    leaf radio-slot-id {
      type uint8;
      description
        "Slot id for radio";
    }
    leaf ap-mac {
      type yang:mac-address;
      description
        "AP mac address";
    }
  }

  grouping aaa-qos-params {
    description
      "AAA QoS parameters sent to the AP";
    leaf aaa-avgdtus {
      type uint32;
      units "kbps";
      description
        "AAA override value for average data rate-upstream";
    }
    leaf aaa-avgrtdtus {
      type uint32;
      units "kbps";
      description
        "AAA override value for average real data rate-upstream";
    }
    leaf aaa-bstdtus {
      type uint32;
      units "kbps";
      description
        "AAA override value for burst data rate-upstream";
    }
    leaf aaa-bstrtdtus {
      type uint32;
      units "kbps";
      description
        "AAA override value for burst real time data rate-upstream";
    }
    leaf aaa-avgdtds {
      type uint32;
      units "kbps";
      description
        "AAA override value for average data rate-downstream";
    }
    leaf aaa-avgrtdtds {
      type uint32;
      units "kbps";
      description
        "AAA override value for average real data rate-downstream";
    }
    leaf aaa-bstdtds {
      type uint32;
      units "kbps";
      description
        "AAA override value for burst data rate-downstream";
    }
    leaf aaa-bstrtdtds {
      type uint32;
      units "kbps";
      description
        "AAA override value for burst real time data rate-downstream";
    }
  }

  grouping qos-client-data {
    description
      "QoS client data";
    leaf client-mac {
      type yang:mac-address;
      description
        "Client MAC address";
    }
    container aaa-qos-params {
      description
        "AAA QoS parameters";
      uses wireless-access-point-oper:aaa-qos-params;
    }
  }

  grouping qos-ap-radio-data {
    description
      "QoS AP Radio data in DB";
    leaf wmm-voice-bw-allocated {
      type uint32;
      units "percentage";
      description
        "Voice Bandwidth allocated for Calls";
    }
    leaf wmm-max-voice-bandwidth {
      type uint32;
      units "percentage";
      description
        "Max RF bandwidth for Calls";
    }
    leaf wmm-bw-in-use {
      type uint32;
      units "percentage";
      description
        "Bandwidth is used in Voice Call (% of config bandwidth)";
    }
    container wmm-cac-stats {
      description
        "CAC stats data for this Radio on AP";
      uses wireless-access-point-oper:wmm-cac-stats;
    }
    leaf lbcac-measure {
      type boolean;
      description
        "load-based CAC setting measure";
    }
    leaf wmm-voice-roam-bw-in-use {
      type uint32;
      units "percentage";
      description
        "Bandwidth is used in Voice roam Call (% of config bandwidth)";
    }
    leaf sip-preferred-calls-mtu-used {
      type uint32;
      units "percentage";
      description
        "Total bandwidth is used for SIP preferred Call (% of config bandwidth)";
    }
    leaf cumulative-call-count {
      type uint32;
      description
        "completed sip call count";
    }
    leaf cumulative-seconds-used {
      type uint32;
      units "seconds";
      description
        "call duration for completed sip calls";
    }
    container sip-cac-stats {
      description
        "SIP CAC statistics";
      uses wireless-access-point-oper:sip-cac-stats;
    }
    leaf total-active-calls {
      type uint16;
      description
        "Total active calls include both TSpec and SIP calls";
    }
    leaf total-rejected-calls {
      type uint16;
      description
        "Total Rejected calls include both TSpec and SIP calls";
    }
  }

  grouping qos-client-voice-statistics {
    description
      "QoS Client Voice Statistics";
    leaf total-num-of-tspec-rcvd {
      type uint32;
      description
        "Total Number of TSPEC requests received";
    }
    leaf new-tspec-from-assoc-req {
      type uint32;
      description
        "Number of New TSPEC received from Assoc Request";
    }
    leaf tspec-renewal-from-assoc-req {
      type uint32;
      description
        "Number of TSPEC renewal received from Assoc Request";
    }
    leaf new-tspec-as-add-ts {
      type uint32;
      description
        "Number of new Add TS requests received";
    }
    leaf tspec-renewal-from-add-ts {
      type uint32;
      description
        "Number of Add TS renewal requests received";
    }
    leaf tspec-process-failed-get-rec {
      type uint32;
      description
        "Number of DB failures while processing TSPEC";
    }
    leaf total-sip-invite-on-caller {
      type uint32;
      description
        "Total number of SIP Invite received on Caller";
    }
    leaf total-sip-invite-on-callee {
      type uint32;
      description
        "Total number of SIP Invite received on Callee";
    }
    leaf total-num-of-call-report {
      type uint32;
      description
        "Total number of call-report received";
    }
    leaf total-sip-failure-trap-send {
      type uint32;
      description
        "Total number of SIP failure trap send";
    }
    leaf num-of-calls-accepted {
      type uint32;
      description
        "Total Number of calls accepted";
    }
    leaf num-of-calls-rejected-insuf-bw {
      type uint32;
      description
        "Number of calls rejected due to Insufficient BW";
    }
    leaf num-of-calls-rejected-qos {
      type uint32;
      description
        "Number of calls rejected due to QoS policy";
    }
    leaf num-of-calls-rejected-phy-rate {
      type uint32;
      description
        "Number of calls rejected due to PHY rate";
    }
    leaf num-of-calls-rej-invalid-tspec {
      type uint32;
      description
        "Number of calls rejected due to Invalid TSPEC";
    }
    leaf num-of-roam-calls-accepted {
      type uint32;
      description
        "Total Number of roam calls accepted";
    }
    leaf num-of-roam-calls-rejected {
      type uint32;
      description
        "Total Number of roam calls rejected";
    }
    leaf num-of-active-sip-calls {
      type uint32;
      description
        "Total Number of active SIP calls";
    }
    leaf num-of-active-tspec-calls {
      type uint32;
      description
        "Total Number of active TSPEC calls";
    }
  }

  grouping qos-global-statistics {
    description
      "QoS Global Statistics";
    container qos-client-voice-stats {
      description
        "QoS Client Voice related Statistics";
      uses wireless-access-point-oper:qos-client-voice-statistics;
    }
  }

  grouping radio-band-sniff-params {
    description
      "Sniffer parameters for the radio band";
    leaf chan-width {
      type wireless-enum-types:chan-width;
      description
        "Channel width supported";
    }
    leaf band {
      type wireless-types:enm-ewlc-dot11-radio-band;
      description
        "Radio band";
    }
    leaf-list channels {
      type uint8;
      ordered-by user;
      description
        "channel list supported";
    }
  }

  grouping ewlc-sniff-radio-data {
    description
      "Sniffer operational parameters for the AP radio";
    leaf sniffer-capable {
      type empty;
      description
        "Sniffer capability for the AP radio";
    }
    leaf sniff-reason-code {
      type wireless-access-point-oper:radio-sniff-dis-rson-code;
      description
        "Sniffer disabled reason code";
    }
    list sniffer-band-params {
      description
        "Sniffer parameters per band supported by AP radio";
      uses wireless-access-point-oper:radio-band-sniff-params;
    }
  }

  grouping ewlc-dual-radio-mode-config-data {
    description
      "Dual radio configuration and capability for AP radio";
    leaf dual-radio-mode {
      type wireless-enum-types:enum-dual-radio-mode;
      description
        "Dual radio mode for AP radio";
    }
    leaf dual-radio-capable {
      type wireless-enum-types:enum-dual-radio-capable;
      description
        "AP radio is dual radio capable";
    }
    leaf dual-radio-mode-op {
      type wireless-enum-types:enum-radio-mode-op;
      description
        "Dual radio mode operation for AP radio";
    }
  }

  grouping ewlc-radio-station-cfg-data {
    description
      "Configurations related to wireless stations";
    leaf station-cfg-config-type {
      type wireless-types:w-config-type;
      description
        "Configurations type. Either Auto or customized";
    }
    leaf medium-occupancy-limit {
      type uint16;
      description
        "Maximum amount of time coordinator may control the
         usage of the wireless medium";
    }
    leaf cfp-period {
      type uint8;
      description
        "Contention free period";
    }
    leaf cfp-max-duration {
      type uint16;
      description
        "Contention free period max duration";
    }
    leaf bssid {
      type yang:mac-address;
      description
        "Bssid of the radio";
    }
    leaf beacon-period {
      type uint16;
      description
        "Beacon time period";
    }
    leaf country-string {
      type string;
      description
        "AP Country Code";
    }
  }

  grouping ewlc-radio-mac-oper-cfg-data {
    description
      "Radio mac operational config data";
    leaf mac-operation-config-type {
      type wireless-types:w-config-type;
      description
        "Radio mac operational config type";
    }
    leaf rts-threshold {
      type uint16;
      description
        "Request to send threshold";
    }
    leaf short-retry-limit {
      type uint8;
      description
        "Short retry limit";
    }
    leaf long-retry-limit {
      type uint8;
      description
        "Long retry limit";
    }
    leaf frag-threshold {
      type uint16;
      description
        "Fragmentation threshold";
    }
    leaf max-tx-life-time {
      type uint32;
      description
        "Transmit life time";
    }
    leaf max-rx-life-time {
      type uint32;
      description
        "Receive life time";
    }
  }

  grouping ewlc-phy-tx-power-cfg-data {
    description
      "Configured tx-power for AP radio";
    leaf phy-tx-power-config-type {
      type wireless-types:w-config-type;
      description
        "Type of Tx power configuration, Auto or Static";
    }
    leaf current-tx-power-level {
      type uint16;
      description
        "Tx Power level in the range from 1 to 8, 1 being the highest";
    }
  }

  grouping ewlc-phy-tx-power-level-cfg-data {
    description
      "Configured Tx power in dBm";
    leaf num-supp-power-levels {
      type uint8;
      description
        "Number of supported transmit power levels of the AP radio";
    }
    leaf tx-power-level-1 {
      type int16;
      units "dBm";
      description
        "TX power level value at index 1 for the AP radio. This is also the default power level. It is same as the maximum power level available on an AP interface.";
    }
    leaf tx-power-level-2 {
      type int16;
      units "dBm";
      description
        "TX power level value at index 2 for the AP radio. It is 1/2 of the maximum power level available on an AP interface.";
    }
    leaf tx-power-level-3 {
      type int16;
      units "dBm";
      description
        "TX power level value at index 3 for the AP radio. It is 1/4 of the maximum power level available on an AP interface.";
    }
    leaf tx-power-level-4 {
      type int16;
      units "dBm";
      description
        "TX power level value at index 4 for the AP radio. It is 1/8 of the maximum power level available on an AP interface.";
    }
    leaf tx-power-level-5 {
      type int16;
      units "dBm";
      description
        "TX power level value at index 5 for the AP radio. It is 1/16 of the maximum power level available on an AP interface.";
    }
    leaf tx-power-level-6 {
      type int16;
      units "dBm";
      description
        "TX power level value at index 6 for the AP radio. It is 1/32 of the maximum power level available on an AP interface.";
    }
    leaf tx-power-level-7 {
      type int16;
      units "dBm";
      description
        "TX power level value at index 7 for the AP radio. It is 1/64 of the maximum power level available on an AP interface.";
    }
    leaf tx-power-level-8 {
      type int16;
      units "dBm";
      description
        "TX power level value at index 8 for the AP radio. It is 1/128 of the maximum power level available on an AP interface.";
    }
    leaf curr-tx-power-in-dbm {
      type int16;
      units "dBm";
      description
        "Transmit Power for the AP radio in dBm";
    }
  }

  grouping ewlc-multi-domain-cap-data {
    description
      "Multi domain capability data";
    leaf first-chan-num {
      type uint16;
      description
        "First channel number in multi domain";
    }
    leaf num-channels {
      type uint16;
      description
        "Number of channels in multi domain";
    }
    leaf max-tx-power-level {
      type uint16;
      description
        "Maximum transmit power level supported";
    }
  }

  grouping ewlc-phy-ht-cfg-data {
    description
      "802.11n configuration";
    leaf ht-enable {
      type uint8;
      description
        "802.11n configuration for the AP radio. It has a value representing the bit flag of MCS rates enabled on the AP radio";
    }
    leaf phy-ht-cfg-config-type {
      type wireless-types:w-config-type;
      description
        "Type of Channel configuration, Auto or Static";
    }
    leaf curr-freq {
      when "((../../../radio-mode != 'radio-mode-monitor') and (../../../radio-mode != 'radio-mode-sniffer') and (../../../radio-mode != 'radio-mode-invalid'))";
      type uint16;
      description
        "Current operating frequency(Channel) on the AP radio";
    }
    leaf chan-width {
      type uint8;
      description
        "Channel width of the AP radio";
    }
    leaf ext-chan {
      type uint8;
      description
        "Current extended channel. Valid if the channel width is more than 20 Mhz";
    }
    leaf vht-enable {
      type boolean;
      description
        "802.11ac configuration for the AP radio.
         True  - 802.11ac is enabled.
         False - 802.11ac is disabled.";
    }
    leaf leg-tx-bf-enabled {
      type uint8;
      description
        "Legacy Tx beamforming enabled";
    }
    leaf rrm-channel-change-reason {
      type wireless-enum-types:rrm-channel-change-reason;
      description
        "Reason for Channel change by RRM";
    }
    leaf freq-string {
      when "((../../../radio-mode != 'radio-mode-monitor') and (../../../radio-mode != 'radio-mode-sniffer'))";
      type string;
      description
        "channel or a comma separated list of channels in case of higher bandwidth";
    }
  }

  grouping ewlc-phy-ht-cap-data {
    description
      "802.11n capabilities";
    leaf vht-capable {
      type boolean;
      description
        "True if AP radio is 802.11ac capable";
    }
    leaf ht-capable {
      type boolean;
      description
        "True if AP radio is 802.11n capable";
    }
  }

  grouping ewlc-phy-he-cap-data {
    description
      "802.11ax Capability data for AP radio";
    leaf he-enabled {
      type boolean;
      description
        "AP radio is 802.11ax enabled";
    }
    leaf he-capable {
      type boolean;
      description
        "AP radio is 802.11ax capable";
    }
    leaf he-single-user-beamformer {
      type uint8;
      description
        "Operation mode as Single User beamforming in HE mode";
    }
    leaf he-multi-user-beamformer {
      type uint8;
      description
        "Operation mode as Multi User beamforming in HE mode";
    }
    leaf he-stbc-mode {
      type uint8;
      description
        "True - STBC TX-RX mode enabled.
         False - STBC TX-RX mode disabled.";
    }
    leaf he-ampdu-tid-bitmap {
      type uint8;
      description
        "Number of traffic identifiers of QoS Data frames
         that HE Station can aggregate in a multi traffic
         identifier in A-MPDU";
    }
    leaf he-cap-tx-rx-mcs-nss {
      type uint16;
      description
        "Number of TX RX spatial streams supported for HE AP";
    }
  }

  grouping ewlc-phy-eht-cap-data {
    description
      "802.11be capability data for AP radio";
    leaf eht-enable {
      type boolean;
      description
        "AP radio is 802.11be enabled";
    }
    leaf eht-capable {
      type boolean;
      description
        "802.11be capability of AP radio";
    }
    leaf subf-capable {
      type boolean;
      description
        "Operation mode as single user beamforming in 802.11be mode";
    }
    leaf mubf-80mhz-cap {
      type boolean;
      description
        "Operation mode as multi user beamforming in 80 MHz 802.11be mode";
    }
    leaf mubf-160mhz-cap {
      type boolean;
      description
        "Operation mode as multi user beamforming in 160 MHz 802.11be mode";
    }
    leaf mubf-320mhz-cap {
      type boolean;
      description
        "Operation mode as multi user beamforming in 320 MHz 802.11be mode";
    }
  }

  grouping cfg-entity-phy-eht-cap {
    description
      "802.11be capability information";
    container data {
      description
        "802.11be capability information";
      uses wireless-access-point-oper:ewlc-phy-eht-cap-data;
    }
  }

  grouping ewlc-antenna-cfg-data {
    description
      "Information related to Antenna configuration";
    leaf diversity-selection {
      type wireless-enum-types:enm-antenna-selection;
      description
        "Diversity selection type, values connectorA, connectorB or enabled.
         Not applicable to 802.11a radio band";
    }
    leaf antenna-mode {
      type wireless-enum-types:enm-antenna-mode;
      description
        "Antenna Mode. For 802.11a this attribute will always be omni.
         Not applicable to 802.11b radio band";
    }
    leaf num-of-antennas {
      type uint8;
      description
        "Number of Antennas present on this AP radio";
    }
  }

  grouping chan-pwr-map {
    description
      "Channel information";
    leaf chan {
      type uint8;
      description
        "Channel number";
    }
  }

  grouping chan-pwr-map-list {
    description
      "Supported channel information for the AP radio";
    list chan-pwr {
      max-elements 64;
      description
        "Supported channels of the AP radio";
      uses wireless-access-point-oper:chan-pwr-map;
    }
  }

  grouping ewlc-chan-pwr-info-data {
    description
      "Antenna parameters for AP radio";
    leaf antenna-gain {
      type uint8;
      units "dBi";
      description
        "Antenna gain for the AP radio, in units of two";
    }
    leaf int-antenna-gain {
      type uint8;
      units "dBi";
      description
        "Internal Antenna gain for the AP radio, in units of two";
    }
    leaf ext-antenna-gain {
      type uint8;
      units "dBi";
      description
        "External Antenna gain for the AP radio, in units of two";
    }
    container chan-pwr-list {
      description
        "The list of supported channels for the AP radio";
      uses wireless-access-point-oper:chan-pwr-map-list;
    }
  }

  grouping cfg-entity-radio-station-cfg {
    description
      "Configurations related to wireless stations";
    container cfg-data {
      description
        "Configuration data";
      uses wireless-access-point-oper:ewlc-radio-station-cfg-data;
    }
  }

  grouping cfg-entity-radio-mac-oper-cfg {
    description
      "Radio mac operational config data";
    container cfg-data {
      description
        "Configuration data";
      uses wireless-access-point-oper:ewlc-radio-mac-oper-cfg-data;
    }
  }

  grouping cfg-entity-phy-tx-power-cfg {
    description
      "Tx-power configured on the radio";
    container cfg-data {
      description
        "Phy Tx Power Configuration";
      uses wireless-access-point-oper:ewlc-phy-tx-power-cfg-data;
    }
  }

  grouping cfg-entity-phy-tx-power-level-cfg {
    description
      "Configured tx power level on the AP radio";
    container cfg-data {
      description
        "Tx power level Configuration";
      uses wireless-access-point-oper:ewlc-phy-tx-power-level-cfg-data;
    }
  }

  grouping cfg-entity-multi-domain-cap {
    description
      "Multi domain capability data";
    container cfg-data {
      description
        "Configuration Data";
      uses wireless-access-point-oper:ewlc-multi-domain-cap-data;
    }
  }

  grouping cfg-entity-phy-ht-cfg {
    description
      "802.11n configuration of the AP radio";
    container cfg-data {
      description
        "802.11n Configuration";
      uses wireless-access-point-oper:ewlc-phy-ht-cfg-data;
    }
  }

  grouping cfg-entity-phy-he-cap {
    description
      "802.11ax Capability information";
    container data {
      description
        "802.11ax Capability information";
      uses wireless-access-point-oper:ewlc-phy-he-cap-data;
    }
  }

  grouping cfg-entity-phy-ht-cap {
    description
      "802.11n capabilities of the AP radio";
    container data {
      description
        "802.11n Capabilities";
      uses wireless-access-point-oper:ewlc-phy-ht-cap-data;
    }
  }

  grouping cfg-entity-antenna-cfg {
    description
      "Configuration related to Antenna";
    container cfg-data {
      description
        "Antenna Configuration";
      uses wireless-access-point-oper:ewlc-antenna-cfg-data;
    }
  }

  grouping entity-channel-power-info {
    description
      "Antenna gain information for AP radio";
    container data {
      description
        "Antenna gain values for AP radio";
      uses wireless-access-point-oper:ewlc-chan-pwr-info-data;
    }
  }

  grouping st-sia-params {
    description
      "Self Identifying Antenna Parameters for the AP radio band";
    leaf is-rptnc-present {
      type boolean;
      description
        "SIA RP-TNC is present for the AP radio.
         True  -  SIA RP-TNC is present.
         False -  SIA RP-TNC is not present.";
    }
    leaf is-dart-present {
      type boolean;
      description
        "SIA DART is present for the AP radio.
         True  -  SIA DART is present.
         False -  SIA DART is not present.";
    }
    leaf antenna-if-type {
      type wireless-enum-types:enm-antenna-if-type;
      description
        "Antenna type connected to the SIA capable AP";
    }
    leaf antenna-gain {
      type uint8;
      units "dBi";
      description
        "External antenna gain for the antenna connected to the SIA capable AP radio";
    }
    leaf marlin4-present {
      type boolean;
      description
        "Marlin 4 antenna connected to AP DART interface";
    }
    leaf dm-serv-type {
      type wireless-enum-types:enm-radio-service-type;
      description
        "Dual-mode radio serving type supported";
    }
  }

  grouping ewlc-radio-band-info {
    description
      "Information of the AP radio band";
    leaf band-id {
      type uint8;
      description
        "Band identifier of the radio interface";
    }
    leaf reg-domain-code {
      type uint16;
      description
        "AP radio regulatory domain code ";
    }
    leaf regulatory-domain {
      type string;
      description
        "Regulatory Domain code for Radio band";
    }
    container mac-oper-cfg {
      description
        "Radio mac operational config data";
      uses wireless-access-point-oper:cfg-entity-radio-mac-oper-cfg;
    }
    container phy-tx-pwr-cfg {
      description
        "Configured radio Tx-power in dBm";
      uses wireless-access-point-oper:cfg-entity-phy-tx-power-cfg;
    }
    container phy-tx-pwr-lvl-cfg {
      description
        "Tx-power level configured on the radio";
      uses wireless-access-point-oper:cfg-entity-phy-tx-power-level-cfg;
    }
    container antenna-cfg {
      description
        "Antenna configuration";
      uses wireless-access-point-oper:cfg-entity-antenna-cfg;
    }
    leaf dot11ac-channel-width-cap {
      type uint8;
      description
        "Channel width";
    }
    leaf secondary-80-channel {
      type uint16;
      description
        "Secondary 80 channel of 80+80 channel width";
    }
    container sia-params {
      description
        "Self Identifying Antenna parameters of the AP radio band";
      uses wireless-access-point-oper:st-sia-params;
    }
  }

  grouping st-sniffer-cfg {
    description
      "Configuration related sniffer mode";
    leaf sniffer-enabled {
      type boolean;
      description
        "Boolean value which indicates if the radio is in sniffer role";
    }
    leaf server-ip {
      type inet:ip-address;
      description
        "Configured IP address of the sniffer server";
    }
  }

  grouping st-bss-color-config {
    description
      "802.11ax BSS Color configuration and capability data for AP radio";
    leaf bss-color-capable {
      type boolean;
      description
        "AP radio is 802.11ax BSS Color capable";
    }
    leaf bss-color {
      type uint8 {
        range "0 .. 63";
      }
      description
        "Configured 802.11ax BSS Color, 0 meaning disabled";
    }
    leaf bss-color-config-type {
      type wireless-types:w-config-type;
      description
        "Type of 802.11ax BSS Color configuration";
    }
  }

  grouping ap-radio-stats-data {
    description
      "AP radio statistics information";
    leaf stuck-ts {
      type yang:date-and-time;
      description
        "First timestamp at which the radio being stuck is observed";
    }
    leaf last-ts {
      type yang:date-and-time;
      description
        "Last timestamp at which the radio being stuck was observed";
    }
    leaf num-radio-stuck-reset {
      type uint32;
      description
        "Number of radio resets done due to radio stuck";
    }
  }

  grouping st-ant-labels {
    description
      "Antenna labels";
    leaf-list label {
      type wireless-access-point-oper:enm-antenna-label;
      ordered-by user;
      description
        "List of antenna labels";
    }
  }

  grouping ewlc-radio-operation-ext-config {
    description
      "Radio operational attributes";
    leaf sp-static-chan {
      type uint16;
      description
        "User configured 6GHz standard power channel";
    }
    leaf sp-static-chan-width {
      type wireless-enum-types:chan-width;
      description
        "User configured 6GHz standard power channel width";
    }
    leaf sp-static-txpwr {
      type int16;
      description
        "User configured standard power TX power in dBm";
    }
  }

  grouping radio-operation-info {
    description
      "Radio operational information";
    container urwb {
      description
        "Ultra Reliable Wireless Backhaul (URWB) configuration on the radio";
      uses wireless-urwb-common-types:st-urwb-radio;
    }
    list urwb-chan-list {
      max-elements 64;
      description
        "List of channels configured for scanning by URWB radio";
      uses wireless-urwb-common-types:st-urwb-chan-list-entry;
    }
    container urwb-exec {
      description
        "URWB execution configuration. The configurations are applied per AP and not part of profile configuration";
      uses wireless-urwb-common-types:st-urwb-radio-exec;
    }
    container wat-cfg {
      description
        "Status of Wireless Active Testing (WAT) configuration";
      uses wireless-types:st-radio-wat-cfg;
    }
    leaf est-beacon-eirp {
      type decimal64 {
        fraction-digits 2;
      }
      units "dBm";
      description
        "Specifies the estimated effective isotropic radiated power (EIRP) of the radio in dBm";
    }
  }

  grouping st-pre-cac-stats {
    description
      "Zero wait DFS pre-CAC statistics";
    leaf request-sent {
      type uint32;
      description
        "Number of requests sent";
    }
    leaf response-received {
      type uint32;
      description
        "Number of responses received";
    }
    leaf failure {
      type uint32;
      description
        "Number of failures";
    }
    leaf request-timeout {
      type uint32;
      description
        "Number of request timeouts";
    }
  }

  grouping st-pre-cac-bypass-stats {
    description
      "Zero wait DFS pre-CAC bypass statistics";
    leaf width-160mhz-assignment {
      type uint32;
      description
        "Number of times channel width set to 160 MHz";
    }
    leaf width-upgraded {
      type uint32;
      description
        "Number of times channel width upgraded";
    }
    leaf channel-space-violation {
      type uint32;
      description
        "Number of times channel space 100 MHz violation";
    }
    leaf channel-misalignment {
      type uint32;
      description
        "Number of times channel misalignment";
    }
    leaf cac-in-progress {
      type uint32;
      description
        "Number of times channel CAC in progress";
    }
    leaf rsvd-channel-unavailable {
      type uint32;
      description
        "Number of times reserved channel unavailable on radar detection";
    }
    leaf rsvd-chnl-space-violation {
      type uint32;
      description
        "Number of times reserved channel violates channel spacing 100 MHz on radar detection";
    }
  }

  grouping st-zwdfs-stats {
    description
      "Zero wait DFS statistics";
    container pre-cac-stats {
      description
        "Zero wait DFS pre-CAC statistics";
      uses wireless-access-point-oper:st-pre-cac-stats;
    }
    container pre-cac-bypass-stats {
      description
        "Zero wait DFS pre-CAC bypass statistics";
      uses wireless-access-point-oper:st-pre-cac-bypass-stats;
    }
  }

  grouping ewlc-radio-operation-config {
    description
      "Radio operational configuration";
    leaf slot-id {
      when "../radio-type != 'radio-remote-lan'";
      type uint8;
      description
        "Radio slot identifier";
    }
    leaf radio-type {
      type wireless-enum-types:enm-radio-type;
      description
        "Type of the radio. Possible values are:
         radio-80211bg    - 802.11bg radio
         radio-80211a     - 802.11a radio
         radio-80211abgn  - Dual band radio
         radio-remote-lan - Remote LAN
         radio-80211-6ghz - 802.11 6 GHz radio";
    }
    leaf admin-state {
      when "../radio-type != 'radio-remote-lan'";
      type wireless-access-point-oper:enum-radio-admin-state;
      description
        "Admin state of the radio interface";
    }
    leaf oper-state {
      when "../radio-type != 'radio-remote-lan'";
      type wireless-access-point-oper:enum-radio-oper-state;
      description
        "Operational state of the radio interface. Even though the admin state is enabled there are various reasons for which the operational state of the radio can be down";
    }
    leaf radio-mode {
      when "../radio-type != 'radio-remote-lan'";
      type wireless-types:enm-ewlc-ap-radio-modes;
      description
        "Current radio mode. Possible values are:
         radio-mode-invalid            - Invalid mode
         radio-mode-local              - Local mode
         radio-mode-monitor            - Monitor mode
         radio-mode-flex-connect       - Remote mode
         radio-mode-rogue-detector     - Rogue detector
         radio-mode-sniffer            - Sniffer mode
         radio-mode-bridge             - Bridge mode
         radio-mode-se-connect         - Spectrum mode
         radio-mode-hybrid-flexconnect - Hybrid mode
         radio-mode-remote-bridge      - Remote Bridge
         radio-mode-sensor             - Sensor mode";
    }
    leaf radio-sub-mode {
      when "../radio-type != 'radio-remote-lan'";
      type wireless-types:radio-sub-mode;
      description
        "Radio mode selection process, possible values are:
         radio-sub-mode-none   - None
         radio-sub-mode-auto   - radio mode is selected automatically
         radio-sub-mode-manual - Manual, radio mode is selected manually";
    }
    leaf radio-subtype {
      when "../radio-type != 'radio-remote-lan'";
      type wireless-types:ap-radio-subtype;
      description
        "Radio sub type indicating the radios capabilities, possible values are:
         ap-radio-subtype-main     - Main
         ap-radio-subtype-rx-only  - Rx-only, radio can only receive
         ap-radio-subtype-slave-ac - Slave AC
         ap-radio-subtype-rem-lan  - Remote lan
         ap-radio-subtype-tx-rx    - Radio can both receive and transmit";
    }
    leaf radio-subband {
      when "(../radio-type = 'radio-80211a')";
      type wireless-enum-types:slot-radio-sub-band;
      description
        "Radio sub band, Valid only if the radio is in 5 GHz band";
    }
    leaf current-band-id {
      when "../radio-type != 'radio-remote-lan'";
      type uint8;
      description
        "Represents radio's current operating band identifier.
         Possible values are:
         0 - current operational band is 2.4GHz
         1 - current operational band is 5GHz";
    }
    leaf current-active-band {
      when "../radio-type != 'radio-remote-lan'";
      type wireless-types:enm-ewlc-dot11-radio-band;
      description
        "Radio's current operating band, Possible values are:
         dot11-2-dot-4-ghz-band - Current operational band is 2.4GHz
         dot11-5-ghz-band       - Current operational band is 5GHz";
    }
    leaf xor-radio-mode {
      when "../radio-type != 'radio-remote-lan'";
      type wireless-types:enum-xor-radio-mode;
      description
        "Dual band(XOR) radio mode possible values are:
         xor-radio-mode-local   - Client serving
         xor-radio-mode-monitor - Monitor mode
         xor-radio-mode-sensor  - sensor mode";
    }
    container station-cfg {
      when "../radio-type != 'radio-remote-lan'";
      description
        "Configurations related to wireless stations";
      uses wireless-access-point-oper:cfg-entity-radio-station-cfg;
    }
    container multi-domain-cap {
      when "../radio-type != 'radio-remote-lan'";
      description
        "Configuration related to multiple domain capabilities";
      uses wireless-access-point-oper:cfg-entity-multi-domain-cap;
    }
    container phy-ht-cfg {
      when "../radio-type != 'radio-remote-lan'";
      description
        "802.11n Configuration";
      uses wireless-access-point-oper:cfg-entity-phy-ht-cfg;
    }
    container phy-ht-cap {
      when "../radio-type != 'radio-remote-lan'";
      description
        "802.11n Capabilities";
      uses wireless-access-point-oper:cfg-entity-phy-ht-cap;
    }
    container xor-phy-ht-cap {
      when "../radio-type != 'radio-remote-lan'";
      description
        "802.11n capabilities for a dual-band radio";
      uses wireless-access-point-oper:cfg-entity-phy-ht-cap;
    }
    container phy-he-cap {
      when "../radio-type != 'radio-remote-lan'";
      description
        "802.11ax Capabilities for radio";
      uses wireless-access-point-oper:cfg-entity-phy-he-cap;
    }
    leaf radio-he-capable {
      when "../radio-type != 'radio-remote-lan'";
      type boolean;
      description
        "Dot11ax support";
    }
    container chan-pwr-info {
      when "../radio-type != 'radio-remote-lan'";
      description
        "Mapping between all channels and allowed power levels on that channel";
      uses wireless-access-point-oper:entity-channel-power-info;
    }
    container sniffer-cfg {
      when "../radio-type != 'radio-remote-lan'";
      description
        "Contains configuration related to sniffer mode or sniffer role";
      uses wireless-access-point-oper:st-sniffer-cfg;
    }
    leaf antenna-pid {
      when "../radio-type != 'radio-remote-lan'";
      type string;
      description
        "Radio Antenna PID";
    }
    list radio-band-info {
      when "../radio-type != 'radio-remote-lan'";
      key "band-id";
      description
        "Radio Band Information";
      uses wireless-access-point-oper:ewlc-radio-band-info;
    }
    list vap-oper-config {
      when "../radio-type != 'radio-remote-lan'";
      key "ap-vap-id";
      description
        "AP SSID Operational information";
      uses wireless-access-point-oper:ewlc-vap-operational-config;
    }
    leaf reg-domain-check-status {
      when "../radio-type != 'radio-remote-lan'";
      type wireless-enum-types:reg-domain-status;
      description
        "regulatory-domain-check-status-not-set - Regulatory Domain check has failed.
         regulatory-domain-check-status-set     - Regulatory Domain check has passed.";
    }
    leaf antenna-gain {
      when "../radio-type != 'radio-remote-lan'";
      type uint8;
      units "0.5 dBi";
      description
        "Antenna gain for the AP radio";
    }
    leaf slot-antenna-type {
      when "../radio-type != 'radio-remote-lan'";
      type wireless-types:radio-slot-antenna-type;
      description
        "Radio slot Antenna type";
    }
    leaf radio-enable-time {
      when "(../oper-state = 'radio-up' and ../radio-type != 'radio-remote-lan')";
      type yang:date-and-time;
      description
        "Radio slot up time for AP";
    }
    leaf dot11n-mcs-rates {
      when "../radio-type != 'radio-remote-lan'";
      type wireless-access-point-oper:flag-dot11n-mcs-rates;
      description
        "802.11n MCS Rates";
    }
    container dual-radio-mode-cfg {
      when "../radio-type != 'radio-remote-lan'";
      description
        "Dual radio mode operation and capability";
      uses wireless-access-point-oper:ewlc-dual-radio-mode-config-data;
    }
    leaf radio-fra-capable {
      when "../radio-type != 'radio-remote-lan'";
      type wireless-enum-types:enum-radio-fra-capable;
      description
        "FRA capability";
    }
    container bss-color-cfg {
      when "../radio-type != 'radio-remote-lan'";
      description
        "802.11ax BSS Color radio configuration and capability";
      uses wireless-access-point-oper:st-bss-color-config;
    }
    leaf highest-throughput-proto {
      when "../radio-type != 'radio-remote-lan'";
      type wireless-enum-types:enm-radio-dot11-proto-supported;
      description
        "Highest throughput supported by radio as per 802.11 protocols";
    }
    leaf cac-active {
      when "../radio-type != 'radio-remote-lan'";
      type boolean;
      description
        "This leaf indicates whether channel availability check is in progress";
    }
    leaf obss-pd-capable {
      when "../radio-type != 'radio-remote-lan'";
      type boolean;
      description
        "AP radio is 802.11ax OBSS PD capable";
    }
    leaf ndp-cap {
      when "../radio-type != 'radio-remote-lan'";
      type wireless-enum-types:ndp-capability;
      description
        "AP neighbor discovery mode capability";
    }
    leaf ndp-on-channel {
      when "../radio-type != 'radio-remote-lan'";
      type boolean;
      description
        "True if AP neighbor discovery mode is on channel,
         False if AP neighbor discovery mode is off channel";
    }
    leaf beam-selection {
      when "../radio-type != 'radio-remote-lan'";
      type wireless-enum-types:enm-beam-selection-mode;
      description
        "Beam selection mode for the AP slot";
    }
    leaf num-ant-enabled {
      when "../radio-type != 'radio-remote-lan'";
      type uint8;
      description
        "Number of antennas enabled for the AP slot";
    }
    leaf cur-ant-bitmap {
      when "../radio-type != 'radio-remote-lan'";
      type wireless-access-point-oper:flag-ant-bitmap;
      description
        "Current antenna bitmap for the AP slot";
    }
    leaf supp-ant-bitmap {
      when "../radio-type != 'radio-remote-lan'";
      type wireless-access-point-oper:flag-ant-bitmap;
      description
        "Supported antenna bitmap for the AP slot";
    }
    leaf supp-160mhz-ant-bitmap {
      when "../radio-type != 'radio-remote-lan'";
      type wireless-access-point-oper:flag-ant-bitmap;
      description
        "Supported antenna bitmap for 160 MHz bandwidth for the AP slot";
    }
    container alloc-ant-labels {
      when "../radio-type != 'radio-remote-lan'";
      description
        "Allocated antenna labels for the AP slot";
      uses wireless-access-point-oper:st-ant-labels;
    }
    leaf dot11ax-transmit-bssid {
      when "(../radio-type = 'radio-80211-6ghz')";
      type yang:mac-address;
      description
        "Transmitted BSSID of the radio";
    }
    leaf mesh-backhaul {
      when "../radio-type != 'radio-remote-lan'";
      type boolean;
      description
        "State of the Mesh backhaul on this radio";
    }
    leaf mesh-designated-downlink {
      when "../radio-type != 'radio-remote-lan'";
      type boolean;
      description
        "State of the designated downlink on this radio";
    }
    leaf max-client-allowed {
      when "../radio-type != 'radio-remote-lan'";
      type uint16;
      description
        "Maximum number of clients allowed per radio";
    }
    leaf obss-pd-srg-capable {
      when "../radio-type != 'radio-remote-lan'";
      type boolean;
      description
        "AP radio is 802.11ax OBSS PD SRG capable";
    }
    container xor-phy-he-cap {
      when "../radio-type != 'radio-remote-lan'";
      description
        "802.11ax Capabilities for XOR 5/6 ghz radio";
      uses wireless-access-point-oper:cfg-entity-phy-he-cap;
    }
    leaf coverage-overlap-factor {
      when "../radio-type != 'radio-remote-lan'";
      type uint8;
      units "percentage";
      description
        "- Added coverage overlap factor for Open RRM FRA features";
    }
    leaf ap-6ghz-pwr-mode {
      when "../radio-type != 'radio-remote-lan'";
      type wireless-types:ap-6ghz-pwr-mode;
      description
        "Current power mode for 6 GHz radio";
    }
    leaf ap-6ghz-pwr-mode-cap {
      when "../radio-type != 'radio-remote-lan'";
      type wireless-types:ap-6ghz-pwr-mode-cap;
      description
        "Power mode capabilities for 6 GHz radio";
    }
    leaf afc-license-needed {
      when "../radio-type != 'radio-remote-lan'";
      type boolean;
      description
        "AFC license needed or not";
    }
    leaf push-afc-resp-done {
      when "../radio-type != 'radio-remote-lan'";
      type boolean;
      description
        "AFC license pushed to AP's driver";
    }
    leaf afc-below-txmin {
      when "../radio-type != 'radio-remote-lan'";
      type boolean;
      description
        "Maximum Tx power allowed by AFC is below the configured minimum Tx power";
    }
    container sniff-data {
      when "../radio-type != 'radio-remote-lan'";
      description
        "Sniffer operation data";
      uses wireless-access-point-oper:ewlc-sniff-radio-data;
    }
    container phy-eht-cap {
      when "../radio-type != 'radio-remote-lan'";
      description
        "802.11be capabilities for radio";
      uses wireless-access-point-oper:cfg-entity-phy-eht-cap;
    }
    leaf puncture-bitmap {
      when "../radio-type != 'radio-remote-lan'";
      type uint32;
      description
        "802.11be preamble puncturing bitmap";
    }
    leaf radio-capabilities {
      when "../radio-type != 'radio-remote-lan'";
      type wireless-access-point-oper:flag-radio-capabilities;
      description
        "AP radio capabilities";
    }
    leaf sia-serial-num {
      when "../radio-type != 'radio-remote-lan'";
      type string;
      description
        "Serial number of the Self-Identifying Antenna (SIA) associated with this radio";
    }
  }

  grouping st-radio-reset-cause-key {
    description
      "Radio reset cause key";
    leaf ap-mac {
      type yang:mac-address;
      description
        "Mac address of AP";
    }
    leaf radio-id {
      type uint8;
      description
        "AP radio identifier";
    }
    leaf cause {
      type wireless-types:radio-reset-cause;
      description
        "Radio reset cause";
    }
    leaf detail-cause {
      type wireless-types:radio-reset-detail-cause;
      description
        "Detailed cause of radio reset";
    }
  }

  grouping st-radio-reset-cause-count {
    description
      "Structure of radio reset cause count";
    leaf count {
      type uint32;
      description
        "Radio reset cause count";
    }
  }

  grouping st-radio-failure-cause-key {
    description
      "Radio failure cause key";
    leaf ap-mac {
      type yang:mac-address;
      description
        "Mac address of AP";
    }
    leaf radio-id {
      type uint8;
      description
        "AP radio identifier";
    }
    leaf cause {
      type wireless-types:radio-reset-cause;
      description
        "Radio reset cause";
    }
    leaf detail-cause {
      type wireless-types:radio-failure-detail-cause;
      description
        "Detailed cause of radio failure";
    }
  }

  grouping st-radio-failure-cause-count {
    description
      "Structure of radio failure cause count";
    leaf count {
      type uint32;
      description
        "Radio failure cause count";
    }
  }

  grouping st-mac-slot-id-comp-key {
    description
      "MAC address and slot id key";
    leaf ap-mac {
      type yang:mac-address;
      description
        "Mac address of AP";
    }
    leaf slot-id {
      type uint8;
      description
        "Radio slot identifier";
    }
  }

  grouping ewlc-radio-op-stats-by-type {
    description
      "Radio statistics by type";
    leaf stats-type {
      type wireless-access-point-oper:enm-radio-op-stats-type;
      description
        "Radio operational stats type";
    }
    leaf tx-fragment-count {
      type uint32;
      description
        "Transmission fragment count";
    }
    leaf multicast-tx-frame-cnt {
      type uint32;
      description
        "Number of multicast 802.11 MSDUs successfully transmitted by the radio";
    }
    leaf failed-count {
      type uint32;
      description
        "Number of times radio failed to transmit 802.11 frame with maximum retries";
    }
    leaf retry-count {
      type uint32;
      description
        "Number of times an MSDU is successfully transmitted after one or more retries";
    }
    leaf multiple-retry-count {
      type uint32;
      description
        "Number of times an MSDU is successfully transmitted after more than one retry";
    }
    leaf frame-duplicate-count {
      type uint32;
      description
        "Number of times a frame was received and the Sequence Control field indicates it was a duplicate";
    }
    leaf rts-success-count {
      type uint32;
      description
        "Number of CTS frames received in response to an RTS frame";
    }
    leaf rts-failure-count {
      type uint32;
      description
        "Number of CTS frames not received in response to an RTS frame";
    }
    leaf ack-failure-count {
      type uint32;
      status deprecated;
      description
        "Number of ACK frames not received when expected";
    }
    leaf rx-fragment-count {
      type uint32;
      description
        "Number of unicast 802.11 MPDUs received by the radio";
    }
    leaf multicast-rx-frame-cnt {
      type uint32;
      description
        "Number of multicast 802.11 MSDUs successfully transmitted by the radio";
    }
    leaf fcs-error-count {
      type uint32;
      description
        "Number of 802.11 frames received with frame check sequence error";
    }
    leaf tx-frame-count {
      type uint32;
      description
        "Number of 802.11 MSDUs successfully transmitted by the radio";
    }
    leaf wep-undecryptable-count {
      type uint32;
      description
        "Number of frames discarded because they could not be decrypted by the radio";
    }
    leaf rx-error-frame-count {
      type uint32;
      description
        "Total number of frames received with error";
    }
    leaf mac-mic-err-frame-count {
      type uint32;
      description
        "Total Number of frames received with MIC error";
    }
    leaf mac-decry-err-frame-count {
      type uint32;
      description
        "Total Number of frames received with decrypt error";
    }
    leaf rx-mgmt-frame-count {
      type uint32;
      description
        "Number of 802.11 management frames received by the radio";
    }
    leaf rx-ctrl-frame-count {
      type uint32;
      description
        "Number of 802.11 control frames received by the radio";
    }
    leaf rx-data-frame-count {
      type uint32;
      description
        "Number of 802.11 data frames received by the radio";
    }
    leaf tx-mgmt-frame-count {
      type uint32;
      description
        "Number of 802.11 management packets transmitted from radio";
    }
    leaf tx-ctrl-frame-count {
      type uint32;
      description
        "Number of 802.11 control packets transmitted from radio";
    }
    leaf tx-data-frame-count {
      type uint32;
      description
        "Number of 802.11 data frames transmitted from radio";
    }
    leaf rx-data-pkt-count {
      type uint32;
      description
        "Number of 802.11 data packets received and processed by the radio";
    }
    leaf tx-data-pkt-count {
      type uint32;
      description
        "Number of 802.11 data packets transmitted from radio";
    }
    leaf noise-floor {
      type int8;
      units "dBm";
      description
        "Noise Floor, as measured by this radio";
    }
  }

  grouping st-rrm-iapp-messages {
    description
      "RRM related IAPP messages";
    leaf rrm-ap-meas-rpt {
      type uint32;
      description
        "IAPP AP RM measurement report";
    }
    leaf tlv-plain-txt-msg {
      type uint32;
      description
        "IAPP TLV plain text message";
    }
    leaf atf-cfs-client {
      type uint32;
      description
        "IAPP ATF CFS client ";
    }
    leaf atf-mesh-rpt {
      type uint32;
      description
        "IAPP ATF mesh report";
    }
    leaf rrm-aggr-neigh-rpt {
      type uint32;
      description
        "IAPP AP RM aggregate neighbor report";
    }
    leaf rrm-chd-client-stat-rpt {
      type uint32;
      description
        "IAPP AP RM CHD client stat report";
    }
    leaf rrm-chd-aggr-rpt {
      type uint32;
      description
        "IAPP AP RM CHD aggregate report";
    }
    leaf rrm-ap-chd-rpt {
      type uint32;
      description
        "IAPP AP RM CHD report";
    }
    leaf rrm-client-rssi-stats-rpt {
      type uint32;
      description
        "IAPP RRM client RSSI stats report";
    }
    leaf rf-neigh-rogue-ap-rpt {
      type uint32;
      description
        "IAPP RF rogue neighbor AP report";
    }
    leaf iapp-tlv-radar-dfs-stats {
      type uint32;
      description
        "IAPP radar DFS stats report";
    }
    leaf tlv-spectrum-aq-rpt-v2 {
      type uint32;
      description
        "IAPP spectrum air quality report";
    }
    leaf tlv-spectrum-idr-rpt-v2 {
      type uint32;
      description
        "IAPP spectrum interferer device report";
    }
  }

  grouping radio-statistics {
    description
      "Radio statistics information";
    leaf aid-user-list {
      type uint16;
      description
        "Number of users associated with this radio";
    }
    leaf tx-fragment-count {
      type uint32;
      description
        "Number of unicast 802.11 MPDU successfully transmitted by the radio";
    }
    leaf multicast-tx-frame-cnt {
      type uint32;
      description
        "Number of multicast 802.11 MSDU successfully transmitted by the radio";
    }
    leaf failed-count {
      type uint32;
      description
        "Number of times radio failed to transmit 802.11 frame with maximum retries";
    }
    leaf retry-count {
      type uint32;
      description
        "Number of times an MSDU is successfully transmitted after one or more retries";
    }
    leaf multiple-retry-count {
      type uint32;
      description
        "Number of times an MSDU is successfully transmitted after more than one retry";
    }
    leaf frame-duplicate-count {
      type uint32;
      description
        "Number of times a frame was received and the Sequence Control field indicates it was a duplicate";
    }
    leaf rts-success-count {
      type uint32;
      description
        "Number of CTS frames received in response to an RTS frame";
    }
    leaf rts-failure-count {
      type uint32;
      description
        "Number of CTS frames not received in response to an RTS frame";
    }
    leaf ack-failure-count {
      type uint32;
      status deprecated;
      description
        "Number of ACK frames not received when expected";
    }
    leaf rx-fragment-count {
      type uint32;
      description
        "Number of unicast 802.11 MPDU received by the radio";
    }
    leaf multicast-rx-frame-cnt {
      type uint32;
      description
        "Number of multicast 802.11 MSDU successfully transmitted by the radio";
    }
    leaf fcs-error-count {
      type uint32;
      description
        "Number of 802.11 frames received with frame check sequence error";
    }
    leaf tx-frame-count {
      type uint32;
      description
        "Number of 802.11 MSDU successfully transmitted by the radio";
    }
    leaf wep-undecryptable-count {
      type uint32;
      description
        "Number of frames discarded because they could not be decrypted by the radio";
    }
    leaf airtime-used-cum {
      type uint64;
      units "microseconds";
      description
        "Total AirTime used cumulatively (in micro seconds) for particular AP per slot";
    }
    leaf radio-uptime-cum {
      type uint32;
      units "seconds";
      description
        "Cumulative radio up time (in seconds) for particular AP per slot";
    }
    leaf cumulative-tx-bytes {
      type uint64;
      units "bytes";
      description
        "Total bytes transmitted cumulatively for particular AP per slot (in bytes)";
    }
    leaf cumulative-rx-bytes {
      type uint64;
      units "bytes";
      description
        "Total bytes received cumulatively for particular AP per slot (in bytes)";
    }
    leaf data-rate {
      type uint32;
      units "bytes per second";
      description
        "Radio data rate (in bytes/second) for particular AP per slot calculated for every 3 minute interval";
    }
    leaf rx-error-frame-count {
      type uint32;
      description
        "Total number of frames received with error";
    }
    leaf mac-mic-err-frame-count {
      type uint32;
      description
        "Total Number of frames received with MIC error";
    }
    leaf rx-mgmt-frame-count {
      type uint32;
      description
        "Number of 802.11 management frames received by the radio";
    }
    leaf rx-ctrl-frame-count {
      type uint32;
      description
        "Number of 802.11 control frames received by the radio";
    }
    leaf rx-data-frame-count {
      type uint32;
      description
        "Number of 802.11 data frames received by the radio";
    }
    leaf tx-mgmt-frame-count {
      type uint32;
      description
        "Number of 802.11 management packets transmitted from radio";
    }
    leaf tx-ctrl-frame-count {
      type uint32;
      description
        "Number of 802.11 control packets transmitted from radio";
    }
    leaf tx-data-frame-count {
      type uint32;
      description
        "Number of 802.11 data frames transmitted from radio";
    }
    leaf rx-data-pkt-count {
      type uint32;
      description
        "Number of 802.11 data packets received and processed by the radio";
    }
    leaf tx-data-pkt-count {
      type uint32;
      description
        "Number of 802.11 data packets transmitted from radio";
    }
    leaf noise-floor {
      type int8;
      description
        "Noise Floor, as measured by this radio";
    }
    container ap-radio-stats {
      description
        "AP radio statistics data";
      uses wireless-access-point-oper:ap-radio-stats-data;
    }
    leaf mac-decry-err-frame-count {
      type uint32;
      description
        "Total Number of frames received with MIC error";
    }
    list radio-stats-list {
      description
        "Radio statistics list";
      uses wireless-access-point-oper:ewlc-radio-op-stats-by-type;
    }
    container dot11k-req-stats-radio {
      description
        "Per radio stats for 11k requests";
      uses wireless-types:st-dot11k-req-stats;
    }
    container dot11v-req-stats-radio {
      description
        "Per radio stats for 11v requests";
      uses wireless-types:st-dot11v-req-stats;
    }
    container rrm-iapp-mesgs-stats {
      description
        "Per radio stats for all IAPP messages received from AP, related to RRM or radio";
      uses wireless-access-point-oper:st-rrm-iapp-messages;
    }
  }

  grouping ewlc-vap-operational-config {
    description
      "WLAN information";
    leaf wlan-id {
      type uint32;
      description
        "Configured Global WLAN ID";
    }
    leaf ap-vap-id {
      type uint16;
      description
        "Access Point WLAN ID";
    }
    leaf bssid-mac {
      type yang:mac-address;
      description
        "BSSID MAC address";
    }
    leaf wtp-mac {
      type yang:mac-address;
      description
        "AP Radio MAC Address";
    }
    leaf wlan-profile-name {
      type string;
      description
        "WLAN profile name";
    }
    leaf ssid {
      type string;
      description
        "WLAN SSID name";
    }
    leaf mlo-state {
      type wireless-types:enm-ewlc-dot11-mlo-state;
      description
        "Multi-link operation status of this VAP";
    }
    leaf mld-mac {
      when "(../mlo-state = 'ewlc-dot11-mlo-enabled')";
      type yang:mac-address;
      description
        "MLD MAC address";
    }
    leaf bp-enabled {
      type boolean;
      description
        "Beacon protection enable status";
    }
  }

  grouping st-ap-radio-neighbor-data {
    description
      "The MAC address, or BSSID, of a neighbor, and their corresponding RSSI.";
    leaf ssid {
      type string;
      description
        "Neighboring BSSID.";
    }
    leaf rssi {
      type int8;
      units "dBm";
      description
        "The RSSI of this neighboring BSSID.";
    }
    leaf channel {
      type uint16;
      description
        "The channel of this neighboring BSSID. This is to utilize 802.11ac nomenclature. For example, 40MHz channel 36-40 represented as channel 38. primary-channel used to identify the primary 20MHz channel of the neighbor.";
    }
    leaf primary-channel {
      type uint16;
      description
        "The primary 20MHz channel, if the neighbor is operating on bonded channel.";
    }
    leaf last-update-rcvd {
      type yang:date-and-time;
      description
        "Time when last update received for the bssid.";
    }
    leaf band {
      type wireless-types:enm-ewlc-dot11-radio-band;
      description
        "Radio band";
    }
  }

  grouping st-wncd-11k-11v-req-stats {
    description
      "Per WNCD stats for 11k and 11v requests";
    leaf inst-id {
      type uint8;
      description
        "WNCD instance ID as key";
    }
    leaf last-clear-sec-11k {
      type yang:date-and-time;
      description
        "Time when the 11k requests stats were last reset";
    }
    leaf last-clear-sec-11v {
      type yang:date-and-time;
      description
        "Time when the 11v requests stats were last reset";
    }
    container stats-dot11k-req {
      description
        "Per WNCD level 11k requests stats";
      uses wireless-types:st-dot11k-req-stats;
    }
    container stats-dot11v-req {
      description
        "Per WNCD level 11v requests stats";
      uses wireless-types:st-dot11v-req-stats;
    }
  }

  grouping st-wncd-iapp-mesgs-stats {
    description
      "Per WNCD stats for IAPP messages";
    leaf inst-id {
      type uint8;
      description
        "WNCD instance ID as key";
    }
    container stats-iapp-mesgs {
      description
        "Per WNCD level iapp messages related to radio and RRM stats";
      uses wireless-access-point-oper:st-rrm-iapp-messages;
    }
  }

  grouping capwap-wtp-predownload-data {
    description
      "AP predownload detailed information";
    leaf wtp-mac {
      type yang:mac-address;
      description
        "MAC Address of the AP Radio";
    }
    container predownload-version {
      description
        "Predownload image version to be used by the AP";
      uses wireless-types:version-info;
    }
    leaf max-retry {
      type uint8;
      description
        "Maximum number of predownload retries by the AP";
    }
    leaf delay-time {
      type uint16;
      description
        "Next retry time for predownload operation by the AP";
    }
    leaf pred-status {
      type wireless-types:enm-predownload-status;
      description
        "Predownload status of the AP";
    }
    leaf ewc-retries {
      type uint16;
      description
        "Number of image predownload retries by the AP";
    }
  }

  grouping st-predownload-stats {
    description
      "Statistics related to AP image predownload operation";
    leaf num-initiated {
      type uint32;
      description
        "Number of APs having initiated predownload";
    }
    leaf num-in-progress {
      type uint32;
      description
        "Number of APs with predownload in progress";
    }
    leaf num-complete {
      type uint32;
      description
        "Number of APs with predownload completed";
    }
    leaf num-unsupported {
      type uint32;
      description
        "Number of joined APs not supporting predownload";
    }
    leaf num-failed {
      type uint32;
      description
        "Number of APs having failed predownload";
    }
    leaf is-predownload-in-progress {
      type boolean;
      description
        "True if predownload is currently in progress";
    }
    leaf num-total {
      type uint32;
      description
        "Total Number of APs that support image predownload";
    }
  }

  grouping st-ewlc-wncd-stats {
    description
      "AP image download and predownload statistics for EWC on AP platforms";
    container predownload-stats {
      description
        "Statistics related to AP image predownload operation";
      uses wireless-access-point-oper:st-predownload-stats;
    }
    leaf downloads-in-progress {
      type uint32;
      description
        "Number of AP image downloads in progress";
    }
    leaf downloads-complete {
      type uint32;
      description
        "Number of completed AP image downloads";
    }
    container wlc-predownload-stats {
      description
        "Statistics related to controller image predownload operation";
      uses wireless-access-point-oper:st-predownload-stats;
    }
  }

  grouping ewlc-mewlc-predownload-rec {
    description
      "Embedded Wireless Controller predownload data";
    leaf pred-state {
      type wireless-types:enm-predwnld-status-ewc;
      description
        "Embedded Wireless Controller predownload state";
    }
    leaf me-capable-ap-count {
      type uint32;
      description
        "Total number of Embedded Wireless Controller capable APs";
    }
    leaf controller-predownload-version {
      type string;
      description
        "Embedded Wireless Controller predownload version";
    }
  }

  grouping st-wtp-img-dwnld-stats {
    description
      "AP image download statistics";
    leaf wtp-mac {
      type yang:mac-address;
      description
        "AP MAC";
    }
    leaf wtp-name {
      type string;
      description
        "AP name";
    }
    leaf download-start-time {
      type yang:timeticks;
      status deprecated;
      description
        "Image download start time";
    }
    leaf download-end-time {
      type yang:timeticks;
      status deprecated;
      description
        "Image download end time";
    }
    leaf img-dwnld-tries {
      type uint16;
      description
        "Image download tries";
    }
    leaf last-dwnld-time {
      type uint32;
      description
        "Last image download time";
    }
    leaf last-dwnld-image-size {
      type uint32;
      description
        "Image size of last downloaded image";
    }
    leaf last-dwnld-is-aborted {
      type boolean;
      description
        "Last image downloaded was aborted or not";
    }
    leaf last-dwnld-is-predwnld {
      type boolean;
      description
        "Last image was pre downloaded or not";
    }
    leaf oob-img-dwld-method {
      type wireless-enum-types:ewlc-ap-image-oob-method;
      description
        "Image download method";
    }
    leaf downl-start-time {
      type yang:date-and-time;
      description
        "Image download start time";
    }
    leaf downl-end-time {
      type yang:date-and-time;
      description
        "Image download end time";
    }
  }

  grouping ap-trace-site-client-info {
    description
      "Client trace list for particular site";
    leaf client-mac {
      type yang:mac-address;
      description
        "Client MAC address";
    }
  }

  grouping ap-trace-ap-client-info {
    description
      "Client trace list for particular AP";
    leaf client-mac {
      type yang:mac-address;
      description
        "Client MAC address";
    }
  }

  grouping ap-client-trace-site-tag-info {
    description
      "Client trace information for a particular site tag";
    leaf site-tag-name {
      type string;
      description
        "Site tag name for client tracing";
    }
    leaf all-clients-tracing {
      type boolean;
      description
        "Client tracing enabled for all clients";
    }
    list ap-trace-site-client-list {
      key "client-mac";
      description
        "Client tracing list for site";
      uses wireless-access-point-oper:ap-trace-site-client-info;
    }
  }

  grouping ap-client-trace-ap-info {
    description
      "Client trace information for a particular AP";
    leaf ap-name {
      type string;
      description
        "AP name for client tracing";
    }
    leaf all-clients-tracing {
      type boolean;
      description
        "Client tracing enabled for all clients";
    }
    list ap-trace-ap-client-list {
      key "client-mac";
      description
        "Client tracing list for AP";
      uses wireless-access-point-oper:ap-trace-ap-client-info;
    }
  }

  grouping st-data-distribution {
    description
      "AMPDU data distribution";
    leaf bytes-0-64 {
      type uint64;
      description
        "Number of AMPDU with size between 0 to 64 bytes";
    }
    leaf bytes-65-128 {
      type uint64;
      description
        "Number of AMPDU with size between 65 to 128 bytes";
    }
    leaf bytes-129-256 {
      type uint64;
      description
        "Number of AMPDU with size between 129 to 256 bytes";
    }
    leaf bytes-257-512 {
      type uint64;
      description
        "Number of AMPDU with size between 257 to 512 bytes";
    }
    leaf bytes-513-1024 {
      type uint64;
      description
        "Number of AMPDU with size between 513 to 1024 bytes";
    }
    leaf bytes-1025-2048 {
      type uint64;
      description
        "Number of AMPDU with size between 1025 to 2048 bytes";
    }
    leaf bytes-2049-4096 {
      type uint64;
      description
        "Number of AMPDU with size between 2049 to 4096 bytes";
    }
    leaf bytes-4097-8192 {
      type uint64;
      description
        "Number of AMPDU with size between 4097 to 8192 bytes";
    }
    leaf bytes-8193-16384 {
      type uint64;
      description
        "Number of AMPDU with size between 8193 to 16384 bytes";
    }
    leaf bytes-16385-32768 {
      type uint64;
      description
        "Number of AMPDU with size between 16385 to 32768 bytes";
    }
    leaf bytes-32769-65536 {
      type uint64;
      description
        "Number of AMPDU with size between 32769 to 65536 bytes";
    }
    leaf bytes-65537-131072 {
      type uint64;
      description
        "Number of AMPDU with size between 65537 to 131072 bytes";
    }
    leaf bytes-131073-262144 {
      type uint64;
      description
        "Number of AMPDU with size between 131073 to 262144 bytes";
    }
    leaf bytes-262145-524288 {
      type uint64;
      description
        "Number of AMPDU with size between 262145 to 524288 bytes";
    }
    leaf bytes-524289-1048576 {
      type uint64;
      description
        "Number of AMPDU with size between 524289 to 1048576 bytes";
    }
  }

  grouping st-mcs-traffic-stats {
    description
      "MCS index list";
    leaf mcs0 {
      type uint64;
      description
        "MCS index 0";
    }
    leaf mcs1 {
      type uint64;
      description
        "MCS index 1";
    }
    leaf mcs2 {
      type uint64;
      description
        "MCS index 2";
    }
    leaf mcs3 {
      type uint64;
      description
        "MCS index 3";
    }
    leaf mcs4 {
      type uint64;
      description
        "MCS index 4";
    }
    leaf mcs5 {
      type uint64;
      description
        "MCS index 5";
    }
    leaf mcs6 {
      type uint64;
      description
        "MCS index 6";
    }
    leaf mcs7 {
      type uint64;
      description
        "MCS index 7";
    }
    leaf mcs8 {
      type uint64;
      description
        "MCS index 8";
    }
    leaf mcs9 {
      type uint64;
      description
        "MCS index 9";
    }
  }

  grouping st-data-wmm {
    description
      "QoS Data frames, per WMM AC";
    leaf video {
      type uint64;
      description
        "Data frames marked as Access Category Video";
    }
    leaf voice {
      type uint64;
      description
        "Data frames marked as Access Category Voice";
    }
    leaf background {
      type uint64;
      description
        "Data frames marked as Access Category background";
    }
    leaf best-effort {
      type uint64;
      description
        "Data frames marked as Access Category best effort";
    }
  }

  grouping st-ssid-counter-by-type {
    description
      "SSID counter for different types";
    leaf stats-type {
      type wireless-access-point-oper:enm-ssid-counter-type;
      description
        "stats type";
    }
    leaf tx-mgmt {
      type uint64;
      description
        "Transmission management count";
    }
    leaf rx-mgmt {
      type uint64;
      description
        "Received management count";
    }
    leaf tx-bytes-data {
      type uint64;
      units "bytes";
      description
        "Total number of bytes of data frames transmitted";
    }
    container tx-data-dist {
      description
        "The distribution of Data frame sizes in bytes of successfully received AMPDU";
      uses wireless-access-point-oper:st-data-distribution;
    }
    container tx-data-wmm {
      description
        "Transmitted QoS Data frames, per WMM AC.";
      uses wireless-access-point-oper:st-data-wmm;
    }
    leaf tx-retries {
      type uint64;
      description
        "Number of frames transmitted with Retry bit set.";
    }
    leaf tx-retries-data {
      type uint64;
      description
        "Number of data frames transmitted with Retry bit set";
    }
    leaf tx-retries-subframes {
      type uint64;
      description
        "Aggregated MPDUs which had individual sub-frames that fail and require retransmission";
    }
    container tx-mcs {
      description
        "Transmitted Data frames, per MCS Index";
      uses wireless-access-point-oper:st-mcs-traffic-stats;
    }
    leaf rx-bytes-data {
      type uint64;
      units "bytes";
      description
        "Total number of bytes of data frames transmitted";
    }
    container rx-data-dist {
      description
        "The distribution of Data frame sizes in bytes of successfully received AMPDU";
      uses wireless-access-point-oper:st-data-distribution;
    }
    container rx-data-wmm {
      description
        "Received 802.11 Data frames, per WMM Access Category.";
      uses wireless-access-point-oper:st-data-wmm;
    }
    container rx-mcs {
      description
        "Received Data frames, per MCS Index";
      uses wireless-access-point-oper:st-mcs-traffic-stats;
    }
    leaf num-assoc-clients {
      type uint16;
      description
        "Number of clients associated to this BSS";
    }
    leaf noise-floor {
      type uint8;
      units "dBm";
      description
        "Noise floor information of the radio.";
    }
    leaf tx-ctrl {
      type uint64;
      description
        "Transmitted 802.11 Control frames";
    }
    leaf rx-ctrl {
      type uint64;
      description
        "Received 802.11 Control frames";
    }
    leaf bss-chan-util {
      type uint8;
      units "percentage";
      description
        "Total 802.11 channel utilization in this BSS. The total channel utilization should include all time periods the AP spent actively receiving and transmitting 802.11 frames in this BSS";
    }
  }

  grouping st-ssid-counter {
    description
      "List of ssid counters";
    leaf bssid-mac {
      type yang:mac-address;
      description
        "Mac address of the bssid";
    }
    leaf vap-id {
      type uint16;
      description
        "VAP id of the WLAN for the access point";
    }
    leaf tx-mgmt {
      type uint64;
      description
        "Number of 802.11 Management frames transmitted";
    }
    leaf rx-mgmt {
      type uint64;
      description
        "Number of 802.11 Management frames received";
    }
    leaf tx-bytes-data {
      type uint64;
      units "bytes";
      description
        "Total number of bytes of data frames transmitted";
    }
    container tx-data-dist {
      description
        "The distribution of Data frame sizes in bytes of successfully received AMPDU";
      uses wireless-access-point-oper:st-data-distribution;
    }
    container tx-data-wmm {
      description
        "Transmitted QoS Data frames, per WMM AC.";
      uses wireless-access-point-oper:st-data-wmm;
    }
    leaf tx-retries {
      type uint64;
      description
        "Number of frames transmitted with Retry bit set.";
    }
    leaf tx-retries-data {
      type uint64;
      description
        "Number of data frames transmitted with Retry bit set";
    }
    leaf tx-retries-subframes {
      type uint64;
      description
        "Aggregated MPDUs which had individual sub-frames that fail and require retransmission";
    }
    container tx-mcs {
      description
        "Transmitted Data frames, per MCS Index";
      uses wireless-access-point-oper:st-mcs-traffic-stats;
    }
    leaf rx-bytes-data {
      type uint64;
      units "bytes";
      description
        "Total number of bytes of data frames transmitted";
    }
    container rx-data-dist {
      description
        "The distribution of Data frame sizes in bytes of successfully received AMPDU";
      uses wireless-access-point-oper:st-data-distribution;
    }
    container rx-data-wmm {
      description
        "Received 802.11 Data frames, per WMM Access Category.";
      uses wireless-access-point-oper:st-data-wmm;
    }
    container rx-mcs {
      description
        "Received Data frames, per MCS Index";
      uses wireless-access-point-oper:st-mcs-traffic-stats;
    }
    leaf num-assoc-clients {
      type uint16;
      description
        "Number of clients associated to this BSS";
    }
    leaf noise-floor {
      type uint8;
      description
        "Noise floor information of the radio.";
    }
    leaf tx-ctrl {
      type uint64;
      description
        "Transmitted 802.11 Control frames";
    }
    leaf rx-ctrl {
      type uint64;
      description
        "Received 802.11 Control frames";
    }
    leaf bss-chan-util {
      type uint8;
      units "percentage";
      description
        "Total 802.11 channel utilization in this BSS. The total channel utilization should include all time periods the AP spent actively receiving and transmitting 802.11 frames in this BSS";
    }
    leaf radio-band {
      type wireless-types:enm-ewlc-dot11-radio-band;
      description
        "Represents radio's current operating band identifier";
    }
    list ssid-counter-list {
      description
        "SSID counter list";
      uses wireless-access-point-oper:st-ssid-counter-by-type;
    }
  }

  grouping ewlc-rlan-key {
    description
      "MAC address and port id key";
    leaf wtp-mac {
      type yang:mac-address;
      description
        "MAC Address of the AP Radio";
    }
    leaf rlan-port-id {
      type uint8;
      description
        "LAN port-id value of AP. The port-id can be between 1 to 4 for LAN ports or port-id 128 is for external module of AP";
    }
  }

  grouping ewlc-rlan-oper-config-entry {
    description
      "AP LAN port operational data";
    leaf rlan-oper-state {
      type boolean;
      description
        "Status of the LAN port";
    }
    leaf rlan-port-status {
      type boolean;
      description
        "Remote LAN status of the LAN port";
    }
    leaf rlan-vlan-valid {
      type boolean;
      description
        "LAN port valid or not";
    }
    leaf rlan-vlan-id {
      type uint32;
      description
        "VLAN id of the LAN port";
    }
    leaf rlan-poe-state {
      type wireless-access-point-oper:ewlc-rlan-poe-state;
      description
        "PoE state of the LAN port";
    }
    leaf power-level-id {
      type uint8;
      description
        "Power level of the LAN port";
    }
  }

  grouping st-iot-device-comp-key {
    description
      "IoT device identifier";
    leaf ap-mac {
      type yang:mac-address;
      description
        "AP radio MAC address";
    }
    leaf device-mac {
      type yang:phys-address;
      description
        "IoT device MAC address";
    }
  }

  grouping st-iot-device {
    description
      "IoT device operational data";
    leaf name {
      type string;
      description
        "IoT device name";
    }
    leaf type {
      type string;
      description
        "IoT device type. For example: light bulb.";
    }
    leaf protocol {
      type string;
      description
        "IoT device protocol. For example: ZigBee.";
    }
    leaf connection-state {
      type string;
      description
        "State of the connection between the AP and the IoT device";
    }
    leaf battery-level {
      type int8 {
        range "-1 .. 100";
      }
      description
        "IoT device battery level";
    }
  }

  grouping st-iot-firmware {
    description
      "IoT radio firmware data";
    leaf ap-mac {
      type yang:mac-address;
      description
        "AP radio MAC address";
    }
    leaf if-name {
      type string;
      description
        "AP IoT radio interface name";
    }
    leaf is-default {
      type empty;
      description
        "IoT radio firmware is default";
    }
    leaf version {
      type string;
      description
        "IoT radio firmware version";
    }
    leaf vendor-name {
      type string;
      description
        "IoT radio firmware vendor name";
    }
    leaf type {
      type wireless-enum-types:iot-radio-firmware-type;
      description
        "IoT radio firmware type";
    }
    leaf desc {
      type string;
      description
        "IoT radio firmware description";
    }
  }

  grouping st-iox-ap {
    description
      "AP IOx application hosting operational data";
    leaf ap-mac {
      type yang:mac-address;
      description
        "AP radio MAC address";
    }
    leaf apphost-state {
      type wireless-access-point-oper:enm-apphost-state;
      description
        "State of the application hosting reported by the AP";
    }
    leaf caf-token {
      type string;
      description
        "Cisco Application hosting Framework token";
    }
    leaf caf-port {
      type uint16;
      description
        "Cisco Application hosting Framework port number";
    }
  }

  grouping st-ap-radio-audit-info {
    description
      "Radio audit info are in sync with WLC configuration";
    leaf channel-sync {
      type empty;
      description
        "Radio channel status";
    }
    leaf bandwidth-sync {
      type empty;
      description
        "Radio bandwidth is in sync with WLC configuration";
    }
    leaf tx-power-sync {
      type empty;
      description
        "Radio transmit power is in sync with WLC configuration";
    }
    leaf admin-state-sync {
      type empty;
      description
        "Radio admin state is in sync with WLC configuration";
    }
    leaf oper-state-sync {
      type empty;
      description
        "Radio operational state is in sync with WLC configuration";
    }
    leaf radio-role-sync {
      type empty;
      description
        "Radio role is in sync with WLC configuration";
    }
    leaf radio-role-oper-sync {
      type empty;
      description
        "Radio role operation is in sync with WLC configuration";
    }
  }

  grouping st-ap-wlan-audit-info {
    description
      "WLAN audit info are in sync with WLC configuration";
    leaf vlan-id-sync {
      type empty;
      description
        "WLAN vlan is in sync with WLC configuration";
    }
    leaf state-sync {
      type empty;
      description
        "WLAN state is in sync with WLC configuration";
    }
    leaf ssid-sync {
      type empty;
      description
        "WLAN ssid is in sync with WLC configuration";
    }
    leaf auth-type-sync {
      type empty;
      description
        "WLAN authentication type is in sync with WLC configuration";
    }
    leaf other-flags-sync {
      type empty;
      description
        "WLAN other flags is in sync with WLC configuration";
    }
  }

  grouping st-ap-audit-summary-info {
    description
      "AP audit info are in sync with WLC configuration";
    leaf wtp-mac {
      type yang:mac-address;
      description
        "MAC address of AP radio interface";
    }
    leaf radio-audit-sync {
      type empty;
      description
        "AP radio audit stats are in sync with WLC configuration";
    }
    leaf wlan-audit-sync {
      type empty;
      description
        "AP Wlan audit stats are in sync with WLC configuration";
    }
    leaf ipv4-acl-sync {
      type empty;
      description
        "AP IPv4 ACL stat is in sync with WLC configuration";
    }
    leaf ipv6-acl-sync {
      type empty;
      description
        "AP IPV6 ACL stat is in sync with WLC configuration";
    }
    leaf last-report-time {
      type yang:date-and-time;
      description
        "Last audit report received time";
    }
  }

  grouping trustpoint-cert-info {
    description
      "Wireless management trustpoint data";
    leaf trustpoint-name {
      type string;
      description
        "Trustpoint name";
    }
    leaf is-cert-available {
      type boolean;
      description
        "Is certificate available";
    }
    leaf is-privkey-available {
      type boolean;
      description
        "Is private key available";
    }
    leaf cert-hash {
      type string;
      description
        "Certificate hash";
    }
    leaf cert-type {
      type wireless-types:enum-trustpoint-cert-type;
      description
        "Certificate type";
    }
    leaf fips-suitability {
      type wireless-access-point-oper:enum-trustpoint-fips-suitability;
      description
        "FIPS Suitability";
    }
  }

  grouping st-trustpoint-cert-info {
    description
      "Certificate information";
    container trustpoint {
      description
        "Trustpoint";
      uses wireless-access-point-oper:trustpoint-cert-info;
    }
  }

  grouping st-ap-sensor-status-key {
    description
      "Compound key of AP sensor status table";
    leaf ap-mac {
      type yang:mac-address;
      description
        "AP radio MAC address";
    }
    leaf sensor-type {
      type wireless-enum-types:enm-ap-sensor-type;
      description
        "AP sensor type";
    }
  }

  grouping st-ap-sensor-status {
    description
      "AP sensor operational status";
    leaf config-state {
      type wireless-enum-types:enm-ap-sensor-state;
      description
        "Sensor configuration state";
    }
    leaf admin-state {
      type wireless-enum-types:enm-ap-sensor-state;
      description
        "Sensor administrative state";
    }
    leaf oper-state {
      type wireless-enum-types:enm-ap-sensor-oper-state;
      description
        "Sensor operational state";
    }
    leaf interval {
      type uint32;
      units "seconds";
      description
        "Sensor data sampling interval";
    }
  }

  grouping st-ap-air-quality {
    description
      "AP air-quality sensor data";
    leaf ap-mac {
      type yang:mac-address;
      description
        "AP radio MAC address";
    }
    leaf last-update {
      type yang:date-and-time;
      description
        "Timestamp of last update received from AP";
    }
    leaf rmox-0 {
      type decimal64 {
        fraction-digits 2;
      }
      units "ohm";
      description
        "Raw metal-oxide resistance";
    }
    leaf rmox-1 {
      type decimal64 {
        fraction-digits 2;
      }
      units "ohm";
      description
        "Raw metal-oxide resistance";
    }
    leaf rmox-2 {
      type decimal64 {
        fraction-digits 2;
      }
      units "ohm";
      description
        "Raw metal-oxide resistance";
    }
    leaf rmox-3 {
      type decimal64 {
        fraction-digits 2;
      }
      units "ohm";
      description
        "Raw metal-oxide resistance";
    }
    leaf rmox-4 {
      type decimal64 {
        fraction-digits 2;
      }
      units "ohm";
      description
        "Raw metal-oxide resistance";
    }
    leaf rmox-5 {
      type decimal64 {
        fraction-digits 2;
      }
      units "ohm";
      description
        "Raw metal-oxide resistance";
    }
    leaf rmox-6 {
      type decimal64 {
        fraction-digits 2;
      }
      units "ohm";
      description
        "Raw metal-oxide resistance";
    }
    leaf rmox-7 {
      type decimal64 {
        fraction-digits 2;
      }
      units "ohm";
      description
        "Raw metal-oxide resistance";
    }
    leaf rmox-8 {
      type decimal64 {
        fraction-digits 2;
      }
      units "ohm";
      description
        "Raw metal-oxide resistance";
    }
    leaf rmox-9 {
      type decimal64 {
        fraction-digits 2;
      }
      units "ohm";
      description
        "Raw metal-oxide resistance";
    }
    leaf rmox-10 {
      type decimal64 {
        fraction-digits 2;
      }
      units "ohm";
      description
        "Raw metal-oxide resistance";
    }
    leaf rmox-11 {
      type decimal64 {
        fraction-digits 2;
      }
      units "ohm";
      description
        "Raw metal-oxide resistance";
    }
    leaf rmox-12 {
      type decimal64 {
        fraction-digits 2;
      }
      units "ohm";
      description
        "Raw metal-oxide resistance";
    }
    leaf iaq {
      type decimal64 {
        fraction-digits 2;
      }
      description
        "Indoor air quality index";
    }
    leaf etoh {
      type decimal64 {
        fraction-digits 2;
      }
      units "ppm";
      description
        "Ethanol alcohol concentration";
    }
    leaf tvoc {
      type decimal64 {
        fraction-digits 2;
      }
      units "mg/m^3";
      description
        "Total volatile organic components";
    }
  }

  grouping st-ap-temperature {
    description
      "AP temperature sensor data";
    leaf ap-mac {
      type yang:mac-address;
      description
        "AP radio MAC address";
    }
    leaf last-update {
      type yang:date-and-time;
      description
        "Timestamp of last update received from AP";
    }
    leaf temp {
      type decimal64 {
        fraction-digits 2;
      }
      units "celsius";
      description
        "Temperature value";
    }
    leaf humidity {
      type decimal64 {
        fraction-digits 2;
      }
      units "%";
      description
        "Relative humidity value";
    }
  }

  grouping st-ap-pressure {
    description
      "AP pressure sensor data";
    leaf ap-mac {
      type yang:mac-address;
      description
        "AP radio MAC address";
    }
    leaf last-update {
      type yang:date-and-time;
      description
        "Timestamp of last update received from AP";
    }
    leaf pressure {
      type decimal64 {
        fraction-digits 2;
      }
      units "Pa";
      description
        "Pressure value";
    }
  }

  grouping st-ap-accelerometer {
    description
      "AP accelerometer sensor data";
    leaf ap-mac {
      type yang:mac-address;
      description
        "AP radio MAC address";
    }
    leaf last-update {
      type yang:date-and-time;
      description
        "Timestamp of last update received from AP";
    }
    leaf x-coord {
      type int16 {
        range "-180 .. 180";
      }
      units "degree";
      description
        "AP sensor accelerometer X coordinate value";
    }
    leaf y-coord {
      type int16 {
        range "-180 .. 180";
      }
      units "degree";
      description
        "AP sensor accelerometer Y coordinate value";
    }
    leaf z-coord {
      type int16 {
        range "-180 .. 180";
      }
      units "degree";
      description
        "AP sensor accelerometer Z coordinate value";
    }
    leaf tilt-angle {
      type int16 {
        range "-180 .. 180";
      }
      units "degree";
      description
        "AP sensor accelerometer tilt angle in degrees";
    }
  }

  grouping ap-neighborhood-index-key {
    description
      "AP neighborhood identifier key information";
    leaf neighborhood-id {
      type uint32;
      description
        "Neighborhood group index of the AP";
    }
    leaf ap-mac {
      type yang:mac-address;
      description
        "Ethernet MAC address of the AP";
    }
  }

  grouping ap-neighborhood-rg-key {
    description
      "AP neighborhood resource group information";
    leaf resource-group-id {
      type int8;
      description
        "Resource group id";
    }
    leaf wtp-mac {
      type yang:mac-address;
      description
        "Radio MAC address of the AP";
    }
  }

  grouping ap-neighborhood-data {
    description
      "AP neighborhood data";
    leaf ap-name {
      type string;
      description
        "AP name";
    }
    leaf area-id {
      type int32;
      description
        "Neighborhood area index of the AP";
    }
  }

  grouping ap-neighborhood-global-details {
    description
      "AP neighborhood global stats per neighborhood area";
    leaf neighborhood-id {
      type uint32;
      description
        "Neighborhood group index of the AP";
    }
    leaf area-id {
      type uint32;
      description
        "Neighborhood area index of the AP";
    }
    leaf num-of-aps {
      type uint32;
      description
        "Number of APs in a neighborhood area";
    }
  }

  grouping ap-nh-resource-group {
    description
      "AP neighborhood resource group details";
    leaf resource-grp-id {
      type uint8;
      description
        "Resource group id";
    }
    leaf resource-grp-name {
      type string;
      description
        "Resource group name";
    }
  }

  grouping ap-nh-area-details {
    description
      "AP neighborhood area details";
    container rg {
      description
        "Resource group id and name";
      uses wireless-access-point-oper:ap-nh-resource-group;
    }
    container ap-nh {
      description
        "AP neighborhood area stats";
      uses wireless-access-point-oper:ap-neighborhood-global-details;
    }
  }

  grouping ap-neighborhood-global-data {
    description
      "AP neighborhood global data stats";
    leaf algorithm-running {
      type boolean;
      description
        "Status of neighborhood algorithm";
    }
    leaf algorithm-itr-count {
      type uint32;
      description
        "Total AP neighborhood algorithm iteration count";
    }
    leaf ideal-capacity-per-rg {
      type uint32;
      description
        "Ideal capacity of APs per resource group";
    }
    leaf num-of-neighborhood {
      type uint32;
      description
        "Total number of calculated neighborhood";
    }
    list nh {
      description
        "AP stats of each neighborhood area";
      uses wireless-access-point-oper:ap-nh-area-details;
    }
  }

  grouping ap-mac-iter-key {
    description
      "Staggered AP upgrade iteration information of upgraded AP ";
    leaf iter-number {
      type uint8;
      description
        "Iteration number";
    }
    leaf radio-mac {
      type yang:mac-address;
      description
        "Radio MAC address of AP";
    }
  }

  grouping mac-iter-key {
    description
      "Staggered AP upgrade iteration information of upgraded AP";
    leaf iter-number {
      type uint16;
      description
        "Iteration number";
    }
    leaf radio-mac {
      type yang:mac-address;
      description
        "Radio MAC address of AP";
    }
  }

  grouping stgrd-upg-upgd-ap {
    description
      "Staggered AP upgrade upgraded AP data";
    leaf ap-mac {
      type yang:mac-address;
      description
        "Radio MAC address of AP";
    }
    leaf eth-mac {
      type yang:mac-address;
      description
        "Ethernet MAC address of the AP";
    }
    leaf wtp-name {
      type string;
      description
        "Name of the AP";
    }
    leaf site-tag {
      type string;
      description
        "Site tag of the AP";
    }
    leaf status {
      type wireless-types:ap-upgd-status;
      description
        "Status of the AP";
    }
    leaf iteration {
      type uint8;
      description
        "Iteration number of the AP";
    }
    leaf serial-iter-num {
      type uint16;
      description
        "Iteration number of AP undergoing serial upgrade";
    }
  }

  grouping stgrd-upg-rmng-ap {
    description
      "Staggered AP upgrade remaining AP data";
    leaf ap-mac {
      type yang:mac-address;
      description
        "Radio MAC address of AP";
    }
    leaf eth-mac {
      type yang:mac-address;
      description
        "Ethernet MAC address of the AP";
    }
    leaf wtp-name {
      type string;
      description
        "Name of the AP";
    }
    leaf site-tag {
      type string;
      description
        "Site tag of the AP";
    }
  }

  grouping stgrd-upg-msng-ap {
    description
      "Staggered AP upgrade missing AP data";
    leaf ap-mac {
      type yang:mac-address;
      description
        "Radio MAC of missing AP";
    }
  }

  grouping stgrd-upg-failed-ap {
    description
      "Staggered AP upgrade failed AP data";
    leaf ap-mac {
      type yang:mac-address;
      description
        "Radio MAC address";
    }
    leaf wtp-name {
      type string;
      description
        "Name of the AP";
    }
    leaf iteration {
      type uint8;
      description
        "Staggered rollover iteration number";
    }
  }

  grouping stgrd-upg-iter {
    description
      "Staggered AP upgrade iteration data";
    leaf iter-num {
      type uint8;
      description
        "Iteration number";
    }
    leaf number-of-aps {
      type uint32;
      description
        "Number of APs in this iteration";
    }
    leaf number-of-aps-rebooted {
      type uint32;
      description
        "Number of APs reloaded";
    }
    leaf start-time {
      type yang:date-and-time;
      description
        "Start time of iteration";
    }
    leaf end-time {
      type yang:date-and-time;
      description
        "End time of the iteration";
    }
  }

  grouping stgrd-upg-site-list {
    description
      "List of sites included in staggered AP upgrade";
    leaf site-name {
      type string;
      description
        "Site tag";
    }
  }

  grouping stgrd-upg-last-list {
    description
      "Staggered AP upgrade last iteration data";
    leaf ap-mac {
      type yang:mac-address;
      description
        "Radio MAC address of AP";
    }
    leaf eth-mac {
      type yang:mac-address;
      description
        "Ethernet MAC address of the AP";
    }
    leaf wtp-name {
      type string;
      description
        "Name of the AP";
    }
    leaf reason {
      type wireless-types:ap-upg-support;
      description
        "Reason for AP to be included in last list";
    }
    leaf status {
      type wireless-types:ap-upgd-status;
      description
        "AP status";
    }
  }

  grouping stgrd-upg-report {
    description
      "Staggered AP upgrade report information";
    leaf cap-percentage {
      type uint8;
      description
        "Percentage of the APs that will be reloaded in each iteration";
    }
    leaf progress-percentage {
      type uint8;
      description
        "Algorithm completion in percentage in each iteration";
    }
    leaf total-aps {
      type uint16;
      description
        "Total number of APs";
    }
    leaf is-filter-based {
      type boolean;
      description
        "Site tag based filter";
    }
    leaf upgraded-ap-count {
      type uint32;
      description
        "Total number of APs upgraded";
    }
    leaf current-ap-count {
      type uint32;
      description
        "Total number of APs being upgraded in this iteration";
    }
    leaf remaining-ap-count {
      type uint32;
      description
        "Total number of APs remaining";
    }
    leaf report-name {
      type string;
      description
        "Name of the upgrade report";
    }
    leaf source-name {
      type string;
      description
        "Source controller name";
    }
    leaf destination-name {
      type string;
      description
        "Destination controller name";
    }
    leaf move-report-name {
      type string;
      description
        "Name of the old report, used to move APs from controller";
    }
    leaf cached-report-name {
      type string;
      description
        "Cached upgrade report name";
    }
    leaf type {
      type wireless-types:enum-ap-upgrade-type;
      description
        "Type of staggered AP upgrade";
    }
    leaf status {
      type wireless-types:ap-upg-status;
      description
        "Status of staggered AP upgrade";
    }
    leaf mode {
      type wireless-types:ap-upg-mode;
      description
        "Mode of staggered AP upgrade";
    }
    leaf fallback-type {
      type wireless-types:ap-upg-fallback-type;
      description
        "Staggered AP upgrade fallback type";
    }
    leaf upgrade-failure-type {
      type wireless-types:ap-upg-failure-reason;
      description
        "Staggered AP upgrade failure reason";
    }
    container from-version {
      description
        "Current version of the APs";
      uses wireless-types:version-info;
    }
    container to-version {
      description
        "New version of the APs";
      uses wireless-types:version-info;
    }
    leaf source-ip {
      type inet:ip-address;
      description
        "Source IP address of AP";
    }
    leaf destination-ip {
      type inet:ip-address;
      description
        "Destination IP address of the AP";
    }
    leaf start-time {
      type yang:date-and-time;
      description
        "Start time of the algorithm";
    }
    leaf predicted-end-time {
      type yang:date-and-time;
      description
        "Predicted end time of the algorithm";
    }
    leaf end-time {
      type yang:date-and-time;
      description
        "Actual end time of the algorithm";
    }
    list stgrd-upgd-ap {
      key "iter-number radio-mac";
      unique "ap-mac";
      status obsolete;
      description
        "List of APs that are upgraded to the new version";
      uses wireless-access-point-oper:stgrd-upg-upgd-ap {
        refine "ap-mac" {
          mandatory true;
        }
      }
      uses wireless-access-point-oper:ap-mac-iter-key;
    }
    list stgrd-upg-current-ap {
      key "ap-mac";
      description
        "List of APs that are handled in the current iteration";
      uses wireless-access-point-oper:stgrd-upg-upgd-ap;
    }
    list stgrd-upg-remaining-ap {
      key "ap-mac";
      description
        "List of APs that are remaining for upgrade";
      uses wireless-access-point-oper:stgrd-upg-rmng-ap;
    }
    list stgrd-upg-missing-ap {
      key "ap-mac";
      description
        "List of APs that went missing after reboot";
      uses wireless-access-point-oper:stgrd-upg-msng-ap;
    }
    list stgrd-upg-iteration {
      key "iter-num";
      description
        "List of iterations in this algorithm Run";
      uses wireless-access-point-oper:stgrd-upg-iter;
    }
    list ap-upgrade-site-list {
      key "site-name";
      description
        "List of sites considered for upgrade site list";
      uses wireless-access-point-oper:stgrd-upg-site-list;
    }
    list ap-staggered-upg-last-list {
      key "ap-mac";
      description
        "List of APs upgraded in last iteration";
      uses wireless-access-point-oper:stgrd-upg-last-list;
    }
    container events {
      description
        "list of events";
      uses event-history-types:event-history;
    }
    leaf oper-type {
      type wireless-types:ap-upg-operation-type;
      description
        "Staggered AP upgrade operation type";
    }
    leaf site-filter-uuid {
      type string;
      description
        "Site-filter table UUID associated with this upgrade report";
    }
    leaf client-steering {
      type boolean;
      description
        "Client steering enabled for this upgrade";
    }
    leaf iteration-expiry {
      type uint8;
      units "minutes";
      description
        "Maximum time allowed per iteration for APs to join back";
    }
    leaf accounting-percent {
      type uint8;
      units "percentage";
      description
        "Minimum percent of APs that should join before next iteration is scheduled";
    }
    leaf accounting-action {
      type wireless-types:enum-ap-upgrade-accounting-action;
      description
        "Action to be taken if less than specified percent of APs have joined back";
    }
    leaf secondary-wlc-set {
      type boolean;
      description
        "Secondary controller configuration available for N+1 upgrades";
    }
    leaf secondary-wlc-name {
      type string;
      description
        "Secondary controller hostname";
    }
    leaf secondary-wlc-ip {
      type inet:ip-address;
      description
        "Secondary controller IP address";
    }
    leaf tertiary-wlc-set {
      type boolean;
      description
        "Tertiary controller configuration available for N+1 upgrades";
    }
    leaf tertiary-wlc-name {
      type string;
      description
        "Tertiary controller hostname";
    }
    leaf tertiary-wlc-ip {
      type inet:ip-address;
      description
        "Tertiary controller IP address";
    }
    leaf client-deauth {
      type boolean;
      description
        "De-authenticate clients connected to the AP before the AP goes for an upgrade";
    }
    leaf tx-power-reduction {
      type boolean;
      description
        "Reduce radio transmission power of the AP when it is selected for upgrade";
    }
    leaf feature-type {
      type wireless-types:enum-ap-upgrade-feature-type;
      description
        "Type of the feature using staggered rollover AP upgrade";
    }
    list stgrd-upg-failed-ap {
      key "ap-mac";
      description
        "List of APs failed to upgrade";
      uses wireless-access-point-oper:stgrd-upg-failed-ap;
    }
    leaf failed-ap-count {
      type uint32;
      description
        "Total number of APs failed to rollover";
    }
    list comp-ap {
      key "iter-number radio-mac";
      unique "ap-mac";
      description
        "List of APs with successfully completed upgrades. This is the new list for upgraded APs, with support for serial AP upgrades.";
      uses wireless-access-point-oper:stgrd-upg-upgd-ap {
        refine "ap-mac" {
          mandatory true;
        }
      }
      uses wireless-access-point-oper:mac-iter-key;
    }
  }

  grouping st-country-oper {
    description
      "Regulatory domain country details";
    leaf country-code {
      type string;
      description
        "Country code string";
    }
    leaf country-string {
      type string;
      description
        "Actual country name string";
    }
    leaf reg-domain-str-80211bg {
      type string;
      description
        "802.11bg regulatory domain string, ^ indicates ROW domain";
    }
    leaf reg-domain-str-80211a {
      type string;
      description
        "802.11a regulatory domain string, ^ indicates ROW domain";
    }
    leaf country-supported {
      type boolean;
      description
        "True if country is supported for the AP.";
    }
    leaf channels-string-11bg {
      type string;
      description
        "802.11bg supported channels string";
    }
    leaf channels-string-11a {
      type string;
      description
        "802.11a supported channels string";
    }
    leaf channels-11bg {
      type string;
      description
        "802.11bg supported channels";
    }
    leaf channels-11a {
      type string;
      description
        "802.11a supported channels";
    }
    leaf dca-channels-11bg {
      type string;
      description
        "802.11bg supported  DCA channels";
    }
    leaf dca-channels-11a {
      type string;
      description
        "802.11a supported DCA channels";
    }
    leaf radar-channels-11a {
      type string;
      description
        "802.11a supported RADAR channels";
    }
    leaf reg-dom-6ghz {
      type string;
      description
        "6Ghz regulatory domain string, ^ indicates ROW domain";
    }
    leaf chan-info-6ghz {
      type string;
      description
        "6Ghz supported channels string";
    }
  }

  grouping st-reg-domain-code {
    description
      "Regulatory domain supported country details";
    leaf-list reg-domain-code {
      type string;
      max-elements 2;
      ordered-by user;
      description
        "802.11 regulatory domain, ^ indicates ROW domain";
    }
  }

  grouping st-supp-country-oper {
    description
      "Supported country regulatory domain details";
    leaf country-code {
      type string;
      description
        "Country code";
    }
    leaf country-string {
      type string;
      description
        "Country name";
    }
    leaf country-code-iso {
      type string;
      description
        "Country ISO name";
    }
    container reg-dom-24ghz {
      description
        "802.11bg regulatory domain, where ^ indicates ROW domain.
         First element indicates indoor regulatory domain and
         second indicates outdoor regulatory domain";
      uses wireless-access-point-oper:st-reg-domain-code;
    }
    container reg-dom-5ghz {
      description
        "802.11a regulatory domain, ^ indicates ROW domain
         First element indicates indoor regulatory domain and
         second indicates outdoor regulatory domain";
      uses wireless-access-point-oper:st-reg-domain-code;
    }
    container reg-dom-6ghz {
      description
        "6GHz regulatory domain, ^ indicates ROW domain
         First element indicates indoor regulatory domain and
         second indicates outdoor regulatory domain";
      uses wireless-access-point-oper:st-reg-domain-code;
    }
    container chan-list-24ghz {
      description
        "802.11bg supported channels";
      uses wireless-rrm-types:st-rrm-channels-list;
    }
    container chan-list-5ghz {
      description
        "802.11a supported channels";
      uses wireless-rrm-types:st-rrm-channels-list;
    }
    container chan-list-6ghz {
      description
        "6GHz supported channels";
      uses wireless-rrm-types:st-rrm-channels-list;
    }
    container chan-list-dca-24ghz {
      description
        "802.11bg supported DCA channels";
      uses wireless-rrm-types:st-rrm-channels-list;
    }
    container chan-list-dca-5ghz {
      description
        "802.11a supported DCA channels";
      uses wireless-rrm-types:st-rrm-channels-list;
    }
    container chan-list-dca-6ghz {
      description
        "6GHz supported DCA channels";
      uses wireless-rrm-types:st-rrm-channels-list;
    }
    container chan-list-psc-6ghz {
      description
        "6GHz PSC channels";
      uses wireless-rrm-types:st-rrm-channels-list;
    }
  }

  grouping site-img-mapping {
    description
      "AP upgrade site to image mapping";
    leaf image-name {
      type string;
      description
        "Image name";
    }
    leaf site-name {
      type string;
      description
        "Site tag name";
    }
  }

  grouping site-img-mapping-status {
    description
      "AP upgrade install operation status";
    leaf committed {
      type wireless-access-point-oper:ap-img-site-status;
      description
        "Install operation is commit";
    }
    leaf activated {
      type wireless-access-point-oper:ap-img-site-status;
      description
        "Install operation is activate";
    }
    leaf prepared {
      type wireless-access-point-oper:ap-img-site-status;
      description
        "Install operation is predownload";
    }
    leaf operation-type {
      type wireless-types:enum-ap-upgrade-type;
      description
        "Operation type";
    }
    leaf nplusone-oper-status {
      type wireless-access-point-oper:ap-img-site-status;
      description
        "N+1 operation status";
    }
    leaf oper-uuid {
      type string;
      description
        "Unique identifier for this set of site-filter operations";
    }
    leaf image-any {
      type boolean;
      description
        "Allow any image for site-filter operations";
    }
  }

  grouping ap-image-data {
    description
      "AP image information";
    leaf image-name {
      type string;
      description
        "AP image name";
    }
    leaf image-location {
      type string;
      description
        "AP image location";
    }
    leaf image-version {
      type string;
      description
        "AP image version";
    }
    leaf is-new {
      type boolean;
      description
        "Enabled for new image added during install operation";
    }
    leaf file-size {
      type uint64;
      description
        "AP image file size";
    }
    leaf-list ap-model-list {
      type string;
      ordered-by user;
      description
        "Supported AP models for AP image";
    }
  }

  grouping st-ap-image-loc {
    description
      "AP image location structure";
    leaf index {
      type uint8;
      description
        "AP image index";
    }
    leaf image-file {
      type string;
      description
        "AP image file name";
    }
    list image-data {
      max-elements 32;
      description
        "AP image information";
      uses wireless-access-point-oper:ap-image-data;
    }
  }

  container access-point-oper-data {
    config false;
    description
      "Root container of access point oper";
    list ap-radio-audit-info {
      key "wtp-mac radio-slot-id";
      description
        "AP radio audit info";
      uses wireless-types:radio-slot-key;
      uses wireless-access-point-oper:st-ap-radio-audit-info;
    }
    list ap-wlan-audit-info {
      key "wtp-mac slot-id wlan-id";
      description
        "AP wlan audit info";
      uses wireless-types:radio-wlanid-key;
      uses wireless-access-point-oper:st-ap-wlan-audit-info;
    }
    list ap-audit-summary-info {
      key "wtp-mac";
      description
        "AP audit summary info";
      uses wireless-access-point-oper:st-ap-audit-summary-info;
    }
    list ap-mac-ssid-info {
      key "ap-mac wlan-id";
      description
        "AP MAC and SSID informations";
      uses wireless-access-point-oper:st-ap-mac-ssid-info;
      uses wireless-types:ap-mac-ssid;
    }
    list ap-nextunnel {
      key "wtp-mac";
      description
        "AP Nextunnel configuration data";
      uses wireless-access-point-oper:st-ap-next-tunnel-cfg;
    }
    list ap-nextunnel-state-info {
      key "wtp-mac";
      description
        "AP Nextunnel state data";
      uses wireless-access-point-oper:st-ap-nextunnel-state-data;
    }
    list ap-nextunnel-if-info {
      key "wtp-mac";
      description
        "AP Nextunnel interface state information";
      uses wireless-access-point-oper:st-ap-nextunnel-if-data;
    }
    list ssid-counters {
      key "wtp-mac slot-id wlan-id";
      description
        "Rx/Tx and data-rates information of SSID's broadcasting in AP";
      uses wireless-access-point-oper:st-ssid-counter;
      uses wireless-types:radio-wlanid-key;
    }
    list radius-counters {
      key "wtp-mac server-group-name server-ip";
      description
        "RADIUS related state information";
      uses wireless-access-point-oper:st-radius-counters;
      uses wireless-types:ap-radius-server-key;
    }
    list ap-radio-neighbor {
      key "ap-mac slot-id bssid";
      description
        "AP radio neighbor information.";
      uses wireless-types:radio-slot-bssid-key;
      uses wireless-access-point-oper:st-ap-radio-neighbor-data;
    }
    list radio-oper-data {
      key "wtp-mac radio-slot-id";
      description
        "Radio operational data corresponding
         to a radio of the 802.11 LWAPP AP";
      uses wireless-types:radio-slot-key;
      uses wireless-access-point-oper:ewlc-radio-operation-config;
    }
    list radio-oper-ext-data {
      key "wtp-mac radio-slot-id";
      description
        "Radio operational additional data corresponding to a radio of the 802.11 LWAPP AP";
      uses wireless-types:radio-slot-key;
      uses wireless-access-point-oper:ewlc-radio-operation-ext-config;
    }
    list radio-reset-stats {
      key "ap-mac radio-id cause detail-cause";
      description
        "Radio reset stats";
      uses wireless-access-point-oper:st-radio-reset-cause-key;
      uses wireless-access-point-oper:st-radio-reset-cause-count;
    }
    list radio-failure-stats {
      key "ap-mac radio-id cause detail-cause";
      description
        "Radio failure stats";
      uses wireless-access-point-oper:st-radio-failure-cause-key;
      uses wireless-access-point-oper:st-radio-failure-cause-count;
    }
    list qos-client-data {
      key "client-mac";
      description
        "QoS client data";
      uses wireless-access-point-oper:qos-client-data;
    }
    list capwap-data {
      key "wtp-mac";
      description
        "Captures the information about the 802.11 LWAPP AP that has joined the controller";
      uses wireless-access-point-oper:capwap-wtp-data;
    }
    list meraki-stats {
      key "conv-timestamp wtp-mac";
      description
        "AP Meraki conversion statistics";
      uses wireless-access-point-oper:wtp-meraki-info-ext;
      uses wireless-access-point-oper:wtp-meraki-info;
      uses wireless-access-point-oper:meraki-stats-key;
    }
    list ap-name-mac-map {
      key "wtp-name";
      description
        "Mapping between AP name and radio MAC of AP";
      uses wireless-access-point-oper:ap-name-mac-map;
    }
    list wtp-slot-wlan-stats {
      key "wtp-mac slot-id wlan-id";
      description
        "AP slot and WLAN stats";
      uses wireless-access-point-oper:ap-radio-wlan-key;
      uses wireless-access-point-oper:wtp-slot-wlan-stats;
    }
    list ap-client-dbg-bundle {
      key "wtp-mac event";
      description
        "AP debug bundle";
      uses wireless-access-point-oper:ap-debug-bundle-key;
      uses wireless-access-point-oper:ap-debug-bundle;
    }
    list ethernet-mac-wtp-mac-map {
      key "ethernet-mac";
      description
        "Mapping between AP ethernet MAC and base radio MAC";
      uses wireless-access-point-oper:ethernet-mac-wtp-mac-map;
    }
    list radio-oper-stats {
      key "ap-mac slot-id";
      description
        "Operational statistics for a particular radio";
      uses wireless-access-point-oper:st-mac-slot-id-comp-key;
      uses wireless-access-point-oper:radio-statistics;
    }
    list radio-zwdfs-stats {
      key "ap-mac slot-id";
      description
        "Zero wait DFS statistics for a particular radio";
      uses wireless-access-point-oper:st-mac-slot-id-comp-key;
      uses wireless-access-point-oper:st-zwdfs-stats;
    }
    list ethernet-if-stats {
      key "wtp-mac if-index";
      description
        "Ethernet interface statistics";
      uses wireless-access-point-oper:ap-ethernet-intf-info;
      uses wireless-access-point-oper:ap-ethernet-intf-id;
    }
    container ewlc-wncd-stats {
      presence "ewlc-wncd-stats";
      description
        "AP image download and predownload statistics for EWC on AP platforms";
      uses wireless-access-point-oper:st-ewlc-wncd-stats;
    }
    list predownload-data {
      key "wtp-mac";
      description
        "AP predownload detailed information";
      uses wireless-access-point-oper:capwap-wtp-predownload-data;
    }
    list iot-devices {
      key "ap-mac device-mac";
      description
        "IoT device operational data";
      uses wireless-access-point-oper:st-iot-device;
      uses wireless-access-point-oper:st-iot-device-comp-key;
    }
    list iot-firmware {
      key "ap-mac";
      description
        "IoT radio firmware operational data";
      uses wireless-access-point-oper:st-iot-firmware;
    }
    list ap-iox-oper-data {
      key "ap-mac";
      description
        "IOx application hosting operational data reported by the AP";
      uses wireless-access-point-oper:st-iox-ap;
    }
    list qos-radio-data {
      key "radio-slot-id ap-mac";
      description
        "This object specify a table for QoS AP Radio data records in DB";
      uses wireless-access-point-oper:qos-ap-radio-data;
      uses wireless-access-point-oper:qos-ap-radio-key;
    }
    container qos-global-stats {
      presence "qos-global-stats";
      description
        "This object specify a table for QoS Global statistics data in DB";
      uses wireless-access-point-oper:qos-global-statistics;
    }
    list oper-data {
      key "wtp-mac";
      description
        "Operational data corresponding to an
         802.11 LWAPP AP";
      uses wireless-access-point-oper:st-ap-oper-data;
    }
    list rlan-oper {
      key "wtp-mac rlan-port-id";
      description
        "LAN information of the AP";
      uses wireless-access-point-oper:ewlc-rlan-oper-config-entry;
      uses wireless-access-point-oper:ewlc-rlan-key;
    }
    list wtp-img-dwnld-stats {
      key "wtp-mac";
      description
        "AP image download statistics";
      uses wireless-access-point-oper:st-wtp-img-dwnld-stats;
    }
    container ewlc-mewlc-predownload-rec {
      presence "ewlc-mewlc-predownload-rec";
      description
        "Embedded Wireless Controller predownload data";
      uses wireless-access-point-oper:ewlc-mewlc-predownload-rec;
    }
    list ap-pwr-info {
      key "wtp-mac";
      description
        "AP power policy info";
      uses wireless-access-point-oper:ap-power-info;
    }
    list cdp-cache-data {
      key "mac-addr cdp-cache-device-id";
      description
        "contains the cached neighbor information obtained via receiving CDP messages on APs. Entries are added when a CDP advertisement is received from a neighboring device. Entries get deleted when CDP is disabled on the interface or globally";
      uses wireless-access-point-oper:cdp-cache-data-op;
      uses wireless-access-point-oper:ewlc-cdp-cache-data-key;
      uses wireless-access-point-oper:cdp-cache-data-index-key;
    }
    list lldp-neigh {
      key "wtp-mac neigh-mac";
      description
        "contains the cached neighbor information obtained via receiving LLDP messages on APs. Entries are added when a LLDP advertisement is received from a neighboring device. Entries get deleted when TTL is set to zero in LLDP payload";
      uses wireless-access-point-oper:lldp-neigh-data-op;
      uses wireless-access-point-oper:lldp-neigh-data-key;
    }
    container tp-cert-info {
      presence "tp-cert-info";
      description
        "Trustpoint Certificate information";
      uses wireless-access-point-oper:st-trustpoint-cert-info;
    }
    list ap-lsc {
      key "expiry-time wtp-mac cert-hash";
      description
        "AP LSC";
      uses wireless-access-point-oper:st-ap-lsc-key;
      uses wireless-access-point-oper:st-ap-lsc;
    }
    list support-bundle-info {
      key "ap-mac";
      description
        "Support bundle file transfer information";
      uses wireless-access-point-oper:support-bundle-info;
    }
    list mewlc-ap-data {
      key "wtp-mac";
      description
        "Embedded Wireless Controller operational data";
      uses wireless-access-point-oper:st-mewlc-ap-oper-data;
    }
    list disc-data {
      key "wtp-mac";
      description
        "Discovery packet counters";
      uses wireless-access-point-oper:st-capwap-discovery-pkt-info;
    }
    list capwap-pkts {
      key "wtp-mac";
      description
        "CAPWAP packet counters";
      uses wireless-access-point-oper:st-ap-capwap-pkt-info;
    }
    list radio-operation-info {
      key "wtp-mac radio-slot-id";
      description
        "Radio operational information including channel list and URWB config";
      uses wireless-types:radio-slot-key;
      uses wireless-access-point-oper:radio-operation-info;
    }
    list country-oper {
      key "country-code";
      description
        "Regulatory Domain country details";
      uses wireless-access-point-oper:st-country-oper;
    }
    list supp-country-oper {
      key "country-code";
      description
        "Supported Regulatory Domain country details";
      uses wireless-access-point-oper:st-supp-country-oper;
    }
    list ap-client-trace-info {
      key "site-tag-name";
      description
        "Client trace information for a particular site";
      uses wireless-access-point-oper:ap-client-trace-site-tag-info;
    }
    list ap-client-trace-ap-info {
      key "ap-name";
      description
        "Client trace information for a particular AP";
      uses wireless-access-point-oper:ap-client-trace-ap-info;
    }
    list ap-neighborhood-data {
      key "ap-mac";
      description
        "Captures the information about the RRM based AP clustering and load-balancing";
      uses wireless-access-point-oper:ap-neighborhood-data;
      uses wireless-access-point-oper:ap-neighborhood-index-key;
      uses wireless-access-point-oper:ap-neighborhood-rg-key;
    }
    container ap-nh-global-data {
      presence "ap-nh-global-data";
      description
        "Captures the information about the RRM based AP clustering algorithm stats";
      uses wireless-access-point-oper:ap-neighborhood-global-data;
    }
    list stgrd-upg-report {
      key "report-name";
      unique "start-time";
      description
        "Staggered AP upgrade report";
      uses wireless-access-point-oper:stgrd-upg-report {
        refine "start-time" {
          mandatory true;
        }
      }
    }
    list site-ap-image-map {
      key "image-name site-name";
      description
        "Site tag and image mapping information";
      uses wireless-access-point-oper:site-img-mapping-status;
      uses wireless-access-point-oper:site-img-mapping;
    }
    list ap-image-prepare-location {
      key "index";
      description
        "AP image for prepare location";
      uses wireless-access-point-oper:st-ap-image-loc;
    }
    list ap-image-active-location {
      key "index";
      description
        "AP image for active location";
      uses wireless-access-point-oper:st-ap-image-loc;
    }
    list ap-sensor-status {
      key "ap-mac sensor-type";
      description
        "AP sensor operational status";
      uses wireless-access-point-oper:st-ap-sensor-status-key;
      uses wireless-access-point-oper:st-ap-sensor-status;
    }
    list ap-air-quality {
      key "ap-mac";
      description
        "AP air-quality sensor data";
      uses wireless-access-point-oper:st-ap-air-quality;
    }
    list ap-temp {
      key "ap-mac";
      description
        "AP temperature sensor data";
      uses wireless-access-point-oper:st-ap-temperature;
    }
    list ap-press {
      key "ap-mac";
      description
        "AP pressure sensor data";
      uses wireless-access-point-oper:st-ap-pressure;
    }
    list ap-accelmtr {
      key "ap-mac";
      description
        "AP accelerometer sensor data";
      uses wireless-access-point-oper:st-ap-accelerometer;
    }
    list ap-reboot {
      key "wtp-mac";
      description
        "Reboot stats for AP";
      uses wireless-access-point-oper:st-ap-reboot;
    }
    list wncd-11k-11v-req-stats {
      key "inst-id";
      description
        "Per WNCD level 11k and 11v requests stats";
      uses wireless-access-point-oper:st-wncd-11k-11v-req-stats;
    }
    list wncd-iapp-mesgs-stats {
      key "inst-id";
      description
        "Per WNCD level iapp messages received stats";
      uses wireless-access-point-oper:st-wncd-iapp-mesgs-stats;
    }
  }
}
