module Cisco-IOS-XE-port-bounce-rpc {
  yang-version 1.1;
  namespace "http://cisco.com/ns/yang/Cisco-IOS-XE-port-bounce-rpc";
  prefix port-bounce-ios-xe-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Copyright (c) 2024, 2026 by Cisco Systems, Inc.
     All rights reserved.";

  revision 2026-08-01 {
    description
      "Added length constraint and extended if-name leaf pattern to include
       50 Gigabit Ethernet and 400 Gigabit Ethernet interface name formats";
    reference
      "3.0.0";
    cisco-semver:module-version "3.0.0";
  }
  revision 2025-03-01 {
    description
      "Fixed port bounce input parameter constraints to accept high speed interface types";
    reference
      "2.0.0";
    cisco-semver:module-version "2.0.0";
  }
  revision 2024-07-01 {
    description
      "Initial revision";
    reference
      "1.0.0";
    cisco-semver:module-version "1.0.0";
  }

  typedef port-bounce-fail-reason {
    type enumeration {
      enum pb-fr-no-fail {
        value 0;
        description
          "No failure seen during port bounce";
      }
      enum pb-fr-if-shut {
        value 1;
        description
          "Interface is in shutdown/administratively-down state.
           Port bounce can be performed on interfaces that are up.";
      }
      enum pb-fr-busy {
        value 2;
        description
          "The interface is being bounced and cannot be
           bounced till the previous bounce action completes.";
      }
      enum pb-fr-plat-block {
        value 3;
        description
          "Port bounce on this interface is blocked by platform";
      }
    }
    description
      "Failure reason for bounce";
  }

  typedef port-bounce-resp-status {
    type enumeration {
      enum pb-act-in-prog {
        value 0;
        description
          "The port bounce action has been initiated";
      }
      enum pb-act-fail {
        value 1;
        description
          "The interface stopped bouncing";
      }
    }
    description
      "Failure reason for bounce";
  }

  grouping port-bounce {
    description
      "Port bounce allows the user to flap a physical port without
       changing the configuration.";
    leaf if-name {
      type string {
        length "1..34";
        pattern '(((((Ten|Forty|Two|Five|Four|App|Fifty)?Gigabit)|Fast)?Ethernet(0|[1-9][0-9]*)(/(0|[1-9][0-9]*))*)|(((TwentyFive|Fifty|Hundred|TwoHundred|FourHundred)GigE)(0|[1-9][0-9]*)(/(0|[1-9][0-9]*))*))';
      }
      mandatory true;
      description
        "Name of the interface that is to be bounced. Port bounce can
         be performed only on the following interface -
          Ethernet, Fast Ethernet, Gigabit Ethernet,
          Two Gigabit Ethernet, Four Gigabit Ethernet,
          Five Gigabit Ethernet, Ten Gigabit Ethernet,
          Twenty Five Gigabit Ethernet, Forty Gigabit Ethernet,
          Fifty Gigabit Ethernet, Hundred Gigabit Ethernet,
          Two Hundred Gigabit Ethernet, Four Hundred Gigabit Ethernet and App Gigabit Ethernet";
    }
  }

  grouping port-bounce-response {
    description
      "Response field for port bounce";
    leaf if-name {
      type string;
      description
        "Name of the interface which the user requested to be bounced.";
    }
    leaf status {
      type port-bounce-ios-xe-rpc:port-bounce-resp-status;
      description
        "Status of port bounce operation";
    }
    leaf reason {
      type port-bounce-ios-xe-rpc:port-bounce-fail-reason;
      description
        "Reason for port-bounce to fail, if there is any failure.";
    }
  }

  rpc port-bounce {
    description
      "RPC request message for port bounce";
    input {
      uses port-bounce-ios-xe-rpc:port-bounce;
    }
    output {
      uses port-bounce-ios-xe-rpc:port-bounce-response;
    }
  }
}
