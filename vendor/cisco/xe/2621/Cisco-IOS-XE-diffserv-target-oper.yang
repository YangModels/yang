module Cisco-IOS-XE-diffserv-target-oper {
  yang-version 1.1;
  namespace "http://cisco.com/ns/yang/Cisco-IOS-XE-diffserv-target-oper";
  prefix diffserv-target-oper;

  import cisco-semver {
    prefix cisco-semver;
  }

  //import ietf-interfaces {
  //  prefix if;
  //}

  organization
    "Cisco Systems, Inc.";
  contact
    "Cisco Systems, Inc. Customer Service Postal: 170 W Tasman Drive
     San Jose, CA 95134 Tel: +1 1800 553-NETS E-mail: cs-yang@cisco.com";
  description "This module contains a collection of YANG definitions for
Diffserv operational data "
            + "Copyright (c) 2017 by Cisco Systems, Inc."
            + "All rights reserved.";

  // =========================================================================
  // REVISION
  // =========================================================================

  revision 2022-11-01 {
    description
      "- Update yang-version to 1.1";
  }
  revision 2019-07-01 {
    description
      "Establish semantic version baseline";
    cisco-semver:module-version "1.0.0";
  }
  revision 2017-02-09 {
    description
      "Initial version";
    reference
      "ietf-diffserv-target.yang";
  }

  identity direction {
    description
      "This is identity of traffic direction";
  }

  identity inbound {
    base direction;
    description
      "Direction of traffic coming into the network entry";
  }

  identity outbound {
    base direction;
    description
      "Direction of traffic going out of the network entry";
  }

  feature target-inline-policy-config {
    description
      "This feature allows the policy configuration
       directly under a target.";
  }

  grouping wred-stats {
    description
      "WRED Counters";
    leaf early-drop-pkts {
      type uint64;
      description
        "Early drop packets ";
    }
    leaf early-drop-bytes {
      type uint64;
      description
        "Early drop bytes ";
    }
  }

  grouping classifier-entry-stats {
    description
      "Classifier Counters";
    container classifier-entry-statistics {
      config false;
      description
        "
         This group defines the classifier filter statistics of
         each classifier entry
         
        ";
      leaf classified-pkts {
        type uint64;
        description
          " Number of total packets which filtered
            to the classifier-entry";
      }
      leaf classified-bytes {
        type uint64;
        description
          " Number of total bytes which filtered
            to the classifier-entry";
      }
      leaf classified-rate {
        type uint64;
        units "bits-per-second";
        description
          " Rate of average data flow through the
            classifier-entry";
      }
    }
  }

  grouping queuing-stats {
    description
      "Queuing Counters";
    container queuing-statistics {
      description
        "queue related statistics ";
      leaf output-pkts {
        type uint64;
        description
          "Number of packets transmitted from queue ";
      }
      leaf output-bytes {
        type uint64;
        description
          "Number of bytes transmitted from queue ";
      }
      leaf queue-size-pkts {
        type uint64;
        description
          "Number of packets currently buffered ";
      }
      leaf queue-size-bytes {
        type uint64;
        description
          "Number of bytes currently buffered ";
      }
      leaf drop-pkts {
        type uint64;
        description
          "Total number of packets dropped ";
      }
      leaf drop-bytes {
        type uint64;
        description
          "Total number of bytes dropped ";
      }
      container wred-stats {
        uses wred-stats;
        description
          "Container for WRED statistics";
      }
    }
  }

  grouping meter-stats {
    description
      "Metering Counters";
    list meter-statistics {
      key "meter-id";
      description
        "Meter statistics";
      leaf meter-id {
        type uint16;
        description
          "Meter Identifier";
      }
      leaf meter-succeed-pkts {
        type uint64;
        description
          "Number of packets which succeed the meter";
      }
      leaf meter-succeed-bytes {
        type uint64;
        description
          "Bytes of packets which succeed the meter";
      }
      leaf meter-failed-pkts {
        type uint64;
        description
          "Number of packets which failed the meter";
      }
      leaf meter-failed-bytes {
        type uint64;
        description
          "Bytes of packets which failed the meter";
      }
    }
  }

  container diffserv-interfaces-state {
    description
      "Interface configuration parameters.";
    config false;
    list diffserv-interface {
      key "name";
      description
        "The list of configured interfaces on the device.";
      leaf name {
        type string;
        description
          "The name of the interface.";
      }
      list diffserv-target-entry {
        key "direction policy-name";
        description
          "policy target for inbound or outbound direction";
        leaf direction {
          type identityref {
            base direction;
          }
          description
            "Direction fo the traffic flow either inbound or outbound";
        }
        leaf policy-name {
          type string;
          description
            "Policy entry name";
        }
        list diffserv-target-classifier-statistics {
          key "classifier-entry-name parent-path";
          description
            "Statistics for each Classifier Entry in a Policy";
          leaf classifier-entry-name {
            type string;
            description
              "Classifier Entry Name";
          }
          leaf parent-path {
            type string;
            description
              "Path of the Classifier Entry in a hierarchical policy ";
          }
          uses classifier-entry-stats;
          uses meter-stats;
          uses queuing-stats;
        }
      }
    }
  }
}
