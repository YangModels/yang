module cisco-xe-openconfig-interfaces-ext{

  yang-version "1";

  // namespace
  namespace "http://cisco.com/ns/yang/cisco-xe-openconfig-interfaces-ext";

  prefix "oc-if-cisco";
  import openconfig-interfaces { prefix oc-if; }


  // import some basic types
  import openconfig-extensions { prefix oc-ext; }
  import tailf-common { prefix tailf; }


  // meta
  organization "OpenConfig working group";

  contact
    "OpenConfig working group
    netopenconfig@googlegroups.com";

  description
    "Module to enable mapping for oc-interfaces.";

  oc-ext:openconfig-version "1.0.2";

  revision "2017-03-05" {
    description
      "Augment oc-interfaces to add hold-time leafs to oc state";
    reference "1.0.2";
  }

  revision "2017-02-25" {
    description
      "Augment oc-interfaces to add required hold-time leafs for Cisco platforms";
    reference "1.0.2";
  }

  // Augment to add holdtime leafs

  augment "/oc-if:interfaces/oc-if:interface/oc-if:hold-time" +
            "/oc-if:config" {
              leaf dampening-time {
                type uint32;
                units milliseconds;
                description
                  "Half-life for penalty time required for IOS-XE dampening.";
             }
          }

  augment "/oc-if:interfaces/oc-if:interface/oc-if:hold-time" +
            "/oc-if:config" {
              leaf maximum-suppressing-time {
                type uint32;
                units milliseconds;
                description
                  "Add start suppressing time required for IOS-XE dampening.";
             }
          }

  augment "/oc-if:interfaces/oc-if:interface/oc-if:hold-time" +
            "/oc-if:state" {
              leaf dampening-time {
                type uint32;
                units milliseconds;
                description
                  "Half-life for penalty time required for IOS-XE dampening.";
             }
          }

  augment "/oc-if:interfaces/oc-if:interface/oc-if:hold-time" +
            "/oc-if:state" {
              leaf maximum-suppressing-time {
                type uint32;
                units milliseconds;
                description
                  "Add start suppressing time required for IOS-XE dampening.";
             }
          }

  augment "/oc-if:interfaces/oc-if:interface" +
            "/oc-if:config" {
              container bandwidth {
                leaf kilobits {
                  type uint32;
                  description
                    "Add bandwidth configuration for XE routers.";
               }
             }
          }

}
