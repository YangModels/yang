module cisco-routing-ext {
  namespace "urn:cisco:params:xml:ns:yang:cisco-routing-ext";
  prefix rt-ext;

  import ietf-routing {
    prefix rt;
  }

  organization "Cisco Systems, Inc.";
  contact
    "Cisco Systems, Inc.
     Customer Service

     Postal: 170 W Tasman Drive
     San Jose, CA 95134

     Tel: +1 1800 553-NETS

     E-mail: cs-yang@cisco.com";
  description
    "This YANG module is an extention to 'ietf-routing'
     module and describes addtional operational
     data for route list";

  revision 2016-07-09 {
    description
      "Removed deviation for last-updated and added it to ietf-routing-devs.yang.";
  }

  revision 2015-05-27 {
    description
      "Proposed";
    reference "TODO";
  }

  identity rip {
    base rt:routing-protocol;
    description
      "RIP.";
  }

  identity is-is {
    base rt:routing-protocol;
    description
      "IS-IS.";
  }

  identity bgp {
    base rt:routing-protocol;
    description
      "BGP.";
  }

  identity eigrp {
    base rt:routing-protocol;
    description
      "Eigrp.";
  }
  identity mobile {
    base rt:routing-protocol;
    description
      "Mobile.";
  }

} // --end module
