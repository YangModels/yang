module Cisco-IOS-XE-template {
  namespace "http://cisco.com/ns/yang/ios-xe/template";
  prefix ios-template;

  import ietf-inet-types {
    prefix inet;
  }


  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Template Yang Model.
     Copyright (c) 2016-2017 by Cisco Systems, Inc.
     All rights reserved.";

  // =========================================================================
  // REVISION
  // =========================================================================

  revision 2017-02-13 {
    description
      "Initial Revision";
  }

  grouping template-error-disable-grouping {
    leaf error-disable-interface {
      type empty;
    }
  }
  grouping template-threshold-grouping-64k {
    container threshold {
      description "threshold";
      container high {
        description "High Threshold";
        leaf high-range {
          description "Set the high threshold";
          type uint16 {
            range "1..65535";
          }
        }
        leaf none {
          description "Disable high threshold";
          type empty;
        }
      }
      leaf low {
        description "Set the low threshold";
        type uint16 {
          range "0..65535";
        }
      }
    }
  }

  grouping template-window-grouping-64k {
    leaf window {
      description "Set window size in number of 10000 frames";
      type uint16 {
        range "1..65535";
      }
    }
  }
    
  grouping template-window-grouping-1800 {
    leaf window {
      description "Set window size in number of 10000 frames";
      type uint16 {
        range "10..1800";
      }
    }
  }
  grouping  config-template-grouping {
    list template_details {
      key "template_name";
      leaf template_name {
        description "Template name";
        type string;
      }
      container ethernet {
        description "Ethernet service";
        container oam {
          description "Operations, Administration and Maintenance";
          container link-monitor {
            description "Ethernet OAM Link Monitor";
            container frame {
              description "Errored frames in a period measured by time";
              uses template-threshold-grouping-64k;
            }
            leaf window {
              description "Set window size in multiple of 100 milliseconds (will be rounded off to second)";
              type uint16 {
                range "10..600";
              }
            }
            container frame-period {
              description "Errored frames in a period measured by number of frames";
              uses template-threshold-grouping-64k;
              uses template-window-grouping-64k;
            }
            container frame-seconds {
              description "Errored frame seconds in a period";
              container threshold {
                description "Errored frame-seconds threshold";
                container high {
                  description "High Threshold";
                  leaf high-range {
                    description "Set the high errored frame-seconds threshold in number of seconds";
                    type uint16 {
                      range "1..900";
                    }
                  }
                  leaf none {
                    description "Disable high threshold";
                    type empty;
                  }
                }
                leaf low {
                  description "Set the low errored frame-seconds threshold in number of seconds";
                  type uint16 {
                    range "1..900";
                  }
                }
              }
              leaf window {
                description "Set window size in multiple of 100 milliseconds (will be rounded off to second)";
                type uint16 {
                  range "100..9000";
                }
              }
            }
            container high-threshold {
              description "Additional high threshold configuration";
              container action {
                description "Specifiy an action when the high threshold is crossed";
                uses template-error-disable-grouping;
              }
            }
            container receive-crc {
              description "Received frames with CRC errors in a period";
              uses template-threshold-grouping-64k;
              uses template-window-grouping-1800;
            }
            container symbol-period {
              description "Errored symbols in a period";
              uses template-threshold-grouping-64k;
              uses template-window-grouping-64k;
            }
            container transmit-crc {
              description "Transmitted frames with CRC errors in a period";
              uses template-threshold-grouping-64k;
              uses template-window-grouping-1800;
            }
          }
          container remote-failure {
            description "Ethernet OAM remote failure indication";
            container critical-event {
              description "Critical event";
              container action {
                description "Specifiy an action when a remote failure is detected";
                uses template-error-disable-grouping;
              }
            }
            container dying-gasp {
              description "Dying gasp";
              container action {
                description "Specifiy an action when a remote failure is detected";
                presence true;
                uses template-error-disable-grouping;
              }
            }
            container link-fault {
              description "Link fault";
              container action {
                description "Specifiy an action when a remote failure is detected";
                presence true;
                uses template-error-disable-grouping;
              }
            }
          }
        }
      }
    }
  }

  /////////////////////////////////////////////////////////
  // native / template
  /////////////////////////////////////////////////////////
  augment "/ios:native/ios:template" {
    uses config-template-grouping;
  }
}
