module Cisco-IOS-XE-flow-monitor-oper {
  yang-version 1;
  namespace "http://cisco.com/ns/yang/Cisco-IOS-XE-flow-monitor-oper";
  prefix flow-monitor-ios-xe-oper;

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for Flexible NetFlow Operational data.
     Copyright (c) 2016-2017 by Cisco Systems, Inc.
     All rights reserved.";

  revision 2017-04-01 {
    description
      "Put keys on one line";
    reference "1.1.0";
  }
  revision 2017-02-07 {
    description
      "Initial revision";
    reference "1.0.0";
  }

  grouping oper-flow-key {
    description
      "Unique identifier of a flow";
    leaf source-address {
      type string;
      description
        "Source address of the flow";
    }
    leaf destination-address {
      type string;
      description
        "Destination address of the flow";
    }
    leaf interface-input {
      type string;
      description
        "Input interface of the flow";
    }
    leaf is-multicast {
      type string;
      description
        "Multicast flow";
    }
    leaf vrf-id-input {
      type int64;
      description
        "VRF ID input";
    }
    leaf source-port {
      type int64;
      description
        "Source port number";
    }
    leaf destination-port {
      type int64;
      description
        "Destination port number";
    }
    leaf ip-tos {
      type string;
      description
        "ip-tos value";
    }
    leaf ip-protocol {
      type int64;
      description
        "IP protocol number";
    }
  }

  grouping oper-flow {
    description
      "Flow details";
    leaf interface-output {
      type string;
      description
        "Output interface of the flow";
    }
    leaf bytes {
      type int64;
      description
        "Number of bytes passed through";
    }
    leaf packets {
      type int64;
      description
        "Number of packets passed through";
    }
  }

  grouping oper-flow-monitor {
    description
      "Flow monitor details";
    leaf name {
      type string;
      description
        "Name of the flow monitor";
    }
    leaf time-collected {
      type uint64;
      description
        "Time the flow monitor data was collected in seconds";
    }
    container flows {
      description
        "All the flows for this flow monitor";
      list flow {
        key "source-address destination-address interface-input is-multicast vrf-id-input source-port destination-port ip-tos ip-protocol";
        description
          "List of flows";
        uses flow-monitor-ios-xe-oper:oper-flow-key;
        uses flow-monitor-ios-xe-oper:oper-flow;
      }
    }
  }

  container flow-monitors {
    config false;
    description
      "All of the flow monitors";
    list flow-monitor {
      key "name";
      description
        "List of Flow monitors";
      uses flow-monitor-ios-xe-oper:oper-flow-monitor;
    }
  }
}
