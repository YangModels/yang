module Cisco-IOS-XE-mdt-cfg {
  yang-version 1;
  namespace "http://cisco.com/ns/yang/Cisco-IOS-XE-mdt-cfg";
  prefix mdt-cfg;

  import Cisco-IOS-XE-mdt-common-defs {
    prefix mdt-common-defs;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG 
     definitions for configuration of streaming telemetry.
     Copyright (c) 2016-2017 by Cisco Systems, Inc.
     All rights reserved.";

  revision 2017-03-02 {
    description
      "Initial revision";
    reference "1.0.0";
  }

  grouping mdt-subscription-cnfg {
    description
      "Subscription configuration information.";
    leaf subscription-id {
      type uint32 {
        range "0 .. 2147483647";
      }
      description
        "Unique subscription identifier.";
    }
    container base {
      description
        "Common subscription information.";
      uses mdt-common-defs:mdt-subscription-base;
    }
    list mdt-receivers {
      key "address port";
      description
        "Configuration of receivers of configured subscriptions.";
      uses mdt-cfg:mdt-receiver-cnfg;
      uses mdt-common-defs:mdt-receiver-id;
    }
  }

  grouping mdt-receiver-cnfg {
    description
      "Configuration information for subscription receiver.";
    leaf protocol {
      type string;
      default "netconf";
      description
        "Receiver transport protocol.";
    }
  }

  container mdt-subscriptions {
    description
      "Subscription configuration";
    list mdt-subscription {
      key "subscription-id";
      description
        "List of subscriptions";
      uses mdt-cfg:mdt-subscription-cnfg;
    }
  }
}
