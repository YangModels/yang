module tailf-netconf-inactive {
  namespace "http://tail-f.com/ns/netconf/inactive/1.0";
  prefix in;

  import ietf-netconf {
    prefix nc;
  }

  import tailf-netconf-transactions {
    prefix tr;
  }

  description
    "This module is used by the NETCONF server to indicate that it
     supports marking nodes as being inactive.  A node that is marked
     as inactive exists in the data store, but is not used by the
     server.  Any node can be marked as inactive.

     In order to not confuse clients that do not understand this
     attribute, the client has to instruct the server to display and
     handle the inactive nodes.  An inactive node is marked with an
     'inactive' XML attribute, and in order to make it active, the
     'active' XML atribute is used.

     The 'inactive' and 'active' attributes are defined in the
     http://tail-f.com/ns/netconf/inactive/1.0 namespace.  The
     'inactive' attribute's value is the string 'inactive', and the
     'active' attribute's value is the string 'active'.";

  grouping inactive-params {
    leaf with-inactive {
      type empty;
    }
  }

  augment "/nc:get/nc:input" {
    uses inactive-params {
      refine with-inactive {
        description
          "If this parameter is present, the NETCONF server will mark
           inactive nodes in the reply with the 'inactive' XML attribute.";
      }
    }
  }

  augment "/nc:get-config/nc:input" {
    uses inactive-params {
      refine with-inactive {
        description
          "If this parameter is present, the NETCONF server will mark
           inactive nodes in the reply with the 'inactive' XML attribute.";
      }
    }
  }

  augment "/nc:edit-config/nc:input" {
    uses inactive-params {
      refine with-inactive {
        description
          "If this parameter is present, the NETCONF server will treat
           inactive nodes as existing, so that an attempt to create a
           node which is inactive will fail, and an attempt to delete
           a node which is inactive will succeed.  Further, the
           NETCONF server accepts the 'inactive' and 'active'
           attributes in the data hierarchy, in order to make nodes
           inactive or active, respectively.";
      }
    }
  }

  augment "/nc:copy-config/nc:input" {
    uses inactive-params {
      refine with-inactive {
        description
          "If this parameter is present, the NETCONF server will treat
           inactive nodes as existing, so that an attempt to create a
           node which is inactive will fail, and an attempt to delete
           a node which is inactive will succeed.  Further, the
           NETCONF server accepts the 'inactive' and 'active'
           attributes in the data hierarchy, in order to make nodes
           inactive or active, respectively.";
      }
    }
  }

  augment "/tr:start-transaction/tr:input" {
    uses inactive-params {
      refine with-inactive {
        description
          "If the parameter is present in <start-transaction>, it MUST
           also be present in any <edit-config>, <copy-config>, <get>,
           or <get-config> operations within the transaction.  If it
           is not present in <start-transaction>, it MUST NOT be
           present in any <edit-config> operation within the
           transaction.";
      }
    }
  }
}
