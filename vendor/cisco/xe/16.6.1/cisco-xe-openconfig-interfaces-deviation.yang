module cisco-xe-openconfig-interfaces-deviation {
  // namespace
  namespace "http://openconfig.net/yang/cisco-xe-openconfig-interfaces-deviation";

  prefix oc-if-devs;

  import openconfig-interfaces {
    prefix oc-if;
  }

  import openconfig-if-ethernet {
    prefix oc-eth;
  }

  import openconfig-if-aggregate {
    prefix oc-lag;
  }

  import openconfig-vlan {
    prefix oc-vlan;
  }

  import openconfig-if-ip {
    prefix oc-ip;
  }

  import ietf-yang-types {
    prefix yang;
  }

  organization
    "Cisco Systems, Inc.";

  contact
    " Cisco Systems, Inc.
    Customer Service

    Postal: 170 W Tasman Drive
    San Jose, CA 95134

    Tel: +1 1800 553-NETS

    E-mail: cs-yang@cisco.com";

  description
    "This module defines deviation statements for openconfig-interfaces module.";

  revision 2017-05-08 {
    description
      "Add deviations to change last-change type under subinterfaces to yang:date-and-time";
  }

  revision 2017-04-13 {
    description
      "Add deviations to hide features not implemented in 16.6.1";
  }

  revision 2017-03-10 {
    description
      "Change type of last-change to yang:date-and-time";
  }

  revision 2017-02-21 {
    description
      "Initial Revision";

    reference
      "RFC 6020: YANG - A Data Modeling Language for the
       Network Configuration Protocol (NETCONF)";
  }

  deviation "/oc-if:interfaces/oc-if:interface/oc-eth:ethernet" +
            "/oc-eth:state" {
      deviate not-supported; 
      description
        "Ethernet state not supported in 16.6.1.";
  }

  deviation "/oc-if:interfaces/oc-if:interface/oc-lag:aggregation" {
      deviate not-supported;
      description
        "Interface aggregation not supported in 16.6.1.";
  }

  deviation "/oc-if:interfaces/oc-if:interface/oc-vlan:routed-vlan" +
            "/oc-ip:ipv4/oc-ip:addresses/oc-ip:address/oc-ip:vrrp" {
      deviate not-supported;
      description
        "IPv4 VRRP not supported in 16.6.1.";
  }

  deviation "/oc-if:interfaces/oc-if:interface/oc-vlan:routed-vlan" +
            "/oc-ip:ipv6/oc-ip:addresses/oc-ip:address/oc-ip:vrrp" {
      deviate not-supported;
      description
        "IPv6 VRRP not supported in 16.6.1.";
  }

  deviation "/oc-if:interfaces/oc-if:interface/oc-if:hold-time" +
            "/oc-if:config/oc-if:up" {
      deviate delete {
        default 0;
      }
      description
        "Hold-time 0 is not configurable on XE, use no dampening.";
  }

  deviation "/oc-if:interfaces/oc-if:interface/oc-if:hold-time" +
            "/oc-if:config/oc-if:down" {
      deviate delete {
        default 0;
      }
      description
        "Hold-time 0 is not configurable on XE, use no dampening.";
  }

  deviation "/oc-if:interfaces/oc-if:interface/oc-if:state" +
            "/oc-if:last-change" {
      deviate replace {
        type yang:date-and-time;
      }
      description
        "Change the type of the last-change flag to date-and-time";
  }

  deviation "/oc-if:interfaces/oc-if:interface/oc-if:subinterfaces/oc-if:subinterface/oc-if:state" +
            "/oc-if:last-change" {
      deviate replace {
        type yang:date-and-time;
      }
      description
        "Change the type of the last-change flag to date-and-time";
  }

}
