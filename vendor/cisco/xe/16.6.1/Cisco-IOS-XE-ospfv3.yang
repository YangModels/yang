module Cisco-IOS-XE-ospfv3 {
  namespace "http://cisco.com/ns/yang/Cisco-IOS-XE-ospfv3";
  prefix ios-ospfv3;

  import ietf-inet-types {
    prefix inet;
  }


  import Cisco-IOS-XE-types {
    prefix ios-types;
  }

  import Cisco-IOS-XE-native {
    prefix ios;
  }

  import Cisco-IOS-XE-ospf {
    prefix ios-ospf;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Open Shorteset Path First (OSPFv3) Yang model.
     Copyright (c) 2016 by Cisco Systems, Inc.
     All rights reserved.";

  // =========================================================================
  // REVISION
  // =========================================================================
  revision 2017-04-28 {
    description
      "inet:ipv6-prefix changed to ios-types:ipv6-prefix";
  }
  revision 2017-04-20 {
    description
      "Remove tailf:cli-flatten-container for address-family ipv4 unicast option";
  }

  revision 2017-02-07 {
    description
      "Initial revision";
  }

  grouping interface-ospfv3-manet-grouping {
    container manet {
      description
        "Mobile Adhoc Networking options";
      container peering {
        description
          "MANET Peering options";
        container cost {
          description
            "Redundant path cost improvement required to peer";
          leaf percent {
            description
              "Relative incremental path cost";
            type uint8 {
              range "0..100";
            }
          }
          leaf threshold {
            description
              "Absolute incremental path cost";
            type uint32 {
              range "0..65535";
            }
          }
        }
        leaf link-metrics {
          description
            "Require link metrics";
          type uint32 {
            range "0..65535";
          }
        }
      }
    }
  }

  grouping interface-ospfv3-cost-grouping {
    container cost {
      description
        "Route cost of this interface";
      leaf value {
        type uint32 {
          range "1..65535";
        }
      }
      container dynamic {
        description
          "Specify dynamic cost options";
        presence "true";
        leaf default {
          description
            "Specify default link metric value";
          type uint32 {
            range "0..65535";
          }
        }
        container hysteresis {
          description
            "Specify hysteresis value for LSA dampening";
          presence "true";
          leaf percent {
            description
              "Specify hysteresis percent changed";
            type uint8 {
              range "1..100";
            }
          }
          leaf threshold {
            description
              "Specify hysteresis threshold value";
            type uint32 {
              range "0..65535";
            }
          }
        }
        container weight {
          description
            "Specify weight to be placed on individual metrics";
          container L2-factor {
            description
              "Specify weight to be given to L2-factor metric";
            presence "true";
            leaf value {
              type uint8 {
                range "0..100";
              }
            }
          }
          container latency {
            description
              "Specify weight to be given to latency metric";
            presence "true";
            leaf value {
              type uint8 {
                range "0..100";
              }
            }
          }
          container resources {
            description
              "Specify weight to be given to resources metric";
            presence "true";
            leaf value {
              type uint8 {
                range "0..100";
              }
            }
          }
          container throughput {
            description
              "Specify weight to be given to throughput metric";
            presence "true";
            leaf value {
              type uint8 {
                range "0..100";
              }
            }
          }
        }
      }
    }
  }

  grouping interface-ospfv3-process-id-grouping {
    // interface * / ospfv3 * authentication
    container authentication {
      description
        "Enable authentication";
      leaf key-chain {
        description
          "Use a key-chain for cryptographic authentication keys";
        type string;
      }
      leaf null {
        description
          "Use no authentication";
        type empty;
      }
    }

    // interface * / ospfv3 * bfd
    uses ios-ospf:interface-ospf-bfd-grouping;

    // interface * / ospfv3 * cost
    uses interface-ospfv3-cost-grouping;

    // interface * / ospfv3 * database-filter
    container database-filter {
      description
        "Filter OSPF LSA during synchronization and flooding";
      choice database {
        leaf all {
          description
            "Filter all LSA";
          type enumeration {
            enum "out";
          }
        }
        leaf disable {
          description
            "Disable LSA Filter on this interface";
          type empty;
        }
      }
    }
    // interface * / ospfv3 * dead-interval
    uses ios-ospf:interface-ospf-dead-interval-grouping;

    // interface * / ospfv3 * demand-circuit
    container demand-circuit {
      description
        "OSPF demand circuit";
      presence "true";
      leaf disable {
        description
          "Disable demand circuit on this interface";
        type empty;
      }
      leaf ignore {
        description
          "Ignore demand circuit auto-negotiation requests";
        type empty;
      }
    }

    // interface * / ospfv3 * flood-reduction
    container flood-reduction {
      description
        "OSPF Flood Reduction";
      presence "true";
      leaf disable {
        type empty;
      }
    }

    // interface * / ospfv3 * hello-interval
    uses ios-ospf:interface-ospf-hello-interval-grouping;

    // interface * / ospfv3 * manet
    uses interface-ospfv3-manet-grouping;

    // interface * / ospfv3 * mtu-ignore
    container mtu-ignore {
      description
        "Ignores the MTU in DBD packets";
      presence "true";
      leaf disable {
        description
          "Disable Ingore MTU on this interface";
        type empty;
      }
    }

    // interface * /  ospfv3 * multi-area
    container multi-area {
      description
        "Set the OSPF multi-area ID";
      leaf id {
        type union {
          type uint32 {
            range "0..4294967295";
          }
          type inet:ipv4-address;
        }
      }
      leaf cost {
        description
          "Interface cost";
        type uint32 {
          range "1..65535";
        }
      }
      leaf disable {
        description
          "disable OSPF multi-area";
        type empty;
      }
    }

    // interface * /  ospfv3 * neighbor
    uses ios-ospf:interface-ospf-neighbor-grouping;

    // interface * /  ospfv3 * network
    uses ios-ospf:interface-ospf-network-grouping;

    // interface * / ospfv3 * prefix-suppression
    uses ios-ospf:interface-ospf-prefix-suppression-grouping;

    // interface * /  ospfv3 * priority
    uses ios-ospf:interface-ospf-priority-grouping;

    // interface * /  ospfv3 * retransmit-interval
    uses ios-ospf:interface-ospf-retransmit-interval-grouping;

    // interface * / ospfv3 * shutdown
    container shutdown {
      description
        "Shut down the interface in OSPFv3";
      presence "true";
      leaf disable {
        description
          "Disable inherited shutdown";
        type empty;
      }
    }

    // interface * / ospfv3 * transmit-delay
    uses ios-ospf:interface-ospf-transmit-delay-grouping;
  }

  // interface * / ospfv3
  grouping config-interface-ospfv3-grouping {
    container ospfv3 {
      description
        "OSPFv3 interface commands";
      list process-id {
        key "id";
        leaf id {
          type uint16;
        }

        uses interface-ospfv3-process-id-grouping;

        //interface * / ospfv3 * ipv4
        container ipv4 {
          description
            "Specify parameters for IPv4";
          list area {
            description
              "Set the OSPF area ID";
            key "id";
            leaf id {
              type ios-types:ospf-area-type;
            }
            leaf instance {
              description
                "Set the OSPF instance";
              type uint8 {
                range "64..95";
              }
            }
          }
          uses interface-ospfv3-process-id-grouping;
        }

        //interface * / ospfv3 * ipv6
        container ipv6 {
          description
            "Specify parameters for IPv6";
          list area {
            description
              "Set the OSPF area ID";
            key "id";
            leaf id {
              type ios-types:ospf-area-type;
            }
            leaf instance {
              description
                "Set the OSPF instance";
              type uint8 {
                range "0..31";
              }
            }
          }
          uses interface-ospfv3-process-id-grouping;
        }
      }

      // interface * / ospfv3 authentication
      container authentication {
        description
          "Enable authentication";
        leaf key-chain {
          description
            "Use a key-chain for cryptographic authentication keys";
          type string;
        }
        leaf null {
          description
            "Use no authentication";
          type empty;
        }
        uses ios-ospf:authentication-ipsec-grouping;
      }

      // interface * / ospfv3 bfd
      uses ios-ospf:interface-ospf-bfd-grouping;

      // interface * / ospfv3 cost
      uses interface-ospfv3-cost-grouping;

      // interface * / ospfv3 database-filter
      container database-filter {
        description
          "Filter OSPF LSA during synchronization and flooding";
        leaf all {
          description
            "Filter all LSA";
          type enumeration {
            enum "out";
          }
        }
      }
      // interface * / ospfv3 dead-interval

      uses ios-ospf:interface-ospf-dead-interval-grouping;

      // interface * / ospfv3 demand-circuit
      container demand-circuit {
        description
          "OSPF Demand Circuit";
        presence "true";
        leaf ignore {
          description
            "Ignore demand circuit auto-negotiation requests";
          type empty;
        }
      }

      // interface * / ospfv3 encryption
      uses ios-ospf:interface-ospf-encryption-grouping;

      // interface * / ospfv3 flood-reduction
      leaf flood-reduction {
        description
          "OSPF Flood Reduction";
        type empty;
      }

      // interface * / ospfv3 hello-interval
      uses ios-ospf:interface-ospf-hello-interval-grouping;

      // interface * / ospfv3 manet
      uses interface-ospfv3-manet-grouping;

      // interface * / ospfv3 mtu-ignore
      leaf mtu-ignore {
        description
          "Ignores the MTU in DBD packets";
        type empty;
      }

      // interface * /  ospfv3 multi-area
      container multi-area {
        description
          "Set the OSPF multi-area ID";
        leaf id {
          type ios-types:ospf-area-type;
        }
        leaf cost {
          description
            "Interface cost";
          type uint32 {
            range "1..65535";
          }
        }
      }

      // interface * /  ospfv3 neighbor
      uses ios-ospf:interface-ospf-neighbor-grouping;

      // interface * /  ospfv3 network
      uses ios-ospf:interface-ospf-network-grouping;

      // interface * / ospfv3 prefix-suppression
      uses ios-ospf:interface-ospf-prefix-suppression-grouping;

      // interface * /  ospfv3 priority
      uses ios-ospf:interface-ospf-priority-grouping;

      // interface * /  ospfv3 retransmit-interval
      uses ios-ospf:interface-ospf-retransmit-interval-grouping;

      // interface * / ospfv3 shutdown
      leaf shutdown {
        description
          "Shut down the interface in OSPFv3";
        type empty;
      }

      // interface * / ospfv3 transmit-delay
      uses ios-ospf:interface-ospf-transmit-delay-grouping;
    }
  }

  grouping ospf-redistribute-bgp-grouping {
    leaf as-number {
      type ios-types:bgp-as-number-type;
    }
    uses ios-ospf:ospf-redistribute-grouping;
  }

  grouping ospf-redistribute-match-grouping {
    leaf metric {
      description
        "Metric for redistributed routes";
      type uint32;
    }
    leaf metric-type {
      description
        "OSPF/IS-IS exterior metric type for redistributed routes";
      type enumeration {
        enum "1" {
        }
        enum "2" {
        }
      }
    }
    leaf nssa-only {
      description
        "Limit redistributed routes to NSSA areas";
      type empty;
    }
    leaf subnets {
      description
        "Consider subnets for redistribution into OSPF";
      type empty;
    }
    leaf route-map {
      description
        "Route map reference";
      type string;
    }
    leaf tag {
      description
        "Set tag for routes redistributed into OSPF";
      type uint32 {
        range "0 .. 4294967295";
      }
    }
  }

  grouping ospf-redistribute-top-match-grouping {
    container match {
      description
        "Redistribution of OSPF routes";
      container internal {
        presence "Redistribute OSPF internal routes";
        description
          "Redistribute OSPF internal routes";
        uses ospf-redistribute-match-grouping;
      }
      container external {
        description
          "Redistribute OSPF external routes";
        presence "Redistribute OSPF external routes";
        leaf external-routes {
          type ios-types:redist-ospf-external-type;
        }
        uses ospf-redistribute-match-grouping;
      }
      container nssa-external {
        description
          "Redistribute OSPF NSSA external routes";
        presence "Redistribute OSPF NSSA external routes";
        leaf nssa-external-routes {
          type ios-types:redist-ospf-external-type;
        }
        uses ospf-redistribute-match-grouping;
      }
    }
  }

  grouping ospf-iso-igrp-redistribute-grouping {
    leaf metric {
      description
        "Metric for redistributed routes";
      type uint32;
    }
    leaf metric-type {
      description
        "OSPF/IS-IS exterior metric type for redistributed routes";
      type enumeration {
        enum "1" {
        }
        enum "2" {
        }
      }
    }
    leaf tag {
      description
        "Set tag for routes redistributed into OSPF";
      type uint32 {
        range "0 .. 4294967295";
      }
    }
    leaf subnets {
      description
        "Consider subnets for redistribution into OSPF";
      type empty;
    }
  }

  grouping ospf-redistribute-grouping {
    container redist-options {
      uses ospf-iso-igrp-redistribute-grouping;
      leaf route-map {
        description
          "Route map reference";
        type string;
      }
      leaf nssa-only {
        description
          "Limit redistributed routes to NSSA areas";
        type empty;
      }
    }
  }

  grouping ospf-redistribute-top-grouping {
    list application {
      description
        "Application";
      key "name";
      leaf name {
        type string;
      }
      uses ospf-redistribute-grouping;
    }
    list bgp {
      description
        "Border Gateway Protocol (BGP)";
      key "as-number";
      uses ospf-redistribute-bgp-grouping;
    }
    container connected {
      description
        "Connected";
      presence "Connected";
      uses ospf-redistribute-grouping;
    }
    list eigrp {
      description
        "Enhanced Interior Gateway Routing Protocol (EIGRP)";
      key "as-number";
      uses ospf-redistribute-bgp-grouping;
    }
    container isis {
      presence "ISO IS-IS";
      description
        "ISO IS-IS";
      choice isis-level-routes-isis-area-choice {
        leaf isis-level-routes {
          type enumeration {
            enum "level-1";
            enum "level-2";
            enum "level-1-2";
          }
        }
        list isis-area {
          key "name";
          leaf name {
            type string;
          }
          leaf isis-level-routes {
            type enumeration {
              enum "level-1";
              enum "level-2";
              enum "level-1-2";
            }
          }
          uses ospf-redistribute-grouping;
        }
      }
      uses ospf-redistribute-grouping;
    }
    container iso-igrp {
      description
        "IGRP for OSI networks";
      presence "IGRP for OSI networks";
      choice area-tag-route-map-choice {
        container area-tag-route-map-container {
          leaf area-tag {
            type string;
          }
          leaf route-map {
            description
              "Route map reference";
            type string;
          }
        }
        leaf route-map {
          description
            "Route map reference";
          type string;
        }
      }
      container iso-igrp-container {
        uses ospf-iso-igrp-redistribute-grouping;
      }
    }
    container lisp {
      description
        "Locator ID Separation Protocol (LISP)";
      uses ospf-redistribute-grouping;
    }
    container mobile {
      description
        "Mobile routes";
      presence "Mobile routes";
      uses ospf-redistribute-grouping;
    }
    container odr {
      description
        "On Demand stub Routes";
      presence "On Demand stub Routes";
      uses ospf-redistribute-grouping;
    }
    list ospf {
      description
        "Open Shortest Path First (OSPF)";
      key "id";
      leaf id {
        type uint32 {
          range "1 .. 65535";
        }
      }
      uses ospf-redistribute-top-match-grouping;
      uses ospf-redistribute-match-grouping;
      leaf vrf {
        description
          "VPN Routing/Forwarding Instance";
        type string;
      }
    }
    list ospfv3 {
      description
        "OSPFv3";
      key "id";
      leaf id {
        type uint32 {
          range "1 .. 65535";
        }
      }
      uses ospf-redistribute-top-match-grouping;
      uses ospf-redistribute-match-grouping;
    }
    list rip {
      description
        "Routing Information Protocol (RIP)";
      key "id";
      leaf id {
        description
          "User selected string identifying this rip process";
        type string;
      }
      uses ospf-redistribute-grouping;
    }
    container static {
      description
        "Static routes";
      presence "Static routes";
      uses ospf-redistribute-grouping;
    }
  }

  grouping queue-depth-grouping {
    leaf options {
      type union {
        type uint32 {
          range "1 .. 2147483647";
        }
        type enumeration {
          enum "unlimited";
        }
      }
    }
  }

  grouping ospf-area-virtual-link-grouping {
    uses ios-ospf:ospf-authentication-key-grouping;
    list message-digest-key {
      description
        "Set message digest key";
      key "id";
      leaf id {
        type uint8 {
          range "1 .. 255";
        }
      }
      container md5 {
        description
          "Use MD5 algorithm";
        leaf auth-type {
          type uint8 {
            range "0 .. 7";
          }
        }
        leaf auth-key {
          type string {
            length "1 .. 16";
          }
        }
      }
    }
  }

  grouping ospfv3-af-ipv4-summary-prefix-grouping {
    list summary-prefix {
      key "prefix";
      leaf prefix {
        type inet:ipv4-prefix;
      }
      choice tag-no-advertise-choice {
        leaf nssa-only {
          type empty;
        }
        leaf tag {
          type uint32 {
            range "0 .. 4294967295";
          }
        }
        leaf not-advertise {
          type empty;
        }
      }
    }
  }

  grouping ospfv3-af-ipv6-summary-prefix-grouping {
    list summary-prefix {
      description
        "Configure IPv6 summary prefix";
      key "prefix";
      leaf prefix {
        type ios-types:ipv6-prefix;
      }
      choice tag-no-advertise-choice {
        leaf nssa-only {
          description
            "Limit summary to NSSA areas";
          type empty;
        }
        leaf tag {
          description
            "Set tag";
          type uint32 {
            range "0 .. 4294967295";
          }
        }
        leaf not-advertise {
          description
            "Do not advertise when translating OSPF type-7 LSA";
          type empty;
        }
      }
    }
  }

  grouping ospfv3-grouping {
    container authentication {
      description
        "Authentication parameters";
      leaf mode {
        description
          "Authentication operation mode";
        type enumeration {
          enum "deployment";
          enum "strict";
        }
      }
    }
    container graceful-restart {
      description
        "Graceful-restart options";
      presence "true";
      container helper {
        description
          "helper support";
        presence "true";
        leaf disable {
          description
            "disable helper support";
          type empty;
        }
        leaf strict-lsa-checking {
          description
            "enable helper strict LSA checking";
          type empty;
        }
      }
      leaf restart-interval {
        description
          "Graceful restart interval";
        type uint16;
      }
    }
    container manet {
      description
        "Specify MANET OSPF parameters";
      container cache {
        description
          "Specify MANET cache sizes";
        leaf acknowledgement {
          description
            "Specify MANET acknowledgement cache size";
          type uint64 {
            range "0..4294967295";
          }
        }
        leaf update {
          description
            "Specify MANET LSA cache size";
          type uint64 {
            range "0..4294967295";
          }
        }
      }
      leaf hello {
        description
          "Unicast Hellos rather than multicast";
        type enumeration {
          enum "unicast";
        }
      }
      container peering {
        description
          "MANET OSPF Smart Peering";
        container selective {
          description
            "Enable selective peering";
          leaf disable {
            description
              "Disable selective peering";
            type empty;
          }
          leaf per-interface {
            description
              "Select peers per interface rather than per node";
            type empty;
          }
          leaf redundancy {
            description
              "Redundant paths";
            type uint8;
          }
        }
      }
      leaf willingness {
        description
          "Specify Relay willingness value";
        type uint8 {
          range "0..255";
        }
      }
    }
  }

  grouping ospfv3-address-family-grouping {
    container authentication {
      description
        "Authentication parameters";
      leaf mode {
        description
          "Authentication operation mode";
        type enumeration {
          enum "deployment";
          enum "normal";
          enum "strict";
        }
      }
    }
    container graceful-restart {
      description
        "Graceful-restart options";
      presence "true";
      leaf disable {
        description
          "Graceful restart disable";
        type empty;
      }
      container helper {
        description
          "helper support";
        presence "true";
        leaf disable {
          description
            "disable helper support";
          type empty;
        }
        leaf strict-lsa-checking {
          description
            "enable helper strict LSA checking";
          type empty;
        }
      }
      leaf restart-interval {
        description
          "Graceful restart interval";
        type uint16;
      }
    }
    container manet {
      description
        "Specify MANET OSPF parameters";
      container cache {
        description
          "Specify MANET cache sizes";
        leaf acknowledgement {
          description
            "Specify MANET acknowledgement cache size";
          type uint64 {
            range "0..4294967295";
          }
        }
        leaf update {
          description
            "Specify MANET LSA cache size";
          type uint64 {
            range "0..4294967295";
          }
        }
      }
      leaf hello {
        description
          "Unicast Hellos rather than multicast";
        type enumeration {
          enum "unicast";
          enum "multicast";
        }
      }
      container peering {
        description
          "MANET OSPF Smart Peering";
        container selective {
          description
            "Enable selective peering";
          leaf disable {
            description
              "Disable selective peering";
            type empty;
          }
          leaf per-interface {
            description
              "Select peers per interface rather than per node";
            type empty;
          }
          leaf redundancy {
            description
              "Redundant paths";
            type uint8;
          }
        }
      }
      leaf willingness {
        description
          "Specify Relay willingness value";
        type uint8 {
          range "0..255";
        }
      }
    }
  }

  grouping config-router-ospfv3-grouping {
    list ospfv3 { 
      description
        "OSPFv3";
      key "id";
      leaf id {
        type uint16 {
          range "1..65535";
        }
      }
      uses ios-ospf:ospf-ospfv3-common-grouping;
      uses ospfv3-grouping;
      // router ospfv3 * / address-family
      container address-family {
        description
          "Enter Address Family command mode";
        container ipv4 {
          description
            "IPv4 Address family";
          container unicast {
            description
              "Address Family Modifier";
            presence "true";
            uses ios-ospf:ospf-ospfv3-common-grouping;
            uses ios-ospf:ospf-ospfv3-common-address-family-grouping;
            uses ospfv3-address-family-grouping;
            uses ospfv3-af-ipv4-summary-prefix-grouping;
          }
          list vrf {
            description
              "Specify parameters for a VPN Routing/Forwarding instance";
            key "vrf";
            leaf vrf {
              type string;
            }
            leaf unicast {
              type empty;
            }
            uses ios-ospf:ospf-ospfv3-common-grouping;
            uses ios-ospf:ospf-ospfv3-common-address-family-grouping;
            uses ospfv3-address-family-grouping;
            uses ospfv3-af-ipv4-summary-prefix-grouping;
          }
        }
        container ipv6 {
          description
            "IPv6 Address family";
          container unicast {
            presence "true";
            uses ios-ospf:ospf-ospfv3-common-grouping;
            uses ios-ospf:ospf-ospfv3-common-address-family-grouping;
            uses ospfv3-address-family-grouping;
            uses ospfv3-af-ipv6-summary-prefix-grouping;
          }
          list vrf {
            description
              "Specify parameters for a VPN Routing/Forwarding instance";
            key "vrf";
            leaf vrf {
              type string;
            }
            leaf unicast {
              type empty;
            }
            
            uses ios-ospf:ospf-ospfv3-common-grouping;
            uses ios-ospf:ospf-ospfv3-common-address-family-grouping;
            uses ospfv3-address-family-grouping;
            uses ospfv3-af-ipv6-summary-prefix-grouping;
          }
        }
      }
    }
  }

  /////////////////////////////////////////////////////////
  // router / ospfv3
  /////////////////////////////////////////////////////////
  augment "/ios:native/ios:router" {
    uses config-router-ospfv3-grouping;
  }

  /////////////////////////////////////////////////////////
  // native / interface *
  /////////////////////////////////////////////////////////
  augment "/ios:native/ios:interface/ios:FastEthernet" {
    uses config-interface-ospfv3-grouping;
  }

  augment "/ios:native/ios:interface/ios:GigabitEthernet" {
    uses config-interface-ospfv3-grouping;
  }

  augment "/ios:native/ios:interface/ios:TenGigabitEthernet" {
    uses config-interface-ospfv3-grouping;
  }

  augment "/ios:native/ios:interface/ios:Port-channel" {
    uses config-interface-ospfv3-grouping;
  }

  augment "/ios:native/ios:interface/ios:Loopback" {
    uses config-interface-ospfv3-grouping;
  }

  augment "/ios:native/ios:interface/ios:Tunnel" {
    uses config-interface-ospfv3-grouping;
  }
}
