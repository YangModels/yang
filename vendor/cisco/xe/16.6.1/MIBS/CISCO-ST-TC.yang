/*
 * Generated by confdc --mib2yang-std
 * Source: mgmt/dmi/model/common/mib-source/CISCO-ST-TC.mib
 */
/*
 * This YANG module has been generated by smidump 0.5.0:
 *
 *      smidump -f yang CISCO-ST-TC
 *
 * Do not edit. Edit the source file instead!
 */

module CISCO-ST-TC {

  namespace "urn:ietf:params:xml:ns:yang:smiv2:CISCO-ST-TC";
  prefix CISCO-ST-TC;

  import ietf-yang-smiv2 {
    prefix "smiv2";
  }

  organization
   "Cisco Systems, Inc.";

  contact
   "Cisco Systems
    Customer Service
    Postal: 170 W Tasman Drive
    San Jose, CA  95134
    USA
    Tel: +1 800 553 -NETS
    E-mail: cs-san@cisco.com";

  description
   "This module defines textual conventions used in
    Storage Area Network technology specific mibs.";

  revision 2012-08-08 {
    description
     "Added sixteenG and automaxSixteenG in fcIfSpeed";
  }

  revision 2011-07-26 {
    description
     "-Added following enum to FcIfSpeed:
      autoMaxEightG.";
  }

  revision 2010-12-24 {
    description
     "-Added following enums to FcIfSpeed:
      autoMax4G, eightG and tenG.";
  }

  revision 2008-05-16 {
    description
     "-Added following enums to FcPortTypes
      TEXTUAL CONVENTION
      npPort, tfPort, tnpPort
      -Added following enums to InterfaceOperMode 
      TEXTUAL CONVENTION.
      npPort, tfPort, tnpPort
      -Added following enums to FcPortModuleTypes
      TEXTUAL CONVENTION
      sfpDwdm, qsfp, x2Dwdm
      - Updated the description of the following objects:
      FcPortTxTypes,
      FcNameId.";
  }

  revision 2005-12-17 {
    description
     "- Added following TCs
      FcIfSfpDiagLevelType 
      FcIfServiceStateType
      - Added following enums in FcPortModuleTypes
      xfp, x2Short, x2Medium, x2Tall, xpakShort, 
      xpakMedium, xpakTall and xenpak. 
      - Added following enums in FcPortTxTypes. 
      tenGigBaseSr, tenGigBaseLr, tenGigBaseEr, 
      tenGigBaseLx4, tenGigBaseSw, tenGigBaseLw, 
      tenGigBaseEw. 
      - Added following enums in FcIfSpeed 
      fourG and autoMaxTwoG.";
  }

  revision 2004-05-18 {
    description
     "Added new textual convention 'InterfaceOperMode'.";
  }

  revision 2003-09-26 {
    description
     "Obtained the OID for this MIB.";
  }

  revision 2003-08-07 {
    description
     "Added stPort(15) to FcPortTypes.";
  }

  revision 2002-10-04 {
    description
     "Added fvPort and portOperDown to FcPortTypes.
      Added FcAddress and FcAddressType.";
  }

  revision 2002-09-24 {
    description
     "Initial version of this MIB module.";
  }

  typedef VsanIndex {
    type int32 {
      range "1..4094";
    }
    description
     "The VSAN id of a VSAN which uniquely identifies
      a VSAN within a fabric. VSAN id is 12-bit 
      wide; so theoretically, 4096 VSANs can be defined in 
      a fabric and this device can be part of. However, VSAN 
      numbers 0 , 4094 and 4095 are reserved.";
  }

  typedef DomainId {
    type int32 {
      range "1..239";
    }
    description
     "The Domain Id of the switch. This is assigned
      dynamically if the Domain Manager is enabled on 
      the switch or could be configured statically by 
      the user.";
  }

  typedef DomainIdOrZero {
    type int32 {
      range "0..239";
    }
    description
     "The Textual convention is an extension to
      textual convetion 'DomainId'. It includes 
      the value '0'in addition the range 1-239.
      Value '0' indicates that Domain Id has  
      been neither configured nor assigned.";
  }

  typedef FcAddressId {
    type binary {
      length "3";
    }
    description
     "Represents Fibre Channel Address ID, a 24-bit
      value unique within the address space of a Fabric.";
  }

  typedef FcNameId {
    type binary {
      length "8";
    }
    description
     "Represents the World Wide Name (WWN) associated with
      a Fibre Channel (FC) entity. A WWN is a 64 bit address
      to uniquely identify each entity within a Fibre Channel
      fabric.";
    reference
     "Fibre Channel Framing and Signaling (FC-FS) Rev 1.70
      - Section 14 Name_Indentifier Formats.";
  }

  typedef FcNameIdOrZero {
    type binary {
      length "0|8|16";
    }
    description
     "The World Wide Name (WWN) associated with a Fibre Channel
      (FC) entity.  WWNs were initially defined as 64-bits in
      length.  The latest definition (for future use) is 128-bits
      long.  The zero-length string value is used in circumstances
      where the WWN is unassigned/unknown.";
  }

  typedef FcClassOfServices {
    type bits {
      bit classF {
        position "0";
      }
      bit class1 {
        position "1";
      }
      bit class2 {
        position "2";
      }
      bit class3 {
        position "3";
      }
      bit class4 {
        position "4";
      }
      bit class5 {
        position "5";
      }
      bit class6 {
        position "6";
      }
    }
    description
     "Represents the class of service capability of an
      NxPort or FxPort.";
  }

  typedef FcPortTypes {
    type enumeration {
      enum "auto" {
        value "1";
      }
      enum "fPort" {
        value "2";
      }
      enum "flPort" {
        value "3";
      }
      enum "ePort" {
        value "4";
      }
      enum "bPort" {
        value "5";
      }
      enum "fxPort" {
        value "6";
      }
      enum "sdPort" {
        value "7";
      }
      enum "tlPort" {
        value "8";
      }
      enum "nPort" {
        value "9";
      }
      enum "nlPort" {
        value "10";
      }
      enum "nxPort" {
        value "11";
      }
      enum "tePort" {
        value "12";
      }
      enum "fvPort" {
        value "13";
      }
      enum "portOperDown" {
        value "14";
      }
      enum "stPort" {
        value "15";
      }
      enum "npPort" {
        value "16";
      }
      enum "tfPort" {
        value "17";
      }
      enum "tnpPort" {
        value "18";
      }
    }
    description
     "Represents fibre channel port types:
      auto (1)   - Mode is determined by port initialization 
                  scheme.
      fPort (2)  - Fibre channel fabric port. 
      flPort (3) - Fibre channel arbitrated loop port.
      ePort (4)  - Fabric Expansion port.
      bPort (5)  - Bridging port.
      fxPort (6) - This port can only be f_port or fl_port.
      sdPort (7) - SPAN destination port. SD_ports transmit 
                  traffic copied from one or more source ports
                  for monitoring purposes.        
      tlPort (8) - Translation loop port.
      nPort (9)   - Fibre channel N port.
      nlPort (10) - Fibre channel NL port.
      nxPort (11) - This port can only be n_port or nl_port.
      
        -- read only port types.
      tePort (12) - Trunking e_port.
                   Note: A port which is administratively set
                   to 'ePort', will operationally have type
                   'tePort' if fcIfOperTrunkMode has the value
                   'trunk'.
      fvPort (13) - Virtual Port.
      portOperDown (14) - port operationally down
                          If a port is operationally down, the
                          port mode is unknown. In such cases
                          the operational port mode is shown 
                          as 'portOperDown'. 
      stPort (15) - SPAN Tunnel destination port.
      npPort (16) - N Proxy port mode applicable only to N-port
                    Virtualizer (NPV)
      tfPort (17) - Trunking fibre channel fabric port.
      tnpPort (18) - Trunking N Proxy port mode applicable only
                    to N-port Virtualizer (NPV).";
  }

  typedef FcPortTxTypes {
    type enumeration {
      enum "unknown" {
        value "1";
      }
      enum "longWaveLaser" {
        value "2";
      }
      enum "shortWaveLaser" {
        value "3";
      }
      enum "longWaveLaserCostReduced" {
        value "4";
      }
      enum "electrical" {
        value "5";
      }
      enum "tenGigBaseSr" {
        value "6";
      }
      enum "tenGigBaseLr" {
        value "7";
      }
      enum "tenGigBaseEr" {
        value "8";
      }
      enum "tenGigBaseLx4" {
        value "9";
      }
      enum "tenGigBaseSw" {
        value "10";
      }
      enum "tenGigBaseLw" {
        value "11";
      }
      enum "tenGigBaseEw" {
        value "12";
      }
    }
    description
     "Represents port transciever technology types.
      unknown (1) - unknown
      longWaveLaser (2) - 1550nm laser
      shortWaveLaser (3) - 850nm laser
      longWaveLaserCostReduced (4) - 1310nm laser
      electrical (5) - electrical 
      tenGigBaseSr (6)  - 10GBASE-SR 850nm laser
      tenGigBaseLr (7)  - 10GBASE-LR 1310nm laser
      tenGigBaseEr (8)  - 10GBASE-ER 1550nm laser
      tenGigBaseLx4 (9) - 10GBASE-LX4 WWDM 1300nm laser
      tenGigBaseSw (10)  - 850nm laser
      tenGigBaseLw (11) - 1310nm laser
      tenGigBaseEw (12) - 1550nm laser
      .";
    reference
     "IEEE Std 802.3-2005 carrier sense multiple access 
      with collision detection (CSMA/CD) access method 
      and physical layer specification.";
  }

  typedef FcPortModuleTypes {
    type enumeration {
      enum "unknown" {
        value "1";
      }
      enum "other" {
        value "2";
      }
      enum "gbic" {
        value "3";
      }
      enum "embedded" {
        value "4";
      }
      enum "glm" {
        value "5";
      }
      enum "gbicWithSerialID" {
        value "6";
      }
      enum "gbicWithoutSerialID" {
        value "7";
      }
      enum "sfpWithSerialID" {
        value "8";
      }
      enum "sfpWithoutSerialID" {
        value "9";
      }
      enum "xfp" {
        value "10";
      }
      enum "x2Short" {
        value "11";
      }
      enum "x2Medium" {
        value "12";
      }
      enum "x2Tall" {
        value "13";
      }
      enum "xpakShort" {
        value "14";
      }
      enum "xpakMedium" {
        value "15";
      }
      enum "xpakTall" {
        value "16";
      }
      enum "xenpak" {
        value "17";
      }
      enum "sfpDwdm" {
        value "18";
      }
      enum "qsfp" {
        value "19";
      }
      enum "x2Dwdm" {
        value "20";
      }
    }
    description
     "Represents module type of the port connector. This
      object refers to the hardware implementation of the port.
      The enums are defined as per FC-GS-4 standard.
      unknown             (1) - unknown
      other               (2) - other
      gbic                (3) - gbic (gigabit interface card)
      embedded            (4) - gbic is part of the line card 
                                and is unremovable
      glm                 (5) - if its a gigabit link module 
                                (GLM). A GLM has a different 
                                form factor than GBIC. GLM is 
                                not supported by our switch.
      gbicWithSerialID    (6) - If GBIC serial id can be read
      gbicWithoutSerialID (7) - If GBIC serial id cannot be read
      sfpWithSerialID     (8) - If small form factor (SFP) 
                                pluggable GBICs serial id can 
                                be read
      sfpWithoutSerialID  (9) - If small form factor (SFP) 
                                pluggable GBICs serial id 
                                cannot be read
      The following enums are module types for 10 gigabit small 
      form factor pluggable sfp port connectors.
      xfp                (10) - xfp 
      x2Short            (11) - x2 short 
      x2Medium           (12) - x2 medium
      x2Tall             (13) - x2 tall
      xpakShort          (14) - xpak short
      xpakMedium         (15) - xpak medium
      xpakTall           (16) - xpak tall
      xenpak             (17) - xenpak
      sfpDwdm            (18) - DWDM SFP type
      qsfp               (19) - Quad small form-factor (QSFP) 
                                                        pluggable type
      x2Dwdm             (20) - x2 DWDM
      .";
  }

  typedef FcIfSpeed {
    type enumeration {
      enum "auto" {
        value "1";
      }
      enum "oneG" {
        value "2";
      }
      enum "twoG" {
        value "3";
      }
      enum "fourG" {
        value "4";
      }
      enum "autoMaxTwoG" {
        value "5";
      }
      enum "eightG" {
        value "6";
      }
      enum "autoMaxFourG" {
        value "7";
      }
      enum "tenG" {
        value "8";
      }
      enum "autoMaxEightG" {
        value "9";
      }
      enum "sixteenG" {
        value "10";
      }
      enum "autoMaxSixteenG" {
        value "11";
      }
    }
    description
     "Represents the speed of a fibre channel port.
      Following are the meanings of the enumerated values:
        auto      (1) - Negotiate to determine the speed 
                        automatically.
        oneG      (2) - 1Gbit 
        twoG      (3) - 2Gbit
        fourG     (4) - 4Gbit 
        autoMaxTwoG (5)  - Negotiate to determine the 
                           speed automatically upto a 
                           maximum of 2Gbit.
        eightG    (6) - 8Gbit
        autoMaxFourG (7) - Negotiate to determine the
                           speed automatically upto a
                           maximum of 4Gbit.          
        tenG      (8) - 10GBit.
        autoMaxEightG (9) - Negotiate to determine the
                           speed automatically upto a
                           maximum of 8Gbit.
        sixteenG  (10) - 16GBit.
        autoMaxSixteenG (11) - Negotiate to determine the
                           speed automatically upto a
                           maximum of 16Gbit.";
  }

  typedef PortMemberList {
    type binary {
      length "0..64";
    }
    description
     "A list of ifIndex's of the ports that are members of
      this list.
      
      The value of this object is a concatenation of zero or
      more 4-octet strings, where each 4-octet string contains
      a 32-bit ifIndex value in network byte order.
      
      A zero length string value means this list has no
      members.";
  }

  typedef FcAddress {
    type binary {
      length "3|8";
    }
    description
     "Represents either the Fibre Channel Address ID or
      the World Wide Name associated with a Fibre
      Channel (FC) Entity.";
  }

  typedef FcAddressType {
    type enumeration {
      enum "wwn" {
        value "1";
      }
      enum "fcid" {
        value "2";
      }
    }
    description
     "Denotes if a Fibre Channel Address is
      a World Wide Name (WWN) or a Fibre
      Channel Address ID (FCID).
      wwn(1) - address is WWN.
      fcid(2) - address is FCID.";
  }

  typedef InterfaceOperMode {
    type enumeration {
      enum "auto" {
        value "1";
      }
      enum "fPort" {
        value "2";
      }
      enum "flPort" {
        value "3";
      }
      enum "ePort" {
        value "4";
      }
      enum "bPort" {
        value "5";
      }
      enum "fxPort" {
        value "6";
      }
      enum "sdPort" {
        value "7";
      }
      enum "tlPort" {
        value "8";
      }
      enum "nPort" {
        value "9";
      }
      enum "nlPort" {
        value "10";
      }
      enum "nxPort" {
        value "11";
      }
      enum "tePort" {
        value "12";
      }
      enum "fvPort" {
        value "13";
      }
      enum "portOperDown" {
        value "14";
      }
      enum "stPort" {
        value "15";
      }
      enum "mgmtPort" {
        value "16";
      }
      enum "ipsPort" {
        value "17";
      }
      enum "evPort" {
        value "18";
      }
      enum "npPort" {
        value "19";
      }
      enum "tfPort" {
        value "20";
      }
      enum "tnpPort" {
        value "21";
      }
    }
    description
     "Represents the operational mode of an interface
      auto (1) - Mode is determined by port initialization
                 scheme.
      fPort (2) - Fibre channel fabric port.
      flPort (3) - Fibre channel arbitrated loop port.
      ePort (4)  - Fabric Expansion port.
      bPort (5)  - Bridging port.
      fxPort (6) - This port can only be f_port or fl_port.
      sdPort (7) - SPAN destination port. SD_ports transmit
                   traffic copied from one or more source
                   ports for monitoring purposes.
      tlPort (8) - Translation loop port.
      nPort (9)   - Fibre channel N port.
      nlPort (10) - Fibre channel NL port.
      nxPort (11) - This port can only be n_port or nl_port.
      
      -- read only port types.
      tePort (12) - Trunking e_port.
                Note: A port which is administratively set
                to 'ePort', will operationally have type
                'tePort' if fcIfOperTrunkMode has the value
                'trunk'.
      fvPort (13) - Virtual Port.
      portOperDown (14) - port operationally down
                        If a port is operationally down, the
                        port mode is unknown. In such cases
                        the operational port mode is shown
                        as 'portOperDown'.
      stPort (15) - SPAN Tunnel destination port.
      mgmtPort(16) - Mgmt Port.
      ipsPort(17) - Ethernet Port.
      evPort(18) - FCIP tunnels on Ethernet ports.
      npPort (19) - N Proxy port mode applicable only 
                    to N-port Virtualizer (NPV).
      tfPort (20) - Trunking fibre channel fabric port.
      tnpPort (21) - Trunking N Proxy port mode applicable only
                            to N-port Virtualizer (NPV).";
  }

  typedef FcIfServiceStateType {
    type enumeration {
      enum "inService" {
        value "1";
      }
      enum "outOfService" {
        value "2";
      }
    }
    description
     "Represents the service state of a Fibre Channel
      interface. Following are the meanings of the 
      enumerated values:
      
      inService    (1) - interface is in service and is
                    allowed to become operational.
      outOfService (2) - interface is removed from service 
                    and is not allowed to become 
                    operational.";
  }

  typedef FcIfSfpDiagLevelType {
    type enumeration {
      enum "unknown" {
        value "1";
      }
      enum "normal" {
        value "2";
      }
      enum "lowWarning" {
        value "3";
      }
      enum "lowAlarm" {
        value "4";
      }
      enum "highWarning" {
        value "5";
      }
      enum "highAlarm" {
        value "6";
      }
    }
    description
     "Represents the severity level of the SFP
      diagnostic information of an interface for 
      temperature, voltage, current, optical 
      transmit and receive power.";
  }

  smiv2:alias "storageTextualConventions" {
    smiv2:oid "1.3.6.1.4.1.9.12.4";
  }

}
