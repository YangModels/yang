/*
 * Generated by confdc --mib2yang-std
 * Source: mgmt/dmi/model/common/mib-source/CISCO-IETF-BFD-MIB.mib
 */
/*
 * This YANG module has been generated by smidump 0.5.0:
 *
 *      smidump -f yang CISCO-IETF-BFD-MIB
 *
 * Do not edit. Edit the source file instead!
 */

module CISCO-IETF-BFD-MIB {

  namespace "urn:ietf:params:xml:ns:yang:smiv2:CISCO-IETF-BFD-MIB";
  prefix CISCO-IETF-BFD-MIB;

  import IF-MIB {
    prefix "if-mib";
  }

  import INET-ADDRESS-MIB {
    prefix "inet-address";
  }

  import SNMPv2-TC {
    prefix "snmpv2-tc";
  }

  import ietf-inet-types {
    prefix "inet";
  }

  import ietf-yang-smiv2 {
    prefix "smiv2";
  }

  import ietf-yang-types {
    prefix "yang";
  }

  organization
   "IETF";

  contact
   "Zafar Ali
    Cisco Systems, Inc. 
    Email:  zali@cisco.com
    
    A S Kiran Koushik
    Cisco Systems, Inc.
    Email: kkoushik@cisco.com
    
    Nobo Akiya
    Cisco Systems, G.K.
    Email: nobo@cisco.com";

  description
   "This document contains the Management information base for
    Bidirectional Forwarding Detection(BFD) Protocol as defined
    in draft-ietf-bfd-base-06.txt.
    
    BFD is a protocol intended to detect faults in the
    bidirectional path between two forwarding engines, including
    interfaces, data link(s), and to the extent possible the forwarding
    engines themselves, with potentially very low latency.  It operates
    independently of media, data protocols, and routing protocols.
    
    This MIB module is based on the Internet Draft
    draft-ietf-bfd-mib-03.txt and draft-ietf-bfd-mib-04.txt";

  revision 2011-04-16 {
    description
     "[Revision added by libsmi due to a LAST-UPDATED clause.]";
  }

  revision 2011-03-14 {
    description
     "Modify value for 'ciscoBfdSessRemoteDiscr' and
      'CiscoBfdInterval' to allow value 0 to conform to latest draft,
      draft-ietf-bfd-mib-10.txt.";
  }

  revision 2010-02-18 {
    description
     "Modify value for ciscoBfdDiag textual convention to conform to
      latest draft-ietf-bfd-mib-07.txt";
  }

  revision 2008-04-24 {
    description
     "Revised version includes support for draft-ietf-bfd-mib-03.txt
      and draft-ietf-bfd-mib-04.txt. In addition to small description
      changes made throughout this MIB, following changes are made:
      * ciscoBfdObjects.ciscoBfdSessTable.ciscoBfdSessEntry
          - ciscoBfdSessState : failing state added
          - ciscoBfdSessVersionNumber : new object added
          - ciscoBfdSessType : new object added
          - ciscoBfdSessInterface : new object added
      * ciscoBfdObjects
          - ciscoBfdSessDiscMapTable : new table added
          - ciscoBfdSessIpMapTable : new table added
      * ciscoBfdComformance
          - ciscoBfdSessGroup : object group deprecated
          - ciscoBfdSess03Group : new object group added
          - ciscoBfdSess04Group : new object group added
          - ciscoBfdSess0304Group : new object group added
      * ciscoBfdCompliances
          - ciscoBfdModuleFullCompliance : module compliance deprecated
          - ciscoBfdModuleFullComplianceRev2 : new module compliance added";
  }

  revision 2007-06-04 {
    description
     "Initial version based on draft-ietf-bfd-mib-03.txt";
  }

  typedef CiscoBfdSessIndexTC {
    type uint32 {
      range "1..4294967295";
    }
    description
     "An index used to uniquely identify BFD sessions.";
    smiv2:display-hint "d";
  }

  typedef CiscoBfdInterval {
    type uint32 {
      range "0..4294967295";
    }
    description
     "The BFD interval delay in microseconds.";
  }

  typedef CiscoBfdDiag {
    type enumeration {
      enum "noDiagnostic" {
        value "0";
      }
      enum "controlDetectionTimeExpired" {
        value "1";
      }
      enum "echoFunctionFailed" {
        value "2";
      }
      enum "neighborSignaledSessionDown" {
        value "3";
      }
      enum "forwardingPlaneReset" {
        value "4";
      }
      enum "pathDown" {
        value "5";
      }
      enum "concatenatedPathDown" {
        value "6";
      }
      enum "administrativelyDown" {
        value "7";
      }
      enum "reverseConcatenatedPathDown" {
        value "8";
      }
    }
    description
     "A common BFD diagnostic code.";
  }


  container CISCO-IETF-BFD-MIB {
    config false;

    container ciscoBfdScalarObjects {
      smiv2:oid "1.3.6.1.4.1.9.10.137.1.1";

      leaf ciscoBfdAdminStatus {
        type enumeration {
          enum "enabled" {
            value "1";
          }
          enum "disabled" {
            value "2";
          }
        }
        description
         "The global administrative status of BFD in this router.
          The value 'enabled' denotes that the BFD Process is 
          active on at least one interface; 'disabled' disables  
          it on all interfaces.";
        smiv2:defval "enabled";
        smiv2:max-access "read-write";
        smiv2:oid "1.3.6.1.4.1.9.10.137.1.1.1";
      }

      leaf ciscoBfdVersionNumber {
        type uint32;
        description
         "The current version number of the BFD protocol.";
        reference
         "BFD Version 0 (draft-katz-ward-bfd-02.txt)";
        smiv2:defval "0";
        smiv2:max-access "read-only";
        smiv2:oid "1.3.6.1.4.1.9.10.137.1.1.3";
      }

      leaf ciscoBfdSessNotificationsEnable {
        type boolean;
        description
         "If this object is set to true(1), then it enables
          the emission of ciscoBfdSessUp and ciscoBfdSessDown 
          notifications; otherwise these notifications are not 
          emitted.";
        reference
         "See also RFC3413 for explanation that  
          notifications are under the ultimate control of the  
          MIB modules in this document.";
        smiv2:defval "false";
        smiv2:max-access "read-write";
        smiv2:oid "1.3.6.1.4.1.9.10.137.1.1.4";
      }
    }

    container ciscoBfdSessTable {
      description
       "The BFD Session Table describes the BFD sessions.";
      reference
       "BFD Version 0 (draft-katz-ward-ciscoBfd-02.txt)";
      smiv2:oid "1.3.6.1.4.1.9.10.137.1.2";

      list ciscoBfdSessEntry {
        key "ciscoBfdSessIndex";
        description
         "The BFD Session Entry describes BFD session.";
        smiv2:oid "1.3.6.1.4.1.9.10.137.1.2.1";

        leaf ciscoBfdSessIndex {
          type CISCO-IETF-BFD-MIB:CiscoBfdSessIndexTC;
          description
           "This object contains an index used to represent a
            unique BFD session on this device.";
          smiv2:max-access "not-accessible";
          smiv2:oid "1.3.6.1.4.1.9.10.137.1.2.1.1";
        }

        leaf ciscoBfdSessApplicationId {
          type uint32;
          description
           "This object contains an index used to indicate
            a local application which owns or maintains this 
            BFD session. For instance, the MPLS VPN process may 
            maintain a subset of the total number of BFD 
            sessions.  This application ID provides a convenient 
            way to segregate sessions by the applications which 
            maintain them.";
          smiv2:max-access "read-only";
          smiv2:oid "1.3.6.1.4.1.9.10.137.1.2.1.2";
        }

        leaf ciscoBfdSessDiscriminator {
          type uint32 {
            range "1..4294967295";
          }
          description
           "This object specifies the local discriminator for this BFD
            session, used to uniquely identify it.";
          smiv2:max-access "read-only";
          smiv2:oid "1.3.6.1.4.1.9.10.137.1.2.1.3";
        }

        leaf ciscoBfdSessRemoteDiscr {
          type uint32 {
            range "0..4294967295";
          }
          description
           "This object specifies the session discriminator chosen
            by the remote system for this BFD session.";
          smiv2:max-access "read-only";
          smiv2:oid "1.3.6.1.4.1.9.10.137.1.2.1.4";
        }

        leaf ciscoBfdSessUdpPort {
          type inet:port-number;
          description
           "The destination UDP Port for BFD. The default value is
            the well-known value for this port. BFD State failing(5)
            is only applicable if this BFD session is running
            version 0";
          reference
           "draft-katz-ward-bfd-02.txt and 
            draft-raggarwa-mpls-bfd-00.txt";
          smiv2:defval "0";
          smiv2:max-access "read-write";
          smiv2:oid "1.3.6.1.4.1.9.10.137.1.2.1.5";
        }

        leaf ciscoBfdSessState {
          type enumeration {
            enum "adminDown" {
              value "1";
            }
            enum "down" {
              value "2";
            }
            enum "init" {
              value "3";
            }
            enum "up" {
              value "4";
            }
            enum "failing" {
              value "5";
            }
          }
          description
           "The perceived state of the BFD session.";
          smiv2:max-access "read-only";
          smiv2:oid "1.3.6.1.4.1.9.10.137.1.2.1.6";
        }

        leaf ciscoBfdSessRemoteHeardFlag {
          type boolean;
          description
           "This object specifies status of BFD packet reception from
            the remote system. Specifically, it is set to true(1) if 
            the local system is actively receiving BFD packets from the  
            remote system, and is set to false(0) if the local system  
            has not received BFD packets recently (within the detection  
            time) or if the local system is attempting to tear down 
            the BFD session.";
          smiv2:max-access "read-only";
          smiv2:oid "1.3.6.1.4.1.9.10.137.1.2.1.7";
        }

        leaf ciscoBfdSessDiag {
          type CISCO-IETF-BFD-MIB:CiscoBfdDiag;
          description
           "A diagnostic code specifying the local system's reason
            for the last transition of the session from up(1)  
            to some other state.";
          smiv2:max-access "read-only";
          smiv2:oid "1.3.6.1.4.1.9.10.137.1.2.1.8";
        }

        leaf ciscoBfdSessOperMode {
          type enumeration {
            enum "asyncModeWEchoFun" {
              value "1";
            }
            enum "asynchModeWOEchoFun" {
              value "2";
            }
            enum "demandModeWEchoFunction" {
              value "3";
            }
            enum "demandModeWOEchoFunction" {
              value "4";
            }
          }
          description
           "This object specifies current operating mode that BFD
            session is operating in.";
          smiv2:max-access "read-only";
          smiv2:oid "1.3.6.1.4.1.9.10.137.1.2.1.9";
        }

        leaf ciscoBfdSessDemandModeDesiredFlag {
          type boolean;
          description
           "This object indicates that the local system's
            desire to use Demand mode. Specifically, it is set  
            to true(1) if the local system wishes to use  
            Demand mode or false(0) if not";
          smiv2:defval "false";
          smiv2:max-access "read-write";
          smiv2:oid "1.3.6.1.4.1.9.10.137.1.2.1.10";
        }

        leaf ciscoBfdSessEchoFuncModeDesiredFlag {
          type boolean;
          description
           "This object indicates that the local system's
            desire to use Echo mode. Specifically, it is set  
            to true(1) if the local system wishes to use  
            Echo mode or false(0) if not";
          smiv2:defval "false";
          smiv2:max-access "read-write";
          smiv2:oid "1.3.6.1.4.1.9.10.137.1.2.1.11";
        }

        leaf ciscoBfdSessControlPlanIndepFlag {
          type boolean;
          description
           "This object indicates that the local system's
            ability to continue to function through a disruption of  
            the control plane. Specifically, it is set  
            to true(1) if the local system BFD implementation is 
            independent of the control plane. Otherwise, the  
            value is set to false(0)";
          smiv2:defval "false";
          smiv2:max-access "read-write";
          smiv2:oid "1.3.6.1.4.1.9.10.137.1.2.1.12";
        }

        leaf ciscoBfdSessAddrType {
          type inet-address:InetAddressType;
          description
           "This object specifies IP address type of the neighboring IP
            address which is being monitored with this BFD session.
            
            Only values unknown(0), ipv4(1) or ipv6(2) 
            have to be supported.  
            
            A value of unknown(0) is allowed only when  
            the outgoing interface is of type point-to-point, or 
            when the BFD session is not associated with a specific  
            interface. 
            
            If any other unsupported values are attempted in a set 
            operation, the agent MUST return an inconsistentValue  
            error.";
          smiv2:max-access "read-write";
          smiv2:oid "1.3.6.1.4.1.9.10.137.1.2.1.13";
        }

        leaf ciscoBfdSessAddr {
          type inet-address:InetAddress;
          description
           "This object specifies the neighboring IP address which is
            being monitored with this BFD session.
            It can also be used to enabled BFD on a specific  
            interface. The value is set to zero when BFD session is not  
            associated with a specific interface.";
          smiv2:max-access "read-write";
          smiv2:oid "1.3.6.1.4.1.9.10.137.1.2.1.14";
        }

        leaf ciscoBfdSessDesiredMinTxInterval {
          type CISCO-IETF-BFD-MIB:CiscoBfdInterval;
          description
           "This object specifies the minimum interval, in
            microseconds, that the local system would like to use when 
                 transmitting BFD Control packets.";
          smiv2:max-access "read-write";
          smiv2:oid "1.3.6.1.4.1.9.10.137.1.2.1.15";
        }

        leaf ciscoBfdSessReqMinRxInterval {
          type CISCO-IETF-BFD-MIB:CiscoBfdInterval;
          description
           "This object specifies the minimum interval, in
            microseconds, between received  BFD Control packets the  
            local system is capable of supporting.";
          smiv2:max-access "read-write";
          smiv2:oid "1.3.6.1.4.1.9.10.137.1.2.1.16";
        }

        leaf ciscoBfdSessReqMinEchoRxInterval {
          type CISCO-IETF-BFD-MIB:CiscoBfdInterval;
          description
           "This object specifies the minimum interval, in
            microseconds, between received BFD Echo packets that this 
            system is capable of supporting.";
          smiv2:max-access "read-write";
          smiv2:oid "1.3.6.1.4.1.9.10.137.1.2.1.17";
        }

        leaf ciscoBfdSessDetectMult {
          type uint32;
          description
           "This object specifies the Detect time multiplier.";
          smiv2:max-access "read-write";
          smiv2:oid "1.3.6.1.4.1.9.10.137.1.2.1.18";
        }

        leaf ciscoBfdSessStorType {
          type snmpv2-tc:StorageType;
          description
           "This variable indicates the storage type for this
            object. Conceptual rows having the value  
            'permanent' need not allow write-access to any  
            columnar objects in the row.";
          smiv2:max-access "read-write";
          smiv2:oid "1.3.6.1.4.1.9.10.137.1.2.1.19";
        }

        leaf ciscoBfdSessRowStatus {
          type snmpv2-tc:RowStatus;
          description
           "This variable is used to create, modify, and/or
            delete a row in this table. When a row in this 
            table has a row in the active(1) state, no  
            objects in this row can be modified except the 
            ciscoBfdSessRowStatus and ciscoBfdSessStorageType.";
          smiv2:max-access "read-write";
          smiv2:oid "1.3.6.1.4.1.9.10.137.1.2.1.20";
        }

        leaf ciscoBfdSessAuthPresFlag {
          type boolean;
          description
           "This object indicates that the local system's
            desire to use Authentication. Specifically, it is set  
            to true(1) if the local system wishes the session  
            to be authenticated or false(0) if not";
          smiv2:defval "false";
          smiv2:max-access "read-write";
          smiv2:oid "1.3.6.1.4.1.9.10.137.1.2.1.21";
        }

        leaf ciscoBfdSessAuthenticationType {
          type enumeration {
            enum "simplePassword" {
              value "1";
            }
            enum "keyedMD5" {
              value "2";
            }
            enum "meticulousKeyedMD5" {
              value "3";
            }
            enum "keyedSHA1" {
              value "4";
            }
            enum "meticulousKeyedSHA1" {
              value "5";
            }
          }
          description
           "The Authentication Type used for this BFD session. This
            field is valid only when the Authentication Present bit is set";
          smiv2:max-access "read-write";
          smiv2:oid "1.3.6.1.4.1.9.10.137.1.2.1.22";
        }

        leaf ciscoBfdSessVersionNumber {
          type uint32;
          description
           "The version number of the BFD protocol that this session is
            running in.";
          reference
           "BFD Version 0 (draft-katz-ward-bfd-02.txt) and BFD Version
            1 (draft-ietf-bfd-base-07.txt)";
          smiv2:defval "0";
          smiv2:max-access "read-only";
          smiv2:oid "1.3.6.1.4.1.9.10.137.1.2.1.23";
        }

        leaf ciscoBfdSessType {
          type enumeration {
            enum "singleHop" {
              value "1";
            }
            enum "multiHop" {
              value "2";
            }
          }
          description
           "The type of this BFD session.";
          smiv2:max-access "read-only";
          smiv2:oid "1.3.6.1.4.1.9.10.137.1.2.1.24";
        }

        leaf ciscoBfdSessInterface {
          type if-mib:InterfaceIndex;
          description
           "This object contains an interface index used to indicate
            the interface which this BFD session is running on.";
          smiv2:max-access "read-only";
          smiv2:oid "1.3.6.1.4.1.9.10.137.1.2.1.25";
        }
      }
    }

    container ciscoBfdSessMapTable {
      description
       "The BFD Session Mapping Table maps the complex
        indexing of the BFD sessions to the flat 
        CiscoBfdSessIndexTC used in the ciscoBfdSessTable.";
      reference
       "BFD Version 0 (draft-katz-ward-bfd-02.txt)";
      smiv2:oid "1.3.6.1.4.1.9.10.137.1.4";

      list ciscoBfdSessMapEntry {
        key "ciscoBfdSessApplicationId ciscoBfdSessDiscriminator ciscoBfdSessAddrType ciscoBfdSessAddr";
        description
         "The BFD Session Entry describes BFD session
          that is mapped to this index.";
        smiv2:oid "1.3.6.1.4.1.9.10.137.1.4.1";

        leaf ciscoBfdSessApplicationId {
          type leafref {
            path "/CISCO-IETF-BFD-MIB:CISCO-IETF-BFD-MIB/CISCO-IETF-BFD-MIB:ciscoBfdSessTable/CISCO-IETF-BFD-MIB:ciscoBfdSessEntry/CISCO-IETF-BFD-MIB:ciscoBfdSessApplicationId";
          }
        }

        leaf ciscoBfdSessDiscriminator {
          type leafref {
            path "/CISCO-IETF-BFD-MIB:CISCO-IETF-BFD-MIB/CISCO-IETF-BFD-MIB:ciscoBfdSessTable/CISCO-IETF-BFD-MIB:ciscoBfdSessEntry/CISCO-IETF-BFD-MIB:ciscoBfdSessDiscriminator";
          }
        }

        leaf ciscoBfdSessAddrType {
          type leafref {
            path "/CISCO-IETF-BFD-MIB:CISCO-IETF-BFD-MIB/CISCO-IETF-BFD-MIB:ciscoBfdSessTable/CISCO-IETF-BFD-MIB:ciscoBfdSessEntry/CISCO-IETF-BFD-MIB:ciscoBfdSessAddrType";
          }
        }

        leaf ciscoBfdSessAddr {
          type leafref {
            path "/CISCO-IETF-BFD-MIB:CISCO-IETF-BFD-MIB/CISCO-IETF-BFD-MIB:ciscoBfdSessTable/CISCO-IETF-BFD-MIB:ciscoBfdSessEntry/CISCO-IETF-BFD-MIB:ciscoBfdSessAddr";
          }
        }

        leaf ciscoBfdSessMapBfdIndex {
          type CISCO-IETF-BFD-MIB:CiscoBfdSessIndexTC;
          description
           "This object indicates the CiscoBfdSessIndexTC referred to
            by the indices of this row. In essence, a mapping is 
            provided between these indices and the ciscoBfdSessTable.";
          smiv2:max-access "read-only";
          smiv2:oid "1.3.6.1.4.1.9.10.137.1.4.1.1";
        }
      }
    }

    container ciscoBfdSessDiscMapTable {
      description
       "The BFD Session Discriminator Mapping Table maps a
        local discriminator value to associated BFD sessions'
        CiscoBfdSessIndexTC used in the ciscoBfdSessTable.";
      reference
       "BFD Version 0 (draft-katz-ward-bfd-02.txt)";
      smiv2:oid "1.3.6.1.4.1.9.10.137.1.5";

      list ciscoBfdSessDiscMapEntry {
        key "ciscoBfdSessDiscriminator";
        description
         "Each row contains a mapping between a local discriminator
          value to an entry in ciscoBfdSessTable.";
        smiv2:oid "1.3.6.1.4.1.9.10.137.1.5.1";

        leaf ciscoBfdSessDiscriminator {
          type leafref {
            path "/CISCO-IETF-BFD-MIB:CISCO-IETF-BFD-MIB/CISCO-IETF-BFD-MIB:ciscoBfdSessTable/CISCO-IETF-BFD-MIB:ciscoBfdSessEntry/CISCO-IETF-BFD-MIB:ciscoBfdSessDiscriminator";
          }
        }

        leaf ciscoBfdSessDiscMapIndex {
          type CISCO-IETF-BFD-MIB:CiscoBfdSessIndexTC;
          description
           "This object indicates the CiscoBfdSessIndexTC referred to by
            the index of this row. In essence, a mapping is 
            provided between this index and the ciscoBfdSessTable.";
          smiv2:max-access "read-only";
          smiv2:oid "1.3.6.1.4.1.9.10.137.1.5.1.1";
        }
      }
    }

    container ciscoBfdSessIpMapTable {
      description
       "The BFD Session IP Mapping Table maps given
        ciscoBfdSessInterface, ciscoBfdSessAddrType, and
        ciscoBbfdSessAddr to an associated BFD sessions'
        CiscoBfdSessIndexTC used in the ciscoBfdSessTable.
        This table SHOULD contains those BFD sessions are
        of IP type: singleHop(1) and multiHop(2).";
      reference
       "BFD Version 0 (draft-katz-ward-bfd-02.txt)";
      smiv2:oid "1.3.6.1.4.1.9.10.137.1.6";

      list ciscoBfdSessIpMapEntry {
        key "ciscoBfdSessInterface ciscoBfdSessAddrType ciscoBfdSessAddr";
        description
         "Each row contains a mapping between ciscoBfdSessInterface,
          ciscoBfdSessAddrType and ciscoBfdSessAddr values to an 
          entry in ciscoBfdSessTable.";
        smiv2:oid "1.3.6.1.4.1.9.10.137.1.6.1";

        leaf ciscoBfdSessInterface {
          type leafref {
            path "/CISCO-IETF-BFD-MIB:CISCO-IETF-BFD-MIB/CISCO-IETF-BFD-MIB:ciscoBfdSessTable/CISCO-IETF-BFD-MIB:ciscoBfdSessEntry/CISCO-IETF-BFD-MIB:ciscoBfdSessInterface";
          }
        }

        leaf ciscoBfdSessAddrType {
          type leafref {
            path "/CISCO-IETF-BFD-MIB:CISCO-IETF-BFD-MIB/CISCO-IETF-BFD-MIB:ciscoBfdSessTable/CISCO-IETF-BFD-MIB:ciscoBfdSessEntry/CISCO-IETF-BFD-MIB:ciscoBfdSessAddrType";
          }
        }

        leaf ciscoBfdSessAddr {
          type leafref {
            path "/CISCO-IETF-BFD-MIB:CISCO-IETF-BFD-MIB/CISCO-IETF-BFD-MIB:ciscoBfdSessTable/CISCO-IETF-BFD-MIB:ciscoBfdSessEntry/CISCO-IETF-BFD-MIB:ciscoBfdSessAddr";
          }
        }

        leaf ciscoBfdSessIpMapIndex {
          type CISCO-IETF-BFD-MIB:CiscoBfdSessIndexTC;
          description
           "This object indicates the CiscoBfdSessIndexTC referred to by
            the indices of this row. In essence, a mapping is 
            provided between these indices and an entry in ciscoBfdSessTable.";
          smiv2:max-access "read-only";
          smiv2:oid "1.3.6.1.4.1.9.10.137.1.6.1.1";
        }
      }
    }
  }

  smiv2:alias "ciscoBfdSessPerfTable" {
    description
     "This table specifies BFD Session performance counters.";
    smiv2:oid "1.3.6.1.4.1.9.10.137.1.3";
  }

  smiv2:alias "ciscoBfdSessPerfEntry" {
    description
     "An entry in this table is created by a BFD-enabled node for
      every BFD Session. ciscoBfdCounterDiscontinuityTime is used to  
      indicate potential discontinuity for all counter objects  
      in this table.";
    smiv2:oid "1.3.6.1.4.1.9.10.137.1.3.1";
  }

  augment "/CISCO-IETF-BFD-MIB:CISCO-IETF-BFD-MIB/CISCO-IETF-BFD-MIB:ciscoBfdSessTable/CISCO-IETF-BFD-MIB:ciscoBfdSessEntry" {
    description
     "An entry in this table is created by a BFD-enabled node for
      every BFD Session. ciscoBfdCounterDiscontinuityTime is used to  
      indicate potential discontinuity for all counter objects  
      in this table.";
    smiv2:oid "1.3.6.1.4.1.9.10.137.1.3.1";

    leaf ciscoBfdSessPerfPktIn {
      type yang:counter32;
      description
       "The total number of BFD messages received for this BFD
        session.";
      smiv2:max-access "read-only";
      smiv2:oid "1.3.6.1.4.1.9.10.137.1.3.1.1";
    }

    leaf ciscoBfdSessPerfPktOut {
      type yang:counter32;
      description
       "The total number of BFD messages sent for this BFD session.";
      smiv2:max-access "read-only";
      smiv2:oid "1.3.6.1.4.1.9.10.137.1.3.1.2";
    }

    leaf ciscoBfdSessUpTime {
      type yang:timestamp;
      description
       "The value of sysUpTime on the most recent occasion at which
        the session came up. If no such up event exists this object 
        contains a zero value.";
      smiv2:max-access "read-only";
      smiv2:oid "1.3.6.1.4.1.9.10.137.1.3.1.3";
    }

    leaf ciscoBfdSessPerfLastSessDownTime {
      type yang:timestamp;
      description
       "The value of sysUpTime on the most recent occasion at which
        the last time communication was lost with the neighbor. If  
        no such down event exist this object contains a zero value.";
      smiv2:max-access "read-only";
      smiv2:oid "1.3.6.1.4.1.9.10.137.1.3.1.4";
    }

    leaf ciscoBfdSessPerfLastCommLostDiag {
      type CISCO-IETF-BFD-MIB:CiscoBfdDiag;
      description
       "The BFD diag code for the last time communication was lost
        with the neighbor. If no such down event exists this object  
        contains a zero value.";
      smiv2:max-access "read-only";
      smiv2:oid "1.3.6.1.4.1.9.10.137.1.3.1.5";
    }

    leaf ciscoBfdSessPerfSessUpCount {
      type yang:counter32;
      description
       "The number of times this session has gone into the Up
        state since the router last rebooted.";
      smiv2:max-access "read-only";
      smiv2:oid "1.3.6.1.4.1.9.10.137.1.3.1.6";
    }

    leaf ciscoBfdSessPerfDiscTime {
      type yang:timestamp;
      description
       "The value of sysUpTime on the most recent occasion at
        which any one or more of the session counters suffered 
        a discontinuity.  
        
        The relevant counters are the specific instances associated  
        with this BFD session of any Counter32 object contained in 
        the ciscoBfdSessPerfTable. If no such discontinuities have occurred  
        since the last re-initialization of the local management 
        subsystem, then this object contains a zero value.";
      smiv2:max-access "read-only";
      smiv2:oid "1.3.6.1.4.1.9.10.137.1.3.1.7";
    }

    leaf ciscoBfdSessPerfPktInHC {
      type yang:counter64;
      description
       "This value represents the total number of BFD messages
        received for this BFD session. It MUST be equal to the 
        least significant 32 bits of ciscoBfdSessPerfPktIn 
        if ciscoBfdSessPerfPktInHC is supported according to 
        the rules spelled out in RFC2863.";
      smiv2:max-access "read-only";
      smiv2:oid "1.3.6.1.4.1.9.10.137.1.3.1.8";
    }

    leaf ciscoBfdSessPerfPktOutHC {
      type yang:counter64;
      description
       "This value represents the total number of
        total number of BFD messages transmitted for this  
        BFD session. It MUST be equal to the 
        least significant 32 bits of ciscoBfdSessPerfPktIn 
        if ciscoBfdSessPerfPktOutHC is supported according to 
        the rules spelled out in RFC2863.";
      smiv2:max-access "read-only";
      smiv2:oid "1.3.6.1.4.1.9.10.137.1.3.1.9";
    }
  }

  notification ciscoBfdSessUp {
    description
     "This notification is generated when the
      ciscoBfdSessState object for one or more contiguous 
      entries in ciscoBfdSessTable are about to enter the up(4) 
      state from some other state. The included values of 
      ciscoBfdSessDiag MUST both be set equal to this 
      new state (i.e: up(4)).  The two instances of  
      ciscoBfdSessDiag in this notification indicate the range  
      of indexes that are affected.  Note that all the indexes  
      of the two ends of the range can be derived from the 
      instance identifiers of these two objects.  For the 
      cases where a contiguous range of sessions 
      have transitioned into the up(4) state at roughly 
      the same time, the device SHOULD issue a single 
      notification for each range of contiguous indexes in 
      an effort to minimize the emission of a large number 
      of notifications.  If a notification has to be 
      issued for just a single ciscoBfdSessEntry, then 
      the instance identifier (and values) of the two 
      ciscoBfdSessDiag objects MUST be the identical.";
    smiv2:oid "1.3.6.1.4.1.9.10.137.0.1";

    container object-1 {

      leaf ciscoBfdSessIndex {
        type leafref {
          path "/CISCO-IETF-BFD-MIB:CISCO-IETF-BFD-MIB/CISCO-IETF-BFD-MIB:ciscoBfdSessTable/CISCO-IETF-BFD-MIB:ciscoBfdSessEntry/CISCO-IETF-BFD-MIB:ciscoBfdSessIndex";
        }
      }

      leaf ciscoBfdSessDiag {
        type leafref {
          path "/CISCO-IETF-BFD-MIB:CISCO-IETF-BFD-MIB/CISCO-IETF-BFD-MIB:ciscoBfdSessTable/CISCO-IETF-BFD-MIB:ciscoBfdSessEntry/CISCO-IETF-BFD-MIB:ciscoBfdSessDiag";
        }
      }
    }

    container object-2 {

      leaf ciscoBfdSessIndex {
        type leafref {
          path "/CISCO-IETF-BFD-MIB:CISCO-IETF-BFD-MIB/CISCO-IETF-BFD-MIB:ciscoBfdSessTable/CISCO-IETF-BFD-MIB:ciscoBfdSessEntry/CISCO-IETF-BFD-MIB:ciscoBfdSessIndex";
        }
      }

      leaf ciscoBfdSessDiag {
        type leafref {
          path "/CISCO-IETF-BFD-MIB:CISCO-IETF-BFD-MIB/CISCO-IETF-BFD-MIB:ciscoBfdSessTable/CISCO-IETF-BFD-MIB:ciscoBfdSessEntry/CISCO-IETF-BFD-MIB:ciscoBfdSessDiag";
        }
      }
    }
  }

  notification ciscoBfdSessDown {
    description
     "This notification is generated when the
      ciscoBfdSessState object for one or more contiguous 
      entries in ciscoBfdSessTable are about to enter the down(2) 
      or adminDown(1) states from some other state. The included  
      values of ciscoBfdSessDiag MUST both be set equal to this 
      new state (i.e: down(2) or adminDown(1)).  The two instances  
      of ciscoBfdSessDiag in this notification indicate the range  
      of indexes that are affected.  Note that all the indexes  
      of the two ends of the range can be derived from the 
      instance identifiers of these two objects.  For 
      cases where a contiguous range of sessions 
      have transitioned into the down(2) or adminDown(1) states  
      at roughly the same time, the device SHOULD issue a single 
      notification for each range of contiguous indexes in 
      an effort to minimize the emission of a large number 
      of notifications.  If a notification has to be 
      issued for just a single ciscoBfdSessEntry, then 
      the instance identifier (and values) of the two 
      ciscoBfdSessDiag objects MUST be the identical.";
    smiv2:oid "1.3.6.1.4.1.9.10.137.0.2";

    container object-1 {

      leaf ciscoBfdSessIndex {
        type leafref {
          path "/CISCO-IETF-BFD-MIB:CISCO-IETF-BFD-MIB/CISCO-IETF-BFD-MIB:ciscoBfdSessTable/CISCO-IETF-BFD-MIB:ciscoBfdSessEntry/CISCO-IETF-BFD-MIB:ciscoBfdSessIndex";
        }
      }

      leaf ciscoBfdSessDiag {
        type leafref {
          path "/CISCO-IETF-BFD-MIB:CISCO-IETF-BFD-MIB/CISCO-IETF-BFD-MIB:ciscoBfdSessTable/CISCO-IETF-BFD-MIB:ciscoBfdSessEntry/CISCO-IETF-BFD-MIB:ciscoBfdSessDiag";
        }
      }
    }

    container object-2 {

      leaf ciscoBfdSessIndex {
        type leafref {
          path "/CISCO-IETF-BFD-MIB:CISCO-IETF-BFD-MIB/CISCO-IETF-BFD-MIB:ciscoBfdSessTable/CISCO-IETF-BFD-MIB:ciscoBfdSessEntry/CISCO-IETF-BFD-MIB:ciscoBfdSessIndex";
        }
      }

      leaf ciscoBfdSessDiag {
        type leafref {
          path "/CISCO-IETF-BFD-MIB:CISCO-IETF-BFD-MIB/CISCO-IETF-BFD-MIB:ciscoBfdSessTable/CISCO-IETF-BFD-MIB:ciscoBfdSessEntry/CISCO-IETF-BFD-MIB:ciscoBfdSessDiag";
        }
      }
    }
  }

  smiv2:alias "ciscoIetfBfdMIB" {
    smiv2:oid "1.3.6.1.4.1.9.10.137";
  }

  smiv2:alias "ciscoBfdNotifications" {
    smiv2:oid "1.3.6.1.4.1.9.10.137.0";
  }

  smiv2:alias "ciscoBfdObjects" {
    smiv2:oid "1.3.6.1.4.1.9.10.137.1";
  }

  smiv2:alias "ciscoBfdScalarObjects" {
    smiv2:oid "1.3.6.1.4.1.9.10.137.1.1";
  }

  smiv2:alias "ciscoBfdConformance" {
    smiv2:oid "1.3.6.1.4.1.9.10.137.3";
  }

  smiv2:alias "ciscoBfdGroups" {
    smiv2:oid "1.3.6.1.4.1.9.10.137.3.1";
  }

  smiv2:alias "ciscoBfdCompliances" {
    smiv2:oid "1.3.6.1.4.1.9.10.137.3.2";
  }

}
