/*
 * Generated by confdc --mib2yang-std
 * Source: mgmt/dmi/model/common/mib-source/IGMP-STD-MIB.mib
 */
/*
 * This YANG module has been generated by smidump 0.5.0:
 *
 *      smidump -f yang IGMP-STD-MIB
 *
 * Do not edit. Edit the source file instead!
 */

module IGMP-STD-MIB {

  namespace "urn:ietf:params:xml:ns:yang:smiv2:IGMP-STD-MIB";
  prefix IGMP-STD-MIB;

  import IF-MIB {
    prefix "if-mib";
  }

  import SNMPv2-TC {
    prefix "snmpv2-tc";
  }

  import ietf-inet-types {
    prefix "inet";
  }

  import ietf-yang-smiv2 {
    prefix "smiv2";
  }

  import ietf-yang-types {
    prefix "yang";
  }

  organization
   "IETF IDMR Working Group.";

  contact
   " Dave Thaler
    Microsoft Corporation
    One Microsoft Way
    Redmond, WA  98052-6399
    US
    
    Phone: +1 425 703 8835
    EMail: dthaler@microsoft.com";

  description
   "The MIB module for IGMP Management.";

  revision 2000-09-28 {
    description
     "Initial version, published as RFC 2933.";
  }


  container IGMP-STD-MIB {
    config false;

    container igmpInterfaceTable {
      description
       "The (conceptual) table listing the interfaces on which IGMP
        is enabled.";
      smiv2:oid "1.3.6.1.2.1.85.1.1";

      list igmpInterfaceEntry {
        key "igmpInterfaceIfIndex";
        description
         "An entry (conceptual row) representing an interface on
          which IGMP is enabled.";
        smiv2:oid "1.3.6.1.2.1.85.1.1.1";

        leaf igmpInterfaceIfIndex {
          type if-mib:InterfaceIndex;
          description
           "The ifIndex value of the interface for which IGMP is
            enabled.";
          smiv2:max-access "not-accessible";
          smiv2:oid "1.3.6.1.2.1.85.1.1.1.1";
        }

        leaf igmpInterfaceQueryInterval {
          type uint32;
          units "seconds";
          description
           "The frequency at which IGMP Host-Query packets are
            transmitted on this interface.";
          smiv2:defval "125";
          smiv2:max-access "read-write";
          smiv2:oid "1.3.6.1.2.1.85.1.1.1.2";
        }

        leaf igmpInterfaceStatus {
          type snmpv2-tc:RowStatus;
          description
           "The activation of a row enables IGMP on the interface.  The
            destruction of a row disables IGMP on the interface.";
          smiv2:max-access "read-write";
          smiv2:oid "1.3.6.1.2.1.85.1.1.1.3";
        }

        leaf igmpInterfaceVersion {
          type uint32;
          description
           "The version of IGMP which is running on this interface.
            This object can be used to configure a router capable of
            running either value.  For IGMP to function correctly, all
            routers on a LAN must be configured to run the same version
            of IGMP on that LAN.";
          smiv2:defval "2";
          smiv2:max-access "read-write";
          smiv2:oid "1.3.6.1.2.1.85.1.1.1.4";
        }

        leaf igmpInterfaceQuerier {
          type inet:ipv4-address;
          description
           "The address of the IGMP Querier on the IP subnet to which
            
            
            
            
            
            this interface is attached.";
          smiv2:max-access "read-only";
          smiv2:oid "1.3.6.1.2.1.85.1.1.1.5";
        }

        leaf igmpInterfaceQueryMaxResponseTime {
          type uint32 {
            range "0..255";
          }
          units "tenths of seconds";
          description
           "The maximum query response time advertised in IGMPv2
            queries on this interface.";
          smiv2:defval "100";
          smiv2:max-access "read-write";
          smiv2:oid "1.3.6.1.2.1.85.1.1.1.6";
        }

        leaf igmpInterfaceQuerierUpTime {
          type yang:timeticks;
          description
           "The time since igmpInterfaceQuerier was last changed.";
          smiv2:max-access "read-only";
          smiv2:oid "1.3.6.1.2.1.85.1.1.1.7";
        }

        leaf igmpInterfaceQuerierExpiryTime {
          type yang:timeticks;
          description
           "The amount of time remaining before the Other Querier
            Present Timer expires.  If the local system is the querier,
            the value of this object is zero.";
          smiv2:max-access "read-only";
          smiv2:oid "1.3.6.1.2.1.85.1.1.1.8";
        }

        leaf igmpInterfaceVersion1QuerierTimer {
          type yang:timeticks;
          description
           "The time remaining until the host assumes that there are no
            IGMPv1 routers present on the interface.  While this is non-
            zero, the host will reply to all queries with version 1
            membership reports.";
          smiv2:max-access "read-only";
          smiv2:oid "1.3.6.1.2.1.85.1.1.1.9";
        }

        leaf igmpInterfaceWrongVersionQueries {
          type yang:counter32;
          description
           "The number of queries received whose IGMP version does not
            match igmpInterfaceVersion, over the lifetime of the row
            entry.  IGMP requires that all routers on a LAN be
            configured to run the same version of IGMP.  Thus, if any
            queries are received with the wrong version, this indicates
            a configuration error.";
          smiv2:max-access "read-only";
          smiv2:oid "1.3.6.1.2.1.85.1.1.1.10";
        }

        leaf igmpInterfaceJoins {
          type yang:counter32;
          description
           "The number of times a group membership has been added on
            this interface; that is, the number of times an entry for
            this interface has been added to the Cache Table.  This
            object gives an indication of the amount of IGMP activity
            over the lifetime of the row entry.";
          smiv2:max-access "read-only";
          smiv2:oid "1.3.6.1.2.1.85.1.1.1.11";
        }

        leaf igmpInterfaceProxyIfIndex {
          type if-mib:InterfaceIndexOrZero;
          description
           "Some devices implement a form of IGMP proxying whereby
            memberships learned on the interface represented by this
            row, cause IGMP Host Membership Reports to be sent on the
            interface whose ifIndex value is given by this object.  Such
            a device would implement the igmpV2RouterMIBGroup only on
            its router interfaces (those interfaces with non-zero
            igmpInterfaceProxyIfIndex).  Typically, the value of this
            object is 0, indicating that no proxying is being done.";
          smiv2:defval "0";
          smiv2:max-access "read-write";
          smiv2:oid "1.3.6.1.2.1.85.1.1.1.12";
        }

        leaf igmpInterfaceGroups {
          type yang:gauge32;
          description
           "The current number of entries for this interface in the
            Cache Table.";
          smiv2:max-access "read-only";
          smiv2:oid "1.3.6.1.2.1.85.1.1.1.13";
        }

        leaf igmpInterfaceRobustness {
          type uint32 {
            range "1..255";
          }
          description
           "The Robustness Variable allows tuning for the expected
            packet loss on a subnet.  If a subnet is expected to be
            lossy, the Robustness Variable may be increased.  IGMP is
            robust to (Robustness Variable-1) packet losses.";
          smiv2:defval "2";
          smiv2:max-access "read-write";
          smiv2:oid "1.3.6.1.2.1.85.1.1.1.14";
        }

        leaf igmpInterfaceLastMembQueryIntvl {
          type uint32 {
            range "0..255";
          }
          units "tenths of seconds";
          description
           "The Last Member Query Interval is the Max Response Time
            inserted into Group-Specific Queries sent in response to
            Leave Group messages, and is also the amount of time between
            Group-Specific Query messages.  This value may be tuned to
            modify the leave latency of the network.  A reduced value
            results in reduced time to detect the loss of the last
            member of a group.  The value of this object is irrelevant
            if igmpInterfaceVersion is 1.";
          smiv2:defval "10";
          smiv2:max-access "read-write";
          smiv2:oid "1.3.6.1.2.1.85.1.1.1.15";
        }
      }
    }

    container igmpCacheTable {
      description
       "The (conceptual) table listing the IP multicast groups for
        which there are members on a particular interface.";
      smiv2:oid "1.3.6.1.2.1.85.1.2";

      list igmpCacheEntry {
        key "igmpCacheAddress igmpCacheIfIndex";
        description
         "An entry (conceptual row) in the igmpCacheTable.";
        smiv2:oid "1.3.6.1.2.1.85.1.2.1";

        leaf igmpCacheAddress {
          type inet:ipv4-address;
          description
           "The IP multicast group address for which this entry
            contains information.";
          smiv2:max-access "not-accessible";
          smiv2:oid "1.3.6.1.2.1.85.1.2.1.1";
        }

        leaf igmpCacheIfIndex {
          type if-mib:InterfaceIndex;
          description
           "The interface for which this entry contains information for
            an IP multicast group address.";
          smiv2:max-access "not-accessible";
          smiv2:oid "1.3.6.1.2.1.85.1.2.1.2";
        }

        leaf igmpCacheSelf {
          type boolean;
          description
           "An indication of whether the local system is a member of
            this group address on this interface.";
          smiv2:defval "true";
          smiv2:max-access "read-write";
          smiv2:oid "1.3.6.1.2.1.85.1.2.1.3";
        }

        leaf igmpCacheLastReporter {
          type inet:ipv4-address;
          description
           "The IP address of the source of the last membership report
            received for this IP Multicast group address on this
            interface.  If no membership report has been received, this
            object has the value 0.0.0.0.";
          smiv2:max-access "read-only";
          smiv2:oid "1.3.6.1.2.1.85.1.2.1.4";
        }

        leaf igmpCacheUpTime {
          type yang:timeticks;
          description
           "The time elapsed since this entry was created.";
          smiv2:max-access "read-only";
          smiv2:oid "1.3.6.1.2.1.85.1.2.1.5";
        }

        leaf igmpCacheExpiryTime {
          type yang:timeticks;
          description
           "The minimum amount of time remaining before this entry will
            be aged out.  A value of 0 indicates that the entry is only
            present because igmpCacheSelf is true and that if the router
            left the group, this entry would be aged out immediately.
            Note that some implementations may process membership
            reports from the local system in the same way as reports
            from other hosts, so a value of 0 is not required.";
          smiv2:max-access "read-only";
          smiv2:oid "1.3.6.1.2.1.85.1.2.1.6";
        }

        leaf igmpCacheStatus {
          type snmpv2-tc:RowStatus;
          description
           "The status of this entry.";
          smiv2:max-access "read-write";
          smiv2:oid "1.3.6.1.2.1.85.1.2.1.7";
        }

        leaf igmpCacheVersion1HostTimer {
          type yang:timeticks;
          description
           "The time remaining until the local router will assume that
            there are no longer any IGMP version 1 members on the IP
            subnet attached to this interface.  Upon hearing any IGMPv1
            Membership Report, this value is reset to the group
            membership timer.  While this time remaining is non-zero,
            the local router ignores any IGMPv2 Leave messages for this
            group that it receives on this interface.";
          smiv2:max-access "read-only";
          smiv2:oid "1.3.6.1.2.1.85.1.2.1.8";
        }
      }
    }
  }

  smiv2:alias "igmpStdMIB" {
    smiv2:oid "1.3.6.1.2.1.85";
  }

  smiv2:alias "igmpMIBObjects" {
    smiv2:oid "1.3.6.1.2.1.85.1";
  }

  smiv2:alias "igmpMIBConformance" {
    smiv2:oid "1.3.6.1.2.1.85.2";
  }

  smiv2:alias "igmpMIBCompliances" {
    smiv2:oid "1.3.6.1.2.1.85.2.1";
  }

  smiv2:alias "igmpMIBGroups" {
    smiv2:oid "1.3.6.1.2.1.85.2.2";
  }

}
