/*
 * Generated by confdc --mib2yang-std
 * Source: mgmt/dmi/model/common/mib-source/OSPF-MIB.mib
 */
/*
 * This YANG module has been generated by smidump 0.5.0:
 *
 *      smidump -f yang OSPF-MIB
 *
 * Do not edit. Edit the source file instead!
 */

module OSPF-MIB {

  namespace "urn:ietf:params:xml:ns:yang:smiv2:OSPF-MIB";
  prefix OSPF-MIB;

  import IF-MIB {
    prefix "if-mib";
  }

  import SNMPv2-TC {
    prefix "snmpv2-tc";
  }

  import ietf-inet-types {
    prefix "inet";
  }

  import ietf-yang-smiv2 {
    prefix "smiv2";
  }

  import ietf-yang-types {
    prefix "yang";
  }

  organization
   "IETF OSPF Working Group";

  contact
   "WG E-Mail: ospf@ietf.org
    
    WG Chairs: acee@cisco.com
               rohit@gmail.com
    
    Editors:   Dan Joyal
               Nortel
               600 Technology Park Drive
               Billerica, MA  01821
               djoyal@nortel.com
    
               Piotr Galecki
               Airvana
               19 Alpha Road
               Chelmsford, MA 01824
               pgalecki@airvana.com
    
               Spencer Giacalone
               CSFB
               Eleven Madison Ave
               New York, NY 10010-3629
               spencer.giacalone@gmail.com";

  description
   "The MIB module to describe the OSPF Version 2
    Protocol.  Note that some objects in this MIB
    module may pose a significant security risk.
    Refer to the Security Considerations section
    in RFC 4750 for more information.
    
    Copyright (C) The IETF Trust (2006).
    This version of this MIB module is part of
    RFC 4750;  see the RFC itself for full legal
    notices.";

  revision 2006-11-10 {
    description
     "Updated for latest changes to OSPF Version 2:
      - updated the General Group with the new
        ospfRFC1583Compatibility, ospfReferenceBandwidth
        and ospfDiscontinuityTime objects
      - added graceful-restart-related objects
      - added stub-router-related objects
      - updated the Area Table with NSSA-related objects
      - added ospfAreaAggregateExtRouteTag object
      - added Opaque LSA-related objects
      - updates to the Compliances and Security sections
      - added area LSA counter table
      - added section describing translation of notification
        parameters between SNMP versions
      - added ospfComplianceObsolete to contain obsolete
        object groups
      - deprecated ospfExtLsdbTable
      See Appendix B of RFC 4750 for more details.
      
      This version published as part of RFC 4750";
  }

  revision 1995-01-20 {
    description
     "The initial SMIv2 revision of this MIB module, published
      in RFC 1850.";
  }

  typedef AreaID {
    type inet:ipv4-address;
    description
     "An OSPF Area Identifier.
      Note that the Area ID, in OSPF, has the same format
      as an IP address, but has the function of defining
      a summarization point for link state advertisements.";
  }

  typedef RouterID {
    type inet:ipv4-address;
    description
     "A OSPF Router Identifier.
      Note that the Router ID, in OSPF, has the same format
      as an IP address, but identifies the router independent
      
      of its IP address.";
  }

  typedef Metric {
    type int32 {
      range "0..65535";
    }
    description
     "The OSPF internal metric.
      Note that the OSPF metric is defined as an unsigned value
      in the range.";
    smiv2:display-hint "d-0";
  }

  typedef BigMetric {
    type int32 {
      range "0..16777215";
    }
    description
     "The OSPF external metric.";
    smiv2:display-hint "d-0";
  }

  typedef Status {
    type enumeration {
      enum "enabled" {
        value "1";
      }
      enum "disabled" {
        value "2";
      }
    }
    description
     "An indication of the operability of an OSPF
      function or feature.  For example, the status
      of an interface: 'enabled' indicates that
      it is willing to communicate with other OSPF routers,
      and 'disabled' indicates that it is not.";
  }

  typedef PositiveInteger {
    type int32 {
      range "0..2147483647";
    }
    description
     "A positive integer.  Values in excess are precluded as
      unnecessary and prone to interoperability issues.";
    smiv2:display-hint "d-0";
  }

  typedef HelloRange {
    type int32 {
      range "1..65535";
    }
    description
     "The range of intervals in seconds on which Hello messages
      are exchanged.";
    smiv2:display-hint "d-0";
  }

  typedef UpToMaxAge {
    type int32 {
      range "0..3600";
    }
    description
     "The values in seconds that one might find or configure
      for variables bounded by the maximum age of an LSA.";
    smiv2:display-hint "d-0";
  }

  typedef DesignatedRouterPriority {
    type int32 {
      range "0..255";
    }
    description
     "The range of values defined for the priority of a system
      for becoming the designated router.";
    smiv2:display-hint "d-0";
  }

  typedef TOSType {
    type int32 {
      range "0..30";
    }
    description
     "Type of Service (TOS) is defined as a mapping to the IP
      Type of Service Flags as defined in the IP Forwarding
      Table MIB
      
          +-----+-----+-----+-----+-----+-----+-----+-----+
          |                 |                       |     |
          |   PRECEDENCE    |    TYPE OF SERVICE    |  0  |
          |                 |                       |     |
          +-----+-----+-----+-----+-----+-----+-----+-----+
      
                   IP TOS                IP TOS
              Field     Policy      Field     Policy
      
              Contents    Code      Contents    Code
              0 0 0 0  ==>   0      0 0 0 1  ==>   2
              0 0 1 0  ==>   4      0 0 1 1  ==>   6
              0 1 0 0  ==>   8      0 1 0 1  ==>  10
              0 1 1 0  ==>  12      0 1 1 1  ==>  14
              1 0 0 0  ==>  16      1 0 0 1  ==>  18
              1 0 1 0  ==>  20      1 0 1 1  ==>  22
              1 1 0 0  ==>  24      1 1 0 1  ==>  26
              1 1 1 0  ==>  28      1 1 1 1  ==>  30
      
       The remaining values are left for future definition.";
    smiv2:display-hint "d-0";
  }

  typedef OspfAuthenticationType {
    type enumeration {
      enum "none" {
        value "0";
      }
      enum "simplePassword" {
        value "1";
      }
      enum "md5" {
        value "2";
      }
    }
    description
     "The authentication type.";
  }


  container OSPF-MIB {
    config false;

    container ospfGeneralGroup {
      smiv2:oid "1.3.6.1.2.1.14.1";

      leaf ospfRouterId {
        type OSPF-MIB:RouterID;
        description
         "A 32-bit integer uniquely identifying the
          router in the Autonomous System.
          By convention, to ensure uniqueness, this
          should default to the value of one of the
          router's IP interface addresses.
          
          This object is persistent and when written
          the entity SHOULD save the change to non-volatile storage.";
        reference
         "OSPF Version 2, C.1 Global parameters";
        smiv2:max-access "read-write";
        smiv2:oid "1.3.6.1.2.1.14.1.1";
      }

      leaf ospfAdminStat {
        type OSPF-MIB:Status;
        description
         "The administrative status of OSPF in the
          router.  The value 'enabled' denotes that the
          OSPF Process is active on at least one interface;
          'disabled' disables it on all interfaces.
          
          This object is persistent and when written
          the entity SHOULD save the change to non-volatile storage.";
        smiv2:max-access "read-write";
        smiv2:oid "1.3.6.1.2.1.14.1.2";
      }

      leaf ospfVersionNumber {
        type enumeration {
          enum "version2" {
            value "2";
          }
        }
        description
         "The current version number of the OSPF protocol is 2.";
        reference
         "OSPF Version 2, Title";
        smiv2:max-access "read-only";
        smiv2:oid "1.3.6.1.2.1.14.1.3";
      }

      leaf ospfAreaBdrRtrStatus {
        type boolean;
        description
         "A flag to note whether this router is an Area
          Border Router.";
        reference
         "OSPF Version 2, Section 3 Splitting the AS into
          Areas";
        smiv2:max-access "read-only";
        smiv2:oid "1.3.6.1.2.1.14.1.4";
      }

      leaf ospfASBdrRtrStatus {
        type boolean;
        description
         "A flag to note whether this router is configured as
          an Autonomous System Border Router.
          
          This object is persistent and when written the
          entity SHOULD save the change to non-volatile storage.";
        reference
         "OSPF Version 2, Section 3.3 Classification of
          routers";
        smiv2:max-access "read-write";
        smiv2:oid "1.3.6.1.2.1.14.1.5";
      }

      leaf ospfExternLsaCount {
        type yang:gauge32;
        description
         "The number of external (LS type-5) link state
          advertisements in the link state database.";
        reference
         "OSPF Version 2, Appendix A.4.5 AS external link
          advertisements";
        smiv2:max-access "read-only";
        smiv2:oid "1.3.6.1.2.1.14.1.6";
      }

      leaf ospfExternLsaCksumSum {
        type int32;
        description
         "The 32-bit sum of the LS checksums of
          the external link state advertisements
          contained in the link state database.  This sum
          can be used to determine if there has been a
          change in a router's link state database and
          to compare the link state database of two
          routers.  The value should be treated as unsigned
          when comparing two sums of checksums.";
        smiv2:max-access "read-only";
        smiv2:oid "1.3.6.1.2.1.14.1.7";
      }

      leaf ospfTOSSupport {
        type boolean;
        description
         "The router's support for type-of-service routing.
          
          This object is persistent and when written
          the entity SHOULD save the change to non-volatile
          storage.";
        reference
         "OSPF Version 2, Appendix F.1.2 Optional TOS
          support";
        smiv2:max-access "read-write";
        smiv2:oid "1.3.6.1.2.1.14.1.8";
      }

      leaf ospfOriginateNewLsas {
        type yang:counter32;
        description
         "The number of new link state advertisements
          that have been originated.  This number is
          incremented each time the router originates a new
          LSA.
          
          Discontinuities in the value of this counter can
          occur at re-initialization of the management system,
          and at other times as indicated by the value of
          ospfDiscontinuityTime.";
        smiv2:max-access "read-only";
        smiv2:oid "1.3.6.1.2.1.14.1.9";
      }

      leaf ospfRxNewLsas {
        type yang:counter32;
        description
         "The number of link state advertisements received
          that are determined to be new instantiations.
          This number does not include newer instantiations
          of self-originated link state advertisements.
          
          Discontinuities in the value of this counter can
          occur at re-initialization of the management system,
          and at other times as indicated by the value of
          ospfDiscontinuityTime.";
        smiv2:max-access "read-only";
        smiv2:oid "1.3.6.1.2.1.14.1.10";
      }

      leaf ospfExtLsdbLimit {
        type int32 {
          range "-1..2147483647";
        }
        description
         "The maximum number of non-default
          AS-external LSAs entries that can be stored in the
          link state database.  If the value is -1, then
          there is no limit.
          
          When the number of non-default AS-external LSAs
          in a router's link state database reaches
          ospfExtLsdbLimit, the router enters
          overflow state.  The router never holds more than
          ospfExtLsdbLimit non-default AS-external LSAs
          in its database.  OspfExtLsdbLimit MUST be set
          identically in all routers attached to the OSPF
          backbone and/or any regular OSPF area (i.e.,
          OSPF stub areas and NSSAs are excluded).
          
          This object is persistent and when written
          the entity SHOULD save the change to non-volatile
          storage.";
        smiv2:defval "-1";
        smiv2:max-access "read-write";
        smiv2:oid "1.3.6.1.2.1.14.1.11";
      }

      leaf ospfMulticastExtensions {
        type int32;
        description
         "A bit mask indicating whether the router is
          forwarding IP multicast (Class D) datagrams
          based on the algorithms defined in the
          multicast extensions to OSPF.
          
          Bit 0, if set, indicates that the router can
          
          forward IP multicast datagrams in the router's
          directly attached areas (called intra-area
          multicast routing).
          
          Bit 1, if set, indicates that the router can
          forward IP multicast datagrams between OSPF
          areas (called inter-area multicast routing).
          
          Bit 2, if set, indicates that the router can
          forward IP multicast datagrams between
          Autonomous Systems (called inter-AS multicast
          routing).
          
          Only certain combinations of bit settings are
          allowed, namely: 0 (no multicast forwarding is
          enabled), 1 (intra-area multicasting only), 3
          (intra-area and inter-area multicasting), 5
          (intra-area and inter-AS multicasting), and 7
          (multicasting everywhere).  By default, no
          multicast forwarding is enabled.
          
          This object is persistent and when written
          the entity SHOULD save the change to non-volatile
          storage.";
        smiv2:defval "0";
        smiv2:max-access "read-write";
        smiv2:oid "1.3.6.1.2.1.14.1.12";
      }

      leaf ospfExitOverflowInterval {
        type OSPF-MIB:PositiveInteger;
        description
         "The number of seconds that, after entering
          OverflowState, a router will attempt to leave
          OverflowState.  This allows the router to again
          originate non-default AS-external LSAs.  When
          set to 0, the router will not leave
          overflow state until restarted.
          
          This object is persistent and when written
          the entity SHOULD save the change to non-volatile
          storage.";
        smiv2:defval "0";
        smiv2:max-access "read-write";
        smiv2:oid "1.3.6.1.2.1.14.1.13";
      }

      leaf ospfDemandExtensions {
        type boolean;
        description
         "The router's support for demand routing.
          This object is persistent and when written
          the entity SHOULD save the change to non-volatile
          storage.";
        reference
         "Extending OSPF to Support Demand Circuits";
        smiv2:max-access "read-write";
        smiv2:oid "1.3.6.1.2.1.14.1.14";
      }

      leaf ospfRFC1583Compatibility {
        type boolean;
        description
         "Indicates metrics used to choose among multiple
          AS-external LSAs.  When RFC1583Compatibility is set to
          enabled, only cost will be used when choosing among
          multiple AS-external LSAs advertising the same
          destination.  When RFC1583Compatibility is set to
          disabled, preference will be driven first by type of
          path using cost only to break ties.
          
          This object is persistent and when written
          the entity SHOULD save the change to non-volatile
          storage.";
        reference
         "OSPF Version 2, Section 16.4.1 External path
          preferences";
        smiv2:max-access "read-write";
        smiv2:oid "1.3.6.1.2.1.14.1.15";
      }

      leaf ospfOpaqueLsaSupport {
        type boolean;
        description
         "The router's support for Opaque LSA types.";
        reference
         "The OSPF Opaque LSA Option";
        smiv2:max-access "read-only";
        smiv2:oid "1.3.6.1.2.1.14.1.16";
      }

      leaf ospfReferenceBandwidth {
        type uint32;
        units "kilobits per second";
        description
         "Reference bandwidth in kilobits/second for
          
          calculating default interface metrics.  The
          default value is 100,000 KBPS (100 MBPS).
          
          This object is persistent and when written
          the entity SHOULD save the change to non-volatile
          storage.";
        smiv2:max-access "read-write";
        smiv2:oid "1.3.6.1.2.1.14.1.17";
      }

      leaf ospfRestartSupport {
        type enumeration {
          enum "none" {
            value "1";
          }
          enum "plannedOnly" {
            value "2";
          }
          enum "plannedAndUnplanned" {
            value "3";
          }
        }
        description
         "The router's support for OSPF graceful restart.
          Options include: no restart support, only planned
          restarts, or both planned and unplanned restarts.
          
          This object is persistent and when written
          the entity SHOULD save the change to non-volatile
          storage.";
        smiv2:max-access "read-write";
        smiv2:oid "1.3.6.1.2.1.14.1.18";
      }

      leaf ospfRestartInterval {
        type int32 {
          range "1..1800";
        }
        units "seconds";
        description
         "Configured OSPF graceful restart timeout interval.
          
          This object is persistent and when written
          the entity SHOULD save the change to non-volatile
          storage.";
        smiv2:max-access "read-write";
        smiv2:oid "1.3.6.1.2.1.14.1.19";
      }

      leaf ospfRestartStrictLsaChecking {
        type boolean;
        description
         "Indicates if strict LSA checking is enabled for
          graceful restart.
          
          This object is persistent and when written
          the entity SHOULD save the change to non-volatile
          
          storage.";
        smiv2:max-access "read-write";
        smiv2:oid "1.3.6.1.2.1.14.1.20";
      }

      leaf ospfRestartStatus {
        type enumeration {
          enum "notRestarting" {
            value "1";
          }
          enum "plannedRestart" {
            value "2";
          }
          enum "unplannedRestart" {
            value "3";
          }
        }
        description
         "Current status of OSPF graceful restart.";
        smiv2:max-access "read-only";
        smiv2:oid "1.3.6.1.2.1.14.1.21";
      }

      leaf ospfRestartAge {
        type uint32;
        units "seconds";
        description
         "Remaining time in current OSPF graceful restart
          interval.";
        smiv2:max-access "read-only";
        smiv2:oid "1.3.6.1.2.1.14.1.22";
      }

      leaf ospfRestartExitReason {
        type enumeration {
          enum "none" {
            value "1";
          }
          enum "inProgress" {
            value "2";
          }
          enum "completed" {
            value "3";
          }
          enum "timedOut" {
            value "4";
          }
          enum "topologyChanged" {
            value "5";
          }
        }
        description
         "Describes the outcome of the last attempt at a
          graceful restart.  If the value is 'none', no restart
          has yet been attempted.  If the value is 'inProgress',
          a restart attempt is currently underway.";
        smiv2:max-access "read-only";
        smiv2:oid "1.3.6.1.2.1.14.1.23";
      }

      leaf ospfAsLsaCount {
        type yang:gauge32;
        description
         "The number of AS-scope link state
          advertisements in the AS-scope link state database.";
        smiv2:max-access "read-only";
        smiv2:oid "1.3.6.1.2.1.14.1.24";
      }

      leaf ospfAsLsaCksumSum {
        type uint32;
        description
         "The 32-bit unsigned sum of the LS checksums of
          the AS link state advertisements contained in the AS-scope
          link state database.  This sum can be used to determine
          if there has been a change in a router's AS-scope link
          state database, and to compare the AS-scope link state
          database of two routers.";
        smiv2:max-access "read-only";
        smiv2:oid "1.3.6.1.2.1.14.1.25";
      }

      leaf ospfStubRouterSupport {
        type boolean;
        description
         "The router's support for stub router functionality.";
        reference
         "OSPF Stub Router Advertisement";
        smiv2:max-access "read-only";
        smiv2:oid "1.3.6.1.2.1.14.1.26";
      }

      leaf ospfStubRouterAdvertisement {
        type enumeration {
          enum "doNotAdvertise" {
            value "1";
          }
          enum "advertise" {
            value "2";
          }
        }
        description
         "This object controls the advertisement of
          stub router LSAs by the router.  The value
          doNotAdvertise will result in the advertisement
          of a standard router LSA and is the default value.
          
          This object is persistent and when written
          the entity SHOULD save the change to non-volatile
          storage.";
        smiv2:max-access "read-write";
        smiv2:oid "1.3.6.1.2.1.14.1.27";
      }

      leaf ospfDiscontinuityTime {
        type yang:timestamp;
        description
         "The value of sysUpTime on the most recent occasion
          at which any one of this MIB's counters suffered
          a discontinuity.
          
          If no such discontinuities have occurred since the last
          re-initialization of the local management subsystem,
          then this object contains a zero value.";
        smiv2:max-access "read-only";
        smiv2:oid "1.3.6.1.2.1.14.1.28";
      }
    }

    container ospfAreaTable {
      description
       "Information describing the configured parameters and
        cumulative statistics of the router's attached areas.
        The interfaces and virtual links are configured
        as part of these areas.  Area 0.0.0.0, by definition,
        is the backbone area.";
      reference
       "OSPF Version 2, Section 6 The Area Data Structure";
      smiv2:oid "1.3.6.1.2.1.14.2";

      list ospfAreaEntry {
        key "ospfAreaId";
        description
         "Information describing the configured parameters and
          cumulative statistics of one of the router's attached areas.
          The interfaces and virtual links are configured as part of
          these areas.  Area 0.0.0.0, by definition, is the backbone
          area.
          
          Information in this table is persistent and when this object
          is written the entity SHOULD save the change to non-volatile
          storage.";
        smiv2:oid "1.3.6.1.2.1.14.2.1";

        leaf ospfAreaId {
          type OSPF-MIB:AreaID;
          description
           "A 32-bit integer uniquely identifying an area.
            Area ID 0.0.0.0 is used for the OSPF backbone.";
          reference
           "OSPF Version 2, Appendix C.2 Area parameters";
          smiv2:max-access "read-only";
          smiv2:oid "1.3.6.1.2.1.14.2.1.1";
        }

        leaf ospfAuthType {
          type OSPF-MIB:OspfAuthenticationType;
          status obsolete;
          description
           "The authentication type specified for an area.";
          reference
           "OSPF Version 2, Appendix D Authentication";
          smiv2:defval "none";
          smiv2:max-access "read-write";
          smiv2:oid "1.3.6.1.2.1.14.2.1.2";
        }

        leaf ospfImportAsExtern {
          type enumeration {
            enum "importExternal" {
              value "1";
            }
            enum "importNoExternal" {
              value "2";
            }
            enum "importNssa" {
              value "3";
            }
          }
          description
           "Indicates if an area is a stub area, NSSA, or standard
            area.  Type-5 AS-external LSAs and type-11 Opaque LSAs are
            not imported into stub areas or NSSAs.  NSSAs import
            AS-external data as type-7 LSAs";
          reference
           "OSPF Version 2, Appendix C.2 Area parameters";
          smiv2:defval "importExternal";
          smiv2:max-access "read-write";
          smiv2:oid "1.3.6.1.2.1.14.2.1.3";
        }

        leaf ospfSpfRuns {
          type yang:counter32;
          description
           "The number of times that the intra-area route
            table has been calculated using this area's
            link state database.  This is typically done
            using Dijkstra's algorithm.
            
            Discontinuities in the value of this counter can occur
            at re-initialization of the management system, and at other
            times as indicated by the value of ospfDiscontinuityTime.";
          smiv2:max-access "read-only";
          smiv2:oid "1.3.6.1.2.1.14.2.1.4";
        }

        leaf ospfAreaBdrRtrCount {
          type yang:gauge32;
          description
           "The total number of Area Border Routers reachable
            within this area.  This is initially zero and is
            calculated in each Shortest Path First (SPF) pass.";
          smiv2:max-access "read-only";
          smiv2:oid "1.3.6.1.2.1.14.2.1.5";
        }

        leaf ospfAsBdrRtrCount {
          type yang:gauge32;
          description
           "The total number of Autonomous System Border
            Routers reachable within this area.  This is
            initially zero and is calculated in each SPF
            pass.";
          smiv2:max-access "read-only";
          smiv2:oid "1.3.6.1.2.1.14.2.1.6";
        }

        leaf ospfAreaLsaCount {
          type yang:gauge32;
          description
           "The total number of link state advertisements
            in this area's link state database, excluding
            AS-external LSAs.";
          smiv2:max-access "read-only";
          smiv2:oid "1.3.6.1.2.1.14.2.1.7";
        }

        leaf ospfAreaLsaCksumSum {
          type int32;
          description
           "The 32-bit sum of the link state
            advertisements' LS checksums contained in this
            area's link state database.  This sum excludes
            external (LS type-5) link state advertisements.
            The sum can be used to determine if there has
            been a change in a router's link state
            database, and to compare the link state database of
            two routers.  The value should be treated as unsigned
            when comparing two sums of checksums.";
          smiv2:defval "0";
          smiv2:max-access "read-only";
          smiv2:oid "1.3.6.1.2.1.14.2.1.8";
        }

        leaf ospfAreaSummary {
          type enumeration {
            enum "noAreaSummary" {
              value "1";
            }
            enum "sendAreaSummary" {
              value "2";
            }
          }
          description
           "The variable ospfAreaSummary controls the
            import of summary LSAs into stub and NSSA areas.
            It has no effect on other areas.
            
            If it is noAreaSummary, the router will not
            originate summary LSAs into the stub or NSSA area.
            It will rely entirely on its default route.
            
            If it is sendAreaSummary, the router will both
            summarize and propagate summary LSAs.";
          smiv2:defval "noAreaSummary";
          smiv2:max-access "read-write";
          smiv2:oid "1.3.6.1.2.1.14.2.1.9";
        }

        leaf ospfAreaStatus {
          type snmpv2-tc:RowStatus;
          description
           "This object permits management of the table by
            facilitating actions such as row creation,
            construction, and destruction.
            
            The value of this object has no effect on
            whether other objects in this conceptual row can be
            modified.";
          smiv2:max-access "read-write";
          smiv2:oid "1.3.6.1.2.1.14.2.1.10";
        }

        leaf ospfAreaNssaTranslatorRole {
          type enumeration {
            enum "always" {
              value "1";
            }
            enum "candidate" {
              value "2";
            }
          }
          description
           "Indicates an NSSA border router's ability to
            perform NSSA translation of type-7 LSAs into
            type-5 LSAs.";
          smiv2:defval "candidate";
          smiv2:max-access "read-write";
          smiv2:oid "1.3.6.1.2.1.14.2.1.11";
        }

        leaf ospfAreaNssaTranslatorState {
          type enumeration {
            enum "enabled" {
              value "1";
            }
            enum "elected" {
              value "2";
            }
            enum "disabled" {
              value "3";
            }
          }
          description
           "Indicates if and how an NSSA border router is
            performing NSSA translation of type-7 LSAs into type-5
            
            LSAs.  When this object is set to enabled, the NSSA Border
            router's OspfAreaNssaExtTranslatorRole has been set to
            always.  When this object is set to elected, a candidate
            NSSA Border router is Translating type-7 LSAs into type-5.
            When this object is set to disabled, a candidate NSSA
            border router is NOT translating type-7 LSAs into type-5.";
          smiv2:max-access "read-only";
          smiv2:oid "1.3.6.1.2.1.14.2.1.12";
        }

        leaf ospfAreaNssaTranslatorStabilityInterval {
          type OSPF-MIB:PositiveInteger;
          units "seconds";
          description
           "The number of seconds after an elected translator
            determines its services are no longer required, that
            it should continue to perform its translation duties.";
          smiv2:defval "40";
          smiv2:max-access "read-write";
          smiv2:oid "1.3.6.1.2.1.14.2.1.13";
        }

        leaf ospfAreaNssaTranslatorEvents {
          type yang:counter32;
          description
           "Indicates the number of translator state changes
            that have occurred since the last boot-up.
            
            Discontinuities in the value of this counter can occur
            at re-initialization of the management system, and at other
            times as indicated by the value of ospfDiscontinuityTime.";
          smiv2:max-access "read-only";
          smiv2:oid "1.3.6.1.2.1.14.2.1.14";
        }
      }
    }

    container ospfStubAreaTable {
      description
       "The set of metrics that will be advertised
        by a default Area Border Router into a stub area.";
      reference
       "OSPF Version 2, Appendix C.2, Area Parameters";
      smiv2:oid "1.3.6.1.2.1.14.3";

      list ospfStubAreaEntry {
        key "ospfStubAreaId ospfStubTOS";
        description
         "The metric for a given Type of Service that
          will be advertised by a default Area Border
          Router into a stub area.
          
          Information in this table is persistent and when this object
          is written the entity SHOULD save the change to non-volatile
          storage.";
        reference
         "OSPF Version 2, Appendix C.2, Area Parameters";
        smiv2:oid "1.3.6.1.2.1.14.3.1";

        leaf ospfStubAreaId {
          type OSPF-MIB:AreaID;
          description
           "The 32-bit identifier for the stub area.  On
            creation, this can be derived from the
            instance.";
          smiv2:max-access "read-only";
          smiv2:oid "1.3.6.1.2.1.14.3.1.1";
        }

        leaf ospfStubTOS {
          type OSPF-MIB:TOSType;
          description
           "The Type of Service associated with the
            metric.  On creation, this can be derived from
            
            the instance.";
          smiv2:max-access "read-only";
          smiv2:oid "1.3.6.1.2.1.14.3.1.2";
        }

        leaf ospfStubMetric {
          type OSPF-MIB:BigMetric;
          description
           "The metric value applied at the indicated Type
            of Service.  By default, this equals the least
            metric at the Type of Service among the
            interfaces to other areas.";
          smiv2:max-access "read-write";
          smiv2:oid "1.3.6.1.2.1.14.3.1.3";
        }

        leaf ospfStubStatus {
          type snmpv2-tc:RowStatus;
          description
           "This object permits management of the table by
            facilitating actions such as row creation,
            construction, and destruction.
            
            The value of this object has no effect on
            whether other objects in this conceptual row can be
            modified.";
          smiv2:max-access "read-write";
          smiv2:oid "1.3.6.1.2.1.14.3.1.4";
        }

        leaf ospfStubMetricType {
          type enumeration {
            enum "ospfMetric" {
              value "1";
            }
            enum "comparableCost" {
              value "2";
            }
            enum "nonComparable" {
              value "3";
            }
          }
          description
           "This variable displays the type of metric
            advertised as a default route.";
          smiv2:defval "ospfMetric";
          smiv2:max-access "read-write";
          smiv2:oid "1.3.6.1.2.1.14.3.1.5";
        }
      }
    }

    container ospfLsdbTable {
      description
       "The OSPF Process's link state database (LSDB).
        The LSDB contains the link state advertisements
        from throughout the areas that the device is attached to.";
      reference
       "OSPF Version 2, Section 12 Link State Advertisements";
      smiv2:oid "1.3.6.1.2.1.14.4";

      list ospfLsdbEntry {
        key "ospfLsdbAreaId ospfLsdbType ospfLsdbLsid ospfLsdbRouterId";
        description
         "A single link state advertisement.";
        smiv2:oid "1.3.6.1.2.1.14.4.1";

        leaf ospfLsdbAreaId {
          type OSPF-MIB:AreaID;
          description
           "The 32-bit identifier of the area from which
            the LSA was received.";
          reference
           "OSPF Version 2, Appendix C.2 Area parameters";
          smiv2:max-access "read-only";
          smiv2:oid "1.3.6.1.2.1.14.4.1.1";
        }

        leaf ospfLsdbType {
          type enumeration {
            enum "routerLink" {
              value "1";
            }
            enum "networkLink" {
              value "2";
            }
            enum "summaryLink" {
              value "3";
            }
            enum "asSummaryLink" {
              value "4";
            }
            enum "asExternalLink" {
              value "5";
            }
            enum "multicastLink" {
              value "6";
            }
            enum "nssaExternalLink" {
              value "7";
            }
            enum "areaOpaqueLink" {
              value "10";
            }
          }
          description
           "The type of the link state advertisement.
            Each link state type has a separate advertisement
            format.
            
            Note: External link state advertisements are permitted
            for backward compatibility, but should be displayed
            in the ospfAsLsdbTable rather than here.";
          reference
           "OSPF Version 2, Appendix A.4.1 The Link State
            Advertisement header";
          smiv2:max-access "read-only";
          smiv2:oid "1.3.6.1.2.1.14.4.1.2";
        }

        leaf ospfLsdbLsid {
          type inet:ipv4-address;
          description
           "The Link State ID is an LS Type Specific field
            containing either a Router ID or an IP address;
            it identifies the piece of the routing domain
            that is being described by the advertisement.";
          reference
           "OSPF Version 2, Section 12.1.4 Link State ID";
          smiv2:max-access "read-only";
          smiv2:oid "1.3.6.1.2.1.14.4.1.3";
        }

        leaf ospfLsdbRouterId {
          type OSPF-MIB:RouterID;
          description
           "The 32-bit number that uniquely identifies the
            originating router in the Autonomous System.";
          reference
           "OSPF Version 2, Appendix C.1 Global parameters";
          smiv2:max-access "read-only";
          smiv2:oid "1.3.6.1.2.1.14.4.1.4";
        }

        leaf ospfLsdbSequence {
          type int32;
          description
           "The sequence number field is a signed 32-bit
            integer.  It starts with the value '80000001'h,
            or -'7FFFFFFF'h, and increments until '7FFFFFFF'h.
            Thus, a typical sequence number will be very negative.
            It is used to detect old and duplicate Link State
            Advertisements.  The space of sequence numbers is linearly
            ordered.  The larger the sequence number, the more recent
            the advertisement.";
          reference
           "OSPF Version 2, Section 12.1.6 LS sequence
            number";
          smiv2:max-access "read-only";
          smiv2:oid "1.3.6.1.2.1.14.4.1.5";
        }

        leaf ospfLsdbAge {
          type int32;
          units "seconds";
          description
           "This field is the age of the link state advertisement
            in seconds.";
          reference
           "OSPF Version 2, Section 12.1.1 LS age";
          smiv2:max-access "read-only";
          smiv2:oid "1.3.6.1.2.1.14.4.1.6";
        }

        leaf ospfLsdbChecksum {
          type int32;
          description
           "This field is the checksum of the complete contents of
            the advertisement, excepting the age field.  The age field
            is excepted so that an advertisement's age can be
            incremented without updating the checksum.  The checksum
            used is the same that is used for ISO connectionless
            
            datagrams; it is commonly referred to as the
            Fletcher checksum.";
          reference
           "OSPF Version 2, Section 12.1.7 LS checksum";
          smiv2:max-access "read-only";
          smiv2:oid "1.3.6.1.2.1.14.4.1.7";
        }

        leaf ospfLsdbAdvertisement {
          type binary {
            length "1..65535";
          }
          description
           "The entire link state advertisement, including
            its header.
            
            Note that for variable length LSAs, SNMP agents
            may not be able to return the largest string size.";
          reference
           "OSPF Version 2, Section 12 Link State Advertisements";
          smiv2:max-access "read-only";
          smiv2:oid "1.3.6.1.2.1.14.4.1.8";
        }
      }
    }

    container ospfAreaRangeTable {
      status obsolete;
      description
       "The Address Range Table acts as an adjunct to the Area
        Table.  It describes those Address Range Summaries that
        are configured to be propagated from an Area to reduce
        the amount of information about it that is known beyond
        its borders.  It contains a set of IP address ranges
        specified by an IP address/IP network mask pair.
        For example, class B address range of X.X.X.X
        with a network mask of 255.255.0.0 includes all IP
        addresses from X.X.0.0 to X.X.255.255.
        
        Note that this table is obsoleted and is replaced
        by the Area Aggregate Table.";
      reference
       "OSPF Version 2, Appendix C.2  Area parameters";
      smiv2:oid "1.3.6.1.2.1.14.5";

      list ospfAreaRangeEntry {
        key "ospfAreaRangeAreaId ospfAreaRangeNet";
        status obsolete;
        description
         "A single area address range.
          
          Information in this table is persistent and when this object
          is written the entity SHOULD save the change to non-volatile
          storage.";
        reference
         "OSPF Version 2, Appendix C.2  Area parameters";
        smiv2:oid "1.3.6.1.2.1.14.5.1";

        leaf ospfAreaRangeAreaId {
          type OSPF-MIB:AreaID;
          status obsolete;
          description
           "The area that the address range is to be found
            within.";
          reference
           "OSPF Version 2, Appendix C.2 Area parameters";
          smiv2:max-access "read-only";
          smiv2:oid "1.3.6.1.2.1.14.5.1.1";
        }

        leaf ospfAreaRangeNet {
          type inet:ipv4-address;
          status obsolete;
          description
           "The IP address of the net or subnet indicated
            by the range.";
          reference
           "OSPF Version 2, Appendix C.2 Area parameters";
          smiv2:max-access "read-only";
          smiv2:oid "1.3.6.1.2.1.14.5.1.2";
        }

        leaf ospfAreaRangeMask {
          type inet:ipv4-address;
          status obsolete;
          description
           "The subnet mask that pertains to the net or
            subnet.";
          reference
           "OSPF Version 2, Appendix C.2 Area parameters";
          smiv2:max-access "read-write";
          smiv2:oid "1.3.6.1.2.1.14.5.1.3";
        }

        leaf ospfAreaRangeStatus {
          type snmpv2-tc:RowStatus;
          status obsolete;
          description
           "This object permits management of the table by
            facilitating actions such as row creation,
            construction, and destruction.
            
            The value of this object has no effect on
            whether other objects in this conceptual row can be
            modified.";
          smiv2:max-access "read-write";
          smiv2:oid "1.3.6.1.2.1.14.5.1.4";
        }

        leaf ospfAreaRangeEffect {
          type enumeration {
            enum "advertiseMatching" {
              value "1";
            }
            enum "doNotAdvertiseMatching" {
              value "2";
            }
          }
          status obsolete;
          description
           "Subnets subsumed by ranges either trigger the
            advertisement of the indicated summary
            (advertiseMatching) or result in the subnet's not
            being advertised at all outside the area.";
          smiv2:defval "advertiseMatching";
          smiv2:max-access "read-write";
          smiv2:oid "1.3.6.1.2.1.14.5.1.5";
        }
      }
    }

    container ospfHostTable {
      description
       "The Host/Metric Table indicates what hosts are directly
        
        attached to the router, what metrics and types
        of service should be advertised for them,
        and what areas they are found within.";
      reference
       "OSPF Version 2, Appendix C.7 Host route
        parameters";
      smiv2:oid "1.3.6.1.2.1.14.6";

      list ospfHostEntry {
        key "ospfHostIpAddress ospfHostTOS";
        description
         "A metric to be advertised, for a given type of
          service, when a given host is reachable.
          
          Information in this table is persistent and when this object
          is written the entity SHOULD save the change to non-volatile
          storage.";
        smiv2:oid "1.3.6.1.2.1.14.6.1";

        leaf ospfHostIpAddress {
          type inet:ipv4-address;
          description
           "The IP address of the host.";
          reference
           "OSPF Version 2, Appendix C.7 Host route parameters";
          smiv2:max-access "read-only";
          smiv2:oid "1.3.6.1.2.1.14.6.1.1";
        }

        leaf ospfHostTOS {
          type OSPF-MIB:TOSType;
          description
           "The Type of Service of the route being configured.";
          reference
           "OSPF Version 2, Appendix C.7 Host route parameters";
          smiv2:max-access "read-only";
          smiv2:oid "1.3.6.1.2.1.14.6.1.2";
        }

        leaf ospfHostMetric {
          type OSPF-MIB:Metric;
          description
           "The metric to be advertised.";
          reference
           "OSPF Version 2, Appendix C.7 Host route parameters";
          smiv2:max-access "read-write";
          smiv2:oid "1.3.6.1.2.1.14.6.1.3";
        }

        leaf ospfHostStatus {
          type snmpv2-tc:RowStatus;
          description
           "This object permits management of the table by
            facilitating actions such as row creation,
            construction, and destruction.
            
            The value of this object has no effect on
            whether other objects in this conceptual row can be
            modified.";
          smiv2:max-access "read-write";
          smiv2:oid "1.3.6.1.2.1.14.6.1.4";
        }

        leaf ospfHostAreaID {
          type OSPF-MIB:AreaID;
          status deprecated;
          description
           "The OSPF area to which the host belongs.
            Deprecated by ospfHostCfgAreaID.";
          reference
           "OSPF Version 2, Appendix C.7 Host parameters";
          smiv2:max-access "read-only";
          smiv2:oid "1.3.6.1.2.1.14.6.1.5";
        }

        leaf ospfHostCfgAreaID {
          type OSPF-MIB:AreaID;
          description
           "To configure the OSPF area to which the host belongs.";
          reference
           "OSPF Version 2, Appendix C.7 Host parameters";
          smiv2:max-access "read-write";
          smiv2:oid "1.3.6.1.2.1.14.6.1.6";
        }
      }
    }

    container ospfIfTable {
      description
       "The OSPF Interface Table describes the interfaces
        from the viewpoint of OSPF.
        It augments the ipAddrTable with OSPF specific information.";
      reference
       "OSPF Version 2, Appendix C.3  Router interface
        parameters";
      smiv2:oid "1.3.6.1.2.1.14.7";

      list ospfIfEntry {
        key "ospfIfIpAddress ospfAddressLessIf";
        description
         "The OSPF interface entry describes one interface
          from the viewpoint of OSPF.
          
          Information in this table is persistent and when this object
          is written the entity SHOULD save the change to non-volatile
          storage.";
        smiv2:oid "1.3.6.1.2.1.14.7.1";

        leaf ospfIfIpAddress {
          type inet:ipv4-address;
          description
           "The IP address of this OSPF interface.";
          smiv2:max-access "read-only";
          smiv2:oid "1.3.6.1.2.1.14.7.1.1";
        }

        leaf ospfAddressLessIf {
          type if-mib:InterfaceIndexOrZero;
          description
           "For the purpose of easing the instancing of
            addressed and addressless interfaces; this
            variable takes the value 0 on interfaces with
            IP addresses and the corresponding value of
            ifIndex for interfaces having no IP address.";
          smiv2:max-access "read-only";
          smiv2:oid "1.3.6.1.2.1.14.7.1.2";
        }

        leaf ospfIfAreaId {
          type OSPF-MIB:AreaID;
          description
           "A 32-bit integer uniquely identifying the area
            to which the interface connects.  Area ID
            0.0.0.0 is used for the OSPF backbone.";
          smiv2:defval "'00000000'H";
          smiv2:max-access "read-write";
          smiv2:oid "1.3.6.1.2.1.14.7.1.3";
        }

        leaf ospfIfType {
          type enumeration {
            enum "broadcast" {
              value "1";
            }
            enum "nbma" {
              value "2";
            }
            enum "pointToPoint" {
              value "3";
            }
            enum "pointToMultipoint" {
              value "5";
            }
          }
          description
           "The OSPF interface type.
            By way of a default, this field may be intuited
            from the corresponding value of ifType.
            Broadcast LANs, such as Ethernet and IEEE 802.5,
            take the value 'broadcast', X.25 and similar
            technologies take the value 'nbma', and links
            that are definitively point to point take the
            value 'pointToPoint'.";
          smiv2:max-access "read-write";
          smiv2:oid "1.3.6.1.2.1.14.7.1.4";
        }

        leaf ospfIfAdminStat {
          type OSPF-MIB:Status;
          description
           "The OSPF interface's administrative status.
            The value formed on the interface, and the interface
            will be advertised as an internal route to some area.
            The value 'disabled' denotes that the interface is
            external to OSPF.";
          smiv2:defval "enabled";
          smiv2:max-access "read-write";
          smiv2:oid "1.3.6.1.2.1.14.7.1.5";
        }

        leaf ospfIfRtrPriority {
          type OSPF-MIB:DesignatedRouterPriority;
          description
           "The priority of this interface.  Used in
            multi-access networks, this field is used in
            the designated router election algorithm.  The
            value 0 signifies that the router is not eligible
            to become the designated router on this particular
            network.  In the event of a tie in this value,
            routers will use their Router ID as a tie breaker.";
          smiv2:defval "1";
          smiv2:max-access "read-write";
          smiv2:oid "1.3.6.1.2.1.14.7.1.6";
        }

        leaf ospfIfTransitDelay {
          type OSPF-MIB:UpToMaxAge;
          units "seconds";
          description
           "The estimated number of seconds it takes to
            transmit a link state update packet over this
            interface.  Note that the minimal value SHOULD be
            1 second.";
          smiv2:defval "1";
          smiv2:max-access "read-write";
          smiv2:oid "1.3.6.1.2.1.14.7.1.7";
        }

        leaf ospfIfRetransInterval {
          type OSPF-MIB:UpToMaxAge;
          units "seconds";
          description
           "The number of seconds between link state advertisement
            retransmissions, for adjacencies belonging to this
            interface.  This value is also used when retransmitting
            
            database description and Link State request packets.
            Note that minimal value SHOULD be 1 second.";
          smiv2:defval "5";
          smiv2:max-access "read-write";
          smiv2:oid "1.3.6.1.2.1.14.7.1.8";
        }

        leaf ospfIfHelloInterval {
          type OSPF-MIB:HelloRange;
          units "seconds";
          description
           "The length of time, in seconds, between the Hello packets
            that the router sends on the interface.  This value must be
            the same for all routers attached to a common network.";
          smiv2:defval "10";
          smiv2:max-access "read-write";
          smiv2:oid "1.3.6.1.2.1.14.7.1.9";
        }

        leaf ospfIfRtrDeadInterval {
          type OSPF-MIB:PositiveInteger;
          units "seconds";
          description
           "The number of seconds that a router's Hello packets have
            not been seen before its neighbors declare the router down.
            This should be some multiple of the Hello interval.  This
            value must be the same for all routers attached to a common
            network.";
          smiv2:defval "40";
          smiv2:max-access "read-write";
          smiv2:oid "1.3.6.1.2.1.14.7.1.10";
        }

        leaf ospfIfPollInterval {
          type OSPF-MIB:PositiveInteger;
          units "seconds";
          description
           "The larger time interval, in seconds, between the Hello
            packets sent to an inactive non-broadcast multi-access
            neighbor.";
          smiv2:defval "120";
          smiv2:max-access "read-write";
          smiv2:oid "1.3.6.1.2.1.14.7.1.11";
        }

        leaf ospfIfState {
          type enumeration {
            enum "down" {
              value "1";
            }
            enum "loopback" {
              value "2";
            }
            enum "waiting" {
              value "3";
            }
            enum "pointToPoint" {
              value "4";
            }
            enum "designatedRouter" {
              value "5";
            }
            enum "backupDesignatedRouter" {
              value "6";
            }
            enum "otherDesignatedRouter" {
              value "7";
            }
          }
          description
           "The OSPF Interface State.";
          smiv2:defval "down";
          smiv2:max-access "read-only";
          smiv2:oid "1.3.6.1.2.1.14.7.1.12";
        }

        leaf ospfIfDesignatedRouter {
          type inet:ipv4-address;
          description
           "The IP address of the designated router.";
          smiv2:defval "'00000000'H";
          smiv2:max-access "read-only";
          smiv2:oid "1.3.6.1.2.1.14.7.1.13";
        }

        leaf ospfIfBackupDesignatedRouter {
          type inet:ipv4-address;
          description
           "The IP address of the backup designated
            router.";
          smiv2:defval "'00000000'H";
          smiv2:max-access "read-only";
          smiv2:oid "1.3.6.1.2.1.14.7.1.14";
        }

        leaf ospfIfEvents {
          type yang:counter32;
          description
           "The number of times this OSPF interface has
            changed its state or an error has occurred.
            
            Discontinuities in the value of this counter can occur
            at re-initialization of the management system, and at other
            times as indicated by the value of ospfDiscontinuityTime.";
          smiv2:max-access "read-only";
          smiv2:oid "1.3.6.1.2.1.14.7.1.15";
        }

        leaf ospfIfAuthKey {
          type binary {
            length "0..256";
          }
          description
           "The cleartext password used as an OSPF
            authentication key when simplePassword security
            is enabled.  This object does not access any OSPF
            cryptogaphic (e.g., MD5) authentication key under
            any circumstance.
            
            If the key length is shorter than 8 octets, the
            agent will left adjust and zero fill to 8 octets.
            
            Unauthenticated interfaces need no authentication
            key, and simple password authentication cannot use
            a key of more than 8 octets.
            
            Note that the use of simplePassword authentication
            is NOT recommended when there is concern regarding
            attack upon the OSPF system.  SimplePassword
            authentication is only sufficient to protect against
            accidental misconfigurations because it re-uses
            cleartext passwords [RFC1704].
            
            When read, ospfIfAuthKey always returns an octet
            string of length zero.";
          reference
           "OSPF Version 2, Section 9 The Interface Data
            Structure";
          smiv2:defval "'0000000000000000'H";
          smiv2:max-access "read-write";
          smiv2:oid "1.3.6.1.2.1.14.7.1.16";
        }

        leaf ospfIfStatus {
          type snmpv2-tc:RowStatus;
          description
           "This object permits management of the table by
            facilitating actions such as row creation,
            construction, and destruction.
            
            The value of this object has no effect on
            whether other objects in this conceptual row can be
            modified.";
          smiv2:max-access "read-write";
          smiv2:oid "1.3.6.1.2.1.14.7.1.17";
        }

        leaf ospfIfMulticastForwarding {
          type enumeration {
            enum "blocked" {
              value "1";
            }
            enum "multicast" {
              value "2";
            }
            enum "unicast" {
              value "3";
            }
          }
          description
           "The way multicasts should be forwarded on this
            interface: not forwarded, forwarded as data
            link multicasts, or forwarded as data link
            unicasts.  Data link multicasting is not
            meaningful on point-to-point and NBMA interfaces,
            and setting ospfMulticastForwarding to 0 effectively
            disables all multicast forwarding.";
          smiv2:defval "blocked";
          smiv2:max-access "read-write";
          smiv2:oid "1.3.6.1.2.1.14.7.1.18";
        }

        leaf ospfIfDemand {
          type boolean;
          description
           "Indicates whether Demand OSPF procedures (hello
            suppression to FULL neighbors and setting the
            DoNotAge flag on propagated LSAs) should be
            performed on this interface.";
          smiv2:defval "false";
          smiv2:max-access "read-write";
          smiv2:oid "1.3.6.1.2.1.14.7.1.19";
        }

        leaf ospfIfAuthType {
          type OSPF-MIB:OspfAuthenticationType;
          description
           "The authentication type specified for an interface.
            
            Note that this object can be used to engage
            in significant attacks against an OSPF router.";
          reference
           "OSPF Version 2, Appendix D Authentication";
          smiv2:defval "none";
          smiv2:max-access "read-write";
          smiv2:oid "1.3.6.1.2.1.14.7.1.20";
        }

        leaf ospfIfLsaCount {
          type yang:gauge32;
          description
           "The total number of link-local link state advertisements
            in this interface's link-local link state database.";
          smiv2:max-access "read-only";
          smiv2:oid "1.3.6.1.2.1.14.7.1.21";
        }

        leaf ospfIfLsaCksumSum {
          type uint32;
          description
           "The 32-bit unsigned sum of the Link State
            Advertisements' LS checksums contained in this
            interface's link-local link state database.
            The sum can be used to determine if there has
            been a change in the interface's link state
            database and to compare the interface link state
            database of routers attached to the same subnet.";
          smiv2:max-access "read-only";
          smiv2:oid "1.3.6.1.2.1.14.7.1.22";
        }

        leaf ospfIfDesignatedRouterId {
          type OSPF-MIB:RouterID;
          description
           "The Router ID of the designated router.";
          smiv2:max-access "read-only";
          smiv2:oid "1.3.6.1.2.1.14.7.1.23";
        }

        leaf ospfIfBackupDesignatedRouterId {
          type OSPF-MIB:RouterID;
          description
           "The Router ID of the backup designated router.";
          smiv2:max-access "read-only";
          smiv2:oid "1.3.6.1.2.1.14.7.1.24";
        }
      }
    }

    container ospfIfMetricTable {
      description
       "The Metric Table describes the metrics to be advertised
        for a specified interface at the various types of service.
        As such, this table is an adjunct of the OSPF Interface
        Table.
        
        Types of service, as defined by RFC 791, have the ability
        to request low delay, high bandwidth, or reliable linkage.
        
        For the purposes of this specification, the measure of
        bandwidth:
        
        Metric = referenceBandwidth / ifSpeed
        
        is the default value.
        The default reference bandwidth is 10^8.
        For multiple link interfaces, note that ifSpeed is the sum
        of the individual link speeds.  This yields a number having
        the following typical values:
        
        Network Type/bit rate   Metric
        
        >= 100 MBPS                 1
        Ethernet/802.3             10
        E1                         48
        T1 (ESF)                   65
        64 KBPS                    1562
        56 KBPS                    1785
        19.2 KBPS                  5208
        9.6 KBPS                   10416
        
        Routes that are not specified use the default
        (TOS 0) metric.
        
        Note that the default reference bandwidth can be configured
        using the general group object ospfReferenceBandwidth.";
      reference
       "OSPF Version 2, Appendix C.3 Router interface
        parameters";
      smiv2:oid "1.3.6.1.2.1.14.8";

      list ospfIfMetricEntry {
        key "ospfIfMetricIpAddress ospfIfMetricAddressLessIf ospfIfMetricTOS";
        description
         "A particular TOS metric for a non-virtual interface
          identified by the interface index.
          
          Information in this table is persistent and when this object
          is written the entity SHOULD save the change to non-volatile
          storage.";
        reference
         "OSPF Version 2, Appendix C.3 Router interface
          parameters";
        smiv2:oid "1.3.6.1.2.1.14.8.1";

        leaf ospfIfMetricIpAddress {
          type inet:ipv4-address;
          description
           "The IP address of this OSPF interface.  On row
            creation, this can be derived from the instance.";
          smiv2:max-access "read-only";
          smiv2:oid "1.3.6.1.2.1.14.8.1.1";
        }

        leaf ospfIfMetricAddressLessIf {
          type if-mib:InterfaceIndexOrZero;
          description
           "For the purpose of easing the instancing of
            addressed and addressless interfaces; this
            variable takes the value 0 on interfaces with
            IP addresses and the value of ifIndex for
            interfaces having no IP address.  On row
            creation, this can be derived from the instance.";
          smiv2:max-access "read-only";
          smiv2:oid "1.3.6.1.2.1.14.8.1.2";
        }

        leaf ospfIfMetricTOS {
          type OSPF-MIB:TOSType;
          description
           "The Type of Service metric being referenced.
            On row creation, this can be derived from the
            instance.";
          smiv2:max-access "read-only";
          smiv2:oid "1.3.6.1.2.1.14.8.1.3";
        }

        leaf ospfIfMetricValue {
          type OSPF-MIB:Metric;
          description
           "The metric of using this Type of Service on
            this interface.  The default value of the TOS 0
            metric is 10^8 / ifSpeed.";
          smiv2:max-access "read-write";
          smiv2:oid "1.3.6.1.2.1.14.8.1.4";
        }

        leaf ospfIfMetricStatus {
          type snmpv2-tc:RowStatus;
          description
           "This object permits management of the table by
            facilitating actions such as row creation,
            construction, and destruction.
            
            The value of this object has no effect on
            whether other objects in this conceptual row can be
            modified.";
          smiv2:max-access "read-write";
          smiv2:oid "1.3.6.1.2.1.14.8.1.5";
        }
      }
    }

    container ospfVirtIfTable {
      description
       "Information about this router's virtual interfaces
        that the OSPF Process is configured to carry on.";
      reference
       "OSPF Version 2, Appendix C.4  Virtual link
        parameters";
      smiv2:oid "1.3.6.1.2.1.14.9";

      list ospfVirtIfEntry {
        key "ospfVirtIfAreaId ospfVirtIfNeighbor";
        description
         "Information about a single virtual interface.
          
          Information in this table is persistent and when this object
          is written the entity SHOULD save the change to non-volatile
          storage.";
        smiv2:oid "1.3.6.1.2.1.14.9.1";

        leaf ospfVirtIfAreaId {
          type OSPF-MIB:AreaID;
          description
           "The transit area that the virtual link
            traverses.  By definition, this is not 0.0.0.0.";
          smiv2:max-access "read-only";
          smiv2:oid "1.3.6.1.2.1.14.9.1.1";
        }

        leaf ospfVirtIfNeighbor {
          type OSPF-MIB:RouterID;
          description
           "The Router ID of the virtual neighbor.";
          smiv2:max-access "read-only";
          smiv2:oid "1.3.6.1.2.1.14.9.1.2";
        }

        leaf ospfVirtIfTransitDelay {
          type OSPF-MIB:UpToMaxAge;
          units "seconds";
          description
           "The estimated number of seconds it takes to
            transmit a Link State update packet over this
            interface.  Note that the minimal value SHOULD be
            1 second.";
          smiv2:defval "1";
          smiv2:max-access "read-write";
          smiv2:oid "1.3.6.1.2.1.14.9.1.3";
        }

        leaf ospfVirtIfRetransInterval {
          type OSPF-MIB:UpToMaxAge;
          units "seconds";
          description
           "The number of seconds between link state
            avertisement retransmissions, for adjacencies
            belonging to this interface.  This value is
            also used when retransmitting database
            description and Link State request packets.  This
            value should be well over the expected
            round-trip time.  Note that the minimal value SHOULD be
            1 second.";
          smiv2:defval "5";
          smiv2:max-access "read-write";
          smiv2:oid "1.3.6.1.2.1.14.9.1.4";
        }

        leaf ospfVirtIfHelloInterval {
          type OSPF-MIB:HelloRange;
          units "seconds";
          description
           "The length of time, in seconds, between the
            Hello packets that the router sends on the
            interface.  This value must be the same for the
            virtual neighbor.";
          smiv2:defval "10";
          smiv2:max-access "read-write";
          smiv2:oid "1.3.6.1.2.1.14.9.1.5";
        }

        leaf ospfVirtIfRtrDeadInterval {
          type OSPF-MIB:PositiveInteger;
          units "seconds";
          description
           "The number of seconds that a router's Hello
            packets have not been seen before its
            neighbors declare the router down.  This should be
            some multiple of the Hello interval.  This
            value must be the same for the virtual neighbor.";
          smiv2:defval "60";
          smiv2:max-access "read-write";
          smiv2:oid "1.3.6.1.2.1.14.9.1.6";
        }

        leaf ospfVirtIfState {
          type enumeration {
            enum "down" {
              value "1";
            }
            enum "pointToPoint" {
              value "4";
            }
          }
          description
           "OSPF virtual interface states.";
          smiv2:defval "down";
          smiv2:max-access "read-only";
          smiv2:oid "1.3.6.1.2.1.14.9.1.7";
        }

        leaf ospfVirtIfEvents {
          type yang:counter32;
          description
           "The number of state changes or error events on
            this virtual link.
            
            Discontinuities in the value of this counter can occur
            at re-initialization of the management system, and at other
            times as indicated by the value of ospfDiscontinuityTime.";
          smiv2:max-access "read-only";
          smiv2:oid "1.3.6.1.2.1.14.9.1.8";
        }

        leaf ospfVirtIfAuthKey {
          type binary {
            length "0..256";
          }
          description
           "The cleartext password used as an OSPF
            authentication key when simplePassword security
            is enabled.  This object does not access any OSPF
            cryptogaphic (e.g., MD5) authentication key under
            any circumstance.
            
            If the key length is shorter than 8 octets, the
            agent will left adjust and zero fill to 8 octets.
            
            Unauthenticated interfaces need no authentication
            key, and simple password authentication cannot use
            a key of more than 8 octets.
            
            Note that the use of simplePassword authentication
            is NOT recommended when there is concern regarding
            attack upon the OSPF system.  SimplePassword
            authentication is only sufficient to protect against
            accidental misconfigurations because it re-uses
            cleartext passwords.  [RFC1704]
            
            When read, ospfIfAuthKey always returns an octet
            string of length zero.";
          reference
           "OSPF Version 2, Section 9 The Interface Data
            Structure";
          smiv2:defval "'0000000000000000'H";
          smiv2:max-access "read-write";
          smiv2:oid "1.3.6.1.2.1.14.9.1.9";
        }

        leaf ospfVirtIfStatus {
          type snmpv2-tc:RowStatus;
          description
           "This object permits management of the table by
            facilitating actions such as row creation,
            construction, and destruction.
            
            The value of this object has no effect on
            whether other objects in this conceptual row can be
            modified.";
          smiv2:max-access "read-write";
          smiv2:oid "1.3.6.1.2.1.14.9.1.10";
        }

        leaf ospfVirtIfAuthType {
          type OSPF-MIB:OspfAuthenticationType;
          description
           "The authentication type specified for a virtual interface.
            
            Note that this object can be used to engage
            in significant attacks against an OSPF router.";
          reference
           "OSPF Version 2, Appendix E Authentication";
          smiv2:defval "none";
          smiv2:max-access "read-write";
          smiv2:oid "1.3.6.1.2.1.14.9.1.11";
        }

        leaf ospfVirtIfLsaCount {
          type yang:gauge32;
          description
           "The total number of link-local link state advertisements
            in this virtual interface's link-local link state database.";
          smiv2:max-access "read-only";
          smiv2:oid "1.3.6.1.2.1.14.9.1.12";
        }

        leaf ospfVirtIfLsaCksumSum {
          type uint32;
          description
           "The 32-bit unsigned sum of the link state
            advertisements' LS checksums contained in this
            virtual interface's link-local link state database.
            The sum can be used to determine if there has
            been a change in the virtual interface's link state
            database, and to compare the virtual interface
            link state database of the virtual neighbors.";
          smiv2:max-access "read-only";
          smiv2:oid "1.3.6.1.2.1.14.9.1.13";
        }
      }
    }

    container ospfNbrTable {
      description
       "A table describing all non-virtual neighbors
        in the locality of the OSPF router.";
      reference
       "OSPF Version 2, Section 10 The Neighbor Data
        Structure";
      smiv2:oid "1.3.6.1.2.1.14.10";

      list ospfNbrEntry {
        key "ospfNbrIpAddr ospfNbrAddressLessIndex";
        description
         "The information regarding a single neighbor.
          
          Information in this table is persistent and when this object
          is written the entity SHOULD save the change to non-volatile
          
          storage.";
        reference
         "OSPF Version 2, Section 10 The Neighbor Data
          Structure";
        smiv2:oid "1.3.6.1.2.1.14.10.1";

        leaf ospfNbrIpAddr {
          type inet:ipv4-address;
          description
           "The IP address this neighbor is using in its
            IP source address.  Note that, on addressless
            links, this will not be 0.0.0.0 but the
            
            address of another of the neighbor's interfaces.";
          smiv2:max-access "read-only";
          smiv2:oid "1.3.6.1.2.1.14.10.1.1";
        }

        leaf ospfNbrAddressLessIndex {
          type if-mib:InterfaceIndexOrZero;
          description
           "On an interface having an IP address, zero.
            On addressless interfaces, the corresponding
            value of ifIndex in the Internet Standard MIB.
            On row creation, this can be derived from the
            instance.";
          smiv2:max-access "read-only";
          smiv2:oid "1.3.6.1.2.1.14.10.1.2";
        }

        leaf ospfNbrRtrId {
          type OSPF-MIB:RouterID;
          description
           "A 32-bit integer (represented as a type
            IpAddress) uniquely identifying the neighboring
            router in the Autonomous System.";
          smiv2:defval "'00000000'H";
          smiv2:max-access "read-only";
          smiv2:oid "1.3.6.1.2.1.14.10.1.3";
        }

        leaf ospfNbrOptions {
          type int32;
          description
           "A bit mask corresponding to the neighbor's
            options field.
            
            Bit 0, if set, indicates that the system will
            operate on Type of Service metrics other than
            TOS 0.  If zero, the neighbor will ignore all
            metrics except the TOS 0 metric.
            
            Bit 1, if set, indicates that the associated
            area accepts and operates on external
            information; if zero, it is a stub area.
            
            Bit 2, if set, indicates that the system is
            capable of routing IP multicast datagrams, that is
            that it implements the multicast extensions to
            OSPF.
            
            Bit 3, if set, indicates that the associated
            area is an NSSA.  These areas are capable of
            carrying type-7 external advertisements, which
            are translated into type-5 external advertisements
            at NSSA borders.";
          reference
           "OSPF Version 2, Section 12.1.2 Options";
          smiv2:defval "0";
          smiv2:max-access "read-only";
          smiv2:oid "1.3.6.1.2.1.14.10.1.4";
        }

        leaf ospfNbrPriority {
          type OSPF-MIB:DesignatedRouterPriority;
          description
           "The priority of this neighbor in the designated
            router election algorithm.  The value 0 signifies
            that the neighbor is not eligible to become
            the designated router on this particular network.";
          smiv2:defval "1";
          smiv2:max-access "read-write";
          smiv2:oid "1.3.6.1.2.1.14.10.1.5";
        }

        leaf ospfNbrState {
          type enumeration {
            enum "down" {
              value "1";
            }
            enum "attempt" {
              value "2";
            }
            enum "init" {
              value "3";
            }
            enum "twoWay" {
              value "4";
            }
            enum "exchangeStart" {
              value "5";
            }
            enum "exchange" {
              value "6";
            }
            enum "loading" {
              value "7";
            }
            enum "full" {
              value "8";
            }
          }
          description
           "The state of the relationship with this neighbor.";
          reference
           "OSPF Version 2, Section 10.1 Neighbor States";
          smiv2:defval "down";
          smiv2:max-access "read-only";
          smiv2:oid "1.3.6.1.2.1.14.10.1.6";
        }

        leaf ospfNbrEvents {
          type yang:counter32;
          description
           "The number of times this neighbor relationship
            has changed state or an error has occurred.
            
            Discontinuities in the value of this counter can occur
            at re-initialization of the management system, and at other
            times as indicated by the value of ospfDiscontinuityTime.";
          smiv2:max-access "read-only";
          smiv2:oid "1.3.6.1.2.1.14.10.1.7";
        }

        leaf ospfNbrLsRetransQLen {
          type yang:gauge32;
          description
           "The current length of the retransmission
            queue.";
          smiv2:max-access "read-only";
          smiv2:oid "1.3.6.1.2.1.14.10.1.8";
        }

        leaf ospfNbmaNbrStatus {
          type snmpv2-tc:RowStatus;
          description
           "This object permits management of the table by
            facilitating actions such as row creation,
            construction, and destruction.
            
            The value of this object has no effect on
            whether other objects in this conceptual row can be
            modified.";
          smiv2:max-access "read-write";
          smiv2:oid "1.3.6.1.2.1.14.10.1.9";
        }

        leaf ospfNbmaNbrPermanence {
          type enumeration {
            enum "dynamic" {
              value "1";
            }
            enum "permanent" {
              value "2";
            }
          }
          description
           "This variable displays the status of the entry;
            'dynamic' and 'permanent' refer to how the neighbor
            became known.";
          smiv2:defval "permanent";
          smiv2:max-access "read-only";
          smiv2:oid "1.3.6.1.2.1.14.10.1.10";
        }

        leaf ospfNbrHelloSuppressed {
          type boolean;
          description
           "Indicates whether Hellos are being suppressed
            to the neighbor.";
          smiv2:max-access "read-only";
          smiv2:oid "1.3.6.1.2.1.14.10.1.11";
        }

        leaf ospfNbrRestartHelperStatus {
          type enumeration {
            enum "notHelping" {
              value "1";
            }
            enum "helping" {
              value "2";
            }
          }
          description
           "Indicates whether the router is acting
            as a graceful restart helper for the neighbor.";
          smiv2:max-access "read-only";
          smiv2:oid "1.3.6.1.2.1.14.10.1.12";
        }

        leaf ospfNbrRestartHelperAge {
          type uint32;
          units "seconds";
          description
           "Remaining time in current OSPF graceful restart
            interval, if the router is acting as a restart
            helper for the neighbor.";
          smiv2:max-access "read-only";
          smiv2:oid "1.3.6.1.2.1.14.10.1.13";
        }

        leaf ospfNbrRestartHelperExitReason {
          type enumeration {
            enum "none" {
              value "1";
            }
            enum "inProgress" {
              value "2";
            }
            enum "completed" {
              value "3";
            }
            enum "timedOut" {
              value "4";
            }
            enum "topologyChanged" {
              value "5";
            }
          }
          description
           "Describes the outcome of the last attempt at acting
            as a graceful restart helper for the neighbor.";
          smiv2:max-access "read-only";
          smiv2:oid "1.3.6.1.2.1.14.10.1.14";
        }
      }
    }

    container ospfVirtNbrTable {
      description
       "This table describes all virtual neighbors.
        Since virtual links are configured
        in the Virtual Interface Table, this table is read-only.";
      reference
       "OSPF Version 2, Section 15 Virtual Links";
      smiv2:oid "1.3.6.1.2.1.14.11";

      list ospfVirtNbrEntry {
        key "ospfVirtNbrArea ospfVirtNbrRtrId";
        description
         "Virtual neighbor information.";
        smiv2:oid "1.3.6.1.2.1.14.11.1";

        leaf ospfVirtNbrArea {
          type OSPF-MIB:AreaID;
          description
           "The Transit Area Identifier.";
          smiv2:max-access "read-only";
          smiv2:oid "1.3.6.1.2.1.14.11.1.1";
        }

        leaf ospfVirtNbrRtrId {
          type OSPF-MIB:RouterID;
          description
           "A 32-bit integer uniquely identifying the
            neighboring router in the Autonomous System.";
          smiv2:max-access "read-only";
          smiv2:oid "1.3.6.1.2.1.14.11.1.2";
        }

        leaf ospfVirtNbrIpAddr {
          type inet:ipv4-address;
          description
           "The IP address this virtual neighbor is using.";
          smiv2:max-access "read-only";
          smiv2:oid "1.3.6.1.2.1.14.11.1.3";
        }

        leaf ospfVirtNbrOptions {
          type int32;
          description
           "A bit mask corresponding to the neighbor's
            options field.
            
            Bit 1, if set, indicates that the system will
            operate on Type of Service metrics other than
            TOS 0.  If zero, the neighbor will ignore all
            metrics except the TOS 0 metric.
            
            Bit 2, if set, indicates that the system is
            network multicast capable, i.e., that it
            implements OSPF multicast routing.";
          smiv2:max-access "read-only";
          smiv2:oid "1.3.6.1.2.1.14.11.1.4";
        }

        leaf ospfVirtNbrState {
          type enumeration {
            enum "down" {
              value "1";
            }
            enum "attempt" {
              value "2";
            }
            enum "init" {
              value "3";
            }
            enum "twoWay" {
              value "4";
            }
            enum "exchangeStart" {
              value "5";
            }
            enum "exchange" {
              value "6";
            }
            enum "loading" {
              value "7";
            }
            enum "full" {
              value "8";
            }
          }
          description
           "The state of the virtual neighbor relationship.";
          smiv2:max-access "read-only";
          smiv2:oid "1.3.6.1.2.1.14.11.1.5";
        }

        leaf ospfVirtNbrEvents {
          type yang:counter32;
          description
           "The number of times this virtual link has
            changed its state or an error has occurred.
            
            Discontinuities in the value of this counter can occur
            at re-initialization of the management system, and at other
            times as indicated by the value of ospfDiscontinuityTime.";
          smiv2:max-access "read-only";
          smiv2:oid "1.3.6.1.2.1.14.11.1.6";
        }

        leaf ospfVirtNbrLsRetransQLen {
          type yang:gauge32;
          description
           "The current length of the retransmission
            queue.";
          smiv2:max-access "read-only";
          smiv2:oid "1.3.6.1.2.1.14.11.1.7";
        }

        leaf ospfVirtNbrHelloSuppressed {
          type boolean;
          description
           "Indicates whether Hellos are being suppressed
            to the neighbor.";
          smiv2:max-access "read-only";
          smiv2:oid "1.3.6.1.2.1.14.11.1.8";
        }

        leaf ospfVirtNbrRestartHelperStatus {
          type enumeration {
            enum "notHelping" {
              value "1";
            }
            enum "helping" {
              value "2";
            }
          }
          description
           "Indicates whether the router is acting
            as a graceful restart helper for the neighbor.";
          smiv2:max-access "read-only";
          smiv2:oid "1.3.6.1.2.1.14.11.1.9";
        }

        leaf ospfVirtNbrRestartHelperAge {
          type uint32;
          units "seconds";
          description
           "Remaining time in current OSPF graceful restart
            interval, if the router is acting as a restart
            helper for the neighbor.";
          smiv2:max-access "read-only";
          smiv2:oid "1.3.6.1.2.1.14.11.1.10";
        }

        leaf ospfVirtNbrRestartHelperExitReason {
          type enumeration {
            enum "none" {
              value "1";
            }
            enum "inProgress" {
              value "2";
            }
            enum "completed" {
              value "3";
            }
            enum "timedOut" {
              value "4";
            }
            enum "topologyChanged" {
              value "5";
            }
          }
          description
           "Describes the outcome of the last attempt at acting
            as a graceful restart helper for the neighbor.";
          smiv2:max-access "read-only";
          smiv2:oid "1.3.6.1.2.1.14.11.1.11";
        }
      }
    }

    container ospfExtLsdbTable {
      status deprecated;
      description
       "The OSPF Process's external LSA link state database.
        
        This table is identical to the OSPF LSDB Table
        in format, but contains only external link state
        advertisements.  The purpose is to allow external
        
        LSAs to be displayed once for the router rather
        than once in each non-stub area.
        
        Note that external LSAs are also in the AS-scope link state
        database.";
      reference
       "OSPF Version 2, Section 12 Link State Advertisements";
      smiv2:oid "1.3.6.1.2.1.14.12";

      list ospfExtLsdbEntry {
        key "ospfExtLsdbType ospfExtLsdbLsid ospfExtLsdbRouterId";
        status deprecated;
        description
         "A single link state advertisement.";
        smiv2:oid "1.3.6.1.2.1.14.12.1";

        leaf ospfExtLsdbType {
          type enumeration {
            enum "asExternalLink" {
              value "5";
            }
          }
          status deprecated;
          description
           "The type of the link state advertisement.
            Each link state type has a separate advertisement
            format.";
          reference
           "OSPF Version 2, Appendix A.4.1 The Link State
            Advertisement header";
          smiv2:max-access "read-only";
          smiv2:oid "1.3.6.1.2.1.14.12.1.1";
        }

        leaf ospfExtLsdbLsid {
          type inet:ipv4-address;
          status deprecated;
          description
           "The Link State ID is an LS Type Specific field
            containing either a Router ID or an IP address;
            it identifies the piece of the routing domain
            that is being described by the advertisement.";
          reference
           "OSPF Version 2, Section 12.1.4 Link State ID";
          smiv2:max-access "read-only";
          smiv2:oid "1.3.6.1.2.1.14.12.1.2";
        }

        leaf ospfExtLsdbRouterId {
          type OSPF-MIB:RouterID;
          status deprecated;
          description
           "The 32-bit number that uniquely identifies the
            originating router in the Autonomous System.";
          reference
           "OSPF Version 2, Appendix C.1 Global parameters";
          smiv2:max-access "read-only";
          smiv2:oid "1.3.6.1.2.1.14.12.1.3";
        }

        leaf ospfExtLsdbSequence {
          type int32;
          status deprecated;
          description
           "The sequence number field is a signed 32-bit
            integer.  It starts with the value '80000001'h,
            or -'7FFFFFFF'h, and increments until '7FFFFFFF'h.
            Thus, a typical sequence number will be very negative.
            It is used to detect old and duplicate link state
            advertisements.  The space of sequence numbers is linearly
            ordered.  The larger the sequence number, the more recent
            the advertisement.";
          reference
           "OSPF Version  2,  Section  12.1.6  LS  sequence
            number";
          smiv2:max-access "read-only";
          smiv2:oid "1.3.6.1.2.1.14.12.1.4";
        }

        leaf ospfExtLsdbAge {
          type int32;
          units "seconds";
          status deprecated;
          description
           "This field is the age of the link state
            advertisement in seconds.";
          reference
           "OSPF Version 2, Section 12.1.1 LS age";
          smiv2:max-access "read-only";
          smiv2:oid "1.3.6.1.2.1.14.12.1.5";
        }

        leaf ospfExtLsdbChecksum {
          type int32;
          status deprecated;
          description
           "This field is the checksum of the complete
            contents of the advertisement, excepting the
            age field.  The age field is excepted so that
            an advertisement's age can be incremented
            without updating the checksum.  The checksum
            used is the same that is used for ISO
            connectionless datagrams; it is commonly referred
            to as the Fletcher checksum.";
          reference
           "OSPF Version 2, Section 12.1.7 LS checksum";
          smiv2:max-access "read-only";
          smiv2:oid "1.3.6.1.2.1.14.12.1.6";
        }

        leaf ospfExtLsdbAdvertisement {
          type binary {
            length "36";
          }
          status deprecated;
          description
           "The entire link state advertisement, including
            its header.";
          reference
           "OSPF Version 2, Section 12  Link State
            Advertisements";
          smiv2:max-access "read-only";
          smiv2:oid "1.3.6.1.2.1.14.12.1.7";
        }
      }
    }

    container ospfAreaAggregateTable {
      description
       "The Area Aggregate Table acts as an adjunct
        to the Area Table.  It describes those address aggregates
        that are configured to be propagated from an area.
        Its purpose is to reduce the amount of information
        that is known beyond an Area's borders.
        
        It contains a set of IP address ranges
        specified by an IP address/IP network mask pair.
        For example, a class B address range of X.X.X.X
        with a network mask of 255.255.0.0 includes all IP
        addresses from X.X.0.0 to X.X.255.255.
        
        Note that if ranges are configured such that one range
        subsumes another range (e.g., 10.0.0.0 mask 255.0.0.0
        and 10.1.0.0 mask 255.255.0.0),
        the most specific match is the preferred one.";
      reference
       "OSPF Version 2, Appendix C.2  Area parameters";
      smiv2:oid "1.3.6.1.2.1.14.14";

      list ospfAreaAggregateEntry {
        key "ospfAreaAggregateAreaID ospfAreaAggregateLsdbType ospfAreaAggregateNet ospfAreaAggregateMask";
        description
         "A single area aggregate entry.
          
          Information in this table is persistent and when this object
          is written the entity SHOULD save the change to non-volatile
          storage.";
        reference
         "OSPF Version 2, Appendix C.2  Area parameters";
        smiv2:oid "1.3.6.1.2.1.14.14.1";

        leaf ospfAreaAggregateAreaID {
          type OSPF-MIB:AreaID;
          description
           "The area within which the address aggregate is to be
            found.";
          reference
           "OSPF Version 2, Appendix C.2 Area parameters";
          smiv2:max-access "read-only";
          smiv2:oid "1.3.6.1.2.1.14.14.1.1";
        }

        leaf ospfAreaAggregateLsdbType {
          type enumeration {
            enum "summaryLink" {
              value "3";
            }
            enum "nssaExternalLink" {
              value "7";
            }
          }
          description
           "The type of the address aggregate.  This field
            specifies the Lsdb type that this address
            aggregate applies to.";
          reference
           "OSPF Version 2, Appendix A.4.1 The Link State
            Advertisement header";
          smiv2:max-access "read-only";
          smiv2:oid "1.3.6.1.2.1.14.14.1.2";
        }

        leaf ospfAreaAggregateNet {
          type inet:ipv4-address;
          description
           "The IP address of the net or subnet indicated
            by the range.";
          reference
           "OSPF Version 2, Appendix C.2 Area parameters";
          smiv2:max-access "read-only";
          smiv2:oid "1.3.6.1.2.1.14.14.1.3";
        }

        leaf ospfAreaAggregateMask {
          type inet:ipv4-address;
          description
           "The subnet mask that pertains to the net or
            subnet.";
          reference
           "OSPF Version 2, Appendix C.2 Area parameters";
          smiv2:max-access "read-only";
          smiv2:oid "1.3.6.1.2.1.14.14.1.4";
        }

        leaf ospfAreaAggregateStatus {
          type snmpv2-tc:RowStatus;
          description
           "This object permits management of the table by
            facilitating actions such as row creation,
            construction, and destruction.
            
            The value of this object has no effect on
            whether other objects in this conceptual row can be
            modified.";
          smiv2:max-access "read-write";
          smiv2:oid "1.3.6.1.2.1.14.14.1.5";
        }

        leaf ospfAreaAggregateEffect {
          type enumeration {
            enum "advertiseMatching" {
              value "1";
            }
            enum "doNotAdvertiseMatching" {
              value "2";
            }
          }
          description
           "Subnets subsumed by ranges either trigger the
            advertisement of the indicated aggregate
            (advertiseMatching) or result in the subnet's not
            being advertised at all outside the area.";
          smiv2:defval "advertiseMatching";
          smiv2:max-access "read-write";
          smiv2:oid "1.3.6.1.2.1.14.14.1.6";
        }

        leaf ospfAreaAggregateExtRouteTag {
          type uint32;
          description
           "External route tag to be included in NSSA (type-7)
            LSAs.";
          smiv2:defval "0";
          smiv2:max-access "read-write";
          smiv2:oid "1.3.6.1.2.1.14.14.1.7";
        }
      }
    }

    container ospfLocalLsdbTable {
      description
       "The OSPF Process's link-local link state database
        for non-virtual links.
        This table is identical to the OSPF LSDB Table
        in format, but contains only link-local Link State
        Advertisements for non-virtual links.  The purpose is
        to allow link-local LSAs to be displayed for each
        non-virtual interface.  This table is implemented to
        support type-9 LSAs that are defined
        in 'The OSPF Opaque LSA Option'.";
      reference
       "OSPF Version 2, Section 12 Link State Advertisements
        and The OSPF Opaque LSA Option";
      smiv2:oid "1.3.6.1.2.1.14.17";

      list ospfLocalLsdbEntry {
        key "ospfLocalLsdbIpAddress ospfLocalLsdbAddressLessIf ospfLocalLsdbType ospfLocalLsdbLsid ospfLocalLsdbRouterId";
        description
         "A single link state advertisement.";
        smiv2:oid "1.3.6.1.2.1.14.17.1";

        leaf ospfLocalLsdbIpAddress {
          type inet:ipv4-address;
          description
           "The IP address of the interface from
            which the LSA was received if the interface is
            numbered.";
          reference
           "OSPF Version 2, Appendix C.3 Interface parameters";
          smiv2:max-access "not-accessible";
          smiv2:oid "1.3.6.1.2.1.14.17.1.1";
        }

        leaf ospfLocalLsdbAddressLessIf {
          type if-mib:InterfaceIndexOrZero;
          description
           "The interface index of the interface from
            which the LSA was received if the interface is
            unnumbered.";
          reference
           "OSPF Version 2, Appendix C.3 Interface parameters";
          smiv2:max-access "not-accessible";
          smiv2:oid "1.3.6.1.2.1.14.17.1.2";
        }

        leaf ospfLocalLsdbType {
          type enumeration {
            enum "localOpaqueLink" {
              value "9";
            }
          }
          description
           "The type of the link state advertisement.
            Each link state type has a separate
            advertisement format.";
          reference
           "OSPF Version 2, Appendix A.4.1 The Link State
            Advertisement header";
          smiv2:max-access "not-accessible";
          smiv2:oid "1.3.6.1.2.1.14.17.1.3";
        }

        leaf ospfLocalLsdbLsid {
          type inet:ipv4-address;
          description
           "The Link State ID is an LS Type Specific field
            containing a 32-bit identifier in IP address format;
            it identifies the piece of the routing domain
            that is being described by the advertisement.";
          reference
           "OSPF Version 2, Section 12.1.4 Link State ID";
          smiv2:max-access "not-accessible";
          smiv2:oid "1.3.6.1.2.1.14.17.1.4";
        }

        leaf ospfLocalLsdbRouterId {
          type OSPF-MIB:RouterID;
          description
           "The 32-bit number that uniquely identifies the
            originating router in the Autonomous System.";
          reference
           "OSPF Version 2, Appendix C.1 Global parameters";
          smiv2:max-access "not-accessible";
          smiv2:oid "1.3.6.1.2.1.14.17.1.5";
        }

        leaf ospfLocalLsdbSequence {
          type int32;
          description
           "The sequence number field is a signed 32-bit
            integer.  It starts with the value '80000001'h,
            or -'7FFFFFFF'h, and increments until '7FFFFFFF'h.
            Thus, a typical sequence number will be very negative.
            It is used to detect old and duplicate link state
            advertisements.  The space of sequence numbers is linearly
            ordered.  The larger the sequence number, the more recent
            the advertisement.";
          reference
           "OSPF Version 2, Section 12.1.6 LS sequence
            number";
          smiv2:max-access "read-only";
          smiv2:oid "1.3.6.1.2.1.14.17.1.6";
        }

        leaf ospfLocalLsdbAge {
          type int32;
          units "seconds";
          description
           "This field is the age of the link state
            advertisement in seconds.";
          reference
           "OSPF Version 2, Section 12.1.1 LS age";
          smiv2:max-access "read-only";
          smiv2:oid "1.3.6.1.2.1.14.17.1.7";
        }

        leaf ospfLocalLsdbChecksum {
          type int32;
          description
           "This field is the checksum of the complete
            contents of the advertisement, excepting the
            age field.  The age field is excepted so that
            an advertisement's age can be incremented
            without updating the checksum.  The checksum
            used is the same that is used for ISO
            connectionless datagrams; it is commonly referred
            to as the Fletcher checksum.";
          reference
           "OSPF Version 2, Section 12.1.7 LS checksum";
          smiv2:max-access "read-only";
          smiv2:oid "1.3.6.1.2.1.14.17.1.8";
        }

        leaf ospfLocalLsdbAdvertisement {
          type binary {
            length "1..65535";
          }
          description
           "The entire link state advertisement, including
            its header.
            
            Note that for variable length LSAs, SNMP agents
            may not be able to return the largest string size.";
          reference
           "OSPF Version 2, Section 12 Link State
            Advertisements";
          smiv2:max-access "read-only";
          smiv2:oid "1.3.6.1.2.1.14.17.1.9";
        }
      }
    }

    container ospfVirtLocalLsdbTable {
      description
       "The OSPF Process's link-local link state database
        for virtual links.
        
        This table is identical to the OSPF LSDB Table
        in format, but contains only link-local Link State
        Advertisements for virtual links.  The purpose is to
        allow link-local LSAs to be displayed for each virtual
        interface.  This table is implemented to support type-9 LSAs
        that are defined in 'The OSPF Opaque LSA Option'.";
      reference
       "OSPF Version 2, Section 12 Link State
        Advertisements and The OSPF Opaque LSA Option";
      smiv2:oid "1.3.6.1.2.1.14.18";

      list ospfVirtLocalLsdbEntry {
        key "ospfVirtLocalLsdbTransitArea ospfVirtLocalLsdbNeighbor ospfVirtLocalLsdbType ospfVirtLocalLsdbLsid ospfVirtLocalLsdbRouterId";
        description
         "A single link state advertisement.";
        smiv2:oid "1.3.6.1.2.1.14.18.1";

        leaf ospfVirtLocalLsdbTransitArea {
          type OSPF-MIB:AreaID;
          description
           "The transit area that the virtual link
            traverses.  By definition, this is not 0.0.0.0.";
          reference
           "OSPF Version 2, Appendix C.3 Interface parameters";
          smiv2:max-access "not-accessible";
          smiv2:oid "1.3.6.1.2.1.14.18.1.1";
        }

        leaf ospfVirtLocalLsdbNeighbor {
          type OSPF-MIB:RouterID;
          description
           "The Router ID of the virtual neighbor.";
          reference
           "OSPF Version 2, Appendix C.3 Interface parameters";
          smiv2:max-access "not-accessible";
          smiv2:oid "1.3.6.1.2.1.14.18.1.2";
        }

        leaf ospfVirtLocalLsdbType {
          type enumeration {
            enum "localOpaqueLink" {
              value "9";
            }
          }
          description
           "The type of the link state advertisement.
            Each link state type has a separate
            advertisement format.";
          reference
           "OSPF Version 2, Appendix A.4.1 The Link State
            Advertisement header";
          smiv2:max-access "not-accessible";
          smiv2:oid "1.3.6.1.2.1.14.18.1.3";
        }

        leaf ospfVirtLocalLsdbLsid {
          type inet:ipv4-address;
          description
           "The Link State ID is an LS Type Specific field
            containing a 32-bit identifier in IP address format;
            it identifies the piece of the routing domain
            that is being described by the advertisement.";
          reference
           "OSPF Version 2, Section 12.1.4 Link State ID";
          smiv2:max-access "not-accessible";
          smiv2:oid "1.3.6.1.2.1.14.18.1.4";
        }

        leaf ospfVirtLocalLsdbRouterId {
          type OSPF-MIB:RouterID;
          description
           "The 32-bit number that uniquely identifies the
            originating router in the Autonomous System.";
          reference
           "OSPF Version 2, Appendix C.1 Global parameters";
          smiv2:max-access "not-accessible";
          smiv2:oid "1.3.6.1.2.1.14.18.1.5";
        }

        leaf ospfVirtLocalLsdbSequence {
          type int32;
          description
           "The sequence number field is a signed 32-bit
            integer.  It starts with the value '80000001'h,
            or -'7FFFFFFF'h, and increments until '7FFFFFFF'h.
            Thus, a typical sequence number will be very negative.
            It is used to detect old and duplicate link state
            advertisements.  The space of sequence numbers is linearly
            ordered.  The larger the sequence number, the more recent
            the advertisement.";
          reference
           "OSPF Version 2, Section 12.1.6 LS sequence
            number";
          smiv2:max-access "read-only";
          smiv2:oid "1.3.6.1.2.1.14.18.1.6";
        }

        leaf ospfVirtLocalLsdbAge {
          type int32;
          units "seconds";
          description
           "This field is the age of the link state
            advertisement in seconds.";
          reference
           "OSPF Version 2, Section 12.1.1 LS age";
          smiv2:max-access "read-only";
          smiv2:oid "1.3.6.1.2.1.14.18.1.7";
        }

        leaf ospfVirtLocalLsdbChecksum {
          type int32;
          description
           "This field is the checksum of the complete
            contents of the advertisement, excepting the
            age field.  The age field is excepted so that
            
            an advertisement's age can be incremented
            without updating the checksum.  The checksum
            used is the same that is used for ISO
            connectionless datagrams; it is commonly
            referred to as the Fletcher checksum.";
          reference
           "OSPF Version 2, Section 12.1.7 LS checksum";
          smiv2:max-access "read-only";
          smiv2:oid "1.3.6.1.2.1.14.18.1.8";
        }

        leaf ospfVirtLocalLsdbAdvertisement {
          type binary {
            length "1..65535";
          }
          description
           "The entire link state advertisement, including
            its header.";
          reference
           "OSPF Version 2, Section 12 Link State
            Advertisements.
            
            Note that for variable length LSAs, SNMP agents
            may not be able to return the largest string size.";
          smiv2:max-access "read-only";
          smiv2:oid "1.3.6.1.2.1.14.18.1.9";
        }
      }
    }

    container ospfAsLsdbTable {
      description
       "The OSPF Process's AS-scope LSA link state database.
        The database contains the AS-scope Link State
        Advertisements from throughout the areas that
        the device is attached to.
        
        This table is identical to the OSPF LSDB Table
        in format, but contains only AS-scope Link State
        Advertisements.  The purpose is to allow AS-scope
        LSAs to be displayed once for the router rather
        than once in each non-stub area.";
      reference
       "OSPF Version 2, Section 12 Link State
        Advertisements";
      smiv2:oid "1.3.6.1.2.1.14.19";

      list ospfAsLsdbEntry {
        key "ospfAsLsdbType ospfAsLsdbLsid ospfAsLsdbRouterId";
        description
         "A single link state advertisement.";
        smiv2:oid "1.3.6.1.2.1.14.19.1";

        leaf ospfAsLsdbType {
          type enumeration {
            enum "asExternalLink" {
              value "5";
            }
            enum "asOpaqueLink" {
              value "11";
            }
          }
          description
           "The type of the link state advertisement.
            Each link state type has a separate
            advertisement format.";
          reference
           "OSPF Version 2, Appendix A.4.1 The Link State
            Advertisement header";
          smiv2:max-access "not-accessible";
          smiv2:oid "1.3.6.1.2.1.14.19.1.1";
        }

        leaf ospfAsLsdbLsid {
          type inet:ipv4-address;
          description
           "The Link State ID is an LS Type Specific field
            containing either a Router ID or an IP address;
            
            it identifies the piece of the routing domain
            that is being described by the advertisement.";
          reference
           "OSPF Version 2, Section 12.1.4 Link State ID";
          smiv2:max-access "not-accessible";
          smiv2:oid "1.3.6.1.2.1.14.19.1.2";
        }

        leaf ospfAsLsdbRouterId {
          type OSPF-MIB:RouterID;
          description
           "The 32-bit number that uniquely identifies the
            originating router in the Autonomous System.";
          reference
           "OSPF Version 2, Appendix C.1 Global parameters";
          smiv2:max-access "not-accessible";
          smiv2:oid "1.3.6.1.2.1.14.19.1.3";
        }

        leaf ospfAsLsdbSequence {
          type int32;
          description
           "The sequence number field is a signed 32-bit
            integer.  It starts with the value '80000001'h,
            or -'7FFFFFFF'h, and increments until '7FFFFFFF'h.
            Thus, a typical sequence number will be very negative.
            It is used to detect old and duplicate link state
            advertisements.  The space of sequence numbers is linearly
            ordered.  The larger the sequence number, the more recent
            the advertisement.";
          reference
           "OSPF Version  2,  Section  12.1.6  LS  sequence
            number";
          smiv2:max-access "read-only";
          smiv2:oid "1.3.6.1.2.1.14.19.1.4";
        }

        leaf ospfAsLsdbAge {
          type int32;
          units "seconds";
          description
           "This field is the age of the link state
            advertisement in seconds.";
          reference
           "OSPF Version 2, Section 12.1.1 LS age";
          smiv2:max-access "read-only";
          smiv2:oid "1.3.6.1.2.1.14.19.1.5";
        }

        leaf ospfAsLsdbChecksum {
          type int32;
          description
           "This field is the checksum of the complete
            contents of the advertisement, excepting the
            age field.  The age field is excepted so that
            an advertisement's age can be incremented
            without updating the checksum.  The checksum
            used is the same that is used for ISO
            connectionless datagrams; it is commonly referred
            to as the Fletcher checksum.";
          reference
           "OSPF Version 2, Section 12.1.7 LS checksum";
          smiv2:max-access "read-only";
          smiv2:oid "1.3.6.1.2.1.14.19.1.6";
        }

        leaf ospfAsLsdbAdvertisement {
          type binary {
            length "1..65535";
          }
          description
           "The entire link state advertisement, including
            its header.";
          reference
           "OSPF Version 2, Section 12 Link State
            Advertisements.
            
            Note that for variable length LSAs, SNMP agents
            may not be able to return the largest string size.";
          smiv2:max-access "read-only";
          smiv2:oid "1.3.6.1.2.1.14.19.1.7";
        }
      }
    }

    container ospfAreaLsaCountTable {
      description
       "This table maintains per-area, per-LSA-type counters";
      smiv2:oid "1.3.6.1.2.1.14.20";

      list ospfAreaLsaCountEntry {
        key "ospfAreaLsaCountAreaId ospfAreaLsaCountLsaType";
        description
         "An entry with a number of link advertisements
          
          of a given type for a given area.";
        smiv2:oid "1.3.6.1.2.1.14.20.1";

        leaf ospfAreaLsaCountAreaId {
          type OSPF-MIB:AreaID;
          description
           "This entry Area ID.";
          smiv2:max-access "not-accessible";
          smiv2:oid "1.3.6.1.2.1.14.20.1.1";
        }

        leaf ospfAreaLsaCountLsaType {
          type enumeration {
            enum "routerLink" {
              value "1";
            }
            enum "networkLink" {
              value "2";
            }
            enum "summaryLink" {
              value "3";
            }
            enum "asSummaryLink" {
              value "4";
            }
            enum "multicastLink" {
              value "6";
            }
            enum "nssaExternalLink" {
              value "7";
            }
            enum "areaOpaqueLink" {
              value "10";
            }
          }
          description
           "This entry LSA type.";
          smiv2:max-access "not-accessible";
          smiv2:oid "1.3.6.1.2.1.14.20.1.2";
        }

        leaf ospfAreaLsaCountNumber {
          type yang:gauge32;
          description
           "Number of LSAs of a given type for a given area.";
          smiv2:max-access "read-only";
          smiv2:oid "1.3.6.1.2.1.14.20.1.3";
        }
      }
    }
  }

  smiv2:alias "ospf" {
    smiv2:oid "1.3.6.1.2.1.14";
  }

  smiv2:alias "ospfGeneralGroup" {
    smiv2:oid "1.3.6.1.2.1.14.1";
  }

  smiv2:alias "ospfRouteGroup" {
    smiv2:oid "1.3.6.1.2.1.14.13";
  }

  smiv2:alias "ospfIntraArea" {
    smiv2:oid "1.3.6.1.2.1.14.13.1";
  }

  smiv2:alias "ospfInterArea" {
    smiv2:oid "1.3.6.1.2.1.14.13.2";
  }

  smiv2:alias "ospfExternalType1" {
    smiv2:oid "1.3.6.1.2.1.14.13.3";
  }

  smiv2:alias "ospfExternalType2" {
    smiv2:oid "1.3.6.1.2.1.14.13.4";
  }

  smiv2:alias "ospfConformance" {
    smiv2:oid "1.3.6.1.2.1.14.15";
  }

  smiv2:alias "ospfGroups" {
    smiv2:oid "1.3.6.1.2.1.14.15.1";
  }

  smiv2:alias "ospfCompliances" {
    smiv2:oid "1.3.6.1.2.1.14.15.2";
  }

}
