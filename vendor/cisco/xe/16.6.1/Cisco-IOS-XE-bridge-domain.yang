module Cisco-IOS-XE-bridge-domain {
  namespace "http://cisco.com/ns/yang/Cisco-IOS-XE-bridge-domain";
  prefix ios-bd;

  import ietf-inet-types {
    prefix inet;
  }

  import Cisco-IOS-XE-native {
    prefix ios;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Bridge Domain Yang model
     Copyright (c) 2016 by Cisco Systems, Inc.
     All rights reserved.";

  // =========================================================================
  // REVISION
  // =========================================================================
  revision 2017-02-07 {
    description
      "Initial revision";
  }

  grouping config-bdomain-mode-grouping {
    container ip {
      description
        "IP related commands";
      container igmp {
        description
          "IP igmp commands";
        container snooping {
          description
            "IP igmp snooping commands";
          presence "true";
          container check {
            description
              "enforce TTL or Rtr-Alert Option checking";
            leaf rtr-alert-option {
              description
                "Only accept IGMP packets with router-alert option";
              type empty;
            }
            leaf ttl {
              description
                "Only accept IGMP packets with TTL=1";
              type empty;
            }
          }
          container explicit-tracking {
            description
              "IGMP explicit host tracking configuration";
            leaf limit {
              description
                "Explicit Host Tracking DB limit";
              type empty;
            }
          }
          leaf immediate-leave {
            description
              "Enable IGMPv2 immediate leave processing";
            type empty;
          }
          leaf last-member-query-count {
            description
              "Last member query count";
            type uint8 {
              range "1..7";
            }
          }
          leaf last-member-query-interval {
            description
              "Last member query interval";
            type uint16 {
              range "100..32767";
            }
          }
          container mrouter {
            description
              "Configure an L2 port as a multicast router port";
            leaf interface {
              description
                "next-hop interface to mrouter";
              type empty;
            }
          }
          container querier {
            description
              "Enable IGMP querier for this Bdomain";
            presence "true";
            leaf address {
              description
                "IGMP querier source IP address";
              type empty;
            }
            leaf max-response-time {
              description
                "IGMP querier maximum response time (sec)";
              type empty;
            }
            leaf query-interval {
              description
                "IGMP querier query interval (sec)";
              type empty;
            }
            leaf tcn {
              description
                "IGMP querier TCN related parameters";
              type empty;
            }
            leaf timer {
              description
                "IGMP other querier timer";
              type empty;
            }
            leaf version {
              description
                "IGMP version";
              type empty;
            }
          }
          leaf report-suppression {
            description
              "Enable IGMP report suppression";
            type empty;
          }
          leaf robustness-variable {
            type uint8 {
              range "1..3";
            }
          }
          leaf static {
            description
              "Configure an L2 port as a member of a group";
            type inet:ipv4-address;
          }
        }
      }
    }
    container mac {
      description
        "MAC Address related commands";
      leaf aging-time {
        description
          "Set age time of mac addresses per bridge domain";
        type uint16 {
          range "30..3600";
        }
      }
      leaf learning {
        description
          "Disable mac learning on bridge domain";
        type empty;
      }
      container limit {
        description
          "Limit the MAC Addresses learnt";
        container action {
          description
            "action when exceeding the limit";
          container flooding {
            description
              "Mac flooding";
            leaf disable {
              description
                "disable";
              type empty;
            }
          }
        }
        container maximum {
          description
            "Maximum";
          leaf addresses {
            description
              "Addresses";
            type uint32 {
              range "1..65536";
            }
          }
        }
      }
    }
    container member {
      description
        "bridge-domain member";
      list mem-ipv4 {
        key "mem-ipv4";
        leaf mem-ipv4 {
          description
            "IP address of the peer";
          type inet:ipv4-address;
        }
        list mem-vcid {
          key "mem-vcid";
          leaf mem-vcid {
            description
              "<1..4294967295>;;Enter VC ID value";
            type uint32 {
              range "1..4294967295";
            }
          }
          container encapsulation {
            description
              "Data encapsulation method";
            presence "true";
            leaf mpls {
              description
                "Use MPLS encapsulation";
              type empty;
            }
          }
          container template {
            description
              "Template to use for encapsulation and protocol configuration";
            presence "true";
            leaf template {
              description
                "<WORD>;;template name (Max size 32)";
              type string;
            }
          }
        }
        container encapsulation {
          description
            "Data encapsulation method";
          leaf mpls {
            description
              "Use MPLS encapsulation";
            type empty;
          }
        }
        leaf template {
          description
            "Template to use for encapsulation and protocol configuration";
          type string;
        }
      }
      list ACR {
        key "acr-int";
        leaf acr-int {
          description
            "<WORD>;;Virtual ACR interface";
          type string;
        }
        container service-instance {
          description
            "ethernt serivce instance";
          list id {
            key "id";
            leaf id {
              description
                "<1..8000>;;Service Instance Identifier";
              type uint16 {
                range "1..8000";
              }
            }
            leaf split-horizon {
              description
                "Configure this port as a member of a split horizon group";
              type empty;
            }
          }
        }
      }
      leaf Analysis-Module {
        description
          "Cisco network analysis service module";
        type uint8;
      }
      leaf Fcpa {
        description
          "Fiber Channel";
        type uint8;
      }
      leaf SBC {
        description
          "Session Border Controller";
        type uint32 {
          range "0..2147483647";
        }
      }
      leaf SONET_ACR {
        description
          "Virtual SONET-ACR controller";
        type uint8;
      }

      leaf _controller {
        type string;
      }

      leaf Service-Engine {
        description
          "Cisco service engine module";
        type uint8;
      }
      leaf Tunnel-tp {
        description
          "MPLS Transport Profile interface";
        type uint16 {
          range "0..65535";
        }
      }
      leaf VPN {
        description
          "VPN interface";
        type uint32 {
          range "0..2147483647";
        }
      }
      leaf Virtual-TokenRing {
        description
          "Virtual TokenRing";
        type uint32 {
          range "0..2147483647";
        }
      }
      leaf ucse {
        description
          "Cisco ucse server";
        type uint8;
      }
      leaf vasileft {
        description
          "VasiLeft interface";
        type uint16 {
          range "1..2000";
        }
      }
      leaf vasiright {
        description
          "VasiRight interface";
        type uint16 {
          range "1..2000";
        }
      }
      leaf vfi {
        description
          "Enter VFI name";
        type string;
      }
      leaf vni {
        type uint32 {
          range "4096..16777215";
        }
      }
      list member-interface {
        key "interface";
        leaf interface {
          type string;
        }
        leaf interface-id {
          type union {
            type string;
            type uint32;
          }
        }
        leaf service-instance {
          description
            "ethernt serivce instance";
          type uint32 {
            range "1..8000";
          }
        }
        container split-horizon {
          description
            "Configure this port as a member of a split horizon group";
          leaf group {
            description
              "Split-horizon group";
            type uint8;
          }
        }
      }
    }
    leaf shutdown {
      description
        "Take the bridge domain admin down";
      type empty;
    }
  }

  grouping config-bridge-domain-grouping {
    list brd-id {
      key "bridge-domain-id";
      leaf bridge-domain-id {
        description
          "<1..8192>;;bridge-domain ID";
        type uint16 {
          range "1..8192";
        }
      }
      uses config-bdomain-mode-grouping;
    }

    container c-mac {
      description
        "Configure c-mac global commands";
      leaf aging-time {
        description
          "Configure aging time for c-mac bridge domains";
        type uint16 {
          range "30..3600";
        }
      }
    }

    container otv {
      description
        "Configure overlay bridge domains";
      container default {
        description
          "Change default setting of overlay bridge domains";
        leaf age-time {
          description
            "Configure default mac aging time of overlay bridge domains";
          type uint16 {
            range "30..3600";
          }
        }
      }
    }

    container parameterized {
      description
        "bridge-domain is derived from parameters";
      container vlan {
        description
          "bridge-domain from service instance vlan";
        presence "true";
        uses config-bdomain-mode-grouping;
      }
    }
  }

  /////////////////////////////////////////////////////////
  // native / bridge-domain
  /////////////////////////////////////////////////////////
  augment "/ios:native/ios:bridge-domain" {
    uses config-bridge-domain-grouping;
  }
}
