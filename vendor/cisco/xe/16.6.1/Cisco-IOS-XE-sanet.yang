module Cisco-IOS-XE-sanet {
  namespace "http://cisco.com/ns/yang/Cisco-IOS-XE-sanet";
  prefix ios-sanet;

  import Cisco-IOS-XE-native {
    prefix ios;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Session Aware Networking (SaNet) Yang model.
     Copyright (c) 2016 by Cisco Systems, Inc.
     All rights reserved.";

  // =========================================================================
  // REVISION
  // =========================================================================
  revision 2017-02-07 {
    description
      "Initial revision";
  }


  grouping config-access-session-grouping {
    container access-session { 
      description
        "Access Sesion Global Configuration Commands";
      container attributes {
        description
          "Attributes Filter List Configuration";
        container filter-list {
          description
            "Filter List Configuration";
          list list {
            description
              "Filter List";
            key name;
            leaf name {
              type string;
            }
            leaf cdp {
              description
                "Include CDP Protocl attributes";
              type empty;
            }
            leaf dhcp {
              description
                "Include DHCP Protocl attributes";
              type empty;
            }
            leaf lldp {
              description
                "Include LLDP Protocl attributes";
              type empty;
            }
          }
        }
      }

      container mac-move {
        description
          "Set required action when a MAC move is detected";
        leaf deny {
          description
            "DENY MAC moves (clears existing session)";
          type empty;
        }
      }
    }
  }

  grouping config-authentication-grouping {
    container authentication {
      description
        "Auth Manager Global Configuration Commands";
      container command {
        description
          "Allow the following CoA commands to be ignored by the switch";
        container bounce-port {
          description
            "CoA bounce-port command";
          leaf ignore {
            description
              "ignore disable-port CoA command";
            type empty;
          }
        }
        container disable-port {
          description
            "CoA disable-port command";
          leaf ignore {
            description "";
            type empty;
          }
        }
      }
      container critical {
        description
          "Set Critical Authentication parameters";
        container recovery {
          description
            "Set Critical Authentication Recovery parameters";
          leaf delay {
            description
              "Set Critical Authentication Recovery Delay period";
            type uint32 {
              range "1..10000";
            }
          }
        }
      }
      container mac-move {
        description
          "Set required action when a MAC move is detected";
        leaf permit {
          description
            "PERMIT MAC moves (clears existing session)";
          type empty;
        }
      }
    }
  }

  grouping config-interface-authentication-grouping {
    container authentication {
      description
        "Auth Manager Interface Configuration Commands";
      leaf control-direction {
        description
          "Set the control-direction on the interface";
        type enumeration {
          enum "both";
          enum "in";
        }
      }
      container event {
        description
          "Set action for authentication events";
        container server {
          description
            "Configure actions for AAA server events";
          container alive {
            description
              "Configure AAA server alive action";
            container action {
              description
                "Required action for authentication event";
              leaf reinitialize {
                description
                  "Reinitialize all authorized clients";
                type empty;
              }
            }
          }
          container dead {
            description
              "Configure AAA server dead action";
            container action {
              description
                "Required action for authentication event";
              container authorize {
                description
                  "Authorize the port";
                presence "true";
                leaf vlan {
                  description
                    "Configure Critical Authorization VLAN";
                  type uint16;
                }
                leaf voice {
                  description
                    "Authorize the port for VOICE traffic";
                  type empty;
                }
              }
              container reinitialize {
                description
                  "Reinitialize all client on the port";
                leaf vlan {
                  description
                    "Configure Critical Authorization VLAN";
                  type uint16;
                }
              }
            }
          }
        }
        container fail {
          description
            "Configure actions for AAA fail events";
          container action {
            description
              "Required action for fail event";
            container authorize {
              description
                "Reinitialize all authorized clients";
              leaf vlan {
                type uint16;
              }
            }
          }
        }
        container no-response {
          description
            "Configure actions for AAA no-response events";
          container action {
            description
              "Required action for no-response event";
            container authorize {
              description
                "Reinitialize all authorized clients";
              leaf vlan {
                type uint16;
              }
            }
          }
        }
      }
      leaf fallback {
        description
          "Enable the Webauth fallback mechanism";
        type string;
      }
      leaf host-mode {
        description
          "Set the Host mode for authentication on this interface";
        type enumeration {
          enum "multi-auth";
          enum "multi-domain";
          enum "multi-host";
          enum "single-host";
        }
      }
      leaf open {
        description
          "Enable or Disable open access on this port";
        type empty;
      }
      container order {
        description
          "Add an authentication method to the order list";
        leaf dot1x {
          description
            "Authentication method dot1x allowed";
          type empty;
        }
        leaf mab {
          description
            "Authentication method mab allowed";
          type empty;
        }
        leaf webauth {
          description
            "Authentication method webauth allowed";
          type empty;
        }
      }
      container priority {
        description
          "Add an authentication method to the priority list";
        leaf dot1x {
          description
            "Authentication method dot1x allowed";
          type empty;
        }
        leaf mab {
          description
            "Authentication method mab allowed";
          type empty;
        }
        leaf webauth {
          description
            "Authentication method webauth allowed";
          type empty;
        }
      }
      leaf port-control {
        description
          "set the port-control value";
        type enumeration {
          enum "auto";
          enum "force-authorized";
          enum "force-unauthorized";
        }
      }
      leaf periodic {
        description
          "Enable or Disable Reauthentication for this port";
        type empty;
      }
      container timer {
        description
          "Set authentication timer values";

        container reauthenticate {
          description
            "Time in seconds after which an automatic re-authenticationshould be initiated (default 1 hour)";
          leaf value {
            type uint16;
          }
          leaf server {
            description
              "Obtain re-authentication timeout value from the server";
            type empty;
          }
        }

        container inactivity {
          description
            "Interval in seconds after which if there is no activity fromthe client then it will be unauthorized (default OFF)";
          container value {
            leaf value {
              type uint16;
            }
            leaf dynamic {
              description
                "Initiate a dynamic probe on inactivity timeout";
              type empty;
            }
          }
          container server {
            description
              "Obtain inactivity timeout value from the server";
            presence "true";
            leaf dynamic {
              description
                "Initiate a dynamic probe on inactivity timeout";
              type empty;
            }
          }
        }

        leaf restart {
          description
            "Interval in seconds after which an attempt should be made toauthenticate an unauthorized port (default 60 sec)";
          type uint16;
        }
      }
      leaf violation {
        description
          "Configure action to take on security violations";
        type enumeration {
          enum "protect";
          enum "replace";
          enum "restrict";
          enum "shutdown";
        }
      }
    }
  }

  // interface * / mab
  grouping config-interface-mab-grouping {
    container mab {
      presence "true";
      leaf eap {
        type empty;
      }
    }
  }

  /////////////////////////////////////////////////////////
  // native
  /////////////////////////////////////////////////////////
  augment "/ios:native" {
    uses config-access-session-grouping;
    uses config-authentication-grouping;
  }

  /////////////////////////////////////////////////////////
  // native / interface  * / authentication
  /////////////////////////////////////////////////////////
  augment "/ios:native/ios:interface/ios:FastEthernet" {
    uses config-interface-authentication-grouping;
    uses config-interface-mab-grouping;
  }

  augment "/ios:native/ios:interface/ios:GigabitEthernet" {
    uses config-interface-authentication-grouping;
    uses config-interface-mab-grouping;
  }

  augment "/ios:native/ios:interface/ios:TenGigabitEthernet" {
    uses config-interface-authentication-grouping;
    uses config-interface-mab-grouping;
  }

  augment "/ios:native/ios:interface/ios:Port-channel" {
    uses config-interface-authentication-grouping;
    uses config-interface-mab-grouping;
  }

  augment "/ios:native/ios:interface/ios:Virtual-Template" {
    uses config-interface-mab-grouping;
  }

  augment "/ios:native/ios:interface/ios:VirtualPortGroup" {
    uses config-interface-mab-grouping;
  }
} //module
