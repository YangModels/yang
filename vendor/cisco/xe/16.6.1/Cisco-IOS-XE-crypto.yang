module Cisco-IOS-XE-crypto {
  namespace "http://cisco.com/ns/yang/Cisco-IOS-XE-crypto";
  prefix ios-crypto;

  import ietf-inet-types {
    prefix inet;
  }


  import Cisco-IOS-XE-native {
    prefix ios;
  }

  import Cisco-IOS-XE-types {
    prefix ios-types;
  }

  import Cisco-IOS-XE-features {
    prefix ios-features;
  }

  import Cisco-IOS-XE-tunnel {
    prefix ios-tun;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Crypto Yang Model.
     Copyright (c) 2016-2017 by Cisco Systems, Inc.
     All rights reserved.";

  // =========================================================================
  // REVISION
  // =========================================================================
  revision 2017-05-10 {
    description
      "inet:ipv6-prefix changed to ios-types:ipv6-prefix";
  }
  revision 2017-05-09 {
    description 
      "adding dependency tailf extension in crypto-map container 
      to add ability to configure multiple crypto commands and interface
      commands in single RPC";
  }
  revision 2017-03-28 {
    description
      "modified name of map-ipv4 container to generic name 
       crypto-map container for ipv4 type crypto maps";
  }
  revision 2017-03-27 {
    description
      "get-config only gets one config though multiple configs exist on device";
  }
  revision 2017-03-24 {
    description
      "Remove banner";
  }
  revision 2017-03-02 {
    description
      "crypto ikev2 is missing ipv6 address leaf in the model";
  }
  revision 2017-02-07 {
    description
      "Initial revision";
  }


  grouping crypto-pki-token-grouping {
    // max-retries  maximum number of consecutive login failures permitted
    container removal {
      description
        "actions to take after token removal";
      leaf timeout {
        description
          "seconds after token removal at which keys from the token are cleared";
        type uint16 {
          range "0..480";
        }
      }
    }
    // secondary    token-specific configuration files
    // user-pin     PIN to access token
  }

  grouping crypto-map-common-grouping {
    leaf description {
      description
        "Description of the crypto map statement policy";
      type string;
    }
    container dialer {
      description
        "Dialer related commands";
      leaf pre-classify {
        description
          "Enable dialer list classification before initiating IKE";
        type empty;
      }
    }
    container match {
      description
        "Match values";
      leaf address {
        description
          "Match address of packets to encrypt";
        type ios-types:ext-acl-type;
      }
    }
    container qos {
      description
        "Quality of Service related commands";
      leaf pre-classify {
        description
          "Enable QOS classification before packets are tunnel encapsulated";
        type empty;
      }
    }
    container reverse-route {
      description
        "Reverse Route Injection.";
      presence "true";
      choice remote-peer-static {
        case remote-peer-case {
          container remote-peer-conatiner {
            leaf remote-peer {
              description
                "Create route in route table for remote tunnel endpoint";
              type inet:ip-address;
            }
            leaf gateway {
              description
                "Force encrypted traffic via this preferred gateway";
              type empty;
            }
            leaf static {
              description
                "Create routes based on static ACLs permanently";
              type empty;
            }
          }
        }
        case static-case {
          leaf static {
            description
              "Create routes based on static ACLs permanently";
            type empty;
          }
        }
      }
    }
  }

  grouping crypto-map-common-set-security-association-grouping {
    leaf dfbit {
      description
        "Handling of encapsulated DF bit.";
      type enumeration {
        enum "clear";
        enum "copy";
        enum "set";
      }
    }
    container dummy {
      description
        "Enable transmitting dummy packets";
      leaf pps {
        description
          "Simulated traffic rate (in pps)";
        type uint8 {
          range "0..25";
        }
      }
      leaf seconds {
        description
          "Simulated traffic rate (in seconds)";
        type uint16 {
          range "1..3600";
        }
      }
    }
    leaf ecn {
      description
        "Handling of ECN bit";
      type enumeration {
        enum "discard";
        enum "propagate";
      }
    }
    container idle-time-container {
      leaf idle-time {
        description
          "Automatically delete IPSec SAs after a given idle period.";
        type uint32 {
          range "60..86400";
        }
      }
      leaf default {
        description
          "All SAs idle-out reset to default peer";
        type empty;
      }
    }
    container lifetime {
      description
        "security association lifetime";
      leaf days {
        description
          "Time-based key duration in days";
        type uint8 {
          range "1..30";
        }
      }
      leaf kilobytes {
        description
          "Volume-based key duration";
        type union {
          type uint64 {
            range "2560..4294967295";
          }
          type enumeration {
            enum "disable";
          }
        }
      }
      leaf seconds {
        description
          "Time-based key duration in seconds";
        type uint64 {
          range "120..2592000";
        }
      }
    }
    container replay {
      description
        "Set replay checking.";
      leaf disable {
        description
          "Disable replay checking";
        type empty;
      }
      leaf window-size {
        description
          "Set replay window size.";
        type enumeration {
          enum "1024";
          enum "128";
          enum "256";
          enum "512";
          enum "64";
        }
      }
    }
  }

  grouping crypto-map-common-set-grouping {
    leaf group {
      description
        "Set the san group parameters";
      type string;
    }
    leaf identity {
      description
        "Identity restriction";
      type string;
    }
    leaf ikev2-profile {
      description
        "Specify ikev2 Profile";
      type string;
    }
    leaf isakmp-profile {
      description
        "Specify isakmp Profile";
      type string;
    }
    container peer {
      description
        "Allowed Encryption/Decryption peer.";
      leaf address {
        type union {
          type inet:ipv4-address;
          type string;
          type inet:ipv6-address;
        }
      }
      leaf default {
        description
          "Reset to default peer in list in the event of a failure";
        type empty;
      }
      leaf dynamic {
        description
          "Resolve the peer address at the time of negotiation";
        type empty;
      }
    }
    container pfs {
      description
        "Specify pfs settings";
      presence "true";
      leaf group {
        type enumeration {
          enum "group1";
          enum "group14";
          enum "group15";
          enum "group16";
          enum "group19";
          enum "group2";
          enum "group20";
          enum "group21";
          enum "group24";
          enum "group5";
        }
      }
    }
    container reverse-route {
      description
        "Reverse Route Injection";
      leaf distance {
        description
          "Distance metric for this static route";
        type uint8;
      }
      leaf tag {
        description
          "Create route and tag it";
        type uint64 {
          range "1..4294967295";
        }
      }
    }
    leaf-list transform-set {
      description
        "Specify list of transform sets in priority order";
      type string;
    }
  }

  grouping crypto-dynamic-map-grouping {
    uses crypto-map-common-grouping;
    container set {
      description
        "Set values for encryption/decryption";
      uses crypto-map-common-set-grouping;
      container ip-in {
        container ip {
          description
            "Interface Internet Protocol config commands";
          leaf access-group {
            description
              "Specify access control for packets";
            type ios-types:exp-acl-type;
          }
          leaf in {
            description
              "inbound packets";
            type empty;
          }
        }
      }
      container ip-out {
        container ip {
          description
            "Interface Internet Protocol config commands";
          leaf access-group {
            description
              "Specify access control for packets";
            type ios-types:exp-acl-type;
          }
          leaf out {
            description
              "outbound packets";
            type empty;
          }
        }
      }
      container nat {
        description
          "Set NAT translation";
        leaf demux {
          description
            "Set NAT demultiplexing";
          type empty;
        }
      }
      container peer-container {
        leaf peer {
          description
            "Allowed Encryption/Decryption peer.";
          type inet:host;
        }
        leaf default {
          description
            "Reset to default peer in list in the event of a failure";
          type empty;
        }
      }
      container security-association {
        description
          "Security association parameters";
        uses crypto-map-common-set-security-association-grouping;
      }
    }
  }

  grouping crypto-dynamic-map-default-grouping {
    leaf description {
      description
        "Description of the crypto map statement policy";
      type empty;
    }
    container dialer {
      description
        "Dialer related commands";
      leaf pre-classify {
        description
          "Enable dialer list classification before initiating IKE";
        type empty;
      }
    }
    container match {
      description
        "Match values";
      leaf address {
        description
          "Match address of packets to encrypt";
        type empty;
      }
    }
    container qos {
      description
        "Quality of Service related commands";
      leaf pre-classify {
        description
          "Enable QOS classification before packets are tunnel encapsulated";
        type empty;
      }
    }
    container reverse-route {
      description
        "Reverse Route Injection.";
      presence "true";
    }
    container set {
      description
        "Set values for encryption/decryption";
      leaf group {
        description
          "Set the san group parameters";
        type empty;
      }
      leaf identity {
        description
          "Identity restriction";
        type empty;
      }
      leaf ikev2-profile {
        description
          "Specify ikev2 Profile";
        type string;
      }
      container ip {
        description
          "Interface Internet Protocol config commands";
        leaf access-group {
          description
            "Specify access control for packets";
          type ios-types:exp-acl-type;
        }
        leaf direction {
          type enumeration {
            enum "in";
            enum "out";
          }
        }
      }
      leaf isakmp-profile {
        description
          "Specify isakmp Profile";
        type string;
      }
      container nat {
        description
          "Set NAT translation";
        leaf demux {
          description
            "Set NAT demultiplexing";
          type empty;
        }
      }
      container peer-container {
        leaf peer {
          description
            "Allowed Encryption/Decryption peer.";
          type inet:host;
        }
        leaf default {
          description
            "Reset to default peer in list in the event of a failure";
          type empty;
        }
      }
      container pfs {
        description
          "Specify pfs settings";
        presence "true";
      }
      container reverse-route {
        description
          "Reverse Route Injection";
        presence "true";
      }
      container security-association {
        description
          "Security association parameters";
        leaf dfbit {
          description
            "Handling of encapsulated DF bit.";
          type empty;
        }
        container dummy {
          description
            "Enable transmitting dummy packets";
          presence "true";
        }
        leaf ecn {
          description
            "Handling of ECN bit";
          type empty;
        }
        container idle-time-container {
          leaf idle-time {
            description
              "Automatically delete IPSec SAs after a given idle period.";
            type empty;
          }
          leaf default {
            description
              "All SAs idle-out reset to default peer";
            type empty;
          }
        }
        container lifetime {
          description
            "security association lifetime";
          leaf days {
            description
              "Time-based key duration in days";
            type empty;
          }
          leaf kilobytes {
            description
              "Volume-based key duration";
            type empty;
          }
          leaf seconds {
            description
              "Time-based key duration in seconds";
            type empty;
          }
        }
        container replay {
          description
            "Set replay checking.";
          leaf disable {
            description
              "Disable replay checking";
            type empty;
          }
          leaf window-size {
            description
              "Set replay window size.";
            type empty;
          }
        }
      }
      leaf transform-set {
        description
          "Specify list of transform sets in priority order";
        type empty;
      }
    }
  }

  grouping crypto-gkm-local-server-id-grouping {
    container range {
      description
        "Assign range of Key Server Sender IDs (unique in entire group)";
      leaf lowest {
        type uint8 {
          range "0..1";
        }
      }
      leaf hyphen {
        type empty;
      }
      leaf highest {
        type uint8 {
          range "0..1";
        }
      }
    }
    leaf value {
      description
        "Assign Key Server Sender ID (unique in entire group)";
      type uint8 {
        range "0..1";
      }
    }
  }

  grouping crypto-gdoi-coop-ks-config-grouping {
    container local {
      description
        "Local key server configurations";
      presence "true";
      leaf priority {
        description
          "Set local server priority";
        type uint8;
      }
    }
    container peer {
      description
        "Peer server configurations";
      container address {
        description
          "Peer server address";
        leaf ipv4 {
          description
            "Set peer server ipv4 address";
          type inet:ipv4-address;
        }
      }
    }
    container protocol {
      description
        "Specify various protocol operational values";
      presence "true";
      leaf pdu {
        description
          "Maximum size of COOP messages";
        type uint32 {
          range "1..65000";
        }
      }
      leaf version {
        description
          "Set COOP ANN version";
        type enumeration {
          enum "base";
          enum "optimize";
        }
      }
    }
  }

  grouping crypto-gkm-sa-ipsec-grouping {
    container match {
      description
        "Match characteristics of packets to encrypt";
      container address {
        description
          "Match addresses of packets to encrypt";
        leaf ipv4 {
          description
            "Match ipv4 packets";
          type ios-types:ext-acl-type;
        }
        leaf ipv6 {
          description
            "Match ipv6 packets";
          type string;
        }
      }
    }
    leaf profile {
      description
        "Configure an ipsec profile for the SA";
      type string;
    }
    container replay {
      description
        "Set replay method";
      container counter {
        description
          "Enable anti-replay check for single source traffic by using sequence number";
        presence "true";
        leaf window-size {
          description
            "Set replay window size.";
          type enumeration {
            enum "1024";
            enum "128";
            enum "256";
            enum "512";
            enum "64";
          }
        }
      }
      container time {
        description
          "Enable anti-replay check for any traffic by using time";
        presence "true";
        leaf window-size {
          description
            "Time based replay window size";
          type uint8 {
            range "1..100";
          }
        }
      }
    }
    container tag {
      description
        "Set inline tagging method";
      container cts {
        description
          "Cisco Trust Security";
        leaf sgt {
          description
            "Security Group Tag";
          type empty;
        }
      }
    }
  }

  grouping crypto-gkm-sa-ipsec-default-grouping {
    container match {
      description
        "Match characteristics of packets to encrypt";
      container address {
        description
          "Match addresses of packets to encrypt";
        presence "true";
      }
    }
    leaf profile {
      description
        "Configure an ipsec profile for the SA";
      type empty;
    }
    container replay {
      description
        "Set replay method";
      presence "true";
    }
    container tag {
      description
        "Set inline tagging method";
      presence "true";
    }
  }

  grouping crypto-gkm-local-server-grouping {
    container address {
      description
        "Configure server source address";
      leaf ipv4 {
        description
          "Set ipv4 address of local server";
        type inet:ipv4-address;
      }
    }
    container authorization {
      description
        "Configure authorization for the group";
      container address {
        description
          "Set authorization by address";
        leaf ipv4 {
          description
            "Set authorization by address";
          type union {
            type uint16 {
              range "1..99";
            }
            type string;
          }
        }
      }
      leaf identity {
        description
          "Set authorization by identity";
        type string;
      }
    }
    leaf gdoi {
      description
        "Enable GDOI (ISAKMP) Protocol for Registration & Rekey";
      type empty;
    }
    leaf gikev2 {
      description
        "Enable G-IKEv2 (IKEv2) Protocol for Registration & Rekey";
      type string;
    }
    container group {
      description
        "Configure parameters for the group (e.g. Suite-B)";
      container size {
        description
          "Set Group Size for Suite-B counter transforms (SID length)";
        leaf large {
          description
            "32-bit Sender ID (FIPS 140-2 Operating Mode)";
          type empty;
        }
        leaf medium {
          description
            "24-bit Sender ID (Default)";
          type empty;
        }
        leaf small {
          description
            "Interoperable with GDOI / G-IKEv2 Standard";
          type enumeration {
            enum "12";
            enum "16";
            enum "8";
          }
        }
      }
    }
    container identifier {
      description
        "Enter Suite-B KSSID (Key Server Sender ID) config mode";
      container default {
        description
          "Set a command to its defaults";
        uses crypto-gkm-local-server-id-grouping;
      }
      uses crypto-gkm-local-server-id-grouping;
    }
    container redundancy {
      description
        "Enter cooperative key server configuration mode";
      container default {
        description
          "Set a command to its defaults";
        uses crypto-gdoi-coop-ks-config-grouping;
      }
      uses crypto-gdoi-coop-ks-config-grouping;
    }
    container registration {
      description
        "Configure registration for the group";
      leaf interface {
        description
          "Identify an interface on which to respond to GKM registrations";
        type string;
      }
      container periodic {
        description
          "Define periodic registrations for the group";
        container crl {
          description
            "On every new CRL";
          leaf trustpoint {
            description
              "For a PKI trustpoint";
            type string;
          }
        }
      }
    }
    container rekey {
      description
        "Configure rekey policy for the group";
      leaf acknowledgement {
        description
          "Request group members to acknowledge rekeys";
        type enumeration {
          enum "any";
          enum "cisco";
          enum "interoperable";
        }
      }
      container address {
        description
          "Define the rekey packet format";
        leaf ipv4 {
          description
            "Match ipv4 packets";
          type ios-types:ext-acl-type;
        }
      }
      container algorithm {
        description
          "Set the rekey encryption algorithm";
        leaf a3des-cbc {
          description
            "Triple DES in CBC mode";
          type empty;
        }
        leaf aes-128 {
          description
            "128 bit AES";
          type empty;
        }
        leaf aes-192 {
          description
            "192 bit AES";
          type empty;
        }
        leaf aes-256 {
          description
            "256 bit AES";
          type empty;
        }
        leaf des-cbc {
          description
            "DES in CBC mode";
          type empty;
        }
      }
      container authentication {
        description
          "Identify the rekey authentication keypair";
        container mypubkey {
          description
            "Identify a keypair associated with this device";
          leaf rsa {
            description
              "Identify an RSA keypair";
            type string;
          }
        }
      }
      container lifetime {
        description
          "Define the rekey lifetime";
        leaf days {
          description
            "Time-based key duration in days";
          type uint8 {
            range "1..30";
          }
        }
        leaf seconds {
          description
            "Time-based key duration in seconds";
          type uint64 {
            range "300..2592000";
          }
        }
      }
      container retransmit {
        description
          "Define the rekey retransmission parameters";
        leaf seconds {
          type uint8 {
            range "10..60";
          }
        }
        choice number-periodic {
          case number-case {
            leaf number {
              description
                "Retransmit this many times";
              type uint8;
            }
          }
          case periodic-case {
            leaf periodic {
              description
                "Periodically send retransmit rekeys";
              type empty;
            }
          }
        }
      }
      container sig-hash {
        description
          "Set rekey signature-hash parameters";
        leaf algorithm {
          description
            "Set the rekey signature-hash algorithm";
          type enumeration {
            enum "sha";
            enum "sha256";
            enum "sha384";
            enum "sha512";
          }
        }
      }
      container transport {
        description
          "Specify the rekey distribution method";
        leaf unicast {
          description
            "specify unicast rekey distribution";
          type empty;
        }
      }
    }
    container sa {
      description
        "Configure a security association";
      container d3p {
        description
          "Enable IP delivery delay detection protocol for all SAs within the group";
        container window {
          description
            "IP-D3P window size";
          leaf msec {
            description
              "IP-D3P window size in milliseconds";
            type uint32 {
              range "1000..100000";
            }
          }
          leaf sec {
            description
              "IP-D3P window size in seconds";
            type uint8;
          }
        }
      }
      list ipsec {
        description
          "Configure an IPsec SA";
        key "sequence";
        leaf sequence {
          type uint16;
        }
        container default {
          description
            "Set a command to its defaults";
          uses crypto-gkm-sa-ipsec-default-grouping;
        }
        uses crypto-gkm-sa-ipsec-grouping;
      }
      container pair-wise-keying {
        description
          "Enable KGS pair-wise-keying";
        leaf safety-limit {
          description
            "KGS safety limit";
          type uint8;
        }
      }
      leaf receive-only {
        description
          "Configure SA to work only in inbound direction";
        type empty;
      }
    }
  }

  grouping crypto-gkm-local-server-default-grouping {
    container address {
      description
        "Configure server source address";
      presence "true";
    }
    container authorization {
      description
        "Configure authorization for the group";
      container address {
        description
          "Set authorization by address";
        leaf ipv4 {
          description
            "Set authorization by address";
          type empty;
        }
      }
      leaf identity {
        description
          "Set authorization by identity";
        type empty;
      }
    }
    leaf gdoi {
      description
        "Enable GDOI (ISAKMP) Protocol for Registration & Rekey";
      type empty;
    }
    leaf gikev2 {
      description
        "Enable G-IKEv2 (IKEv2) Protocol for Registration & Rekey";
      type empty;
    }
    container group {
      description
        "Configure parameters for the group (e.g. Suite-B)";
      container size {
        description
          "Set Group Size for Suite-B counter transforms (SID length)";
        presence "true";
      }
    }
    container identifier {
      description
        "Enter Suite-B KSSID (Key Server Sender ID) config mode";
      presence "true";
    }
    container redundancy {
      description
        "Enter cooperative key server configuration mode";
      presence "true";
    }
    container registration {
      description
        "Configure registration for the group";
      leaf interface {
        description
          "Identify an interface on which to respond to GKM registrations";
        type string;
      }
      container periodic {
        description
          "Define periodic registrations for the group";
        container crl {
          description
            "On every new CRL";
          leaf trustpoint {
            description
              "For a PKI trustpoint";
            type empty;
          }
        }
      }
    }
    container rekey {
      description
        "Configure rekey policy for the group";
      leaf acknowledgement {
        description
          "Request group members to acknowledge rekeys";
        type empty;
      }
      container address {
        description
          "Define the rekey packet format";
        presence "true";
      }
      container algorithm {
        description
          "Set the rekey encryption algorithm";
        presence "true";
      }
      container authentication {
        description
          "Identify the rekey authentication keypair";
        presence "true";
      }
      container lifetime {
        description
          "Define the rekey lifetime";
        leaf days {
          description
            "Time-based key duration in days";
          type empty;
        }
        leaf seconds {
          description
            "Time-based key duration in seconds";
          type empty;
        }
      }
      container retransmit {
        description
          "Define the rekey retransmission parameters";
        presence "true";
      }
      container sig-hash {
        description
          "Set rekey signature-hash parameters";
        leaf algorithm {
          description
            "Set the rekey signature-hash algorithm";
          type empty;
        }
      }
      container transport {
        description
          "Specify the rekey distribution method";
        leaf unicast {
          description
            "specify unicast rekey distribution";
          type empty;
        }
      }
    }
    container sa {
      description
        "Configure a security association";
      container d3p {
        description
          "Enable IP delivery delay detection protocol for all SAs within the group";
        presence "true";
      }
      list ipsec {
        description
          "Configure an IPsec SA";
        key "sequence";
        leaf sequence {
          type uint16;
        }
      }
      container pair-wise-keying {
        description
          "Enable KGS pair-wise-keying";
        presence "true";
      }
      leaf receive-only {
        description
          "Configure SA to work only in inbound direction";
        type empty;
      }
    }
  }

  grouping crypto-gdio-grouping {
    container client {
      description
        "Set the group client parameters";
      leaf bypass-policy {
        description
          "Allow group-key management traffic sent to this GM only";
        type empty;
      }
      container protocol {
        description
          "Group Member Registration & Rekey Protocol";
        leaf gdoi {
          description
            "Use GDOI (ISAKMP) Protocol for Registration & Rekey";
          type empty;
        }
        leaf gikev2 {
          description
            "Use G-IKEv2 Protocol for Registration & Rekey";
          type string;
        }
      }
      container recovery-check {
        description
          "Specify GM recovery check parameters";
        leaf interval {
          description
            "Waiting period(sec) between consecutive recovery registrations";
          type uint16 {
            range "100..1000";
          }
        }
      }
      container registration {
        description
          "Set the group client management/register interface";
        leaf interface {
          description
            "Set the group client management/register interface";
          type string;
        }
      }
      container rekey {
        description
          "Set the group client acceptable rekey ciphers and hashs";
        container encryption {
          description
            "Set the group client acceptable rekey ciphers";
          leaf rekey-3des-cbc {
            type empty;
          }
          leaf aes-128 {
            description
              "128 bit AES";
            type empty;
          }
          leaf aes-192 {
            description
              "192 bit AES";
            type empty;
          }
          leaf aes-256 {
            description
              "256 bit AES";
            type empty;
          }
          leaf des-cbc {
            description
              "DES in CBC mode";
            type empty;
          }
        }
        container hash {
          description
            "Set the group client acceptable rekey hash";
          leaf sha {
            description
              "Secure Hash Standard";
            type empty;
          }
          leaf sha256 {
            description
              "Secure Hash Standard 2 (256 bit)";
            type empty;
          }
          leaf sha384 {
            description
              "Secure Hash Standard 2 (384 bit)";
            type empty;
          }
          leaf sha512 {
            description
              "Secure Hash Standard 2 (512 bit)";
            type empty;
          }
        }
      }
      container status {
        description
          "group-member status";
        container active-sa {
          description
            "TEK SA with positive remaining lifetime";
          leaf track {
            description
              "enable stub tracking object";
            type uint16 {
              range "1..1000";
            }
          }
        }
      }
      leaf-list transform-sets {
        description
          "Specify list of group client acceptable transform sets";
        type string;
      }
      leaf transport-encrypt-key {
        description
          "Enforce group or pair-wise keying";
        type enumeration {
          enum "group-key";
          enum "pair-wise-key";
        }
      }
    }
    container identity {
      description
        "Set the identity of the group";
      container address {
        description
          "Set the identity of the group as an address";
        leaf ipv4 {
          description
            "Set the identity of the group as an IPv4 address";
          type inet:ipv4-address;
        }
      }
      leaf number {
        description
          "Set the identity of the group as a number";
        type uint64;
      }
    }
    leaf passive {
      description
        "Set the group in passive mode";
      type empty;
    }
    container server {
      description
        "Set the group server for of the group";
      container address {
        description
          "Identify the group server by address";
        leaf-list ipv4 {
          description
            "Set the IPv4 address of the group server";
          type inet:ipv4-address;
        }
        leaf-list ipv6 {
          description
            "Set the IPv6 address of the group server";
          type inet:ipv6-address;
        }
      }
      container hostname {
        description
          "Identify the group server by hostname";
        leaf ipv4 {
          description
            "Set the IPv4 hostname of the group server";
          type string;
        }
      }
      container local {
        description
          "Configure GKM group server defined locally";
        uses crypto-gkm-local-server-grouping;
        container default {
          description
            "Set a command to its defaults";
          uses crypto-gkm-local-server-default-grouping;
        }
      }
    }
  }

  grouping crypto-gdio-default-grouping {
    container client {
      description
        "Set the group client parameters";
      leaf bypass-policy {
        description
          "Allow group-key management traffic sent to this GM only";
        type empty;
      }
      container protocol {
        description
          "Group Member Registration & Rekey Protocol";
        presence "true";
      }
      container recovery-check {
        description
          "Specify GM recovery check parameters";
        presence "true";
      }
      container registration {
        description
          "Set the group client management/register interface";
        leaf interface {
          description
            "Set the group client management/register interface";
          type empty;
        }
      }
      container rekey {
        description
          "Set the group client acceptable rekey ciphers and hashs";
        container encryption {
          description
            "Set the group client acceptable rekey ciphers";
          presence "true";
        }
        container hash {
          description
            "Set the group client acceptable rekey hash";
          presence "true";
        }
      }
      container status {
        description
          "group-member status";
        container active-sa {
          description
            "TEK SA with positive remaining lifetime";
          presence "true";
        }
      }
      leaf transform-sets {
        description
          "Specify list of group client acceptable transform sets";
        type empty;
      }
      leaf transport-encrypt-key {
        description
          "Enforce group or pair-wise keying";
        type enumeration {
          enum "group-key";
          enum "pair-wise-key";
        }
      }
    }
    container identity {
      description
        "Set the identity of the group";
      presence "true";
    }
    leaf passive {
      description
        "Set the group in passive mode";
      type empty;
    }
    container server {
      description
        "Set the group server for of the group";
      container address {
        description
          "Identify the group server by address";
        leaf ipv4 {
          description
            "Set the IPv4 address of the group server";
          type inet:ipv4-address;
        }
      }
      container hostname {
        description
          "Identify the group server by hostname";
        leaf ipv4 {
          description
            "Set the IPv4 hostname of the group server";
          type string;
        }
      }
      leaf local {
        description
          "Configure GKM group server defined locally";
        type empty;
      }
    }
  }

  grouping crypto-identity-grouping {
    leaf description {
      description
        "Description of the crypto identity";
      type string;
    }
    leaf dn {
      description
        "Distinguished name identifier";
      type string;
    }
    leaf fqdn {
      description
        "Fully qualified distinguished name identifier";
      type string;
    }
  }

  grouping crypto-identity-default-grouping {
    leaf description {
      description
        "Description of the crypto identity";
      type empty;
    }
    leaf dn {
      description
        "Distinguished name identifier";
      type string;
    }
    leaf fqdn {
      description
        "Fully qualified distinguished name identifier";
      type string;
    }
  }

  grouping crypto-ikev2-keyring-peer-grouping {
    container address {
      description
        "Specify IPv4/IPv6 address of peer";
      choice ipv4-ipv6 {
        case ipv4-case {
          container ipv4 {
            leaf ipv4-address {
              type inet:ipv4-address;
            }
            leaf ipv4-mask {
              type inet:ipv4-address;
            }
          }
        }
        case ipv6-case {
          leaf ipv6-prefix {
            type ios-types:ipv6-prefix;
          }
        }
      }
    }
    leaf description {
      description
        "Specify a description of this peer";
      type string;
    }
    leaf hostname {
      description
        "Hostname of peer";
      type string;
    }
    container identity {
      description
        "Specify IKE identity to use";
      leaf address {
        description
          "IP address";
        type union {
          type inet:ipv4-address;
          type inet:ipv6-address;
        }
      }
      container email {
        description
          "Use email address";
        leaf name {
          type string;
        }
        leaf domain {
          description
            "email Domain Name";
          type string;
        }
      }
      container fqdn {
        description
          "Use FQDN";
        leaf name {
          type string;
        }
        leaf domain {
          description
            "email Domain Name";
          type string;
        }
      }
      leaf key-id {
        description
          "proprietary types of identification (ID KEY ID)";
        type string;
      }
    }
    container pre-shared-key {
      description
        "specify the pre-shared key";
      leaf local {
        description
          "specify signing key";
        type empty;
      }
      leaf remote {
        description
          "specify verifying key";
        type empty;
      }
      choice encryption-hex {
        case encryption-case {
          leaf encryption {
            type enumeration {
              enum "0";
              enum "6";
            }
          }
          leaf key {
            type string;
          }
        }
        case hex-case {
          leaf hex {
            description
              "Key entered in hex string";
            type string;
          }
        }
      }
    }
  }

  grouping crypto-ikev2-profile-aaa-authorization-grouping {
    list list {
      description
        "AAA method list";
      key "name";
      leaf name {
        type string;
      }
      leaf username {
        type string;
      }
      leaf local {
        description
          "Local AAA Authorization";
        when "../username";
        type empty;
      }
      leaf name-mangler {
        description
          "Specify the name-mangler to derive AAA username";
        type string;
      }
      container password {
        description
          "Specify the AAA password";
        leaf encryption {
          type enumeration {
            enum "0";
            enum "6";
          }
        }
        leaf key {
          type string;
        }
      }
    }
  }

  grouping crypto-ikev2-profile-authentication-grouping {
    leaf username {
      description
        "EAP username";
      type string;
    }
    container password {
      description
        "EAP password";
      leaf encryption {
        type enumeration {
          enum "0";
          enum "6";
        }
      }
      leaf key {
        type string;
      }
    }
  }

  grouping crypto-ikev2-profile-authentication-key-grouping {
    container key {
      description
        "specify key";
      leaf encryption {
        type enumeration {
          enum "0";
          enum "6";
        }
      }
      leaf key {
        type string;
      }
    }
  }

  grouping crypto-ikev2-profile-grouping {
    container aaa {
      description
        "Specify AAA related configs";
      container accounting {
        description
          "AAA accounting";
        leaf anyconnect-eap {
          description
            "AAA list to use when IKEv2 remote auth method is AnyConnect EAP";
          type string;
        }
        leaf cert {
          description
            "AAA list to use when IKEv2 remote auth method is certificate based";
          type string;
        }
        leaf eap {
          description
            "AAA list to use when IKEv2 remote auth method is EAP";
          type string;
        }
        leaf psk {
          description
            "AAA list to use when IKEv2 remote auth method is PSK";
          type string;
        }
      }
      container authentication {
        description
          "AAA authentication";
        leaf anyconnect-eap {
          description
            "AAA AnyConnect EAP authentication";
          type string;
        }
        leaf eap {
          description
            "AAA EAP authentication";
          type string;
        }
      }
      container authorization {
        description
          "AAA authorization";
        container group {
          description
            "AAA group authorization";
          container anyconnect-eap {
            description
              "AAA list to use when IKEv2 remote auth method is anyconnect eap based";
            uses crypto-ikev2-profile-aaa-authorization-grouping;
          }
          container cert {
            description
              "AAA list to use when IKEv2 remote auth method is certificate based";
            uses crypto-ikev2-profile-aaa-authorization-grouping;
          }
          container eap {
            description
              "AAA list to use when IKEv2 remote auth method is EAP";
            uses crypto-ikev2-profile-aaa-authorization-grouping;
          }
          container psk {
            description
              "AAA list to use when IKEv2 remote auth method is PSK";
            uses crypto-ikev2-profile-aaa-authorization-grouping;
          }
          leaf override {
            description
              "Override user authorization with group authorization.By default, group authorization isoverridden with user authorization";
            type empty;
          }
        }
        container user {
          description
            "AAA user authorization";
          container anyconnect-eap {
            description
              "AAA list to use when IKEv2 remote auth method is anyconnect eap based";
            leaf cached {
              description
                "Use cached attributes from EAP authentication or AAA pre-shared key fetch";
              type empty;
            }
            uses crypto-ikev2-profile-aaa-authorization-grouping;
          }
          container cert {
            description
              "AAA list to use when IKEv2 remote auth method is certificate based";
            uses crypto-ikev2-profile-aaa-authorization-grouping;
          }
          container eap {
            description
              "AAA list to use when IKEv2 remote auth method is EAP";
            leaf cached {
              description
                "Use cached attributes from EAP authentication or AAA pre-shared key fetch";
              type empty;
            }
            uses crypto-ikev2-profile-aaa-authorization-grouping;
          }
          container psk {
            description
              "AAA list to use when IKEv2 remote auth method is PSK";
            leaf cached {
              description
                "Use cached attributes from EAP authentication or AAA pre-shared key fetch";
              type empty;
            }
            uses crypto-ikev2-profile-aaa-authorization-grouping;
          }
        }
      }
    }
    container authentication {
      description
        "Set authentication method";
      container local {
        description
          "Set local authentication method";
        container eap {
          description
            "Extended Authentication Protocol";
          presence "true";
          container gtc {
            description
              "eap method gtc credentials";
            uses crypto-ikev2-profile-authentication-grouping;
          }
          container md5 {
            description
              "eap method md5 credentials";
            uses crypto-ikev2-profile-authentication-grouping;
          }
          container mschapv2 {
            description
              "eap method mschapv2 credentials";
            uses crypto-ikev2-profile-authentication-grouping;
          }
        }
        leaf ecdsa-sig {
          description
            "ECDSA Signature";
          type empty;
        }
        container pre-share {
          description
            "Pre-Shared Key";
          presence "true";
          uses crypto-ikev2-profile-authentication-key-grouping;
        }
        leaf rsa-sig {
          description
            "Rivest-Shamir-Adleman Signature";
          type empty;
        }
      }
      container remote {
        description
          "Set remote authentication method";
        container anyconnect-eap {
          description
            "AnyConnect EAP";
          container aggregate {
            description
              "use aggregate auth for anyconnect eap";
            presence "true";
            leaf cert-request {
              description
                "use double authentication during anyconnect eap";
              type empty;
            }
          }
        }
        container eap {
          description
            "Extended Authentication Protocol";
          presence "true";
          leaf query-identity {
            description
              "query EAP identity from peer";
            type empty;
          }
          leaf timeout {
            description
              "timeout";
            type uint8 {
              range "45..180";
            }
          }
        }
        leaf ecdsa-sig {
          description
            "ECDSA Signature";
          type empty;
        }
        container pre-share {
          description
            "Pre-Shared Key";
          presence "true";
          uses crypto-ikev2-profile-authentication-key-grouping;
        }
        leaf rsa-sig {
          description
            "Rivest-Shamir-Adleman Signature";
          type empty;
        }
      }
    }
    container config-exchange {
      description
        "config-exchange options";
      leaf request {
        description
          "enable config-exchange request";
        type empty;
      }
      leaf set {
        description
          "config-exchange set options";
        type enumeration {
          enum "accept";
          enum "send";
        }
      }
    }
    leaf description {
      description
        "Specify a description of this profile";
      type string;
    }
    container dpd {
      description
        "Enable IKE liveness check for peers";
      leaf interval {
        type uint16 {
          range "10..3600";
        }
      }
      leaf retry {
        type uint8 {
          range "2..60";
        }
      }
      leaf query {
        type enumeration {
          enum "on-demand";
          enum "periodic";
        }
      }
    }
    container identity {
      description
        "Specify IKE identity to use";
      container local {
        description
          "Specify the local IKE identity to use for the negotiation";
        choice identity {
          case address-case {
            leaf address {
              description
                "address";
              type inet:ip-address;
            }
          }
          case dn-case {
            leaf dn {
              description
                "Distinguished Name";
              type empty;
            }
          }
          case email-case {
            leaf email {
              description
                "Fully qualified email string
              email <user@domain>";
              type string;
            }
          }
          case fqdn-case {
            leaf fqdn {
              description
                "Fully qualified domain name string
                 FQDN <host.domain>";
              type string;
            }
          }
          case key-id-case {
            leaf key-id {
              description
                "key-id opaque string - proprietary types of identification
                 key-id string";
              type string;
            }
          }
        }
      }	
    }
    container initial-contact {
      description
        "initial-contact processing options";
      leaf force {
        description
          "Enforces initial-contact based clean-up";
        type empty;
      }
    }
    leaf ivrf {
      description
        "I-VRF of the profile";
      type string;
    }
    container keyring {
      description
        "Specify keyring to use";
      list aaa {
        description
          "AAA based keyring";
        key "name";
        leaf name {
          type string;
        }
        leaf name-mangler {
          description
            "Specify the name-mangler to derive username";
          type string;
        }
        container password {
          description
            "Specify the AAA password";
          leaf encryption {
            type enumeration {
              enum "0";
              enum "6";
            }
          }
          leaf key {
            type string;
          }
        }
      }
      leaf local {
        description
          "Local keyring";
        type string;
      }
    }
    container lifetime {
      description
        "Set lifetime for ISAKMP security association";
      leaf seconds {
        type uint32 {
          range "120..86400";
        }
      }
      leaf certificate {
        description
          "Enable certificate based lifetime";
        type empty;
      }
    }
    container match {
      description
        "Match values of peer";
      container address {
        description
          "IP address";
        container local {
          description
            "Local address";
          leaf ip {
            type inet:ip-address;
          }
          leaf interface {
            description
              "Specify an interface";
            type string;
          }
        }
      }
      leaf certificate {
        description
          "Peer certificate attributes";
        type string;
      }
      container fvrf {
        description
          "fvrf of the profile";
        leaf name {
          type string;
        }
        leaf any {
          description
            "Any fvrf";
          type empty;
        }
      }
      container identity {
        description
          "IKE identity";
        container remote {
          description
            "Remote identity";
          container address {
            description
              "IP address(es)";
            list ipv4 {
              key "ipv4-address";
              leaf ipv4-address {
                type inet:ipv4-address;
              }
              leaf ipv4-mask {
              type inet:ipv4-address;
              }
            }
            leaf-list ipv6-prefix {
              type ios-types:ipv6-prefix;
            }
          }
          leaf any {
            description
              "match any peer identity";
            type empty;
          }
          container email {
            description
              "Fully qualified email string [Max. 255 char(s)]";
            leaf name {
              type string;
            }
            leaf domain {
              description
                "match domain instead of exact";
              type string;
            }
          }
          container fqdn {
            description
              "Fully qualified domain name string [Max. 255 char(s)]";
            leaf name {
              type string;
            }
            leaf domain {
              description
                "match domain instead of exact";
              type string;
            }
          }
          leaf key-id {
            description
              "key-id opaque string";
            type string;
          }
        }
      }
    }
    container nat {
      description
        "NAT-transparency";
      leaf keepalive {
        description
          "NAT keepalive interval";
        type uint16 {
          range "5..3600";
        }
      }
    }
    container pki {
      description
        "Specify certificate authorities to trust";
      leaf trustpoint {
        description
          "Cert authority trustpoint for RSA sig";
        type string;
      }
      leaf use {
        type enumeration {
          enum "sign";
          enum "verify";
        }
      }
    }
    container reconnect {
      description
        "Enable profile for auto re-connect";
      presence "true";
      leaf timeout {
        description
          "timeout value for session in reconnect state";
        type uint32 {
          range "600..86400";
        }
      }
    }
    container redirect {
      description
        "IKEv2 Redirect Mechanism for load-balancing";
      container gateway {
        description
          "Enables Redirect Mechanism on Gateway";
        leaf auth {
          description
            "Redirect at SA authentication";
          type empty;
        }
      }
    }
    leaf shutdown {
      description
        "shutdown the IKEv2 profile";
      type empty;
    }
    container virtual-template {
      description
        "Specify the virtual-template for dynamic interface creation.";
      leaf number {
        type uint16 {
          range "1..4095";
        }
      }
      leaf mode {
        description
          "Enabling Tunnel Auto Mode";
        type enumeration {
          enum "auto";
        }
      }
    }
  }

  grouping crypto-ikev2-grouping {
    container authorization {
      description
        "IKEv2 authorization";
      list policy {
        description
          "IKEv2 authorization policy";
        key "policy-name";
        leaf policy-name {
          type string;
        }
        /*route set interface*/
        container route {
          container set {
            container interface {
              leaf interface-default {
                type empty;
              }
              list interface-list {
                key "interface-name";
                leaf interface-name {
                  type string;
                }
              }
            }
          }
        }
      }
    }
    leaf certificate-cache {
      description
        "Cache for storing certs fetched from HTTP URLs";
      type uint16;
    }
    container client {
      description
        "IKEv2 client configuration";
      list flexvpn {
        key "flexvpn-name";
        leaf flexvpn-name {
          description
            "Configure an IKEv2 FlexVPN client";
          type string;
        }
        list peer {
          key "peer-id";
          leaf peer-id {
            type uint8;
          }
          container peer-id-container {
            leaf peer-address {
              type inet:ip-address;
            }
            leaf track {
              type uint16 {
                range "0..1000";
              }
            }
            leaf up-down {
              type enumeration {
                enum "up";
                enum "down";
              }
            }
          }
        }
        container connect {
          leaf track {
            type uint16 {
              range "0..1000";
            }
          }
          leaf up-down {
            type enumeration {
              enum "up";
              enum "down";
            }
          }
        }
        list source {
          key "source-id";
          leaf source-id {
            type uint8 {
              range "1..255";
            }
          }
          container source-id-container{
            leaf interface-name {
              type string;
            }
            leaf track {
              type uint16 {
                range "1..1000";
              }
            }
          }
        }
        container client {
          container connect {
            leaf Tunnel {
              type uint32 {
                range "0..2147483647";
              }
            }
          }
        }
      }
    }
    leaf cluster {
      description
        "Cluster load-balancer settings";
      type empty;
    }
    leaf cookie-challenge {
      description
        "Set Cookie-challenge watermark";
      type uint16;
    }
    container cts {
      description
        "Cisco Trust Security";
      leaf sgt {
        description
          "Security Group Tag";
        type empty;
      }
    }
    container diagnose {
      description
        "IKEV2 diagnose";
      leaf error {
        description
          "Start IKEv2 error trace debug";
        type uint16 {
          range "1..1000";
        }
      }
    }
    leaf disconnect-revoked-peers {
      description
        "Disconnect Crypto Session with Cert Revoked Peer";
      type empty;
    }
    container dpd-container {
      leaf dpd {
        description
          "Enable IKE liveness check for peers";
        type uint16 {
          range "10..3600";
        }
      }
      leaf retry-interval {
        type uint8 {
          range "2..60";
        }
      }
      leaf dpd-query {
        type enumeration {
          enum "on-demand";
          enum "periodic";
        }
      }
    }
    container fragmentation {
      description
        "Enable fragmentation of ikev2 packets";
      presence "true";
      leaf mtu {
        description
          "MTU size for fragmentation";
        type uint16 {
          range "68..1500";
        }
      }
    }
    container http-url {
      description
        "Enable http URL lookup";
      leaf cert {
        description
          "Enable certificate lookup based on HTTP-based URL";
        type empty;
      }
    }
    list keyring {
      description
        "Define IKEv2 Keyring";
      key "name";
      leaf name {
        type string;
      }
      list peer {
        description
          "Configure a Peer and associated keys";
        key "name";
        leaf name {
          type string;
        }
        uses crypto-ikev2-keyring-peer-grouping;
      }
    }
    container limit {
      description
        "Limit the number of maximum and negotiating sa";
      container max-neg-sa {
        leaf max-in-negotation-sa {
          description
            "Limit the maximum number of negotiating SA";
          type uint32 {
            range "1..9999";
          }
        }
        leaf direction {
          type enumeration {
            enum "incoming";
            enum "outgoing";
          }
        }
      }
      leaf max-sa {
        description
          "Limit the maximum number of SA allowed";
        type uint32 {
          range "1..9999";
        }
      }
    }
    leaf name-mangler {
      description
        "Name mangler";
      type string;
    }
    container nat {
      description
        "NAT-transparency";
      leaf keepalive {
        description
          "Set NAT keepalive interval";
        type uint16 {
          range "5..3600";
        }
      }
    }
    list policy {
      description
        "Define IKEV2 policies";
      key "name";
      leaf name {
        type string;
      }
      container match {
        description
          "Match values of local fields";
        container address {
          description
            "Specify the address to match";
          leaf local {
            description
              "Local address";
            type inet:ip-address;
          }
        }
        container fvrf {
          description
            "Specify fvrf";
          leaf name {
            type string;
          }
          leaf any {
            description
              "Any fvrf";
            type empty;
          }
        }
      }
      leaf proposal {
        description
          "Specify Proposal";
        type string;
      }
    }
    list profile {
      description
        "Define IKEV2 profiles";
      key "name";
      leaf name {
        type string;
      }
      uses crypto-ikev2-profile-grouping;
    }
    list proposal {
      description
        "Define IKEV2 proposals";
      key "name";
      leaf name {
        type string;
      }
      container encryption {
        description
          "Set encryption algorithm(s) for proposal";
        leaf en-3des {
          description
            "3DES";
          type empty;
        }
        leaf aes-cbc-128 {
          description
            "AES-CBC-128";
          type empty;
        }
        leaf aes-cbc-192 {
          description
            "AES-CBC-192";
          type empty;
        }
        leaf aes-cbc-256 {
          description
            "AES-CBC-256";
          type empty;
        }
        leaf aes-gcm-128 {
          description
            "Combined-mode,128 bit key,16 byte ICV(Authentication Tag)";
          type empty;
        }
        leaf aes-gcm-256 {
          description
            "Combined-mode,256 bit key,16 byte ICV(Authentication Tag)";
          type empty;
        }
        leaf des {
          description
            "DES";
          type empty;
        }
      }
      container group {
        description
          "Set the Diffie-Hellman group(s)";
        leaf one {
          description
            "DH 768 MODP";
          type empty;
        }
        leaf fourteen {
          description
            "DH 2048 MODP";
          type empty;
        }
        leaf fifteen {
          description
            "DH 3072 MODP";
          type empty;
        }
        leaf sixteen {
          description
            "DH 4096 MODP";
          type empty;
        }
        leaf nineteen {
          description
            "DH 256 ECP";
          type empty;
        }
        leaf two {
          description
            "DH 1024 MODP";
          type empty;
        }
        leaf twenty {
          description
            "DH 384 ECP";
          type empty;
        }
        leaf twenty-one {
          description
            "DH 521 ECP";
          type empty;
        }
        leaf twenty-four {
          description
            "DH 2048 (256 subgroup) MODP";
          type empty;
        }
        leaf five {
          description
            "DH 1536 MODP";
          type empty;
        }
      }
      container integrity {
        description
          "Set integrity hash algorithm(s) for proposal";
        leaf md5 {
          description
            "Message Digest 5";
          type empty;
        }
        leaf sha1 {
          description
            "Secure Hash Standard";
          type empty;
        }
        leaf sha256 {
          description
            "Secure Hash Standard 2 (256 bit)";
          type empty;
        }
        leaf sha384 {
          description
            "Secure Hash Standard 2 (384 bit)";
          type empty;
        }
        leaf sha512 {
          description
            "Secure Hash Standard 2 (512 bit)";
          type empty;
        }
      }
      container prf {
        description
          "Set prf algorithm(s) for proposal";
        leaf md5 {
          description
            "Message Digest 5";
          type empty;
        }
        leaf sha1 {
          description
            "Secure Hash Standard";
          type empty;
        }
        leaf sha256 {
          description
            "Secure Hash Standard 2 (256 bit)";
          type empty;
        }
        leaf sha384 {
          description
            "Secure Hash Standard 2 (384 bit)";
          type empty;
        }
        leaf sha512 {
          description
            "Secure Hash Standard 2 (512 bit)";
          type empty;
        }
      }
    }
    container reconnect {
      description
        "Cluster Reconnect";
      leaf key {
        description
          "Cluster Reconnect key";
        type uint8 {
          range "1..2";
        }
      }
      choice value-active {
        case value-case {
          leaf value {
            type string {
              length "1..128";
            }
          }
        }
        case active-case {
          leaf active {
            description
              "Current active cluster reconnect key";
            type string {
              length "1..128";
            }
          }
        }
      }
    }
    container redirect {
      description
        "IKEv2 Redirect Mechanism for load-balancing";
      container client {
        description
          "Enables Redirect Mechanism on Client";
        presence "true";
        leaf max-redirects {
          description
            "Redirect loop detection";
          type uint8;
        }
      }
      leaf gateway {
        description
          "Enables Redirect Mechanism on Gateway";
        type enumeration {
          enum "auth";
          enum "init";
        }
      }
    }
    leaf window {
      description
        "IKEV2 window size";
      type uint8;
    }
  }

  grouping crypto-ipsec-profile-grouping {
    leaf description {
      description
        "Description of the crypto map statement policy";
      type string;
    }
    container dialer {
      description
        "Dialer related commands";
      leaf pre-classify {
        description
          "Enable dialer list classification before initiating IKE";
        type empty;
      }
    }
    container redundancy {
      description
        "Configure HA for this ipsec profile";
      leaf name {
        type string;
      }
      leaf stateful {
        description
          "enable stateful failover";
        type empty;
      }
    }
    leaf responder-only {
      description
        "Do not initiate SAs from this device";
      type empty;
    }
    container set {
      description
        "Set values for encryption/decryption";
      uses crypto-map-common-set-grouping;
      leaf mixed-mode {
        description
          "Turn on IPSec mixed-mode";
        type empty;
      }
      container security-association {
        description
          "Security association parameters";
        uses crypto-map-common-set-security-association-grouping;
        leaf level {
          description
            "specify a security association granularity level for identities";
          type enumeration {
            enum "per-host";
          }
        }
      }
      container security-policy {
        description
          "Maximum number of Security Policy entries that can be negotiated with the peer";
        leaf limit {
          description
            "limit  0 - 50000";
          type uint32 {
            range "0..50000";
          }
        }
      }
    }
  }

  grouping crypto-ipsec-profile-default-grouping {
    leaf description {
      description
        "Description of the crypto map statement policy";
      type empty;
    }
    container dialer {
      description
        "Dialer related commands";
      leaf pre-classify {
        description
          "Enable dialer list classification before initiating IKE";
        type empty;
      }
    }
    leaf redundancy {
      description
        "Configure HA for this ipsec profile";
      type empty;
    }
    leaf responder-only {
      description
        "Do not initiate SAs from this device";
      type empty;
    }
    container set {
      description
        "Set values for encryption/decryption";
      leaf group {
        description
          "Set the san group parameters";
        type empty;
      }
      leaf identity {
        description
          "Identity restriction";
        type empty;
      }
      leaf ikev2-profile {
        description
          "Specify ikev2 Profile";
        type string;
      }
      leaf isakmp-profile {
        description
          "Specify isakmp Profile";
        type empty;
      }
      leaf mixed-mode {
        description
          "Turn on IPSec mixed-mode";
        type empty;
      }
      container pfs {
        description
          "Specify pfs settings";
        presence "true";
      }
      container reverse-route {
        description
          "Reverse Route Injection";
        presence "true";
      }
      container security-association {
        description
          "Security association parameters";
        leaf dfbit {
          description
            "Handling of encapsulated DF bit.";
          type empty;
        }
        container dummy {
          description
            "Enable transmitting dummy packets";
          presence "true";
        }
        leaf ecn {
          description
            "Handling of ECN bit";
          type empty;
        }
        container idle-time-container {
          leaf idle-time {
            description
              "Automatically delete IPSec SAs after a given idle period.";
            type empty;
          }
          leaf default {
            description
              "All SAs idle-out reset to default peer";
            type empty;
          }
        }
        leaf level {
          description
            "specify a security association granularity level for identities";
          type enumeration {
            enum "per-host";
          }
        }
        container lifetime {
          description
            "security association lifetime";
          leaf days {
            description
              "Time-based key duration in days";
            type empty;
          }
          leaf kilobytes {
            description
              "Volume-based key duration";
            type empty;
          }
          leaf seconds {
            description
              "Time-based key duration in seconds";
            type empty;
          }
        }
        container replay {
          description
            "Set replay checking.";
          leaf disable {
            description
              "Disable replay checking";
            type empty;
          }
          leaf window-size {
            description
              "Set replay window size.";
            type empty;
          }
        }
      }
      container security-policy {
        description
          "Maximum number of Security Policy entries that can be negotiated with the peer";
        leaf limit {
          description
            "limit  0 - 50000";
          type uint32 {
            range "0..50000";
          }
        }
      }
      leaf transform-set {
        description
          "Specify list of transform sets in priority order";
        type empty;
      }
    }
  }

  grouping crypto-ipsec-grouping {
    leaf df-bit {
      description
        "Handling of encapsulated DF bit.";
      type enumeration {
        enum "clear";
        enum "copy";
        enum "set";
      }
    }
    leaf fragmentation {
      description
        "Handling of fragmentation of near-MTU sized packets";
      type enumeration {
        enum "after-encryption";
        enum "before-encryption";
      }
    }
    leaf ipv4-deny {
      description
        "Configure global ipv4 deny policy.";
      type enumeration {
        enum "clear";
        enum "drop";
        enum "jump";
      }
    }
    leaf nat-transparency {
      description
        "IPsec NAT transparency model";
      type enumeration {
        enum "spi-matching";
        enum "udp-encapsulation";
      }
    }
    container optional {
      description
        "Enable optional encryption for IPSec";
      presence "true";
      leaf retry {
        description
          "Configure length of IPSec retry interval";
        type uint32 {
          range "60..86400";
        }
      }
    }
    list profile {
      description
        "Configure an ipsec policy profile";
      key "name";
      leaf name {
        type string;
      }
      container default {
        description
          "Set a command to its defaults";
        uses crypto-ipsec-profile-default-grouping;
      }
      uses crypto-ipsec-profile-grouping;
    }
    container security-association {
      description
        "Security association parameters";
      container dummy {
        description
          "Enable transmitting dummy packets";
        leaf pps {
          description
            "Simulated traffic rate (in pps)";
          type uint8 {
            range "0..25";
          }
        }
        leaf seconds {
          description
            "Simulated traffic rate (in seconds)";
          type uint16 {
            range "1..3600";
          }
        }
      }
      leaf ecn {
        description
          "Handling of ECN bit";
        type enumeration {
          enum "discard";
          enum "propagate";
        }
      }
      leaf idle-time {
        description
          "Automatically delete IPSec SAs after a given idle period.";
        type uint32 {
          range "60..86400";
        }
      }
      container lifetime {
        description
          "security association lifetime";
        leaf days {
          description
            "Time-based key duration in days";
          type uint8 {
            range "1..30";
          }
        }
        leaf kilobytes {
          description
            "Volume-based key duration";
          type union {
            type uint64 {
              range "2560..4294967295";
            }
            type enumeration {
              enum "disable";
            }
          }
        }
        leaf seconds {
          description
            "Time-based key duration in seconds";
          type uint64 {
            range "120..2592000";
          }
        }
      }
      container replay {
        description
          "Set replay checking.";
        leaf disable {
          description
            "Disable replay checking";
          type empty;
        }
        leaf window-size {
          description
            "Set replay window size.";
          type enumeration {
            enum "1024";
            enum "128";
            enum "256";
            enum "512";
            enum "64";
          }
        }
      }
    }
    list transform-set {
      description
        "Define transform and settings";
      key "tag";
      leaf tag {
        type string;
      }
      leaf ah-hmac {
        type enumeration {
          enum "ah-md5-hmac";
          enum "ah-sha-hmac";
          enum "ah-sha256-hmac";
          enum "ah-sha384-hmac";
          enum "ah-sha512-hmac";
        }
      }
      leaf comp-lzs {
        description
          "IP Compression using the LZS compression algorithm";
        type empty;
      }
      leaf esp {
        type enumeration {
          enum "esp-3des";
          enum "esp-aes";
          enum "esp-des";
          enum "esp-gcm";
          enum "esp-gmac";
          enum "esp-null";
          enum "esp-seal";
        }
      }
      leaf key-bit {
        type enumeration {
          enum "128";
          enum "192";
          enum "256";
        }
      }
      leaf esp-hmac {
        type enumeration {
          enum "esp-md5-hmac";
          enum "esp-sha-hmac";
          enum "esp-sha256-hmac";
          enum "esp-sha384-hmac";
          enum "esp-sha512-hmac";
        }
      }
      container default {
        description
          "Set a command to its defaults";
        leaf mode {
          description
            "encapsulation mode (transport/tunnel)";
          type empty;
        }
      }
      container mode {
        description
          "encapsulation mode (transport/tunnel)";
        container transport {
          description
            "transport (payload encapsulation) mode";
          presence "true";
          leaf require {
            description
              "Accept only the configured encapsulation mode.";
            type empty;
          }
        }
        leaf tunnel {
          description
            "tunnel (datagram encapsulation) mode";
          type empty;
        }
      }
    }
  }

  grouping crypto-isakmp-policy-grouping {
    leaf authentication {
      description
        "Set authentication method for protection suite";
      type enumeration {
        enum "pre-share";
        enum "rsa-encr";
        enum "rsa-sig";
      }
    }
    container encryption {
      description
        "Set encryption algorithm for protection suite";
      leaf a3des {
        type empty;
      }
      container aes {
        description
          "AES - Advanced Encryption Standard.";
        presence "true";
        leaf key {
          type enumeration {
            enum "128";
            enum "192";
            enum "256";
          }
        }
      }
      leaf des {
        description
          "DES - Data Encryption Standard (56 bit keys).";
        type empty;
      }
    }
    leaf group {
      description
        "Set the Diffie-Hellman group";
      type enumeration {
        enum "1";
        enum "14";
        enum "15";
        enum "16";
        enum "19";
        enum "2";
        enum "20";
        enum "21";
        enum "24";
        enum "5";
      }
    }
    leaf hash {
      description
        "Set hash algorithm for protection suite";
      type enumeration {
        enum "md5";
        enum "sha";
        enum "sha256";
        enum "sha384";
        enum "sha512";
      }
    }
  }

  grouping crypto-isakmp-profile-grouping {
    leaf accounting {
      description
        "Enable AAA Accounting for IPSec Sessions";
      type string;
    }
    container ca {
      description
        "Specify certificate authorities to trust";
      leaf trust-point {
        description
          "Cert authority trustpoint for RSA sig";
        type string;
      }
    }
    container client {
      description
        "Specify client configuration settings";
      container authentication {
        description
          "Use Extended Authentication";
        leaf list {
          description
            "AAA authentication list to use";
          type string;
        }
      }
      container configuration {
        description
          "Specify client configuration settings";
        leaf address {
          description
            "Specify client network address configuration";
          type enumeration {
            enum "initiate";
            enum "respond";
          }
        }
        leaf group {
          description
            "Specify group profile attributes for client";
          type string;
        }
      }
      container pki {
        description
          "Use username in the crypto certificate for authorization";
        container authorization {
          description
            "User authorization parameters";
          leaf list {
            description
              "AAA user authorization list";
            type string;
          }
        }
      }
    }
    leaf description {
      description
        "Specify a description of this profile";
      type string;
    }
    container initiate {
      description
        "Initiator property";
      container mode {
        description
          "Phase 1 negotiation mode to use";
        presence "true";
        leaf aggressive {
          description
            "Start agressive mode negotiation";
          type empty;
        }
      }
    }
    container isakmp {
      description
        "ISAKMP Authorization command";
      container authorization {
        description
          "Authorization parameters.";
        leaf list {
          description
            "AAA authorization list to use";
          type string;
        }
      }
    }
    container keepalive {
      description
        "Set a keepalive interval for use with IOS peers";
      leaf number {
        type uint16 {
          range "10..3600";
        }
      }
      leaf retry {
        description
          "Retry interval if keepalive fails";
        type uint8 {
          range "2..60";
        }
      }
    }
    leaf keyring {
      description
        "Specify keyring to use";
      type union {
        type string;
        type enumeration {
          enum "default";
        }
      }
    }
    leaf local-address {
      description
        "Interface to use for local address for this isakmp profile";
      type string;
    }
    container match {
      description
        "Match values of peer";
      leaf certificate {
        description
          "Peer certificate attributes";
        type string;
      }
      container identity {
        description
          "Peer identity";
        container ipv4-address {
          leaf address {
            description
              "IP Address(es)";
            type inet:ipv4-address;
          }
          leaf mask {
            type inet:ipv4-address;
          }
          leaf vrf {
            type string;
          }
        }
        container address {
          description
            "IP Address(es)";
          leaf ipv6 {
            description
              "IPv6 Address(es)";
            type ios-types:ipv6-prefix;
          }
          leaf vrf {
            type string;
          }
        }
        leaf group {
          description
            "Group name";
          type string;
        }
        container host {
          description
            "match a hostname/domain";
          container domain-name {
            leaf name {
              type string;
            }
            leaf vrf {
              type string;
            }
          }
          container domain-match {
            leaf domain {
              description
                "match domain instead of exact";
              type string;
            }
            leaf vrf {
              type string;
            }
          }
        }
        container user-fqdn {
          description
            "match a hostname/domain";
          container domain-name {
            leaf name {
              type string;
            }
            leaf vrf {
              type string;
            }
          }
          container domain-match {
            leaf domain {
              description
                "match domain instead of exact";
              type string;
            }
            leaf vrf {
              type string;
            }
          }
        }
      }
    }
    leaf qos-group {
      description
        "Apply a Qos policy class map for this profile";
      type uint16 {
        range "1..1023";
      }
    }
    container self-identity {
      description
        "Specify Identity to use";
      container address {
        description
          "Use IPv4 address";
        presence "true";
        leaf ipv6 {
          description
            "Use IPv6 address";
          type empty;
        }
      }
      container fqdn {
        description
          "Use FQDN";
        presence "true";
        leaf id {
          type string;
        }
      }
      leaf user-fqdn {
        description
          "Use user FQDN";
        type string;
      }
    }
    leaf virtual-template {
      description
        "Specify the virtual-template for dynamic interface creation.";
      type uint16 {
        range "1..4095";
      }
    }
    leaf vrf {
      description
        "Specify the VRF it is related to";
      type string;
    }
  }

  grouping crypto-isakmp-profile-default-grouping {
    leaf accounting {
      description
        "Enable AAA Accounting for IPSec Sessions";
      type empty;
    }
    container ca {
      description
        "Specify certificate authorities to trust";
      leaf trust-point {
        description
          "Cert authority trustpoint for RSA sig";
        type string;
      }
    }
    container client {
      description
        "Specify client configuration settings";
      container authentication {
        description
          "Use Extended Authentication";
        leaf list {
          description
            "AAA authentication list to use";
          type empty;
        }
      }
      container configuration {
        description
          "Specify client configuration settings";
        leaf address {
          description
            "Specify client network address configuration";
          type enumeration {
            enum "initiate";
            enum "respond";
          }
        }
        leaf group {
          description
            "Specify group profile attributes for client";
          type string;
        }
      }
      container pki {
        description
          "Use username in the crypto certificate for authorization";
        container authorization {
          description
            "User authorization parameters";
          presence "true";
        }
      }
    }
    leaf description {
      description
        "Specify a description of this profile";
      type string;
    }
    container initiate {
      description
        "Initiator property";
      container mode {
        description
          "Phase 1 negotiation mode to use";
        presence "true";
      }
    }
    container isakmp {
      description
        "ISAKMP Authorization command";
      container authorization {
        description
          "Authorization parameters.";
        leaf list {
          description
            "AAA authorization list to use";
          type empty;
        }
      }
    }
    container keepalive {
      description
        "Set a keepalive interval for use with IOS peers";
      presence "true";
    }
    leaf keyring {
      description
        "Specify keyring to use";
      type union {
        type string;
        type enumeration {
          enum "default";
        }
      }
    }
    leaf local-address {
      description
        "Interface to use for local address for this isakmp profile";
      type empty;
    }
    container match {
      description
        "Match values of peer";
      leaf certificate {
        description
          "Peer certificate attributes";
        type string;
      }
      container identity {
        description
          "Peer identity";
        container ipv4-address {
          leaf address {
            description
              "IP Address(es)";
            type inet:ipv4-address;
          }
          leaf mask {
            type inet:ipv4-address;
          }
          leaf vrf {
            type string;
          }
        }
        container address {
          description
            "IP Address(es)";
          leaf ipv6 {
            description
              "IPv6 Address(es)";
            type ios-types:ipv6-prefix;
          }
          leaf vrf {
            type string;
          }
        }
        leaf group {
          description
            "Group name";
          type string;
        }
        container host {
          description
            "match a hostname/domain";
          container domain-name {
            leaf name {
              type string;
            }
            leaf vrf {
              type string;
            }
          }
          container domain-match {
            leaf domain {
              description
                "match domain instead of exact";
              type string;
            }
            leaf vrf {
              type string;
            }
          }
        }
        container user-fqdn {
          description
            "match a hostname/domain";
          container domain-name {
            leaf name {
              type string;
            }
            leaf vrf {
              type string;
            }
          }
          container domain-match {
            leaf domain {
              description
                "match domain instead of exact";
              type string;
            }
            leaf vrf {
              type string;
            }
          }
        }
      }
    }
    leaf qos-group {
      description
        "Apply a Qos policy class map for this profile";
      type empty;
    }
    container self-identity {
      description
        "Specify Identity to use";
      presence "true";
    }
    leaf virtual-template {
      description
        "Specify the virtual-template for dynamic interface creation.";
      type empty;
    }
    leaf vrf {
      description
        "Specify the VRF it is related to";
      type empty;
    }
  }

  grouping crypto-isakmp-client-configuration-group-grouping {
    leaf access-restrict {
      description
        "Restrict clients in this group to an interface";
      type string;
    }
    leaf acl {
      description
        "Specify split tunneling inclusion access-list number";
      type union {
        type uint16 {
          range "100..199";
        }
        type string {
          pattern "[a-zA-Z].*";
        }
      }
    }
    container auto-update {
      description
        "Configure auto-upgrade";
      leaf client {
        description
          "Configure client";
        type string;
      }
      leaf url {
        description
          "Configure URL to download from";
        type string;
      }
      leaf rev {
        description
          "Use comma delimited list of revision strings only";
        type string;
      }
    }
    leaf backup-gateway {
      description
        "Specify backup gateway";
      type string;
    }
    leaf browser-proxy {
      description
        "Configure browser-proxy";
      type string;
    }
    container configuration {
      description
        "Push configuration to the client";
      leaf url {
        description
          "URL for the client to fetch configuration";
        type enumeration {
          enum "bootflash:";
          enum "cns:";
          enum "flash:";
          enum "ftp:";
          enum "http:";
          enum "https:";
          enum "null:";
          enum "nvram:";
          enum "pram:";
          enum "rcp:";
          enum "scp:";
          enum "system:";
          enum "tar:";
          enum "tftp:";
          enum "tmpsys:";
        }
      }
      leaf version {
        description
          "version of the configuration available at the URL";
        type uint32 {
          range "1..32767";
        }
      }
    }
    container crypto {
      description
        "Client group crypto aaa attribute list";
      container aaa {
        description
          "AAA directive";
        container attribute {
          description
            "AAA attribute directive";
          leaf list {
            description
              "AAA attribute list";
            type string;
          }
        }
      }
    }
    container dhcp {
      description
        "Configure DHCP parameters";
      leaf giaddr {
        description
          "Specify giaddr for dhcp scope";
        type inet:ipv4-address;
      }
      leaf server {
        description
          "Specify dhcp server";
        type union {
          type inet:ipv4-address;
          type string;
        }
      }
      leaf timeout {
        description
          "Configure DHCP response timeout in seconds";
        type uint8 {
          range "4..30";
        }
      }
    }
    container dns {
      description
        "Specify DNS Addresses";
      leaf primary {
        type inet:ipv4-address;
      }
      leaf secondary {
        type inet:ipv4-address;
      }
    }
    leaf domain {
      description
        "Set default domain name to send to client";
      type string;
    }
    container firewall {
      description
        "Enforce group firewall feature";
      leaf are-u-there {
        description
          "firewall attribute, are-u-there";
        type empty;
      }
      leaf policy {
        description
          "Specify firewall policy";
        type string;
      }
    }
    leaf group-lock {
      description
        "Enforce group lock feature";
      type empty;
    }
    leaf include-local-lan {
      description
        "Enable Local LAN Access with no split tunnel";
      type empty;
    }
    container key {
      description
        "pre-shared key/IKE password";
      leaf encryption {
        type enumeration {
          enum "0";
          enum "6";
        }
      }
      leaf key {
        type string;
      }
    }
    leaf max-logins {
      description
        "Set maximum simultaneous logins for users in this group";
      type uint8 {
        range "1..10";
      }
    }
    leaf max-users {
      description
        "Set maximum number of users for this group";
      type uint32 {
        range "1..5000";
      }
    }
    leaf netmask {
      description
        "netmask used by the client for local connectivity";
      type inet:ipv4-address;
    }
    leaf pfs {
      description
        "The client should propose PFS";
      type empty;
    }
    leaf pool {
      description
        "Set name of address pool";
      type string;
    }
    leaf save-password {
      description
        "Allows remote client to save XAUTH password";
      type empty;
    }
    leaf smartcard-removal-disconnect {
      description
        "Enables smartcard-removal-disconnect";
      type empty;
    }
    leaf split-dns {
      description
        "DNS name to append for resolution";
      type string;
    }
    container wins {
      description
        "Specify WINS Addresses";
      leaf primary {
        type inet:ipv4-address;
      }
      leaf secondary {
        type inet:ipv4-address;
      }
    }
  }

  grouping crypto-isakmp-peer-grouping {
    leaf description {
      description
        "IKE peer specific description";
      type string {
        length "1..80";
      }
    }
    container set {
      description
        "set peer policy attributes";
      container aggressive-mode {
        description
          "aggressive mode attributes";
        container client-endpoint {
          description
            "specify a tunnel-client-endpoint attribute";
          leaf fqdn {
            description
              "Use the fqdn as tunnel-client-endpoint";
            type string;
          }
          leaf ipv4-address {
            description
              "Use the IP address as tunnel-client-endpoint";
            type inet:ipv4-address;
          }
          leaf ipv6-address {
            description
              "Use the IPv6 address as tunnel-client-endpoint";
            type inet:ipv6-address;
          }
          leaf user-fqdn {
            description
              "Use the user-fqdn as tunnel-client-endpoint";
            type string;
          }
        }
        container password {
          description
            "specify a tunnel-password attribute";
          leaf encryption {
            type enumeration {
              enum "0";
              enum "6";
            }
          }
          leaf key {
            type string;
          }
        }
      }
    }
  }

  grouping crypto-isakmp-grouping {
    leaf aggressive-mode {
      description
        "Disable ISAKMP aggressive mode";
      type enumeration {
        enum "disable";
      }
    }
    container client {
      description
        "Set client configuration policy";
      container configuration {
        description
          "Set client configuration policy";
        container address-pool {
          description
            "Set network address for client";
          leaf local {
            description
              "Set a local address pool for clients";
            type string;
          }
        }
        leaf browser-proxy {
          description
            "Set browser proxy attributes for client";
          type string;
        }
        list group {
          description
            "Set group profile attributes for client";
          key "name";
          leaf name {
            type string;
          }
          uses crypto-isakmp-client-configuration-group-grouping;
        }
      }
      list firewall {
        description
          "Define client firewall";
        key "policy-name";
        leaf policy-name {
          type string;
        }
        leaf optional {
          description
            "firewall policy is optional";
          type enumeration {
            enum "cisco-integrated-client-firewall";
            enum "cisco-security-agent";
            enum "zonelabs-zonealarm";
            enum "zonelabs-zonealarmpro";
          }
        }
        leaf required {
          description
            "firewall policy is mandatory";
          type enumeration {
            enum "cisco-integrated-client-firewall";
            enum "cisco-security-agent";
            enum "zonelabs-zonealarm";
            enum "zonelabs-zonealarmpro";
          }
        }
        container policy {
          description
            "Define Cisco firewall Policy";
          container central-policy-push {
            description
              "Define Cisco Protection Policy";
            when "../../optional = 'cisco-integrated-client-firewall' or ../../required = 'cisco-integrated-client-firewall' or ../../optional = 'zonelabs-zonealarm' or ../../required = 'zonelabs-zonealarm' or ../../optional = 'zonelabs-zonealarmpro' or ../../required = 'zonelabs-zonealarmpro'";
            container access-list {
              description
                "Specify access list";
              leaf direction {
                type enumeration {
                  enum "in";
                  enum "out";
                }
              }
              leaf acl {
                type union {
                  type uint16 {
                    range "100..199";
                  }
                  type string {
                    pattern "[a-zA-Z].*";
                  }
                }
              }
            }
          }
          leaf check-presence {
            description
              "Define firewall are-you-there policy";
            when "../../optional = 'cisco-security-agent' or ../../required = 'cisco-security-agent' or ../../optional = 'zonelabs-zonealarm' or ../../required = 'zonelabs-zonealarm' or ../../optional = 'zonelabs-zonealarmpro' or ../../required = 'zonelabs-zonealarmpro'";
            type empty;
          }
        }
      }
    }
    container default {
      description
        "ISAKMP default policy";
      leaf policy {
        description
          "Enable default policies for ISAKMP protection suite";
        type empty;
      }
    }
    leaf disconnect-revoked-peers {
      description
        "Disconnect Crypto Session with Revoked Peer";
      type empty;
    }
    leaf enable {
      description
        "Enable ISAKMP";
      type empty;
    }
    leaf fragmentation {
      description
        "IKE Fragmentation enabled if required";
      type empty;
    }
    leaf identity {
      description
        "Set the identity which ISAKMP will use";
      type enumeration {
        enum "address";
        enum "dn";
        enum "hostname";
      }
    }
    leaf invalid-spi-recovery {
      description
        "Initiate IKE and send Invalid SPI Notify";
      type empty;
    }
    container keepalive {
      description
        "Set a keepalive interval for use with IOS peers";
      leaf number {
        type uint16 {
          range "10..3600";
        }
      }
      leaf retry-number {
        type uint8 {
          range "2..60";
        }
      }
      leaf send {
        type enumeration {
          enum "on-demand";
          enum "periodic";
        }
      }
    }
    container key {
      description
        "Set pre-shared key for remote peer";
      container key-address {
        leaf encryption {
          type enumeration {
            enum "0";
            enum "6";
          }
        }
        leaf key {
          type string;
        }
        choice ipv4-ipv6 {
          case ipv4 {
            container addr4-container {
              leaf address {
                description
                  "define shared key with IP address";
                type inet:ipv4-address;
              }
              leaf mask {
                type inet:ipv4-address;
              }
              leaf no-xauth {
                description
                  "Bypasses XAuth for this peer";
                type empty;
              }
            }
          }
          case ipv6 {
            container addr6-container {
              container address {
                description
                  "define shared key with IP address";
                leaf ipv6 {
                  description
                    "define shared key with IPv6 address";
                  type ios-types:ipv6-prefix;
                }
                leaf no-xauth {
                  description
                    "Bypasses XAuth for this peer";
                  type empty;
                }
              }
            }
          }
        }
      }
      container key-host {
        leaf encryption {
          type enumeration {
            enum "0";
            enum "6";
          }
        }
        leaf key {
          type string;
        }
        container host-container {
          leaf hostname {
            description
              "define shared key with hostname";
            type string;
          }
          leaf no-xauth {
            description
              "Bypasses XAuth for this peer";
            type empty;
          }
        }
      }
    }
    container nat {
      description
        "Set a nat  keepalive interval for use with IOS peers";
      leaf keepalive {
        description
          "Set a nat keepalive interval for use with IOS peers";
        type uint16 {
          range "5..3600";
        }
      }
    }
    container peer {
      description
        "Set Peer Policy";
      container ipv4-addr {
        list address {
          description
            "define peer policy for IP address";
          key "ipv4";
          leaf ipv4 {
            type inet:ipv4-address;
          }
          leaf vrf {
            description
              "specify front door vrf of the peer";
            type string;
          }
          uses crypto-isakmp-peer-grouping;
        }
      }
      container ipv6-addr {
        list address {
          description
            "define peer policy for IP address";
          key "ipv6";
          leaf ipv6 {
            description
              "define peer policy for IPv6 address";
            type inet:ipv6-address;
          }
          leaf vrf {
            description
              "specify front door vrf of the peer";
            type string;
          }
          uses crypto-isakmp-peer-grouping;
        }
      }
      list hostname {
        description
          "hostname  define peer policy for hostname";
        key "name";
        leaf name {
          type string;
        }
        leaf vrf {
          description
            "specify front door vrf of the peer";
          type string;
        }
        uses crypto-isakmp-peer-grouping;
      }
    }
    list policy {
      description
        "Set policy for an ISAKMP protection suite";
      key "number";
      leaf number {
        type uint32 {
          range "1..10000";
        }
      }
      container default {
        description
          "Set a command to its defaults";
        uses crypto-isakmp-policy-grouping;
        leaf lifetime {
          description
            "Set lifetime for ISAKMP security association";
          type empty;
        }
      }
      uses crypto-isakmp-policy-grouping;
      leaf lifetime {
        description
          "Set lifetime for ISAKMP security association";
        type uint32 {
          range "60..86400";
        }
      }
    }
    list profile {
      description
        "Define ISAKMP Profiles";
      key "name";
      leaf name {
        type string;
      }
      container default {
        description
          "Set a command to its defaults";
        uses crypto-isakmp-profile-default-grouping;
      }
      uses crypto-isakmp-profile-grouping;
    }
    container xauth {
      description
        "Set Extended Authentication values";
      leaf timeout {
        description
          "Set Extended Authentication timeout";
        type uint8 {
          range "5..90";
        }
      }
    }
  }

  grouping crypto-key-decrypt-rc-rsa-np-grouping {
    leaf name {
      description
        "Name of keypair to decrypt.";
      type string;
    }
    leaf passphrase {
      description
        "decryption key.";
      type string;
    }
  }

  grouping crypto-key-decrypt-rc-rsa-grouping {
    container ec {
      description
        "EC keys";
      presence "true";
      uses crypto-key-decrypt-rc-rsa-np-grouping;
    }
    container rsa {
      description
        "RSA keys";
      presence "true";
      uses crypto-key-decrypt-rc-rsa-np-grouping;
    }
  }

  grouping crypto-key-encrypt-rc-rsa-np-grouping {
    leaf name {
      description
        "Name of keypair to encrypt.";
      type string;
    }
    leaf passphrase {
      description
        "encryption key.";
      type string;
    }
  }

  grouping crypto-key-encrypt-rc-rsa-grouping {
    container ec {
      description
        "EC keys";
      presence "true";
      uses crypto-key-encrypt-rc-rsa-np-grouping;
    }
    container rsa {
      description
        "RSA keys";
      presence "true";
      uses crypto-key-encrypt-rc-rsa-np-grouping;
    }
  }

  grouping crypto-key-url-file-ex-grouping {
    leaf file {
      type enumeration {
        enum "bootflash:";
        enum "flash:";
        enum "ftp:";
        enum "http:";
        enum "https:";
        enum "null:";
        enum "nvram:";
        enum "pram:";
        enum "rcp:";
        enum "scp:";
        enum "system:";
        enum "tftp:";
        enum "tmpsys:";
      }
    }
  }

  grouping crypto-key-url-file-im-grouping {
    leaf file {
      type enumeration {
        enum "bootflash:";
        enum "cns:";
        enum "flash:";
        enum "ftp:";
        enum "http:";
        enum "https:";
        enum "null:";
        enum "nvram:";
        enum "pram:";
        enum "rcp:";
        enum "scp:";
        enum "system:";
        enum "tar:";
        enum "tftp:";
        enum "tmpsys:";
      }
    }
  }

  grouping crypto-key-export-pem-grouping {
    container pem {
      description
        "File type to export";
      choice terminal-url {
        case terminal-case {
          container terminal {
            description
              "Export via the terminal (cut-and-paste)";
            choice des-3des {
              case pk-3des-case {
                leaf pk-3des {
                  description
                    "Encrypt the private key with 3DES";
                  type string;
                }
              }
              case des-case {
                leaf des {
                  description
                    "Encrypt the private key with DES";
                  type string;
                }
              }
            }
          }
        }
        case url-case {
          container url {
            description
              "Export via the file systems";
            uses crypto-key-url-file-ex-grouping;
            choice des-3des {
              case url-3des-case {
                leaf url-3des {
                  description
                    "Encrypt the private key with 3DES";
                  type string;
                }
              }
              case des-case {
                leaf des {
                  description
                    "Encrypt the private key with DES";
                  type string;
                }
              }
            }
          }
        }
      }
    }
  }

  grouping crypto-key-pubkey-key-grouping {
    leaf address {
      description
        "Assign an address to the key";
      type inet:ipv4-address;
    }
    container key-string {
      description
        "Key data";
      leaf hex-data {
        type string;
      }
      leaf quit {
        description
          "Exit data entry mode";
        type empty;
      }
    }
    leaf serial-number {
      description
        "Serial number of the device";
      type string;
    }
  }

  grouping crypto-key-pubkey-key-default-grouping {
    leaf address {
      description
        "Assign an address to the key";
      type empty;
    }
    container key-string {
      description
        "Key data";
      presence "true";
    }
    leaf serial-number {
      description
        "Serial number of the device";
      type empty;
    }
  }

  grouping crypto-key-pubkey-chain-grouping {
    list addressed-key {
      description
        "Public key associated with an address";
      key "ip";
      leaf ip {
        type inet:ipv4-address;
      }
      leaf use {
        type enumeration {
          enum "encryption";
          enum "signature";
        }
      }
      uses crypto-key-pubkey-key-grouping;
      container default {
        description
          "Set a command to its defaults";
        uses crypto-key-pubkey-key-default-grouping;
      }
    }
    list named-key {
      description
        "Public key associated with a name";
      key "name";
      leaf name {
        type string;
      }
      leaf use {
        type enumeration {
          enum "encryption";
          enum "signature";
        }
      }
      uses crypto-key-pubkey-key-grouping;
      container default {
        description
          "Set a command to its defaults";
        uses crypto-key-pubkey-key-default-grouping;
      }
    }
  }

  grouping crypto-key-pubkey-chain-default-grouping {
    list addressed-key {
      description
        "Public key associated with an address";
      key "ip";
      leaf ip {
        type inet:ipv4-address;
      }
      leaf use {
        type enumeration {
          enum "encryption";
          enum "signature";
        }
      }
    }
    list named-key {
      description
        "Public key associated with a name";
      key "name";
      leaf name {
        type string;
      }
      leaf use {
        type enumeration {
          enum "encryption";
          enum "signature";
        }
      }
    }
  }

  grouping crypto-key-grouping {
    container decrypt {
      description
        "Decrypt a keypair.";
      uses crypto-key-decrypt-rc-rsa-grouping;
      container write {
        description
          "Will write the configuration to startup-config.";
        uses crypto-key-decrypt-rc-rsa-grouping;
      }
    }
    container encrypt {
      description
        "Encrypt a keypair.";
      uses crypto-key-encrypt-rc-rsa-grouping;
      container write {
        description
          "Will write the configuration to startup-config.";
        uses crypto-key-encrypt-rc-rsa-grouping;
      }
    }
    container export {
      description
        "Export keys";
      list ec {
        description
          "Export EC keys";
        key "label";
        leaf label {
          type string;
        }
        uses crypto-key-export-pem-grouping;
      }
      list rsa {
        description
          "Export RSRA keys";
        key "label";
        leaf label {
          type string;
        }
        uses crypto-key-export-pem-grouping;
      }
    }
    container generate {
      description
        "Generate new keys";
      container ec {
        description
          "Generate EC keys for ECDSA";
        leaf keysize {
          description
            "Number of bits";
          type enumeration {
            enum "256";
            enum "384";
          }
        }
        leaf exportable {
          description
            "Allow key to be exported";
          type empty;
        }
        leaf label {
          description
            "Provide a label";
          type string;
        }
      }
      container rsa {
        description
          "Generate RSA keys";
        presence "true";
        leaf encryption {
          description
            "Generate a general purpose RSA key pair for signing and encryption";
          type empty;
        }
        leaf exportable {
          description
            "Allow the key to be exported";
          type empty;
        }
        leaf general-keys {
          description
            "Generate a general purpose RSA key pair for signing and encryption";
          type empty;
        }
        leaf label {
          description
            "Provide a label";
          type string;
        }
        leaf modulus {
          description
            "Provide number of modulus bits on the command line";
          type uint16 {
            range "360..4096";
          }
        }
        leaf on {
          description
            "create key on specified device.";
          type string;
        }
        leaf redundancy {
          description
            "Allow the key to be synced to high-availability peer";
          type empty;
        }
        leaf signature {
          description
            "Generate a general purpose RSA key pair for signing and encryption";
          type empty;
        }
        leaf storage {
          description
            "Store key on specified device";
          type string;
        }
        leaf usage-keys {
          description
            "Generate separate RSA key pairs for signing and encryption";
          type empty;
        }
      }
    }
    container import {
      description
        "Import keys";
      list ec {
        description
          "Import EC keys";
        key "name";
        leaf name {
          type string;
        }
        leaf exportable {
          description
            "Allow key to be exported";
          type empty;
        }
        choice terminal-url {
          case terminal-case {
            leaf terminal {
              description
                "Import via the terminal (cut-and-paste)";
              type string;
            }
          }
          case url-case {
            container url {
              description
                "Export via the file systems";
              uses crypto-key-url-file-im-grouping;
              leaf key {
                type string;
              }
            }
          }
        }
      }
      list rsa {
        description
          "Import RSA keys";
        key "label";
        leaf label {
          type string;
        }
        leaf encryption {
          description
            "Encryption key";
          type empty;
        }
        leaf exportable {
          description
            "Allow the key to be exported";
          type empty;
        }
        leaf general-purpose {
          description
            "General Purpose key";
          type empty;
        }
        leaf on {
          description
            "Make this an on-token key";
          type string;
        }
        leaf pem {
          description
            "File type to import";
          type empty;
        }
        leaf redundancy {
          description
            "Sync this key to the standby";
          type empty;
        }
        leaf signature {
          description
            "Signature key";
          type empty;
        }
        leaf storage {
          description
            "Store key on specified device";
          type string;
        }
        leaf usage-keys {
          description
            "Usage key pairs";
          type empty;
        }
        choice terminal-url {
          case terminal-case {
            leaf terminal {
              description
                "Import via the terminal (cut-and-paste)";
              type string;
            }
          }
          case url-case {
            container url {
              description
                "Export via the file systems";
              uses crypto-key-url-file-im-grouping;
              leaf key {
                type string;
              }
            }
          }
        }
      }
    }
    container move {
      description
        "Move keys";
      container rsa {
        description
          "Move RSA keys";
        leaf label {
          type string;
        }
        leaf non-exportable {
          description
            "Do Not allow the key to be exported";
          type empty;
        }
        leaf on {
          description
            "Make this an on-token key";
          type string;
        }
        leaf redundancy {
          description
            "Sync this key to the standby";
          type empty;
        }
        leaf storage {
          description
            "Store key on specified device";
          type string;
        }
      }
    }
    container pubkey-chain {
      description
        "Peer public key chain management";
      container rsa {
        description
          "Peer RSA public key chain management";
        uses crypto-key-pubkey-chain-grouping;
        container default {
          description
            "Set a command to its defaults";
          uses crypto-key-pubkey-chain-default-grouping;
        }
      }
    }
    leaf storage {
      description
        "default storage location for keypairs";
      type string;
    }
    container zeroize {
      description
        "Remove keys";
      container ec {
        description
          "Remove EC keys";
        presence "true";
        leaf label {
          type string;
        }
      }
      container pubkey-chain {
        description
          "Remove peer's cached public key";
        presence "true";
        leaf index {
          type uint16;
        }
      }
      container rsa {
        description
          "Remove RSA keys";
        presence "true";
        leaf label {
          type string;
        }
      }
    }
  }

  grouping crypto-keyring-key-grouping {
    leaf key {
      description
        "specify the key";
      type empty;
    }
    leaf encryption {
      type enumeration {
        enum "0";
        enum "6";
      }
    }
    leaf unencryt-key {
      type string;
    }
  }

  grouping crypto-keyring-grouping {
    leaf description {
      description
        "Specify a description about this keyring";
      type string;
    }
    leaf local-address {
      description
        "Limit the keyring usage to a local address";
      type string;
    }
    container pre-shared-key {
      description
        "Pre-Shared Key";
      container address {
        description
          "pre shared key by address";
        choice ipv4-ipv6 {
          case ipv4 {
            list ipv4 {
              description 
                "address prefix";
              key "ipv4-addr";
              leaf ipv4-addr {
                type inet:ipv4-address;
              }
              leaf mask {
                description
                    "address prefix mask";
                type inet:ipv4-address;
              }
              uses crypto-keyring-key-grouping;
            }
          }
          case ipv6 {
            list ipv6 {
              description
                "define shared key with IPv6 address";
              key "ipv6";
              leaf ipv6 {
                description
                  "IPv6 prefix mask";
                type ios-types:ipv6-prefix;
              }
              uses crypto-keyring-key-grouping;
            }
          } 
        }
      }
      list hostname {
        description
          "hostname  define peer policy for hostname";
        key "name";
        leaf name {
          type string;
        }
        uses crypto-keyring-key-grouping;
      }
    }
    container rsa-pubkey {
      description
        "Peer RSA public key chain management";
      container addr {
        leaf address {
          description
            "Public key associated with an address";
          type inet:ipv4-address;
        }
        leaf way {
          type enumeration {
            enum "encryption";
            enum "signature";
          }
        }
      }
      container hostname {
        leaf name {
          description
            "Public key associated with a hostname";
          type string;
        }
        leaf way {
          type enumeration {
            enum "encryption";
            enum "signature";
          }
        }
      }
    }
  }

  grouping crypto-map-grouping {
    uses crypto-map-common-grouping;
    container set {
      description
        "Set values for encryption/decryption";
      uses crypto-map-common-set-grouping;
      container security-association {
        description
          "Security association parameters";
        uses crypto-map-common-set-security-association-grouping;
        leaf level {
          description
            "specify a security association granularity level for identities";
          type enumeration {
            enum "per-host";
          }
        }
      }
    }
  }

  grouping crypto-map-default-grouping {
    leaf description {
      description
        "Description of the crypto map statement policy";
      type empty;
    }
    container dialer {
      description
        "Dialer related commands";
      leaf pre-classify {
        description
          "Enable dialer list classification before initiating IKE";
        type empty;
      }
    }
    container match {
      description
        "Match values";
      leaf address {
        description
          "Match address of packets to encrypt";
        type empty;
      }
    }
    container qos {
      description
        "Quality of Service related commands";
      leaf pre-classify {
        description
          "Enable QOS classification before packets are tunnel encapsulated";
        type empty;
      }
    }
    container reverse-route {
      description
        "Reverse Route Injection.";
      presence "true";
    }
    container set {
      description
        "Set values for encryption/decryption";
      leaf group {
        description
          "Set the san group parameters";
        type empty;
      }
      leaf identity {
        description
          "Identity restriction";
        type empty;
      }
      leaf ikev2-profile {
        description
          "Specify ikev2 Profile";
        type string;
      }
      leaf isakmp-profile {
        description
          "Specify isakmp Profile";
        type empty;
      }
      container pfs {
        description
          "Specify pfs settings";
        presence "true";
      }
      container reverse-route {
        description
          "Reverse Route Injection";
        presence "true";
      }
      container security-association {
        description
          "Security association parameters";
        leaf dfbit {
          description
            "Handling of encapsulated DF bit.";
          type empty;
        }
        container dummy {
          description
            "Enable transmitting dummy packets";
          presence "true";
        }
        leaf ecn {
          description
            "Handling of ECN bit";
          type empty;
        }
        container idle-time-container {
          leaf idle-time {
            description
              "Automatically delete IPSec SAs after a given idle period.";
            type empty;
          }
          leaf default {
            description
              "All SAs idle-out reset to default peer";
            type empty;
          }
        }
        leaf level {
          description
            "specify a security association granularity level for identities";
          type enumeration {
            enum "per-host";
          }
        }
        container lifetime {
          description
            "security association lifetime";
          leaf days {
            description
              "Time-based key duration in days";
            type empty;
          }
          leaf kilobytes {
            description
              "Volume-based key duration";
            type empty;
          }
          leaf seconds {
            description
              "Time-based key duration in seconds";
            type empty;
          }
        }
        container replay {
          description
            "Set replay checking.";
          leaf disable {
            description
              "Disable replay checking";
            type empty;
          }
          leaf window-size {
            description
              "Set replay window size.";
            type empty;
          }
        }
      }
      leaf transform-set {
        description
          "Specify list of transform sets in priority order";
        type empty;
      }
    }
  }

  grouping crypto-map-gdoi-mapping-grouping {
    leaf activate {
      description
        "Activate the crypto map to work in fail-close mode";
      type empty;
    }
    container match {
      description
        "Match address of packets for fail-close";
      leaf address {
        description
          "Match address of packets for fail-close.";
        type ios-types:ext-acl-type;
      }
    }
  }

  grouping crypto-map-gdoi-default-mapping-grouping {
    leaf activate {
      description
        "Activate the crypto map to work in fail-close mode";
      type empty;
    }
    container match {
      description
        "Match address of packets for fail-close";
      leaf address {
        description
          "Match address of packets for fail-close.";
        type empty;
      }
    }
  }

  grouping time-grouping {
    container time {
      choice date-month {
        case date1 {
          leaf date1 {
            type uint8 {
              range "1..31";
            }
          }
        }
        case month1 {
          leaf month1 {
            type string;
          }
        }
      }
      choice month-date {
        case date2 {
          leaf date2 {
            when "../month1";
            type uint8 {
              range "1..31";
            }
          }
        }
        case month2 {
          leaf month2 {
            when "../date1";
            type string;
          }
        }
      }
      leaf year {
        type uint16 {
          range "1993..2035";
        }
      }
      leaf clock {
        type string;
      }
      leaf utc {
        description
          "Time is in UTC (not local Time Zone)";
        type empty;
      }
    }
  }

  grouping compare-time-grouping {
    container eq {
      description
        "Equal";
      uses time-grouping;
    }
    container ge {
      description
        "Greater than or equal";
      uses time-grouping;
    }
    container lt {
      description
        "Less Than";
      uses time-grouping;
    }
    container ne {
      description
        "Not Equal";
      uses time-grouping;
    }
  }

  grouping compare-string-grouping {
    leaf co {
      description
        "Contains";
      type string;
    }
    leaf eq {
      description
        "Equal";
      type string;
    }
    leaf nc {
      description
        "Does not contain";
      type string;
    }
    leaf ne {
      description
        "Not Equal";
      type string;
    }
  }


  grouping crypto-pki-certificate-map-grouping {
    container alt-subject-name {
      description
        "Alternate subject name";
      uses compare-string-grouping;
    }
    container expires-on {
      description
        "Expiration date/time";
      uses compare-time-grouping;
    }
    container issuer-name {
      description
        "Certificate issuer name";
      uses compare-string-grouping;
    }
    container name {
      description
        "Any subject name field";
      uses compare-string-grouping;
    }
    container serial-number {
      description
        "Certificate serial number (hexidecimal)";
      uses compare-string-grouping;
    }
    container subject-name {
      description
        "Certificate subject name";
      uses compare-string-grouping;
    }
    container unstructured-subject-name {
      description
        "Unstructured subject name";
      uses compare-string-grouping;
    }
    container valid-start {
      description
        "Valid after date/time";
      uses compare-time-grouping;
    }
  }

  grouping crypto-pki-profile-enrollment-auth-grouping {
    leaf command {
      description
        "command to authenticate or enroll";
      type string;
    }
    leaf terminal {
      description
        "authenticate or enroll using terminal";
      type empty;
    }
    container url {
      description
        "url to authenticate/enroll";
      leaf name {
        type string;
      }
      leaf vrf {
        description
          "VRF to use for certificate enrollment ";
        type string;
      }
    }
  }

  grouping crypto-pki-profile-enrollment-grouping {
    container authentication {
      description
        "Retrieve CA certificate(s)";
      uses crypto-pki-profile-enrollment-auth-grouping;
    }
    container enrollment {
      description
        "Enroll router with a CA";
      uses crypto-pki-profile-enrollment-auth-grouping;
      leaf credential {
        description
          "Use existing router cert for new enrollment";
        type string;
      }
    }
    leaf method-est {
      description
        "Use EST for this profile";
      type empty;
    }
    list parameter {
      description
        "Define a parameter value or prompt";
      key "number";
      leaf number {
        type uint8 {
          range "1..8";
        }
      }
      choice prompt-value {
        case prompt-case {
          leaf prompt {
            description
              "Define a parameter prompt";
            type string;
          }
        }
        case value-case {
          leaf value {
            description
              "Define a parameter value";
            type string;
          }
        }
      }
    }
    container reenrollment {
      description
        "Re-enroll router with a CA";
      uses crypto-pki-profile-enrollment-auth-grouping;
    }
    leaf source-interface {
      description
        "Interface used as source address";
      type string;
    }
  }


  grouping config-crypto-grouping {
    // crypto call
    container call {
      description
        "Configure Crypto Call Admission Control";
      container admission {
        description
          "Configure Crypto Call Admission Control";
        container limit {
          description
            "Configure Crypto Call Admission Control limits";
          container all {
            description
              "onfigure Crypto Call Admission Control total in-negotiation SA limit";
            leaf in-negotiation-sa {
              description
                "Maximum number of in-negotiation SAs allowed";
              type uint32 {
                range "10..99999";
              }
            }
          }
          container ike {
            description
              "Configure Crypto Call Admission Control active IKE SA limit";
            leaf in-negotiation-sa {
              description
                "Maximum number of in-negotiation IKE SAs allowed";
              type uint32 {
                range "10..99999";
              }
            }
            leaf sa {
              description
                "Maximum active IKE SAs allowed";
              type uint32 {
                range "0..99999";
              }
            }
          }
          container ipsec {
            description
              "Configure Crypto Call Admission Control active IPSec SA limit";
            leaf sa {
              description
                "Maximum active IPSec SAs allowed";
              type uint32 {
                range "0..99999";
              }
            }
          }
        }
      }
    }
    // crypto dynamic-map
    list dynamic-map {
      description
        "Specify a dynamic crypto map template";
      key "name sequence";
      leaf name {
        type string;
      }
      leaf sequence {
        type uint16;
      }
      container default {
        description
          "Set a command to its defaults";
        uses crypto-dynamic-map-default-grouping;
      }
      uses crypto-dynamic-map-grouping;
    }
    // crypto engine
    container engine {
      description
        "Enter a crypto engine configurable menu";
      leaf software {
        description
          "Software crypto engine";
        type enumeration {
          enum "ipsec";
          enum "isakmp";
        }
      }
    }
    // crypto gdoi
    container gdoi {
      description
        "Configure GKM (Group Key Management, GDOI or G-IKEv2) Policy";
      list group {
        description
          "Configure a GKM (Group Key Management, GDOI or G-IKEv2) Group";
        key "name";
        leaf name {
          type string;
        }
        leaf ipv6 {
          description
            "IPv6 GKM (Group Key Management) Group";
          type empty;
        }
        uses crypto-gdio-grouping;
        container default {
          description
            "Set a command to its defaults";
          uses crypto-gdio-default-grouping;
        }
      }
    }
    // crypto ikev2
    container ikev2 {
      description
        "Configure IKEv2 Options";
      uses crypto-ikev2-grouping;
    }
    // crypto gkm
    container gkm {
      description
        "Configure GKM (Group Key Management, GDOI or G-IKEv2) Policy";
      list group {
        description
          "Configure a GKM (Group Key Management, GDOI or G-IKEv2) Group";
        key "name";
        leaf name {
          type string;
        }
        leaf ipv6 {
          description
            "IPv6 GKM (Group Key Management) Group";
          type empty;
        }
        uses crypto-gdio-grouping;
        container default {
          description
            "Set a command to its defaults";
          uses crypto-gdio-default-grouping;
        }
      }
    }
    // crypto identity
    list identity {
      description
        "Enter a crypto identity list";
      key "name";
      leaf name {
        type string;
      }
      container default {
        description
          "Set a command to its defaults";
        uses crypto-identity-default-grouping;
      }
      uses crypto-identity-grouping;
    }
    // crypto ipsec
    container ipsec {
      description
        "Configure IPSEC policy";
      uses crypto-ipsec-grouping;
    }
    // crypto isakmp
    container isakmp {
      description
        "Configure ISAKMP policy";
      uses crypto-isakmp-grouping;
    }
    // crypto key
    container key {
      description
        "Long term key operations";
      uses crypto-key-grouping;
    }
    // crypto keyring
    list keyring {
      description
        "Key ring commands";
      key "name";
      leaf name {
        type string;
      }
      leaf vrf {
        description
          "Mention a vrf it belongs to";
        type string;
      }
      container default {
        description
          "Set a command to its defaults";
        uses crypto-keyring-grouping;
      }
      uses crypto-keyring-grouping;
    }
    // crypto logging
    container logging {
      description
        "logging messages";
      container ezvpn {
        description
          "ezvpn logging enable/disable";
        presence "true";
        leaf group {
          description
            "ezvpn group";
          type string;
        }
      }
      leaf ikev2 {
        description
          "logging IKEv2 sessions";
        type empty;
      }
      leaf session {
        description
          "logging up/down session";
        type empty;
      }
    }

    // crypto map 
    container crypto-map {
      list map {
        description
          "Enter a crypto map";
        key "name";
        leaf name {
          type string;
        }
        leaf ipv6 {
          description
            "IPv6 crypto map";
          type empty;
        }
        leaf sequence-number {
          type uint16;
        }
        leaf keying {
          type enumeration {
            enum "ipsec-isakmp";
            enum "ipsec-manual";
            enum "gdoi";
            enum "ckm";
          }
        }
        choice dynamic-profile {
          case dynamic-case {
            leaf dynamic {
              description
                "Enable dynamic crypto map support";
              when "../keying = 'ipsec-isakmp'";
              type string;
            }
          }
          case profile-case {
            leaf profile {
              description
                "Enable crypto map as a crypto-profile";
              when "../keying = 'ipsec-isakmp'";
              type string;
            }
          }
        }
        container default {
          description
            "Set a command to its defaults";
          uses crypto-map-default-grouping;
        }
        uses crypto-map-grouping;
      }
    }
    container map-ipv6-gdoi {
      list map {
        description
          "Enter a crypto map";
        key "name";
        leaf name {
          type string;
        }
        leaf ipv6 {
          description
            "IPv6 crypto map";
          type empty;
        }
        leaf gdoi {
          description
            "Configure crypto map gdoi features";
          type enumeration {
            enum "fail-close";
          }
        }
        container default {
          description
            "Set a command to its defaults";
          uses crypto-map-gdoi-default-mapping-grouping;
        }
        uses crypto-map-gdoi-mapping-grouping;
      }
    }
    container map-client {
      list map {
        description
          "Enter a crypto map";
        key "name";
        leaf name {
          type string;
        }
        leaf ipv6 {
          description
            "IPv6 crypto map";
          type empty;
        }
        container client {
          description
            "Specify client configuration settings";
          container accounting {
            description
              "Accounting parameters.";
            leaf list {
              description
                "AAA accounting list to use";
              type string;
            }
          }
          container authentication {
            description
              "Use Extended Authentication";
            leaf list {
              description
                "AAA authentication list to use";
              type string;
            }
          }
          container configuration {
            description
              "Specify client configuration settings";
            container address {
              description
                "Specify client network address configuration";
              leaf initiate {
                description
                  "Push the network address to the client";
                type empty;
              }
              leaf respond {
                description
                  "Respond to network address requests from the client";
                type empty;
              }
            }
          }
        }
        container isakmp {
          description
            "Specify isakmp configuration settings";
          leaf authorization {
            description
              "Authorization parameters.";
            type empty;
          }
          leaf list {
            description
              "AAA Authorization list to use";
            type string;
          }
        }
        leaf isakmp-profile {
          description
            "Specify isakmp profile to use";
          type string;
        }
        leaf local-address {
          description
            "Interface to use for local address for this crypto map";
          type string;
        }
        container redundancy {
          description
            "High availability options for this map";
          container replay-interval {
            description
              "HA replay counter interval";
            leaf inbound {
              description
                "HA inbound replay counter interval";
              type uint32 {
                range "0..1000";
              }
            }
            leaf outbound {
              description
                "HA outbound replay counter interval";
              type uint32 {
                range "1000..10000";
              }
            }
          }
        }
      }
    }
    // crypto mib
    container mib {
      description
        "Configure Crypto-related MIB Parameters";
      container ipsec {
        description
          "onfigure MIB Parameters";
        container flowmib {
          description
            "Configure IPSec Flow-MIB Parameters";
          container history {
            description
              "Configure IPSEC Flow MIB History Parameters";
            container failure {
              description
                "Configure IPSEC Flow MIB Failure History Parameters";
              leaf size {
                description
                  "Configure IPSEC Flow MIB Tunnel Failure History Window Size";
                type uint8;
              }
            }
            container tunnel {
              description
                "Configure IPSEC Flow MIB Tunnel History Parameters";
              leaf size {
                description
                  "Configure IPSEC Flow MIB Tunnel Failure History Window Size";
                type uint8;
              }
            }
          }
        }
      }
    }
    // crypto pki
    container pki {
      description
        "Public Key components";
      leaf authenticate {
        description
          "Get the CA certificate";
        type string;
      }
      container certificate {
        description
          "Actions on certificates";

/* Hex-data is not supported
        container certificate {
          tailf:cli-drop-node-name;
          tailf:cli-exit-command "quit";
          list hex-data {
            tailf:cli-drop-node-name;
            tailf:cli-suppress-mode;
            ordered-by "user";
            key hex;
            leaf hex {
              tailf:cli-multi-value;
              type string {
              }
            }
          }
        }
Hex-data is not supported */

        // crypto pki certificate chain *
        list chain {
          description
            "Identify certificates";
          key "name";
          leaf name {
            type string;
          }
          // crypto pki certificate chain * / certificate *
          list certificate {
            description
              "Certificate issued by the CA";
            key "serial";
            leaf serial {
              type string;
            }
            leaf certtype {
              type enumeration {
                enum "ca";
                enum "ra-encrypt";
                enum "ra-general";
                enum "ra-sign";
                enum "rollover";
                enum "self-signed";
              }
            }

/* Hex-data is not supported
            list hex-data {
              tailf:cli-drop-node-name;
              tailf:cli-suppress-mode;
              ordered-by "user";
              key hex;
              leaf hex {
                tailf:cli-multi-value;
                type string {
                }
              }
            }
Hex-data is not supported */

          }
        }
        list map {
          description
            "Define certificate attributes map";
          key "tag";
          leaf tag {
            type string;
          }
          leaf sequence {
            type uint16;
          }
          uses crypto-pki-certificate-map-grouping;
        }
        leaf pool {
          description
            "Identify CA certificates in pool";
          type empty;
        }
        leaf query {
          description
            "Get certificates from the CA after reboot";
          type empty;
        }
        container storage {
          description
            "specify where to store certificates";
          leaf path {
            type union {
              type enumeration {
                enum "bootflash:";
                enum "flash:";
                enum "nvram:";
              }
              type string;
            }
          }
          leaf on {
            description
              "Create keypairs on device";
            type empty;
          }
          leaf with-keypair {
            description
              "Store certificates with keypair";
            type empty;
          }
        }
        leaf validate {
          description
            "Validate a certificate chain";
          type string;
        }
      }
      // crypto pki crl
      container crl {
        description
          "Actions on certificate revocation lists";
        container cache {
          description
            "Cache which holds recently parsed CRLs";
          leaf size {
            description
              "Size of the recently parsed CRL cache";
            type uint32 {
              range "0..131072";
            }
          }
        }
        container download {
          description
            "auto-download CRL";
          container schedule {
            description
              "Schedule time to auto-download CRL";
            leaf prepublish {
              description
                "Requests CRL at prepublish time";
              type uint16;
            }
            container retries {
              description
                "Retry request for failed CDP locations";
              leaf number {
                type uint8 {
                  range "1..15";
                }
              }
              leaf interval {
                description
                  "retry time interval for each attempt";
                type uint16 {
                  range "15..600";
                }
              }
            }
            container time {
              description
                "Request auto-download CRL at this time";
              leaf date {
                type enumeration {
                  enum "Friday";
                  enum "Monday";
                  enum "Saturday";
                  enum "Sunday";
                  enum "Thursday";
                  enum "Tuesday";
                  enum "Wednesday";
                }
              }
              leaf clock {
                type string;
              }
            }
          }
          leaf trustpoint {
            description
              "Trustpoint to auto-download CRL";
            type string;
          }
          container url {
            description
              "URL to auto-download CRL";
            leaf name {
              type string;
            }
            leaf source-interface {
              description
                "Interface used as source address";
              type string;
            }
            leaf vrf {
              description
                "VRF to use for CRL download";
              type string;
            }
          }
        }
        leaf request {
          description
            "Requests a current CRL";
          type string;
        }
      }
      leaf enroll {
        description
          "Request a certificate from a CA";
        type string;
      }
      list export {
        description
          "Export certificate or PKCS12 file";
        key "name";
        leaf name {
          type string;
        }
        container pem {
          description
            "Export to PEM files";
          container terminal {
            description
              "Export via the terminal (cut-and-paste)";
            presence "true";
            container pem-3des {
              description
                "Encrypt the private key with 3DES";
              leaf password {
                description
                  "Passphrase";
                type string;
              }
            }
            container des {
              description
                "Encrypt the private key with DES";
              leaf password {
                description
                  "Passphrase";
                type string;
              }
            }
            leaf rollover {
              description
                "Export the rollover CA certificate";
              type empty;
            }
          }
          container url {
            description
              "Export via the file systems";
            uses crypto-key-url-file-ex-grouping;
            leaf encrypt {
              type enumeration {
                enum "3des";
                enum "des";
              }
            }
            leaf password {
              description
                "Passphrase";
              when "../encrypt";
              type string;
            }
          }
        }
        container pkcs12 {
          description
            "Export to PKCS12 file";
          uses crypto-key-url-file-ex-grouping;
          leaf password {
            description
              "Passphrase";
            type string;
          }
        }
      }
      //crypto pki import
      list import {
        description
          "Import certificate or PKCS12 file";
        key "name";
        leaf name {
          type string;
        }
        leaf certificate {
          description
            "Import a certificate from a TFTP server or the terminal";
          type empty;
        }
        container pem {
          description
            "Import from PEM files";
          leaf check {
            description
              "Validate certificate on input";
            type empty;
          }
          leaf exportable {
            description
              "Allow the key as to be exported";
            type empty;
          }
          container terminal {
            description
              "Import via the terminal (cut-and-paste)";
            leaf password {
              description
                "Passphrase";
              type string;
            }
          }
          container url {
            description
              "Export via the file systems";
            uses crypto-key-url-file-ex-grouping;
            leaf password {
              description
                "Passphrase";
              type string;
            }
          }
          leaf usage-keys {
            description
              "Usage key pairs";
            type empty;
          }
        }
        container pkcs12 {
          description
            "Import from PKCS12 file";
          uses crypto-key-url-file-ex-grouping;
          leaf password {
            description
              "Passphrase";
            type string;
          }
        }
      }
      // crypto pki profile enrollment
      container profile {
        description
          "Define a certificate profile";
        list enrollment {
          description
            "Define an enrollment profile";
          key "tag";
          leaf tag {
            type string;
          }
          uses crypto-pki-profile-enrollment-grouping;
          container default {
            description
              "Set a command to its defaults";
            uses crypto-pki-profile-enrollment-grouping;
          }
        }
      }
      //crypto pki server
      container server {
        description
          "Enable IOS Certificate server";
        leaf name {
          type string;
        }
        leaf rollover {
          description
            "Rollover the server's key and certificate";
          type empty;
        }
        leaf cancel {
          description
            "Cancel a pending rollover";
          type empty;
        }
      }
      // crypto pki trustpoint *
      list trustpoint {
        description
          "Define a CA trustpoint";
        key "id";
        leaf id {
          type string;
        }
        //  authorization     Authorization parameters.
        //  certificate       certificate options
        //  chain-validation  Validation parameters
        //  crl               CRL options

        container auto-enroll {
          description
            "Automatically enroll this router identity";
          leaf percent {
            description
              "renewal percentage";
            type ios-types:percentage;
          }
          leaf regenerate {
            description
              "Regenerate keys on re-enrollment";
            type empty;
          } 
        }
        container enrollment {
          description
            "Enrollment parameters";
          leaf http-proxy {
            description
              "HTTP proxy server for enrollment";
            type string;
          }
          container mode {
            description
              "Mode supported by the Certificate Authority";
            leaf ra {
              description
                "Registration Authority mode";
              type empty;
            }
          }
          leaf pkcs12 {
            type empty;
          }
          leaf profile {
            description
              "Specify an profile for enrollment";
            type string;
          }
          container retry {
            description
              "Polling parameters";
            leaf count {
              description
                "How many times to poll CA for our certificate";
              type uint8 {
                range "1..100";
              }
            }
            leaf period {
              description
                "How long to wait between requests to CA for our certificate";
              type uint8 {
                range "1..60";
              }
            }
          }
          leaf selfsigned {
            description
              "Generate a Self Signed Certificate";
            type empty;
          }
          container terminal {
            description
              "Enroll via the terminal (cut-and-paste)";
            presence "true";
            leaf pem {
              description
                "Include PEM encapsulation boundaries";
              type empty;
            }
          }
          leaf url {
            description
              "CA server enrollment URL";
            type string;
          }
        }
        container password {
          description
            "revocation password";
          presence true;
          leaf encryption_type {
            description
              "Encryption type";
            type uint8 {
              range "0..9";
            }
          }
          leaf clear_password {
            description
              "revocation password";
            type string;
          }
        }   
        //  exit              Exit from certificate authority trustpoint
        //                    entry mode
        //  fingerprint       CA Certificate Fingerprint
        //  fqdn              include fully-qualified domain name
        //  hash              Hash algorithm
        //  ip-address        include ip address
        //  ip-extension      RFC3779 IP extension for device certificate
        //                    request
        //  match             Match a certificate map
        //  no                Negate a command or set its defaults
        //  ocsp              OCSP parameters
        //  on                create keypair on device.
        //  password          revocation password
        //  primary           Specify trustpoint as primary
        //  query             Query parameters
        //  regenerate        Regenerate keys on re-enrollment
        leaf revocation-check {
          description
            "Revocation checking options";
          type enumeration {
            enum "crl";
            enum "none";
            enum "ocsp";
          }
        }
        //  root              Protocol to get CA certificate
        container rsakeypair {
          description
            "Specify rsakeypair for this identity";  
          leaf key-label {
            description
              "RSA keypair label";
            type string;
          }
          leaf gen-key {
            description
              "General Purpose or Signature Key length";
            type uint16 {
              range "360..4096";
            }
          }
          leaf encrypt-key {
            description
              "Encryption Key length";
            type uint16 {
              range "360..4096";
            }
          }
        }
        container serial-number {
          description
            "help";
          presence true;
          leaf none {
            description
              "do not include serial number";
            type empty;
          }
        }
        container ip-address {
          description
            "include ip address";
          leaf address-line {
            description
              "interface name or ip address";
            type string;
          }
          leaf none {
            description
              "do not include ip address";
            type empty;
          }
        }
        //  serial-number     include serial number
        //  show              Show this router trustpoint
        //  source            Specify source
        //  storage           key and certificate storage location to use
        //                    with this trustpoint.
        leaf subject-name {
          description
            "Subject Name";
          type string;
        }
        //  usage             Certificate Usage
        //  vrf               vrf to use for enrollment and obtaining CRLs
        leaf vrf {
          description
          "Name of VRF to use with trustpoint";
          type string;
        }
      }
      // crypto pki token *
      container token {
        description
          "Configure cryptographic token";
        list token-name {
          key "name";
          leaf name {
            type string;
          }
          uses crypto-pki-token-grouping;
        }
      }
      // crypto pki trustpool
      container trustpool {
        description
          "Define CA trustpool";
        container import {
          description
            "Import a trustpool bundle";
          presence "true";
          leaf clean {
            description
              "Remove all downloaded trustpool certificates prior to import";
            type empty;
          }
          leaf terminal {
            description
              "Import bundle via the terminal (cut-and-paste) in PEM format";
            type empty;
          }
          container url {
            description
              "Import via the file systems";
            uses crypto-key-url-file-im-grouping;
          }
        }
      }
      // crypto pki default
      container default {
        description
          "set default values for tokens";
        uses crypto-pki-token-grouping;
      }
    }
    //crypto tls-tunnel 
    container tls-tunnel {
      list tls-tunnel-list {
        description
          "Configure Crypto TLS-Tunnel Options";
        key tunnel-name;
        leaf tunnel-name {
          description
            "Name of TLS-Tunnel";
          type string;
        }
        list local-interface {
          description
            "Specify the WAN interfaces";
          key "interface-name" ;
          leaf interface-name {
            type string;
          }
          leaf priority {
            description
              "priority level";
            type uint8 {
              range "1..3";
            }
          }
        }
        container overlay-address {
          description
            "Specify the Overlay Address";
          leaf addresses {
            type inet:ip-address;
          }
          leaf vrf {
            description
              "VRF name";
            type string;
          }
        }  
        container protection {
          description
            "Cipher-Suite";
          leaf protection {
            type enumeration {
              enum "dhe-psk-aes128-cbc-sha1";
              enum "dhe-psk-aes256-cbc-sha1";
              enum "psk-aes128-cbc-sha1";
              enum "psk-aes256-cbc-sha1";
            }
          }
        }   
        container psk {
          description
            "Specify the Pre-Shared Key";
          list id {
            key "id";
            leaf id {
              type string;
            }
            container key {
              uses crypto-keyring-key-grouping;
            }  
          }   
        }
        container server {
          description
            "Specify the Server Address";
          list ipv4 {
            key "ipv4";
            leaf ipv4 {
              type inet:ipv4-address;
            }
            leaf port {
               type uint32;
             }
          }                  
          list ipv6 {                     
            key "ipv6";
            leaf ipv6 {
              type inet:ipv6-address;
            }
            leaf port {
              type uint32;
            }
          }
        }
      }
    }
    // crypto ssl
    container ssl {
      description
        "Configure Crypto SSL Options";
      container authorization {
        description
          "ssl authorization";
        leaf policy {
          description
            "Crypto SSL authorization policy";
          type string;
        }
      }
      container diagnose {
        description
          "SSLVPN diagnose";
        leaf error {
          description
            "Start error trace debug";
          type uint16 {
            range "1..1000";
          }
        }
      }
      leaf policy {
        description
          "Define SSL policies";
        type string;
      }
      leaf profile {
        description
          "Define SSL profiles";
        type string;
      }
      container proposal {
        description
          "Define ssl Proposal";
        leaf name {
          type string;
        }
        container protection {
          description
            "Specify the protection algorithms";
          leaf rsa-3des-ede-sha1 {
            description
              "RSA, 3DES and SHA1";
            type empty;
          }
          leaf rsa-aes128-sha1 {
            description
              "RSA, AES128 and SHA1";
            type empty;
          }
          leaf rsa-aes256-sha1 {
            description
              "RSA, AES256 and SHA1";
            type empty;
          }
          leaf rsa-rc4128-md5 {
            description
              "RSA, RC4 and MD5";
            type empty;
          }
        }
      }
    }
    // crypto vpn
    container vpn {
      description
        "Configure crypto vpn commands";
      container anyconnect {
        description
          "Configure anyconnect client package";
        container file {
          leaf filename {
            type string;
          }
          leaf sequence {
            description
              "client-side download sequence num (priority) of this package";
            type uint8;
          }
        }
        container profile-container {
          leaf profile {
            description
              "Configure anyconnect client profile";
            type string;
          }
          leaf filename {
            type string;
          }
        }
      }
      leaf csd {
        description
          "Configure Secure Desktop package";
        type string;
      }
    }
    leaf xauth {
      description
        "X-Auth parameters";
      type string;
    }
  }

  grouping config-interface-crypto-grouping {
    container crypto {
      description
        "Encryption/Decryption commands";
      container map {
        description
          "Assign a Crypto Map";
        leaf tag {
          type string;
        }
        leaf redundancy {
          description
            "enable redundancy";
          type string;
        }
        leaf stateful {
          description
            "enable stateful failover";
          type empty;
        }
      }
      container ipsec {
        description
          "Set IPSec parameters";
        leaf df-bit {
          description
            "Handling of encapsulated DF bit.";
          type enumeration {
            enum "clear";
            enum "copy";
            enum "set";
          }
        }
        leaf fragmentation {
          description
            "Handling of fragmentation of near-MTU sized packets";
          type enumeration {
            enum "after-encryption";
            enum "before-encryption";
          }
        }
      }
    }
  }

  grouping config-interface-ipv6-crypto-grouping {
    container crypto {
      description "Encryption/Decryption commands";
      leaf map {
        description "Assign an IPv6  Crypto Map";
        type string;
      }
    }
  }

  grouping config-key-grouping {
      list chain {
        description
          "Key-chain management";
        key "name";
        leaf name {
          type string;
        }
        leaf macsec {
          type empty;
        }
        list key {
          description
            "Configure a key";
          key "id";
          leaf id {
            type string;
          }
          leaf cryptographic-algorithm {
            description
              "Set cryptographic authentication algorithm";
            type enumeration {
              enum "aes-128-cmac";
              enum "aes-256-cmac";
              enum "hmac-sha-1";
              enum "hmac-sha-256";
              enum "hmac-sha-384";
              enum "hmac-sha-512";
              enum "md5";
            }
          }
          container key-string {
            description
              "Set key string";
            leaf encryption {
              type enumeration {
                enum "0";
                enum "6";
                enum "7";
              }
            }
            leaf key {
              type string {
                length "0..80";
              }
            }
          }
        }
      }
  }

  grouping config-interface-tunnel-ipsec-grouping {
    container ipsec {
      description
        "Use ipsec to protect this tunnel interface";
      leaf profile {
        description
          "Determine the ipsec policy profile to use.";
        type string;
      }
      leaf ikev2-profile {
        description
          "ikev2 policy profile";
        type string;
      }
    }
  }

  /////////////////////////////////////////////////////////
  // native / key *
  /////////////////////////////////////////////////////////
  augment "/ios:native/ios:key" {
    uses config-key-grouping;
  }

  /////////////////////////////////////////////////////////
  // native / crypto
  /////////////////////////////////////////////////////////
  augment "/ios:native/ios:crypto" {
    uses config-crypto-grouping;
  }

  /////////////////////////////////////////////////////////
  // native / interface * / Tunnel / 
  /////////////////////////////////////////////////////////
  augment "/ios:native/ios:interface/ios:Tunnel" +
    "/ios-tun:tunnel/ios-tun:protection"{
    uses config-interface-tunnel-ipsec-grouping {
      if-feature ios-features:crypto; 
    }
  }

  /////////////////////////////////////////////////////////
  // native / interface * / crypto
  /////////////////////////////////////////////////////////
  augment "/ios:native/ios:interface/ios:FastEthernet" {
    uses config-interface-crypto-grouping {
      if-feature ios-features:crypto; 
    }
  }

  augment "/ios:native/ios:interface/ios:GigabitEthernet" {
    uses config-interface-crypto-grouping {
      if-feature ios-features:crypto; 
    }
  }

  augment "/ios:native/ios:interface/ios:TenGigabitEthernet" {
    uses config-interface-crypto-grouping {
      if-feature ios-features:crypto; 
    }
  }

  augment "/ios:native/ios:interface/ios:Loopback" {
    uses config-interface-crypto-grouping {
      if-feature ios-features:crypto; 
    }
  }

  augment "/ios:native/ios:interface/ios:Tunnel" {
    uses config-interface-crypto-grouping {
      if-feature ios-features:crypto; 
    }
  }

  augment "/ios:native/ios:interface/ios:Port-channel" {
    uses config-interface-crypto-grouping {
      if-feature ios-features:crypto; 
    }
  }

  augment "/ios:native/ios:interface/ios:Virtual-Template" {
    uses config-interface-crypto-grouping {
      if-feature ios-features:crypto; 
    }
  }

  augment "/ios:native/ios:interface/ios:Vlan" {
    uses config-interface-crypto-grouping {
      if-feature ios-features:crypto; 
    }
  }

  /////////////////////////////////////////////////////////
  // native / interface * / ipv6 crypto
  /////////////////////////////////////////////////////////
  augment "/ios:native/ios:interface/ios:FastEthernet/ios:ipv6" {
    uses config-interface-ipv6-crypto-grouping {
      if-feature ios-features:crypto;
    }
  }

  augment "/ios:native/ios:interface/ios:GigabitEthernet/ios:ipv6" {
    uses config-interface-ipv6-crypto-grouping {
      if-feature ios-features:crypto;
    }
  }

  augment "/ios:native/ios:interface/ios:TenGigabitEthernet/ios:ipv6" {
    uses config-interface-ipv6-crypto-grouping {
      if-feature ios-features:crypto;
    }
  }

  augment "/ios:native/ios:interface/ios:Loopback/ios:ipv6" {
    uses config-interface-ipv6-crypto-grouping {
      if-feature ios-features:crypto;
    }
  }

  augment "/ios:native/ios:interface/ios:Tunnel/ios:ipv6" {
    uses config-interface-ipv6-crypto-grouping {
      if-feature ios-features:crypto;
    }
  }

  augment "/ios:native/ios:interface/ios:Port-channel/ios:ipv6" {
    uses config-interface-ipv6-crypto-grouping {
      if-feature ios-features:crypto;
    }
  }

  augment "/ios:native/ios:interface/ios:Virtual-Template/ios:ipv6" {
    uses config-interface-ipv6-crypto-grouping {
      if-feature ios-features:crypto;
    }
  }

  augment "/ios:native/ios:interface/ios:Vlan/ios:ipv6" {
    uses config-interface-ipv6-crypto-grouping {
      if-feature ios-features:crypto;
    }
  }

}
