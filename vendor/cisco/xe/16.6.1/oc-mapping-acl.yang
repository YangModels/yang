module oc-mapping-acl {

  yang-version "1";

  // namespace
  namespace "http://openconfig.net/yang/oc-mapping-acl";

  prefix "oc-map-acl";

  import ietf-inet-types { prefix inet; }
  import openconfig-interfaces { prefix oc-if; }
  import openconfig-extensions { prefix oc-ext; }

  // meta
  organization "OpenConfig working group";

  contact
    "OpenConfig working group
    www.openconfig.net";

  description
    "This module defines mapping state data
    that must be saved to implement the openconfig-acl
    model because the capabilities are not implemented
    on XE devices";

  oc-ext:openconfig-version "0.2.0";

  revision "2017-01-17" {
    description
      "Initial revision";
    reference "TBD";
  }

  // grouping statements

  // input interface
  grouping input-interface-config {
    description
      "Config of interface";
  }

  // Access List Entries
  grouping access-list-entries-config {
    description
      "Access List Entries (ACE) config.";

    leaf sequence-id {
      type uint32;
      description
        "The sequence id determines the order in which ACL entries
        are applied.  The sequence id must be unique for each entry
        in an ACL set.  Target devices should apply the ACL entry
        rules in the order determined by sequence id, rather than
        the relying only on order in the list.";
    }

  }

  grouping access-list-entries-top {
    description
      "Access list entries to level container";

    container acl-entries {
      description
        "Access list entries container";

      list acl-entry {
        key "sequence-id";
        description
          "List of ACL entries comprising an ACL set";

        uses access-list-entries-config;
        leaf ip-version {
           type inet:ip-version;
           description
               "IP version of the header.";
        }
      }
    }
  }

  grouping acl-config {
    description
      "Global configuration data for ACLs";
  }

  grouping acl-set-top {
    description
      "Access list entries variables top level container";

    container acl-sets {
      description
        "Access list entries variables enclosing container";

      list acl-set {
        key "name";
        description
          "List of ACL sets, each comprising of a list of ACL
          entries";

        leaf name {
          type string;
          description
            "Reference to the name list key";
        }

        container config {
          description
            "Access list config";
          uses acl-set-config;
          uses access-list-entries-top;
        }

      }
    }
  }

  grouping interface-acl-entries-config {
    description
      "Configuration data for per-interface ACLs";

  }

  grouping acl-set-config {
    description
      "Access Control List config";

    leaf name {
      type string;
      description
        "The name of the access-list set";
    }

    leaf acl-type {
      type inet:ip-version;
      description
        "The type of the access-list set";
    }

    leaf description {
      type string;
      description
        "Description, or comment, for the ACL set";
    }

  }

  grouping interface-acl-entries-top {
    description
      "Top-level grouping for per-interface ACL entries";

    container acl-entries {
      config false;
      description
        "Enclosing container for list of references to ACLs";

      list acl-entry {
        key "sequence-id";
        description
          "List of ACL entries assigned to an interface";

        leaf sequence-id {
          type string;
          description
            "Reference to per-interface acl entry key";
        }

        // no config container since the enclosing container is
        // read-only

      }
    }
  }

  grouping interface-ingress-acl-config {
    description
      "Configuration data for per-interface ingress ACLs";

    leaf set-name {
      type string;
      description
        "Reference to the ACL set applied on ingress";
    }
  }

  grouping interface-ingress-acl-top {
    description
      "Top-level grouping for per-interface ingress ACL data";

    container ingress-acl-sets {
      description
        "Enclosing container the list of ingress ACLs on the
        interface";

      list ingress-acl-set {
        key "set-name";
        description
          "List of ingress ACLs on the interface";

        leaf set-name {
          type string;
          description
            "Reference to set name list key";
        }

        container config {
          description
            "Configuration data ";

          uses interface-ingress-acl-config;
        }

        container state {

          config false;

          description
            "Operational state data for interface ingress ACLs";

          uses interface-ingress-acl-config;
        }

        uses interface-acl-entries-top;
      }
    }
  }

  grouping interface-egress-acl-config {
    description
      "Configuration data for per-interface egress ACLs";

    leaf set-name {
      type string;
      description
        "Reference to the ACL set applied on egress";
    }
  }

  grouping interface-egress-acl-top {
    description
      "Top-level grouping for per-interface egress ACL data";

    container egress-acl-sets {
      description
        "Enclosing container the list of egress ACLs on the
        interface";

      list egress-acl-set {
        key "set-name";
        description
          "List of egress ACLs on the interface";

        leaf set-name {
          type string;
          description
            "Reference to set name list key";
        }

        container config {
          description
            "Configuration data ";

          uses interface-egress-acl-config;
        }

        uses interface-acl-entries-top;
      }
    }
  }

  grouping acl-interfaces-config {
    description
      "Configuration data for interface references";

    leaf id {
      type oc-if:interface-id;
      description
        "User-defined identifier for the interface -- a common
        convention could be '<if name>.<subif index>'";
    }
  }

  grouping acl-interfaces-top {
    description
      "Top-level grouping for interface-specific ACL data";

    container interfaces {
      description
        "Enclosing container for the list of interfaces on which
        ACLs are set";

      list interface {
        key "id";
        description
          "List of interfaces on which ACLs are set";

        leaf id {
          type string;
          description
            "Reference to the interface id list key";
        }

        container config {
          description
            "Configuration for ACL per-interface data";

          uses acl-interfaces-config;
        }


        uses oc-if:interface-ref;
        uses interface-ingress-acl-top;
        uses interface-egress-acl-top;
      }
    }
  }


  grouping acl-top {
    description
      "Top level grouping for ACL data and structure";

    container acl-mapping {
      description
        "Top level enclosing container for ACL model config
        and operational state data";

      uses acl-config;
      uses acl-set-top;
      uses acl-interfaces-top;
    }
  }

  // data definition statements
  uses acl-top;

  // augment statements

  // rpc statements

  // notification statements

}
