module Cisco-IOS-XE-card {
  namespace "http://cisco.com/ns/yang/Cisco-IOS-XE-card";
  prefix ios-card;

  import Cisco-IOS-XE-native {
    prefix ios;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE Card Yang model.
     Copyright (c) 2016 by Cisco Systems, Inc.
     All rights reserved.";

  // =========================================================================
  // REVISION
  // =========================================================================
  revision 2017-02-07 {
    description
      "Initial revision";
  }

  grouping config-card-grouping {
    container card {
      description
        "Configure T1/E1 SPA";
      leaf type {
        type enumeration {
          enum "t1";
          enum "e1";
        }
      }
      leaf slot {
        type uint32;
      }
      leaf bay {
        type uint32;
      }
    }
  }

  /////////////////////////////////////////////////////////
  // native / card
  /////////////////////////////////////////////////////////
  augment "/ios:native" {
    uses config-card-grouping;
  }
} //module
