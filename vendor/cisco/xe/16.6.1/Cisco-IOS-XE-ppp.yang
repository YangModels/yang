module Cisco-IOS-XE-ppp {
  namespace "http://cisco.com/ns/yang/Cisco-IOS-XE-ppp";
  prefix ios-ppp;

  import ietf-inet-types {
    prefix inet;
  }

  import Cisco-IOS-XE-native {
    prefix ios;
  }


  import Cisco-IOS-XE-features {
    prefix ios-features;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Point-to-Point Protocol (PPP) Yang model.
     Copyright (c) 2016 by Cisco Systems, Inc.
     All rights reserved.";

  // =========================================================================
  // REVISION
  // =========================================================================
  revision 2017-02-07 {
    description
      "Initial revision";
  }


  grouping config-ppp-grouping {
    container packet {
      description
        "Configure control packet rate throttling";
      leaf throttle {
        description
          "Configure control packet rate throttling";
        type uint32 {
          range "1..100000";
        }
      }
      leaf allow_time {
        type uint32 {
          range "1..3600";
        }
      }
      leaf block_time {
        type uint32 {
          range "2..3600";
        }
      }
    }
  }

  grouping config-multilink-grouping {
    leaf bundle-name {
      description
        "Select method for naming multilink bundles";
      type enumeration {
        enum "authenticated";
        enum "both";
        enum "endpoint";
        enum "rfc";
      }
    }
    leaf virtual-template {
      description
        "virtual-template interface";
      type uint16 {
        range "1..4095";
      }
    }
  }

  grouping config-interface-p2p-grouping {
    // interface * / ppp
    container ppp {
      description
        "Point-to-Point Protocol";
      leaf accounting {
        description
          "Set PPP network accounting method";
        type union {
          type string;
          type enumeration {
            enum "default";
          }
        }
      }
      // interface * /ppp chap
      container chap {
        description
          "Set CHAP authentication parameters";
        leaf hostname {
          description
            "Set alternate CHAP hostname";
          type string;
        }
        leaf challenge-length {
          description
            "Challenge Length for CHAP";
          type uint8 {
            range "16..63";
          }
        }
      }
      // interface * / ppp authentication
      container authentication {
        description
          "Set PPP link authentication method";
        leaf method {
          type enumeration {
            enum "chap";
            enum "eap";
            enum "ms-chap";
            enum "ms-chap-v2";
            enum "pap";
          }
        }
        leaf list-name {
          type string;
        }
        leaf chap {
          when "not(../method = 'chap')" {
          }
          type empty;
        }
        leaf callback {
          description
            "Authenticate remote on callback only";
          type empty;
        }
        leaf callin {
          description
            "Authenticate remote on incoming call only";
          type empty;
        }
        leaf callout {
          description
            "Authenticate remote on outgoing call only";
          type empty;
        }
        leaf default {
          description
            "Use the default authentication list";
          type empty;
        }
        leaf eap {
          description
            "Extensible Authentication Protocol (EAP)";
          when "not(../method = 'eap')" {
          }
          type empty;
        }
        leaf ms-chap {
          description
            "Microsoft Challenge Handshake Authentication Protocol (MS-CHAP)";
          when "not(../method = 'ms-chap')" {
          }
          type empty;
        }
        leaf ms-chap-v2 {
          description
            "Microsoft CHAP Version 2 (MS-CHAP-V2)";
          when "not(../method = 'ms-chap-v2')" {
          }
          type empty;
        }
        leaf one-time {
          description
            "Allow use of username*OTP for one-time passwords";
          type empty;
        }
        leaf optional {
          description
            "Allow peer to refuse to authenticate";
          type empty;
        }
        leaf pap {
          description
            "Password Authentication Protocol (PAP)";
          when "not(../method = 'pap')" {
          }
          type empty;
        }
      }
      // interface * / ppp authorization
      leaf authorization {
        description
          "Set PPP network authorization method";
        type union {
          type string;
          type enumeration {
            enum "default";
          }
        }
      }
      // interface * / ppp ipcp
      container ipcp {
        description
          "Set IPCP negotiation options";
        container dns {
          description
            "Specify DNS negotiation options";
          leaf primary {
            type inet:ipv4-address;
          }
        }
      }
      // interface * / ppp multilink
      container multilink {
        description
          "Make interface multilink capable";
        presence "true";
        container links {
          description
            "Specify the limits on the number of links in a bundle";
          container minimum {
            description
              "Minimum number of links desired in the bundle";
            leaf minimum-value {
              type uint8;
            }
            leaf mandatory {
              description
                "Disable network layer until minimum number of links is reach";
              type empty;
            }
          }
        }
        // interface * / ppp multilink group
        leaf group {
          description
            "Put interface in a multilink bundle";
          type uint32 {
            range "1..2147483647";
          }
        }
        // interface * / ppp multilink endpoint
        container endpoint {
          description
            "Configure the local Endpoint Discriminator";
          leaf string {
            description
              "Use specified string";
            type string;
          }
        }
        // interface * / ppp multilink fragment
        container fragment {
          description
            "Specify fragmentation parameters";
          container delay {
            description
              "Specify the maximum delay for each fragment";
            leaf delay-value {
              type uint16 {
                range "0..1000";
              }
            }
            leaf additional-delay-value {
              type uint16 {
                range "1..999";
              }
            }
          }
        }
      }
    }
  }
  /////////////////////////////////////////////////////////
  // native / ppp
  /////////////////////////////////////////////////////////
  augment "/ios:native/ios:ppp" {
    uses config-ppp-grouping;
  }

  /////////////////////////////////////////////////////////
  // native / multilink
  /////////////////////////////////////////////////////////
  augment "/ios:native/ios:multilink" {
    uses config-multilink-grouping {
      if-feature ios-features:multilink;
    }    
  }

  /////////////////////////////////////////////////////////
  // native / interface
  /////////////////////////////////////////////////////////
  augment "/ios:native/ios:interface/ios:Multilink" {
      uses config-interface-p2p-grouping {
        if-feature ios-features:multilink;
      } 
  }

  augment "/ios:native/ios:interface/ios:Serial" {
      uses config-interface-p2p-grouping {
        if-feature ios-features:multilink;
      }    
  }

  augment "/ios:native/ios:interface/ios:Virtual-Template" {
      uses config-interface-p2p-grouping {
        if-feature ios-features:multilink;
      }
  }
} //module
