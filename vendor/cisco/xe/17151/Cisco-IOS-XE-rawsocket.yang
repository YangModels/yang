module Cisco-IOS-XE-rawsocket {
  yang-version 1.1;
  namespace "http://cisco.com/ns/yang/Cisco-IOS-XE-rawsocket";
  prefix ios-rawsocket;

  import Cisco-IOS-XE-native {
    prefix ios;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Rawsocket Yang model.
     Copyright (c)2019 by Cisco Systems, Inc.
     All rights reserved.";

  revision 2024-07-01 {
    description
      "Added when statement for tcp and udp container";
    cisco-semver:module-version "2.0.0";
  }
  revision 2022-11-01 {
    description
      "- Update yang-version to 1.1";
    cisco-semver:module-version "1.3.0";
  }
  revision 2022-03-01 {
    description
      "- Added support for async-line-range
       - Add max-retries leaf under tcp container";
    cisco-semver:module-version "1.2.0";
  }
  revision 2021-11-01 {
    description
      "- Add support for media-type and duplex";
    cisco-semver:module-version "1.1.0";
  }
  revision 2020-03-01 {
    description
      "- Initial revision";
    cisco-semver:module-version "1.0.0";
  }

  grouping config-rawsocket-grouping {
    container packet-length {
      description
        "packet length";
      when 'current()/../tcp or current()/../udp';
      leaf packet-length-value {
        description
          "packet size (byte) to trigger tx";
        type uint16 {
          range "10..1400";
        }
      }
      leaf fragment-off {
        description
          "frame send in full, packet size could exceed packet-length";
        type empty;
      }
    }
    leaf packet-timer {
      description
        "timer(ms) to trigger tx, default (15)";
      when 'current()/../tcp or current()/../udp';
      type uint16 {
        range "3..1000";
      }
      default "15";
    }
    leaf special-char {
      description
        "character (ASCII value) to trigger tx";
      when 'current()/../tcp or current()/../udp';
      type uint8 {
        range "0..255";
      }
    }
    container tcp {
      description
        "protocol tcp";
      when '/ios:native/ios:interface/ios:Serial[ios:name = current()/../../ios:first-name]/ios:encapsulation/ios:raw-tcp';
      leaf tcp-session {
        description
          "number of tcp session allowed, default (32)";
        type uint8 {
          range "1..32";
        }
        default "32";
      }
      list client {
        description
          "raw tcp client mode";
        max-elements 32;
        key "destination-ip destination-port";
        leaf destination-ip {
          description
            "destination ip address";
          type inet:ipv4-address;
        }
        leaf destination-port {
          description
            "destination port number";
          type uint16 {
            range "1..65535";
          }
        }
        leaf optional-local-ip {
          description
            "optional local ip address";
          type inet:ipv4-address;
        }
        leaf optional-local-port {
          description
            "optional local port number";
          type uint16 {
            range "1..65535";
          }
        }
      }
      leaf max-retries {
        description
          "tcp session idle timeout (minutes), default (5)";
        type uint16 {
          range "1..1000";
        }
        default "10";
      }
      leaf idle-timeout {
        description
          "tcp session idle timeout (minutes), default (5)";
        type uint8 {
          range "1..120";
        }
        default "5";
      }
      leaf dscp {
        description
          "Set DSCP value in IP packet";
        type union {
          type uint8 {
            range "0..63";
          }
          type enumeration {
            enum af11;
            enum af12;
            enum af13;
            enum af21;
            enum af22;
            enum af23;
            enum af31;
            enum af32;
            enum af33;
            enum af41;
            enum af42;
            enum af43;
            enum cs1;
            enum cs2;
            enum cs3;
            enum cs4;
            enum cs5;
            enum cs6;
            enum cs7;
            enum default;
            enum ef;
          }
        }
      }
      container server {
        description
          "raw tcp server mode";
        leaf local-port {
          description
            "local port number";
          type uint16 {
            range "1..65535";
          }
        }
        leaf local-ip {
          description
            "local ip address";
          when '../local-port';
          type inet:ipv4-address;
        }
      }
    }
    container udp {
      description
        "protocol udp";
      when '/ios:native/ios:interface/ios:Serial[ios:name = current()/../../ios:first-name]/ios:encapsulation/ios:raw-udp';
      list connection {
        description
          "raw connection mode";
        max-elements 32;
        key "destination-ip destination-port";
        leaf destination-ip {
          description
            "destination ip address";
          type inet:ipv4-address;
        }
        leaf destination-port {
          description
            "destination port number";
          type uint16 {
            range "1..65535";
          }
        }
        leaf local-port {
          description
            "local port number";
          type uint16 {
            range "1..65535";
          }
        }
        leaf optional-local-ip {
          description
            "optional local ip address";
          type inet:ipv4-address;
        }
      }
    }
  }

  grouping config-rawsocket-grouping-deprecated {
    container packet-length {
      status deprecated;
      description
        "packet length";
      when 'current()/../tcp or current()/../udp';
      leaf packet-length-value {
        status deprecated;
        description
          "packet size (byte) to trigger tx";
        type uint16 {
          range "10..1400";
        }
      }
      leaf fragment-off {
        status deprecated;
        description
          "frame send in full, packet size could exceed packet-length";
        type empty;
      }
    }
    leaf packet-timer {
      status deprecated;
      description
        "timer(ms) to trigger tx, default (15)";
      when 'current()/../tcp or current()/../udp';
      type uint16 {
        range "3..1000";
      }
      default "15";
    }
    leaf special-char {
      status deprecated;
      description
        "character (ASCII value) to trigger tx";
      when 'current()/../tcp or current()/../udp';
      type uint8 {
        range "0..255";
      }
    }
    container tcp {
      status deprecated;
      description
        "protocol tcp";
      leaf tcp-session {
        status deprecated;
        description
          "number of tcp session allowed, default (32)";
        type uint8 {
          range "1..32";
        }
        default "32";
      }
      list client {
        status deprecated;
        description
          "raw tcp client mode";
        max-elements 32;
        key "destination-ip destination-port";
        leaf destination-ip {
          status deprecated;
          description
            "destination ip address";
          type inet:ipv4-address;
        }
        leaf destination-port {
          status deprecated;
          description
            "destination port number";
          type uint16 {
            range "1..65535";
          }
        }
        leaf optional-local-ip {
          status deprecated;
          description
            "optional local ip address";
          type inet:ipv4-address;
        }
        leaf optional-local-port {
          status deprecated;
          description
            "optional local port number";
          type uint16 {
            range "1..65535";
          }
        }
      }
      leaf idle-timeout {
        status deprecated;
        description
          "tcp session idle timeout (minutes), default (5)";
        type uint8 {
          range "1..120";
        }
        default "5";
      }
      leaf dscp {
        status deprecated;
        description
          "Set DSCP value in IP packet";
        type union {
          type uint8 {
            range "0..63";
          }
          type enumeration {
            enum af11;
            enum af12;
            enum af13;
            enum af21;
            enum af22;
            enum af23;
            enum af31;
            enum af32;
            enum af33;
            enum af41;
            enum af42;
            enum af43;
            enum cs1;
            enum cs2;
            enum cs3;
            enum cs4;
            enum cs5;
            enum cs6;
            enum cs7;
            enum default;
            enum ef;
          }
        }
      }
      container server {
        status deprecated;
        description
          "raw tcp server mode";
        leaf local-port {
          status deprecated;
          description
            "local port number";
          type uint16 {
            range "1..65535";
          }
        }
        leaf local-ip {
          status deprecated;
          description
            "local ip address";
          when '../local-port';
          type inet:ipv4-address;
        }
      }
    }
    container udp {
      status deprecated;
      description
        "protocol udp";
      list connection {
        status deprecated;
        description
          "raw connection mode";
        max-elements 32;
        key "destination-ip destination-port";
        leaf destination-ip {
          status deprecated;
          description
            "destination ip address";
          type inet:ipv4-address;
        }
        leaf destination-port {
          status deprecated;
          description
            "destination port number";
          type uint16 {
            range "1..65535";
          }
        }
        leaf local-port {
          status deprecated;
          description
            "local port number";
          type uint16 {
            range "1..65535";
          }
        }
        leaf optional-local-ip {
          status deprecated;
          description
            "optional local ip address";
          type inet:ipv4-address;
        }
      }
    }
  }

  augment "/ios:native/ios:line/ios:async-line-single" {
    container raw-socket {
      description
        "rawsocket configuration";
      uses config-rawsocket-grouping;
    }
  }

  augment "/ios:native/ios:line/ios:async-line-range" {
    container raw-socket {
      description
        "rawsocket configuration";
      uses config-rawsocket-grouping;
    }
  }

  augment "/ios:native/ios:line/ios:async-line" {
    container raw-socket {
      description
        "rawsocket configuration";
      status deprecated;
      uses config-rawsocket-grouping-deprecated;
    }
  }

  augment "/ios:native/ios:interface/ios:Async" {
    leaf media-type {
      description
        "Media type of async interface";
      type enumeration {
        enum rs232 {
          description
            "RS232";
        }
        enum rs485 {
          description
            "RS485";
        }
      }
    }
    leaf duplex-mode {
      when "../media-type = 'rs485'";
      type enumeration {
        enum full-duplex;
        enum half-duplex;
      }
    }
  }
}
