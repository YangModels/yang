module Cisco-IOS-XE-nwpi-types {
  yang-version 1.1;
  namespace "http://cisco.com/ns/yang/Cisco-IOS-XE-nwpi-types";
  prefix Cisco-IOS-XE-nwpi-types;

  import Cisco-IOS-XE-common-types {
    prefix common-types-ios-xe;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     network wide path insight types.
     Copyright (c) 2020-2024 by Cisco Systems, Inc.
     All rights reserved.";

  revision 2024-07-01 {
    description
      "- Added network instance for domain information type.
       - Added network instance for test type.
       - Added new type network instance identity.";
    reference
      "1.6.0";
    cisco-semver:module-version "1.6.0";
  }
  revision 2024-03-01 {
    description
      "- Added ThousandEyes support.";
    reference
      "1.5.0";
    cisco-semver:module-version "1.5.0";
  }
  revision 2023-11-01 {
    description
      "- Added username and user group in synthetic test.";
    reference
      "1.4.0";
    cisco-semver:module-version "1.4.0";
  }
  revision 2023-07-01 {
    description
      "- Added trace model support.
       - Added synthetic test support.";
    reference
      "1.3.0";
    cisco-semver:module-version "1.3.0";
  }
  revision 2022-11-01 {
    description
      "Update yang-version to 1.1";
    reference
      "1.2.0";
    cisco-semver:module-version "1.2.0";
  }
  revision 2021-07-01 {
    description
      "1, the option to update trace filter without changing trace mode.
       2, added domain info, domain filter and local state define.";
    reference
      "1.1.0";
    cisco-semver:module-version "1.1.0";
  }
  revision 2020-11-01 {
    description
      "Initial revision";
    reference
      "1.0.0";
    cisco-semver:module-version "1.0.0";
  }

  typedef nwpi-action-type {
    type enumeration {
      enum action-start-trace {
        value 0;
        description
          "Start trace";
      }
      enum action-stop-trace {
        value 1;
        description
          "Stop trace";
      }
      enum action-clear-trace {
        value 2;
        description
          "Clear trace data";
      }
      enum action-enable-nwpi {
        value 3;
        description
          "Enable network wide path insight";
      }
      enum action-disable-nwpi {
        value 4;
        description
          "Disable network wide path insight";
      }
      enum action-update-policy {
        value 5;
        description
          "Update trace policy";
      }
    }
    description
      "Network wide path insight action type";
  }

  typedef nwpi-target-type {
    type enumeration {
      enum target-vpn-id {
        value 0;
        description
          "SD-WAN VPN identifier type";
      }
      enum target-vrf-name {
        value 1;
        description
          "VRF name type";
      }
    }
    description
      "Network wide path insight target type";
  }

  typedef nwpi-trace-mod {
    type enumeration {
      enum mod-none {
        value 0;
        description
          "None trace model";
      }
      enum mod-manual {
        value 1;
        description
          "Manual trace model";
      }
      enum mod-auto-on {
        value 2;
        description
          "Auto-On trace model";
      }
      enum mod-test-only {
        value 3;
        description
          "Test only trace model";
      }
      enum mod-ext1 {
        value 4;
        description
          "Extension 1 trace model";
      }
      enum mod-ext2 {
        value 5;
        description
          "Extension 2 trace model";
      }
      enum mod-ext3 {
        value 6;
        description
          "Extension 3 trace model";
      }
      enum mod-ext4 {
        value 7;
        description
          "Extension 4 trace model";
      }
    }
    description
      "Network wide path insight trace model";
  }

  grouping nwpi-domain-info {
    description
      "Domain information";
    leaf domain-id {
      type uint16;
      description
        "Domain identifier";
    }
    leaf domain-name {
      type string;
      description
        "Domain name";
    }
    leaf vpn-id {
      type uint16;
      description
        "SD-WAN VPN identifier";
    }
    leaf ni-type {
      type common-types-ios-xe:net-inst-type;
      description
        "Network instance type. Differentiates between the default routing instance and VRFs";
    }
    leaf ni-name {
      type string;
      description
        "Network instance name. If the Network instance type is net-inst-default, then name is not meaningful";
    }
  }

  grouping nwpi-domain-filter {
    description
      "Internet domain and its host addresses";
    container info {
      description
        "Domain information";
      uses Cisco-IOS-XE-nwpi-types:nwpi-domain-info;
    }
    leaf-list host {
      type inet:ip-address;
      ordered-by user;
      description
        "List of hosts belong to the domain";
    }
  }

  grouping nwpi-vpg-intf {
    description
      "Virtual port group interfaces";
    leaf vpg-name {
      type string;
      description
        "Virtual port group name";
    }
    leaf-list app-addr {
      type inet:ip-address;
      ordered-by user;
      description
        "List of appliance addresses mapped to virtual port group";
    }
  }

  grouping nwpi-lcl-te-agent {
    description
      "Local hosted ThousandEyes agent";
    list vpg-intf {
      description
        "List of virtual port group interfaces used by local ThousandEyes agent";
      uses Cisco-IOS-XE-nwpi-types:nwpi-vpg-intf;
    }
  }

  grouping nwpi-local-state {
    description
      "Local trace state";
    leaf-list vpn {
      type uint16;
      ordered-by user;
      description
        "List of VPN where trace is running on";
    }
    container local-agent {
      description
        "Local hosted ThousandEyes agent";
      uses Cisco-IOS-XE-nwpi-types:nwpi-lcl-te-agent;
    }
  }

  grouping nwpi-test {
    description
      "Network wide path insight synthetic test";
    leaf test-id {
      type uint16;
      description
        "Test identifier";
    }
    leaf vpn-id {
      type uint16;
      description
        "SD-WAN VPN identifier";
    }
    leaf test-intvl {
      type uint16;
      units "minutes";
      description
        "Test interval (minutes)";
    }
    leaf target-url {
      type string;
      description
        "Target URL";
    }
    leaf dns-svr {
      type inet:ip-address;
      description
        "DNS server";
    }
    leaf dscp {
      type uint8;
      description
        "DSCP value to test";
    }
    leaf username {
      type string;
      description
        "Source identity username";
    }
    leaf user-grp {
      type string;
      description
        "Source identity user group";
    }
    leaf ni-type {
      type common-types-ios-xe:net-inst-type;
      description
        "Network instance type";
    }
    leaf ni-name {
      type string;
      description
        "Network instance name";
    }
  }

  grouping trace-key {
    description
      "Key to index trace record";
    leaf trc-id {
      type uint16;
      description
        "Trace identifier";
    }
    leaf trc-mod {
      type Cisco-IOS-XE-nwpi-types:nwpi-trace-mod;
      description
        "Network wide path insight trace model";
    }
  }

  grouping nwpi-te-agent {
    description
      "ThousandEyes agent information";
    leaf-list agent-addr {
      type inet:ip-address;
      ordered-by user;
      description
        "List of IP addresses configured on ThousandEyes agent";
    }
  }

  grouping nwpi-net-identity {
    description
      "Network instance identity";
    leaf ni-type {
      type common-types-ios-xe:net-inst-type;
      description
        "Network instance type. Differentiates between the default routing instance and VRFs";
    }
    leaf ni-name {
      type string;
      description
        "Network instance name. If the Network instance type is net-inst-default, then name is not meaningful";
    }
  }
}
