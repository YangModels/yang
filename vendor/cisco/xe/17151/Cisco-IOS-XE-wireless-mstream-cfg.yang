module Cisco-IOS-XE-wireless-mstream-cfg {
  yang-version 1.1;
  namespace "http://cisco.com/ns/yang/Cisco-IOS-XE-wireless-mstream-cfg";
  prefix wireless-mstream-cfg;

  import Cisco-IOS-XE-wireless-enum-types {
    prefix wireless-enum-types;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Model for managing multicast configurations
     Copyright (c) 2016-2020, 2022 by Cisco Systems, Inc.
     All rights reserved.";

  revision 2024-07-01 {
    description
      "Added pattern constraints";
    reference
      "5.0.0";
    cisco-semver:module-version "5.0.0";
  }
  revision 2022-11-01 {
    description
      "Update yang-version to 1.1";
    reference
      "4.1.0";
    cisco-semver:module-version "4.1.0";
  }
  revision 2021-03-01 {
    description
      "- Add ASCII 32-126 and leading/trailing spaces restriction for stream name";
    reference
      "4.0.0";
    cisco-semver:module-version "4.0.0";
  }
  revision 2019-05-01 {
    description
      "Added semantic version";
    reference
      "3.1.0";
    cisco-semver:module-version "3.1.0";
  }
  revision 2019-03-03 {
    description
      "- Multicast related leaves name change
       - Updated descriptions
       - Removed currently unused rrc-type leaf";
    reference
      "3.0.0";
    cisco-semver:module-version "3.0.0";
  }
  revision 2018-01-24 {
    description
      "The first generally available version";
    reference
      "2.0.0";
    cisco-semver:module-version "2.0.0";
  }
  revision 2017-05-05 {
    description
      "Initial revision";
    reference
      "1.0.0";
    cisco-semver:module-version "1.0.0";
  }

  grouping mstreamgrp {
    description
      "Multicast group";
    leaf group-name {
      type string {
        pattern '[!-~]([ -~]*[!-~])?';
      }
      description
        "Multicast stream group name";
    }
    leaf start-ip-addr {
      type inet:ip-address;
      must "starts-with(../start-ip-addr, '224.') or starts-with(../start-ip-addr, '225.') or
            starts-with(../start-ip-addr, '226.') or starts-with(../start-ip-addr, '227.') or
            starts-with(../start-ip-addr, '228.') or starts-with(../start-ip-addr, '229.') or
            starts-with(../start-ip-addr, '230.') or starts-with(../start-ip-addr, '231.') or
            starts-with(../start-ip-addr, '232.') or starts-with(../start-ip-addr, '233.') or
            starts-with(../start-ip-addr, '234.') or starts-with(../start-ip-addr, '235.') or
            starts-with(../start-ip-addr, '236.') or starts-with(../start-ip-addr, '237.') or
            starts-with(../start-ip-addr, '238.') or starts-with(../start-ip-addr, '239.') or
            contains(substring(../start-ip-addr, 1, 4), 'ff00')" {
        error-message "Multicast address is invalid";
        error-app-tag "must-violation";
      }
      default "0.0.0.0";
      description
        "Multicast stream group start IP address";
    }
    leaf end-ip-addr {
      type inet:ip-address;
      must "starts-with(../end-ip-addr, '224.') or starts-with(../end-ip-addr, '225.') or
            starts-with(../end-ip-addr, '226.') or starts-with(../end-ip-addr, '227.') or
            starts-with(../end-ip-addr, '228.') or starts-with(../end-ip-addr, '229.') or
            starts-with(../end-ip-addr, '230.') or starts-with(../end-ip-addr, '231.') or
            starts-with(../end-ip-addr, '232.') or starts-with(../end-ip-addr, '233.') or
            starts-with(../end-ip-addr, '234.') or starts-with(../end-ip-addr, '235.') or
            starts-with(../end-ip-addr, '236.') or starts-with(../end-ip-addr, '237.') or
            starts-with(../end-ip-addr, '238.') or starts-with(../end-ip-addr, '239.') or
            contains(substring(../end-ip-addr, 1, 4), 'ff00')" {
        error-message "Multicast address is invalid";
        error-app-tag "must-violation";
      }
      default "0.0.0.0";
      description
        "Multicast stream group end IP address";
    }
    leaf pak-size {
      type uint16 {
        range "100 .. 1500";
      }
      default "1200";
      description
        "Expected packet size for the stream";
    }
    leaf bandwidth {
      type uint16 {
        range "1 .. 35000";
      }
      default "1000";
      description
        "Expected bandwidth for the stream";
    }
    leaf is-admitted {
      type boolean;
      default "true";
      description
        "Admit the Multicast stream or deny";
    }
    leaf is-periodical {
      type boolean;
      default "false";
      description
        "Multicast RRC is periodical or initial";
    }
    leaf qos {
      type wireless-enum-types:media-stream-qos;
      default "mstream-video";
      description
        "Multicast stream QOS value";
    }
    leaf priority {
      type uint16 {
        range "1 .. 8";
      }
      default "4";
      description
        "Multicast stream priority";
    }
    leaf rrc-violation {
      type uint16 {
        range "1 .. 2";
      }
      default "2";
      description
        "Decision to drop or fall-back to best-effort in case of RRC violation";
    }
  }

  grouping mstreamglob {
    description
      "Multicast stream global";
    leaf multicast-direct-state {
      type boolean;
      default "false";
      description
        "Multicast direct state";
    }
    leaf url {
      type string {
        pattern '[A-Za-z0-9@.:/?=%,&-]*';
      }
      default "";
      description
        "Media stream session description protocol (SDP) URL";
    }
    leaf email {
      type string {
        pattern '[A-Za-z0-9@._-]*';
      }
      default "";
      description
        "Media stream SDP email ID";
    }
    leaf phone {
      type string {
        pattern '([0-9]+(-[0-9]+)*)?';
      }
      default "";
      description
        "Media stream SDP phone number";
    }
    leaf note {
      type string;
      default "";
      description
        "Media stream SDP Note to client when stream is denied";
    }
    leaf msg-state {
      type boolean;
      default "false";
      description
        "Media stream SDP message state";
    }
  }

  container mstream-cfg-data {
    description
      "multicast Cisco_IOS_XE_wireless_mstream_cfg";
    container mstream-groups {
      description
        "Multicast stream groups";
      list mstream-group {
        key "group-name";
        description
          "List of multicast stream groups";
        uses wireless-mstream-cfg:mstreamgrp;
      }
    }
    container mstream-glob {
      presence "mstreamglob";
      description
        "Multicast stream global";
      uses wireless-mstream-cfg:mstreamglob;
    }
  }
}
