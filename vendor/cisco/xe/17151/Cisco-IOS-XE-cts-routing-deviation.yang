module Cisco-IOS-XE-cts-routing-deviation {
  yang-version 1.1;
  namespace "http://cisco.com/ns/yang/Cisco-IOS-XE-cts-routing-deviation";
  prefix ios-cts-d;

  import Cisco-IOS-XE-native {
    prefix ios;
  }
  import Cisco-IOS-XE-cts {
    prefix ios-cts;
  }
  import cisco-semver {
    prefix cisco-semver;
  }

  organization
    "Cisco Systems";
  description
    "Cisco XE Native Deviation YANG module for IOS
     Copyright (c) 2020 by Cisco Systems, Inc.
     All rights reserved.";

  revision 2022-11-01 {
    description
      "- Update yang-version to 1.1";
    cisco-semver:module-version "1.3.0";
  }
  revision 2020-08-26 {
    description
      "Added sgt-cache deviation for Loopback interface";
    cisco-semver:module-version "1.0.1";
  }

  deviation "/ios:native/ios:cts/ios-cts:role-based/ios-cts:enforcement-only/ios-cts:enforcement" {
    deviate add {
      must "not(/ios:native/ios:interface/*/ios-cts:cts/ios-cts:role-based/ios-cts:enforcement-routing = 'true')" {
        error-message "There is at least one interface that has role-based enforcement configured.Please remove all interface enforcement configuration(s) before attempting global enable.";
      }
    }
  }
}
