module Cisco-IOS-XE-interfaces-deviation {
  yang-version 1.1;
  namespace "http://cisco.com/ns/yang/Cisco-IOS-XE-interfaces-deviation";
  prefix ios-interfaces-d;

  import Cisco-IOS-XE-native {
    prefix ios;
  }
  import cisco-semver {
    prefix cisco-semver;
  }

  organization
    "Cisco Systems";
  description
    "Cisco XE Interfaces Deviation YANG module for IOS
     Copyright (c) 2024 by Cisco Systems, Inc.
     All rights reserved.";

  revision 2024-07-01 {
    description
      "Make shutdown leaf not supported for L2LISP-subinterface";
    cisco-semver:module-version "1.3.0";
  }

  deviation "/ios:native/ios:interface/ios:L2LISP-subinterface/ios:L2LISP/ios:shutdown" {
    deviate not-supported;
  }

  deviation "/ios:native/ios:interface/ios:LISP-subinterface/ios:LISP/ios:vrf-choice/ios:vrf/ios:vrf/ios:forwarding" {
    deviate delete {
      must '/ios:native/ios:vrf/ios:definition[ios:name=current()]' {
        error-message "VRF must be created 1st, deleted last";
      }
    }
  }
}
