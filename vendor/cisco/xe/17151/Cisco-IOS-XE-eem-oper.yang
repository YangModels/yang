module Cisco-IOS-XE-eem-oper {
  yang-version 1.1;
  namespace "http://cisco.com/ns/yang/Cisco-IOS-XE-eem-oper";
  prefix eem-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG
     definitions for event manager policy operational data.
     Copyright (c) 2023 by Cisco Systems, Inc.
     All rights reserved.";

  revision 2023-11-01 {
    description
      "Initial revision";
    reference
      "1.0.0";
    cisco-semver:module-version "1.0.0";
  }

  typedef eem-policy-class {
    type enumeration {
      enum eem-class-unknown {
        value 0;
        description
          "Unknown policy class";
      }
      enum eem-class-script {
        value 1;
        description
          "Script policy class";
      }
      enum eem-class-applet {
        value 2;
        description
          "Applet policy class";
      }
      enum eem-class-app {
        value 3;
        description
          "App policy class";
      }
      enum eem-class-callhome {
        value 4;
        description
          "Call home policy class";
      }
      enum eem-class-axp {
        value 5;
        description
          "Axp policy class";
      }
      enum eem-class-shell {
        value 6;
        description
          "Shell policy class";
      }
      enum eem-class-onep {
        value 7;
        description
          "Onep policy class";
      }
      enum eem-class-system {
        value 8;
        description
          "System policy class";
      }
    }
    description
      "Event Manager policy class type";
  }

  typedef eem-policy-type {
    type enumeration {
      enum eem-policy-type-system {
        value 0;
        description
          "System policy type";
      }
      enum eem-policy-type-user {
        value 1;
        description
          "User policy type";
      }
      enum eem-policy-type-unknown {
        value 2;
        description
          "Unknown policy type";
      }
    }
    description
      "event manager policy type";
  }

  typedef eem-event {
    type enumeration {
      enum eem-event-type-app {
        value 0;
        description
          "Application event type";
      }
      enum eem-event-type-process-term {
        value 1;
        description
          "Process terminate event type";
      }
      enum eem-event-type-process-abort {
        value 2;
        description
          "Process abort event type";
      }
      enum eem-event-type-process-start {
        value 3;
        description
          "Process start event type";
      }
      enum eem-event-type-process-user-restart {
        value 4;
        description
          "Process user restart event type";
      }
      enum eem-event-type-process-user-shutdown {
        value 5;
        description
          "Process user shutdown event type";
      }
      enum eem-event-type-timer-watchdog {
        value 6;
        description
          "Timer watchdog event type";
      }
      enum eem-event-type-timer-countdown {
        value 7;
        description
          "Timer countdown event type";
      }
      enum eem-event-type-timer-absolute {
        value 8;
        description
          "Timer absolute event type";
      }
      enum eem-event-type-timer-cron {
        value 9;
        description
          "Timer cron event type";
      }
      enum eem-event-type-counter {
        value 10;
        description
          "Counter event type";
      }
      enum eem-event-type-syslog {
        value 11;
        description
          "Syslog event type";
      }
      enum eem-event-type-snmp {
        value 12;
        description
          "SNMP event type";
      }
      enum eem-event-type-wdsysmon {
        value 13;
        description
          "WD system monitor event type";
      }
      enum eem-event-type-intf {
        value 14;
        description
          "Interface event type";
      }
      enum eem-event-type-ioswd {
        value 15;
        description
          "IOS WD event type";
      }
      enum eem-event-type-rf {
        value 16;
        description
          "RF event type";
      }
      enum eem-event-type-gold {
        value 17;
        description
          "Gold event type";
      }
      enum eem-event-type-memthresh {
        value 18;
        description
          "Memory threshold event type";
      }
      enum eem-event-type-cli {
        value 19;
        description
          "CLI command event type";
      }
      enum eem-event-type-none {
        value 20;
        description
          "None event type";
      }
      enum eem-event-type-oir {
        value 21;
        description
          "OIR event type";
      }
      enum eem-event-type-hw-env {
        value 22;
        description
          "Hardware environment event type";
      }
      enum eem-event-type-test {
        value 23;
        description
          "Test event type";
      }
      enum eem-event-type-config {
        value 24;
        description
          "Config event type";
      }
      enum eem-event-type-env {
        value 25;
        description
          "ENV event type";
      }
      enum eem-event-type-resource {
        value 26;
        description
          "Resource event type";
      }
      enum eem-event-type-track {
        value 27;
        description
          "Track event type";
      }
      enum eem-event-type-rpc {
        value 28;
        description
          "RPC event type";
      }
      enum eem-event-type-snmp-proxy {
        value 29;
        description
          "SNMP proxy event type";
      }
      enum eem-event-type-ipsla {
        value 30;
        description
          "IPSLA event type";
      }
      enum eem-event-type-routing {
        value 31;
        description
          "Routing event type";
      }
      enum eem-event-type-nf {
        value 32;
        description
          "NF event type";
      }
      enum eem-event-type-snmp-obj {
        value 33;
        description
          "SNMP object event type";
      }
      enum eem-event-type-powernet {
        value 34;
        description
          "Power net event type";
      }
      enum eem-event-type-id {
        value 35;
        description
          "Identity event type";
      }
      enum eem-event-type-nd {
        value 36;
        description
          "ND event type";
      }
      enum eem-event-type-mat {
        value 37;
        description
          "MAT event type";
      }
      enum eem-event-type-stats {
        value 38;
        description
          "Statistics event type";
      }
      enum eem-event-type-dvrinfra {
        value 39;
        description
          "DVR INFRA event type";
      }
      enum eem-event-type-dmvpn {
        value 40;
        description
          "DM VPN event type";
      }
      enum eem-event-type-msp {
        value 41;
        description
          "MSP event type";
      }
      enum eem-event-type-ds {
        value 42;
        description
          "DS event type";
      }
      enum eem-event-type-ged {
        value 43;
        description
          "GED event type";
      }
      enum eem-event-type-crash {
        value 44;
        description
          "Crash event type";
      }
      enum eem-event-type-ethernet {
        value 45;
        description
          "Ethernet event type";
      }
      enum eem-event-type-testb1 {
        value 46;
        description
          "TEST B1 event type";
      }
      enum eem-event-type-num {
        value 47;
        description
          "Num event type";
      }
    }
    description
      "Event manager event type";
  }

  grouping eem-policy-info {
    description
      "Entries for EEM policy table data";
    leaf index {
      type uint32;
      description
        "Policy index number";
    }
    leaf name {
      type string;
      description
        "Name of embedded event manager policy";
    }
    leaf event-type {
      type eem-ios-xe-oper:eem-event;
      description
        "Event type of embedded event manager policy";
    }
    leaf class {
      type eem-ios-xe-oper:eem-policy-class;
      description
        "Policy class of embedded event manager policy";
    }
    leaf type {
      type eem-ios-xe-oper:eem-policy-type;
      description
        "Policy type of embedded event manager policy";
    }
    leaf trap {
      type boolean;
      description
        "SNMP trap status of embedded event manager policy";
    }
    leaf time {
      type yang:date-and-time;
      description
        "Time of embedded event manager policy registration";
    }
  }

  container eem-oper-data {
    config false;
    description
      "This is top level container for EEM operational data";
    list eem-policy-info {
      key "index";
      description
        "Event manager policy data";
      uses eem-ios-xe-oper:eem-policy-info;
    }
  }
}
