module cisco-xe-openconfig-evpn-deviation {
  namespace "http://cisco.com/ns/cisco-xe-openconfig-evpn-deviation";
  prefix oc-evpn-devs;

  import openconfig-network-instance {
    prefix oc-netinst;
  }

  organization
    "Cisco Systems, Inc.";
  contact
    "Cisco Systems, Inc.
     Customer Service

     Postal: 170 W Tasman Drive
     San Jose, CA 95134

     Tel: +1 1800 553-NETS

     E-mail: cs-yang@cisco.com";
  description
    "This module defines deviation statements for openconfig-evpn module.
     Copyright (c) 2024 by Cisco Systems, Inc.
     All rights reserved.";

  revision 2024-07-01 {
    description
      "Removed vxlan deviation";
  }
  revision 2023-11-01 {
    description
      "Initial Revision";
  }

  deviation "/oc-netinst:network-instances/oc-netinst:network-instance/oc-netinst:evpn" {
    deviate not-supported;
    description
      "Currently not supported";
  }
}
