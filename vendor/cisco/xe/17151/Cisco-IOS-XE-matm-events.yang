module Cisco-IOS-XE-matm-events {
  yang-version 1.1;
  namespace "http://cisco.com/ns/yang/Cisco-IOS-XE-matm-events";
  prefix matm-ios-xe-events;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG Definitions
     for MATM event notification.
     Copyright (c) 2023 by Cisco Systems, Inc.
     All rights reserved.";

  revision 2024-03-01 {
    description
      "Initial revision";
    reference
      "1.0.0";
    cisco-semver:module-version "1.0.0";
  }

  grouping mac-flap-interface-event {
    description
      "MAC flap event";
    leaf prev-port-name {
      type string;
      description
        "The port name of the previous interface MAC is learnt";
    }
    leaf new-port-name {
      type string;
      description
        "The port name of the new interface MAC is learnt";
    }
    leaf vlan-id {
      type uint16;
      description
        "VLAN identifier associated with the port";
    }
    leaf client-mac {
      type yang:mac-address;
      description
        "MAC address which is flapped between ports";
    }
  }

  notification mac-flap-intf-event {
    description
      "MAC flap event notification";
    uses matm-ios-xe-events:mac-flap-interface-event;
  }
}
