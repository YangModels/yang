module Cisco-IOS-XE-l2vpn {
  yang-version 1.1;
  namespace "http://cisco.com/ns/yang/Cisco-IOS-XE-l2vpn";
  prefix ios-l2vpn;

  import cisco-semver {
    prefix cisco-semver;
  }
  import ietf-inet-types {
    prefix inet;
  }
  import Cisco-IOS-XE-native {
    prefix ios;
  }
  import Cisco-IOS-XE-interface-common {
    prefix ios-ifc;
  }
  import Cisco-IOS-XE-ethernet {
    prefix ios-eth;
  }
  import Cisco-IOS-XE-features {
    prefix ios-features;
  }
  import Cisco-IOS-XE-types {
    prefix ios-types;
  }
  import Cisco-IOS-XE-mpls {
    prefix ios-mpls;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Layer 2 Virtual Private Network (L2VPN) Yang model.
     Copyright (c) 2016-2023 by Cisco Systems, Inc.
     All rights reserved.";

  revision 2024-07-01 {
    description
      "- Obsolete old models deprecated before 17.9
       - Add EVPN ESI LAG sync-only intra-es command";
    cisco-semver:module-version "4.6.0";
  }
  revision 2024-03-01 {
    description
      "- Add support for L2VPN SDWAN instance commands
       - Add new EVPN ethernet-segment commands
       - Add EVPN ethernet-segment LACP Auto
       - Obsolete old models deprecated before 17.6
       - Remove vlan-based instance and rename df-election to active-election
         for L2VPN SDWAN";
    cisco-semver:module-version "4.5.0";
  }
  revision 2023-11-01 {
    description
      "- Add support for profile related commands
       - Add local-routing command for profile
       - Add default value of the leafs defined under profile";
    cisco-semver:module-version "4.4.0";
  }
  revision 2023-07-01 {
    description
      "- Added address resolution flooding suppression to per-EVI config
       - Add support for profile related commands";
    cisco-semver:module-version "4.3.0";
  }
  revision 2023-03-01 {
    description
      "- Removed must constraint on l2vpn xconnect interface";
    cisco-semver:module-version "4.2.0";
  }
  revision 2022-11-01 {
    description
      "- Update yang-version to 1.1";
    cisco-semver:module-version "4.1.0";
  }
  revision 2022-07-01 {
    description
      "- Modified route-target from export leaf and import leaf to lists";
    cisco-semver:module-version "4.0.0";
  }
  revision 2022-03-01 {
    description
      "- Added l2vpn local connect config model
       - Added explicit exit for l2vpn subcommands
       - Allowed manual to be configured with encapsulation type mpls";
    cisco-semver:module-version "3.2.0";
  }
  revision 2021-11-01 {
    description
      "- Change node type to boolean for auto-route-target, tlv,
         notification and route-watch leaf nodes
       - Added l2vpn evpn vpws context
       - Add l2vpn evpn multihoming proxy-mac-ip disable";
    cisco-semver:module-version "3.1.0";
  }
  revision 2021-03-01 {
    description
      "- Added l2vpn evpn multicast advertise
       - Various major fixes in l2vpn global, Vfi, Xconnect, Pseudowire and
         Interface Pseudowire
       - Adding mandatory true/must statement for l2vpn";
    cisco-semver:module-version "3.0.0";
  }
  revision 2020-11-01 {
    description
      "- Added re-originate route-type 5
       - Various minor fixes in pseudowire-class and l2tp-class
       - Added policy container under segment-routing traffic-eng";
    cisco-semver:module-version "2.4.0";
  }
  revision 2020-07-01 {
    description
      "- Added argument . to local-name() Xpath function
       - Added IP local learn per-MAC limits
       - Added encryption for l2tp-class";
    cisco-semver:module-version "2.2.0";
  }
  revision 2020-03-01 {
    description
      "- Added 'default-gateway advertise' to per-EVI config
       - Added l2tp-class for l2tpv3 protocol under pseudowire-class
       - Added 'cookie and password' to l2tp-class config
       - Added 'xconnect' to Cellular interface config";
    cisco-semver:module-version "2.1.0";
  }
  revision 2019-11-01 {
    description
      "- Added EVPN state logging support
       - Added pseudo wire config
       - Fixed status for leaf nodes which parent nodes were in obsolete status";
    cisco-semver:module-version "2.0.0";
  }
  revision 2019-07-01 {
    description
      "- Establish semantic version baseline
       - Added 'default-gateway advertise' to 'l2vpn evpn' global
       - Added IP local learning to evpn global and instance
       - Added segment routing options for preferred path
       - Added global Ethernet segment support";
    cisco-semver:module-version "1.0.0";
  }
  revision 2019-01-22 {
    description
      "Added leaf for App-hosting Gigabit Ethernet interface";
  }
  revision 2018-12-06 {
    description
      "Added replication type to evpn instance";
  }
  revision 2018-10-16 {
    description
      "Added l2tp-class and l2tpv2 changes for pseudowire-class";
  }
  revision 2018-08-02 {
    description
      "Added interface ESI identifier type support";
  }
  revision 2018-02-13 {
    description
      "Added Evpn support";
  }
  revision 2017-11-27 {
    description
      "Added Change 25GE name";
  }
  revision 2017-11-14 {
    description
      "This revision has changes for new 40 and 100GE interface addition";
  }
  revision 2017-09-15 {
    description
      "This revision has changes for new 2gig interface addition";
  }
  revision 2017-08-16 {
    description
      "This revision has changes for new 5gig and 25gig interfaces addition";
  }
  revision 2017-08-10 {
    description
      "Add mtu for l2 vfi";
  }
  revision 2017-02-07 {
    description
      "Initial revision";
  }

  grouping config-interface-pseudowire-flow-label {
    container static {
      description
        "Enable flow labels even if not signaled by remote peer";
      presence "true";
      leaf advertise {
        description
          "Send Flow Label Sub-TLV";
        type empty;
      }
    }
  }

  grouping config-interface-pseudowire-grouping {
    leaf description {
      description
        "Interface specific description";
      type string;
    }
    leaf shutdown {
      description
        "Shutdown the selected interface";
      type empty;
    }
    leaf encapsulation-config {
      description
        "Data encapsulation method";
      must 'not(../source/template/type/pseudowire)';
      type enumeration {
        enum l2tpv3;
        enum mpls;
        enum udp;
      }
    }
    leaf encapsulation {
      description
        "Data encapsulation method";
      status obsolete;
      type enumeration {
        enum l2tpv2;
        enum l2tpv3;
        enum mpls;
        enum udp;
      }
    }
    container signaling {
      description
        "Signaling options";
      container protocol {
        description
          "Signaling protocol to use";
        choice protocol-options {
          case ldp-case {
            leaf ldp {
              description
                "Use LDP signaling";
              when "../../../encapsulation-config = 'mpls'";
              type empty;
            }
          }
          case l2tpv3-case {
            container l2tpv3 {
              description
                "Use L2TPV3 signaling";
              when "../../../encapsulation-config = 'l2tpv3'";
              presence "true";
              leaf l2tp-class-name {
                description
                  "l2tp-class name";
                must '/ios:native/ios:l2tp-class[ios:name = current()]' {
                  error-message "Please make sure to configure l2tp-class before configuring this.";
                }
                type string;
              }
            }
          }
          case none-case {
            leaf none {
              description
                "No signaling, use manually configured pseudowires";
              type empty;
            }
          }
        }
      }
    }
    container bandwidth {
      description
        "Set bandwidth informational parameter";
      when '../encapsulation-config';
      must 'bandwidth-value or (not(bandwidth-value) and not(persistent))' {
        error-message "Please make sure to configure bandwidth-value";
      }
      leaf bandwidth-value {
        description
          "Bandwidth in kilobits";
        type uint32 {
          range "1..10000000";
        }
      }
      leaf persistent {
        description
          "Do not release bandwidth when pseudowire is down";
        type empty;
      }
    }
    container label {
      description
        "MPLS local and remote pseudowire static labels";
      when "../encapsulation-config = 'mpls' and ../signaling/protocol/none";
      must '../neighbor and ((local and remote) or (not(local) and not(remote)))' {
        error-message "Please make sure to configure neighbor first and also configure both local and remote";
      }
      leaf local {
        description
          "Local pseudowire label";
        must '. > /ios:native/ios:mpls/ios-mpls:label/ios-mpls:range/ios-mpls:static/ios-mpls:min and . < /ios:native/ios:mpls/ios-mpls:label/ios-mpls:range/ios-mpls:static/ios-mpls:max';
        type uint32 {
          range "16..1048575";
        }
      }
      leaf remote {
        description
          "Remote pseudowire label";
        type uint32 {
          range "16..1048575";
        }
      }
    }
    leaf mtu {
      description
        "set Maximum Transmission Unit";
      when '../encapsulation-config';
      type uint16 {
        range "64..65535";
      }
    }
    container ip {
      description
        "Specify IP parameters";
      when "../encapsulation-config = 'l2tpv3' or ../encapsulation-config = 'udp'";
      container dfbit {
        description
          "DF bit options for tunnel";
        leaf set {
          description
            "Set the DF bit in the tunnel header";
          type empty;
        }
      }
      container local {
        description
          "Specify local information";
        container interface {
          description
            "Source interface for pseudowire";
          uses ios-ifc:interface-grouping;
        }
      }
      container pmtu {
        description
          "Enable Path MTU for tunnel";
        when "../../encapsulation-config = 'l2tpv3'";
        presence "true";
        leaf max {
          description
            "Maximum Path MTU for session";
          type uint16 {
            range "68..65535";
          }
        }
      }
      leaf protocol {
        description
          "Specific IP protocol number to use";
        when "../../encapsulation-config = 'l2tpv3'";
        type enumeration {
          enum l2tp;
          enum uti;
          enum udp;
        }
      }
      container tos {
        description
          "Specify ToS options for IP tunnel header";
        leaf reflect {
          description
            "Reflect IP payload ToS on tunnel";
          type empty;
        }
        leaf value {
          description
            "IP ToS value";
          type uint8;
        }
      }
      leaf ttl {
        description
          "Specify TTL value for IP tunnel header";
        type uint8;
      }
    }
    leaf control-word-config {
      description
        "Control-word options";
      when "../encapsulation-config = 'mpls'";
      type enumeration {
        enum exclude;
        enum include;
      }
    }
    leaf control-word {
      description
        "Include control-word in pseudowire packets";
      when "../encapsulation = 'mpls'";
      status obsolete;
      type empty;
    }
    leaf interworking {
      description
        "Interworking options for pseudowire";
      type enumeration {
        enum ethernet;
        enum ip;
        enum vlan;
      }
    }
    container load-balance {
      description
        "Loadbalancing for pseudowire";
      when "../encapsulation-config = 'mpls'";
      container flow {
        description
          "Enable flow based load balancing for pseudowire";
        presence "true";
        leaf ethernet {
          description
            "Ethernet pseudowire flow classification";
          type enumeration {
            enum dst-mac;
            enum src-dst-mac;
            enum src-mac;
          }
        }
        leaf ip {
          description
            "IP pseudowire flow classification";
          type enumeration {
            enum dst-ip;
            enum src-dst-ip;
            enum src-ip;
          }
        }
      }
      container flow-label {
        description
          "Enable flow aware transport of pseudowire";
        choice flow-label-options {
          case both-case {
            container both {
              description
                "Enable FAT pseudowire in both directions";
              presence "true";
              uses config-interface-pseudowire-flow-label;
            }
          }
          case receive-case {
            container receive {
              description
                "Enable FAT pseudowire in the receive direction";
              presence "true";
              uses config-interface-pseudowire-flow-label;
            }
          }
          case transmit-case {
            container transmit {
              description
                "Enable FAT pseudowire in the transmit direction";
              presence "true";
              uses config-interface-pseudowire-flow-label;
            }
          }
        }
      }
    }
    container monitor {
      description
        "Active monitoring of xconnect peer";
      when "../encapsulation-config = 'mpls'";
      container peer {
        description
          "Active monitoring of xconnect peer";
        container bfd {
          description
            "BFD active monitoring for the xconnect peer";
          presence "true";
          container local {
            description
              "Specify local endpoint information to map to a BFD session";
            container interface {
              description
                "Source interface for pseudowire";
              uses ios-ifc:interface-grouping;
            }
          }
        }
      }
    }
    container neighbor {
      description
        "Neighbor options";
      must '(router-id and vc-id) or (not(router-id) and not(vc-id))' {
        error-message "router-id and vc-id must be configured";
      }
      leaf router-id {
        description
          "IP address of the peer PE";
        type inet:ipv4-address;
      }
      leaf vc-id {
        description
          "Virtual Circuit ID value";
        type uint64 {
          range "1..4294967295";
        }
      }
    }
    container preferred-path {
      description
        "Preferred path";
      when '../encapsulation-config';
      container interface {
        description
          "Output Interface";
        must 'Tunnel or Tunnel-tp or ((not(Tunnel) and not(disable-fallback)) or (not(Tunnel-tp) and not(disable-fallback)))' {
          error-message "Please make sure to configure Tunnel or Tunnel-tp";
        }
        choice Tunnel-Tunnel-tp {
          case Tunnel-case {
            leaf Tunnel {
              description
                "Tunnel interface";
              type uint64 {
                range "0..2147483647";
              }
            }
          }
          case Tunnel-tp-case {
            leaf Tunnel-tp {
              description
                "MPLS Transport Profile interface";
              type uint16;
            }
          }
        }
        leaf disable-fallback {
          description
            "disable fall back to alternative route";
          type empty;
        }
      }
      container peer-container {
        must 'peer or (not(peer) and not(disable-fallback))' {
          error-message "Please make sure to configure peer ";
        }
        leaf peer {
          description
            "Peer Address";
          type union {
            type string;
            type inet:ipv4-address;
          }
        }
        leaf disable-fallback {
          description
            "disable fall back to alternative route";
          type empty;
        }
      }
      container segment-routing {
        description
          "Segment-routing option";
        container traffic-eng {
          description
            "Segment-routing traffic engineering option";
          choice attribute-set-policy {
            container attribute-set-v2 {
              description
                "Set MPLS traffic engineering attribute for auto-tunnel";
              must 'te-profile or (not(te-profile) and not(disable-fallback))' {
                error-message "Please make sure to configure te-profile ";
              }
              leaf te-profile {
                description
                  "MPLS traffic engineering profile name";
                type string;
              }
              leaf disable-fallback {
                description
                  "disable fall back to alternative route";
                type empty;
              }
            }
            container policy-v2 {
              description
                "Set SR traffic engineering policy";
              must 'name or (not(name) and not(disable-fallback))' {
                error-message "Please make sure to configure policy name";
              }
              leaf name {
                description
                  "SR traffic engineering policy name";
                type string;
              }
              leaf disable-fallback {
                description
                  "disable fall back to alternative route";
                type empty;
              }
            }
          }
          container attribute-set {
            status obsolete;
            description
              "Set MPLS traffic engineering attribute for auto-tunnel,
               (OBSOLETE, use attribute-set-v2)";
            leaf te-profile {
              status obsolete;
              description
                "MPLS traffic engineering profile name,
                 (OBSOLETE, use attribute-set-v2/te-profile)";
              type string;
            }
            leaf disable-fallback {
              status obsolete;
              description
                "disable fall back to alternative route,
                 (OBSOLETE, use attribute-set-v2/disable-fallback)";
              type empty;
            }
          }
          container policy {
            status obsolete;
            description
              "Set SR traffic engineering policy,
               (OBSOLETE, use policy-v2)";
            leaf name {
              status obsolete;
              description
                "SR traffic engineering policy name,
                 (OBSOLETE, use policy-v2/name)";
              type string;
            }
            leaf disable-fallback {
              status obsolete;
              description
                "disable fall back to alternative route,
                 (OBSOLETE, use policy-v2/fallback)";
              type empty;
            }
          }
        }
      }
    }
    container pseudowire {
      description
        "Pseudowire parameters";
      when "(../encapsulation-config = 'mpls') and (../signaling/protocol/none)";
      container type {
        description
          "Pseudowire type";
        leaf type-value {
          description
            "<1-17>  Pseudowire Type in hex format
                      1  Frame Relay DLCI (Martini Mode)
                      2  ATM AAL5 service data unit virtual circuit connection transport
                      3  ATM transparent cell transport
                      4  Ethernet Tagged Mode
                      5  Ethernet
                      6  HDLC
                      7  PPP
                      8  SONET/SDH Circuit Emulation Service Over MPLS
                      9  ATM n-to-one virtual circuit connection cell transport
                      A  ATM n-to-one virtual path connection cell transport
                      B  IP Layer2 Transport
                      C  ATM one-to-one virtual circuit connection Cell Mode
                      D  ATM one-to-one virtual path connection Cell Mode
                      E  ATM AAL5 PDU virtual circuit connection transport
                      F  Frame-Relay Port mode
                     10  SONET/SDH Circuit Emulation over Packet
                     11  Structure-agnostic E1 over Packet
                     12  Structure-agnostic T1 (DS1) over Packet
                     13  Structure-agnostic E3 over Packet
                     14  Structure-agnostic T3 (DS3) over Packet
                     15  Circuit Emulation Service over Packet Switched Network basic mode
                     16  TDM-over-IP adaptation layer 1 Mode
                     17  Circuit Emulation Service over Packet Switched Network TDM with CAS";
          type enumeration {
            enum 1;
            enum 2;
            enum 3;
            enum 4;
            enum 5;
            enum 6;
            enum 7;
            enum 8;
            enum 9;
            enum A;
            enum B;
            enum C;
            enum D;
            enum E;
            enum F;
            enum 10;
            enum 11;
            enum 12;
            enum 13;
            enum 14;
            enum 15;
            enum 16;
            enum 17;
          }
        }
      }
    }
    container protocol-mpls {
      when "../encapsulation = 'mpls'";
      status obsolete;
      leaf protocol {
        description
          "Signaling protocol to use";
        status obsolete;
        type enumeration {
          enum ldp;
          enum none;
        }
      }
    }
    container protocol-l2tpv2 {
      when "../encapsulation = 'l2tpv2'";
      status obsolete;
      leaf protocol {
        description
          "Signaling protocol to use";
        status obsolete;
        type enumeration {
          enum l2tpv2;
          enum none;
        }
      }
    }
    container protocol-l2tpv3 {
      when "../encapsulation = 'l2tpv3'";
      status obsolete;
      leaf protocol {
        description
          "Signaling protocol to use";
        status obsolete;
        type enumeration {
          enum l2tpv3;
          enum l2tpv3ietf;
          enum none;
        }
      }
    }
    container pseudowire-sequencing {
      description
        "Sequencing options for pseudowire";
      when "../encapsulation-config = 'mpls' or ../encapsulation-config = 'l2tpv3'";
      choice sequencing-option {
        case both-case {
          leaf both {
            description
              "Transmit and receive sequence numbers";
            type empty;
          }
        }
        case receive-case {
          leaf receive {
            description
              "Receive sequence numbers";
            type empty;
          }
        }
        case resync-case {
          leaf resync {
            description
              "Enable Rx sequencing out-of-order detection/recovery";
            when "../../encapsulation = 'l2tpv3'";
            status obsolete;
            type uint16 {
              range "5..65535";
            }
          }
        }
        case transmit-case {
          leaf transmit {
            description
              "Transmit sequence numbers";
            type empty;
          }
        }
      }
      leaf resync-v2 {
        description
          "Enable Rx sequencing out-of-order detection/recovery";
        when "(../both or ../receive or ../transmit) and (../../encapsulation-config = 'l2tpv3' or (../../encapsulation-config = 'mpls' and not(../../signaling/protocol/none)))";
        type uint16 {
          range "5..65535";
        }
      }
    }
    leaf sequencing {
      description
        "Sequencing options for pseudowire";
      when "../encapsulation = 'mpls' or ../encapsulation = 'l2tpv3'";
      status obsolete;
      type enumeration {
        enum both;
        enum receive;
        enum resync;
        enum transmit;
      }
    }
    container source {
      description
        "Get config from another source";
      container template {
        description
          "Get config from a template";
        container type {
          description
            "Type of the template";
          leaf pseudowire {
            description
              "Template customized interface pseudowire";
            must 'not(../../../../encapsulation-config)';
            type string;
          }
        }
      }
    }
    container status {
      description
        "Pseudowire status capabilities";
      when '../encapsulation-config';
      presence "true";
      container admin-down {
        description
          "Admin down of Attachment Circuit";
        when "../../encapsulation-config = 'l2tpv3'";
        leaf disconnect {
          description
            "Disconnect the session";
          type empty;
        }
      }
      container control-plane {
        description
          "control plane status events";
        leaf route-watch-boolean {
          description
            "listen on the control plane to route-watch events";
          type boolean;
          default "true";
        }
        leaf route-watch {
          status obsolete;
          description
            "listen on the control plane to route-watch events
             (OBSOLETE, use route-watch-boolean)";
          type empty;
        }
      }
      container suppress {
        description
          "Suppress sending status message to the remote peer";
        when "../../encapsulation-config = 'mpls'";
        leaf standby {
          description
            "Suppress sending standby status message to the remote peer";
          type empty;
        }
      }
      leaf decoupled {
        description
          "Reflect standby status of the attachment circuit as up on the pseudowire";
        type empty;
      }
      container peer {
        description
          "peer status configuration";
        container topology {
          description
            "change status behaviour based on peer topology";
          leaf dual-homed {
            description
              "Our peer(s) are participating in a redundant solution with some form of redundancyprotocol running between the peer routers, Only one of the remote peers will advertise astatus of UP at a time. The other will advertise standby. Change our configuration so we can send a status of UP on both active and redundant pseudowires";
            type empty;
          }
        }
      }
      container redundancy {
        description
          "Xconnect redundancy configuration";
        leaf master {
          description
            "Put the xconnect redundancy group on this node in master mode";
          type empty;
        }
      }
      container protocol {
        description
          "Status protocol configuration";
        when "../../encapsulation-config = 'mpls'and ../../signaling/protocol/none";
        container notification {
          description
            "Status notification protocol";
          leaf static {
            description
              "Static PW OAM protocol";
            type leafref {
              path "/ios:native/ios:l2vpn/ios-l2vpn:pseudowire/ios-l2vpn:static-oam/ios-l2vpn:class/ios-l2vpn:pw-nm";
            }
          }
        }
      }
    }
    container switching {
      description
        "Switching TLV on/off for pseudowire";
      when "../encapsulation-config = 'mpls'";
      leaf tlv-boolean {
        description
          "Switching TLV on/off for pseudowire";
        type boolean;
        default "true";
      }
      leaf tlv {
        status obsolete;
        description
          "Switching TLV on/off for pseudowire
           (OBSOLETE, use tlv-boolean)";
        type empty;
      }
    }
    container vc {
      description
        "Virtual Circuit options";
      when "../encapsulation-config = 'mpls'";
      leaf type {
        description
          "Virtual Circuit type to use";
        type enumeration {
          enum ethernet;
          enum vlan;
        }
      }
    }
    container udp {
      description
        "UDP port configuration commands";
      when "../encapsulation-config = 'udp'";
      container port {
        description
          "UDP port number";
        must '(local and remote) or (not(local) and not(remote))' {
          error-message "Configure both local and remote";
        }
        leaf local {
          description
            "Local UDP port number";
          type uint32 {
            range "49152..57343";
          }
        }
        leaf remote {
          description
            "Remote UDP port number";
          type uint32 {
            range "49152..57343";
          }
        }
      }
    }
    container tlv {
      description
        "TLV config command";
      when "../encapsulation-config = 'mpls' and ../signaling/protocol/none";
      leaf template {
        must '/ios:native/ios:l2vpn/ios-l2vpn:pseudowire/ios-l2vpn:tlv/ios-l2vpn:template[ios-l2vpn:tlv-nm = current()]' {
          error-message "Please make sure to configure l2vpn pseudowire tlv template <name> before configuring this.";
        }
        description
          "TLV template";
        type string;
      }
      list tlv-list {
        must '(length and tlv-value-dec-fmt) or (length and dec) or (length and hexstr) or (length and str) or (not(length) and not(tlv-value-dec-fmt) and not(dec) and not(hexstr) and not(str))' {
          error-message "tlv-length and tlv-length-choice must be configured";
        }
        key "tlv-type";
        leaf tlv-type {
          description
            "TLV value in hex format";
          type uint8 {
            range "1..40";
          }
        }
        uses config-l2vpn-pseudowire-tlv-template-tlv;
      }
    }
  }

  grouping config-interface-efp-xconnect-grouping {
    choice xconnect-choice {
      container xconnect {
        leaf address {
          type inet:ipv4-address;
        }
        leaf vcid {
          type uint32 {
            range "1..4294967295";
          }
        }
        leaf encapsulation {
          description
            "Data encapsulation method";
          type enumeration {
            enum mpls;
            enum l2tpv3;
          }
        }
        leaf manual {
          description
            "Manually configure L2TP session parameters";
          type empty;
        }
        leaf pw-class {
          description
            "Optional pseudowire-class to use for advanced configuration";
          type string;
        }
        leaf sequencing {
          description
            "Configure sequencing options for xconnect";
          when "../encapsulation = 'l2tpv3'";
          type enumeration {
            enum both;
            enum receive;
            enum transmit;
          }
        }
        container backup {
          description
            "Xconnect backup configuration commands";
          container peer {
            description
              "Backup pseudowire";
            leaf peer-router-ip-addr {
              type inet:ipv4-address;
            }
            leaf vcid {
              type uint32 {
                range "1..4294967295";
              }
            }
            leaf pw-class {
              type string;
            }
            leaf priority {
              description
                "Optional priority to use for backup pseudowire.";
              type uint8 {
                range "1..10";
              }
            }
          }
          container delay {
            description
              "backup delay time";
            leaf min {
              type uint32;
            }
            leaf max {
              type uint32;
            }
          }
        }
        leaf mtu {
          type uint32;
        }
      }
      container xconnect-pw-class {
        container xconnect {
          description
            "Xconnect commands";
          leaf address {
            type inet:ipv4-address;
          }
          leaf vcid {
            type uint32 {
              range "1..4294967295";
            }
          }
          leaf pw-class {
            description
              "Pseudowire-class to use for encapsulation and protocol configuration";
            type string;
          }
          container udp {
            description
              "UDP";
            container port {
              description
                "UDP ports";
              leaf local {
                type uint32;
              }
              leaf remote {
                type uint32;
              }
            }
          }
        }
      }
    }
  }

  grouping config-interface-virtual-ppp-pseudo-grouping {
    container pseudowire {
      description
        "pseudowire commands";
      presence "true";
      leaf address {
        description
          "IP address of peer";
        type inet:ipv4-address;
      }
      leaf vcid {
        description
          "VC ID value";
        type uint32 {
          range "1..4294967295";
        }
      }
      leaf encapsulation {
        description
          "Data encapsulation method";
        type enumeration {
          enum mpls;
          enum l2tpv2;
          enum l2tpv3;
        }
      }
      leaf manual {
        description
          "Manually configure L2TP session parameters";
        when "../encapsulation = 'l2tpv3' or ../encapsulation = 'mpls'";
        type empty;
      }
      leaf sequence {
        description
          "Configure sequencing options for xconnect";
        when "../encapsulation = 'l2tpv3'";
        type enumeration {
          enum both;
          enum receive;
          enum transmit;
        }
      }
      leaf pw-class {
        description
          "Pseudowire-class to use for encapsulation and protocol configuration";
        type leafref {
          path "/ios:native/ios:pseudowire-class/ios:name";
        }
        must '/ios:native/ios:pseudowire-class[ios:name=current()]/ip/local/interface/interface-name' {
          error-message "Please make sure pw-class is configured with local-interface and valid.";
        }
      }
      container backup {
        description
          "pseudowire backup configuration commands";
        container peer {
          description
            "Backup pseudowire";
          leaf peer-router-ip-addr {
            description
              "IP address of peer";
            type inet:ipv4-address;
          }
          leaf vcid {
            description
              "Peer VC ID value";
            type uint32 {
              range "1..4294967295";
            }
          }
          leaf pw-class {
            description
              "Optional pseudowire-class to use for backup pseudowire";
            type leafref {
              path "/ios:native/ios:pseudowire-class/ios:name";
            }
            must '/ios:native/ios:pseudowire-class[ios:name=current()]/ip/local/interface/interface-name' {
              error-message "Please make sure pw-class is configured with local-interface and valid.";
            }
          }
          leaf priority {
            description
              "Optional priority to use for backup pseudowire.";
            type uint8 {
              range "1..10";
            }
          }
        }
        container delay {
          description
            "backup delay time";
          presence "true";
          leaf enable {
            description
              "Enable Delay";
            type uint16 {
              range "0..180";
            }
          }
          leaf disable {
            description
              "Disable Delay";
            type union {
              type uint16 {
                range "0..180";
              }
              type enumeration {
                enum never;
              }
            }
          }
        }
      }
    }
  }

  grouping config-interface-xconnect-grouping {
    container xconnect {
      description
        "Xconnect commands";
      leaf address {
        type inet:ipv4-address;
      }
      leaf vcid {
        type uint32 {
          range "1..4294967295";
        }
      }
      leaf encapsulation {
        description
          "Data encapsulation method";
        type enumeration {
          enum mpls;
          enum l2tpv3;
        }
      }
      leaf manual {
        description
          "Manually configure L2TP session parameters";
        when "../encapsulation = 'l2tpv3' or ../encapsulation = 'mpls'";
        type empty;
      }
      leaf sequence {
        description
          "Configure sequencing options for xconnect";
        when "../encapsulation = 'l2tpv3'";
        type enumeration {
          enum both;
          enum receive;
          enum transmit;
        }
      }
      leaf pw-class {
        description
          "Pseudowire-class to use for encapsulation and protocol configuration";
        type string;
      }
    }
  }

  grouping config-l2-grouping {
    list vfi {
      if-feature "ios-features:l2vpn";
      description
        "Configure a virtual forwarding instance";
      key "name";
      leaf name {
        type string;
      }
      leaf mode {
        type enumeration {
          enum autodiscovery;
          enum manual;
          enum point-to-point;
        }
      }
      leaf evc {
        when "../mode = 'autodiscovery' or ../mode = 'manual'";
        type string;
      }
      container vpn {
        description
          "VPN configuration";
        when "../mode = 'autodiscovery' or ../mode = 'manual'";
        leaf id {
          description
            "VPN id";
          type uint64 {
            range "1..4294967295";
          }
        }
      }
      leaf bridge-domain {
        description
          "bridge-domain";
        type uint16 {
          range "1..16384";
        }
      }
      leaf mtu {
        description
          "MTU size in bytes";
        type uint32;
      }
      list neighbor {
        description
          "VFI neighbor configuration";
        key "router-id";
        leaf router-id {
          type inet:ipv4-address;
        }
        leaf vc-id {
          type uint64 {
            range "1..4294967295";
          }
        }
        leaf encapsulation {
          description
            "Connection encapsulation type";
          type enumeration {
            enum l2tpv3;
            enum mpls;
          }
        }
        leaf pw-class {
          description
            "Pseudowire-class configuration";
          type string;
        }
      }
    }
  }

  grouping config-l2vpn-evpn-main {
    container evpn {
      description
        "Ethernet Virtual Private Network (EVPN) configuration";
      container replication-type {
        description
          "Specify method for replicating BUM traffic";
        choice replication-type-choice {
          leaf ingress {
            description
              "Ingress replication";
            type empty;
          }
          leaf static {
            description
              "Static replication";
            type empty;
          }
          leaf p2mp {
            description
              "p2mp replication";
            type empty;
          }
          leaf mp2mp {
            description
              "mp2mp replication";
            type empty;
          }
        }
      }
      container arp {
        description
          "arp parameters";
        status obsolete;
        container flooding-suppression {
          status obsolete;
          leaf disable {
            status obsolete;
            type empty;
          }
        }
      }
      container mac {
        description
          "MAC parameters";
        container duplication {
          description
            "MAC duplication detection";
          leaf limit {
            description
              "Number of MAC moves within specified time interval";
            type uint16 {
              range "2..1000";
            }
          }
          leaf time {
            description
              "MAC duplication timer";
            type uint32 {
              range "10..36000";
            }
          }
        }
      }
      container ip {
        description
          "IP parameters";
        container duplication {
          description
            "IP duplication detection";
          leaf limit {
            description
              "Number of IP moves within specified time interval";
            type uint16 {
              range "2..1000";
            }
          }
          leaf time {
            description
              "IP duplication timer";
            type uint32 {
              range "10..36000";
            }
          }
        }
        container local-learning {
          description
            "IP local learning";
          leaf disable {
            description
              "Disable IP local learning from dataplane";
            type empty;
          }
          container limit {
            description
              "Limit number of locally learned IP addresses that can be stored";
            container per-mac {
              description
                "Limit number of IP addresses that can be learned per-MAC";
              leaf ipv4 {
                description
                  "Limit number of IPv4 addresses";
                type uint32 {
                  range "0..32000";
                }
                default "4";
              }
              leaf ipv6 {
                description
                  "Limit number of IPv6 addresses";
                type uint32 {
                  range "0..32000";
                }
                default "12";
              }
            }
          }
          container time {
            description
              "IP local learning timer values";
            leaf down {
              description
                "Down time in minutes";
              type uint32 {
                range "1..1440";
              }
              default "10";
            }
            leaf poll {
              description
                "Polling interval in minutes";
              type uint32 {
                range "1..1440";
              }
              default "1";
            }
            leaf reachable {
              description
                "Reachable lifetime in minutes";
              type uint32 {
                range "1..1440";
              }
              default "5";
            }
            leaf stale {
              description
                "Stale lifetime in minutes";
              type uint32 {
                range "1..1440";
              }
              default "30";
            }
          }
        }
      }
      container mpls {
        description
          "MPLS label config";
        container label {
          container mode {
            choice mode-choice {
              leaf per-ce {
                description
                  "Allocate one MPLS label per Customer Edge device";
                type empty;
              }
              leaf per-evi {
                description
                  "Allocate one MPLS label per EVPN Instance";
                type empty;
              }
              leaf per-bd {
                description
                  "Allocate one MPLS label per Bridge Domain";
                type empty;
              }
            }
          }
        }
      }
      container multihoming {
        description
          "Evpn multihoming config";
        container peering {
          description
            "BGP peering parameters";
          leaf adjacent {
            description
              "multihoming adjacent disable";
            type empty;
          }
        }
        container device-id {
          description
            "EVPN Device ID for Port-Channel, default as 0000.5e00.0101";
          leaf id {
            description
              "Device ID (System MAC)";
            type string {
              pattern '[A-Fa-f0-9:.]+';
            }
          }
        }
        container ethernet-segment {
          description
            "Ethernet-Segment options";
          container auto {
            description
              "Ethernet-Segment auto-config options";
            container id-range {
              description
                "Ethernet-Segment auto-config local discriminator range, default: 64512-65535";
              leaf start {
                description
                  "Ethernet-Segment local discriminator range start";
                type uint16 {
                  range "1..65535";
                }
              }
              leaf end {
                description
                  "Ethernet-Segment local discriminator range end";
                type uint16 {
                  range "1..65535";
                }
              }
            }
          }
        }
        container aliasing {
          leaf disable {
            type empty;
          }
        }
        container proxy-mac-ip {
          leaf disable {
            description
              "Disable multihoming proxy MAC/IP routes";
            type empty;
          }
        }
      }
      container router-id {
        description
          "Select interface to prefer for evpn router-id";
        container interface {
          uses ios-ifc:interface-grouping;
        }
      }
      container default-gateway {
        description
          "EVPN Default Gateway parameters";
        leaf advertise {
          description
            "Advertise Default Gateway MAC/IP routes";
          type empty;
        }
      }
      container logging {
        description
          "Configure logging flags";
        container vpws {
          description
            "Configure EVPN VPWS logging flags";
          leaf vc-state {
            description
              "vc-state transition logging";
            type empty;
          }
        }
        container peer {
          description
            "Configure EVPN peer logging";
          leaf state {
            description
              "Peer state transition logging";
            type empty;
          }
        }
      }
      container route-target {
        description
          "Route Target VPN Extended Communities";
        container auto {
          description
            "Automatically set a route-target";
          leaf vni {
            description
              "Set vni-based route-target";
            type empty;
          }
        }
      }
      container flooding-suppression {
        description
          "Suppress flooding of broadcast, multicast, and/or unknown unicast packets";
        container address-resolution {
          description
            "Suppress flooding of Address Resolution and Neighbor Discovery Protocol packets";
          leaf disable {
            description
              "Disable flooding suppression";
            type empty;
          }
        }
      }
      container multicast {
        description
          "Multicast parameters";
        leaf advertise {
          description
            "Enable and advertise L2 multicast capability";
          type empty;
        }
        leaf sync-only {
          description
            "Only advertise multicast join/leave sync routes";
          when '../advertise';
          type empty;
        }
        leaf intra-es {
          description
            "Enable multicast intra-ES tunnel";
          when '../sync-only';
          type empty;
        }
      }
      container anycast-gateway {
        description
          "Anycast Gateway";
        container mac {
          description
            "Enable Anycast Gateway MAC";
          leaf auto {
            description
              "Enable Auto Anycast Gateway MAC";
            type empty;
          }
        }
      }
    }
  }

  grouping config-l2vpn-evpn-instance-sub-cmd {
    container replication-type {
      description
        "Specify method for replicating BUM traffic";
      choice replication-type-choice {
        case ingress-case {
          leaf ingress {
            description
              "Ingress replication";
            type empty;
          }
        }
        case static-case {
          leaf static {
            description
              "Static replication";
            type empty;
          }
        }
        case static-p2mp {
          leaf p2mp {
            description
              "p2mp replication";
            type empty;
          }
        }
        case static-mp2mp {
          leaf mp2mp {
            description
              "mp2mp replication";
            type empty;
          }
        }
      }
    }
    leaf encapsulation {
      description
        "Data encapsulation method";
      type enumeration {
        enum vxlan;
        enum mpls;
      }
    }
    container auto-route-target_cont {
      leaf auto-route-target-boolean {
        description
          "Automatically set a route-target";
        type boolean;
        default "true";
      }
      leaf auto-route-target {
        status obsolete;
        description
          "Automatically set a route-target
           (OBSOLETE, use auto-route-target-boolean)";
        type empty;
      }
    }
    container rd {
      description
        "EVPN Route Distinguisher";
      leaf rd-value {
        description
          "ASN:nn or IP-address:nn";
        type string;
      }
    }
    container route-target-v2 {
      description
        "Route Target VPN Extended Communities";
      list export {
        key "rt-value";
        leaf rt-value {
          description
            "ASN:nn or IP-address:nn";
          type string {
            pattern '[0-9\.:]+[0-9]+';
          }
        }
      }
      list import {
        key "rt-value";
        leaf rt-value {
          description
            "ASN:nn or IP-address:nn";
          type string {
            pattern '[0-9\.:]+[0-9]+';
          }
        }
      }
    }
    container route-target {
      status obsolete;
      description
        "Route Target VPN Extended Communities (Obsolete, use route-target-entry)";
      leaf rt-value {
        status obsolete;
        description
          "ASN:nn or IP-address:nn";
        type string;
      }
      container both {
        status obsolete;
        description
          "Both import and export Target-VPN community";
        leaf rt-value {
          status obsolete;
          description
            "ASN:nn or IP-address:nn";
          type string;
        }
      }
      container export {
        status obsolete;
        leaf rt-value {
          status obsolete;
          description
            "ASN:nn or IP-address:nn (Obsolete, use rt-value-entry)";
          type string;
        }
      }
      container import {
        status obsolete;
        description
          "Import Target-VPN community (Obsolete, use import-entry)";
        leaf rt-value {
          status obsolete;
          description
            "ASN:nn or IP-address:nn (Obsolete, use rt-value-entry)";
          type string;
        }
      }
    }
    container ip {
      description
        "IP parameters";
      container local-learning {
        description
          "IP local learning";
        choice local-learning-choice {
          case disable-case {
            leaf disable {
              description
                "Disable IP local learning from dataplane";
              type empty;
            }
          }
          case enable-case {
            leaf enable {
              description
                "Enable IP local learning from dataplane";
              type empty;
            }
          }
        }
      }
    }
    container default-gateway {
      description
        "Default Gateway parameters";
      leaf advertise {
        description
          "Advertise Default Gateway MAC/IP routes";
        type enumeration {
          enum disable;
          enum enable;
        }
      }
    }
    container re-originate {
      description
        "Re-originate route";
      when "../encapsulation = 'vxlan'";
      leaf route-type5 {
        description
          "Re-originate route-type 5";
        type empty;
      }
    }
    container multicast {
      description
        "Multicast parameters";
      leaf advertise {
        description
          "Advertise L2 multicast capability";
        type enumeration {
          enum disable;
          enum enable;
          enum sync-only;
        }
      }
      leaf intra-es {
        description
          "Enable multicast intra-ES tunnel";
        when "../advertise = 'sync-only'";
        type empty;
      }
    }
    container flooding-suppression {
      description
        "Suppress flooding of broadcast, multicast, and/or unknown unicast packets";
      must '../../vlan-aware or ../../vlan-based or ../../vlan-bundle' {
        error-message "Only configurable when EVPN service type is vlan-aware, vlan-based, or vlan-bundle";
      }
      leaf address-resolution {
        description
          "Suppress flooding of Address Resolution and Neighbor Discovery Protocol packets";
        type enumeration {
          enum disable;
          enum enable;
        }
      }
    }
    container vpws {
      description
        "EVPN Virtual Private Wire Service configuration";
      list context {
        description
          "EVPN VPWS context";
        key "name";
        leaf name {
          description
            "EVPN VPWS context name";
          type string;
        }
        container member {
          description
            "EVPN member configuration";
          list interface {
            key "interface";
            leaf interface {
              description
                "Interface name";
              must '/ios:native/ios:interface/*[concat(local-name(.), ios:name) = current()]';
              type string;
            }
            choice config-interface {
              case config-interface-service-instance {
                list service-instance-config {
                  description
                    "Ethernet Service Instance";
                  key "service-instance-id";
                  leaf service-instance-id {
                    description
                      "Service Instance ID";
                    type uint16 {
                      range "1..16384";
                    }
                  }
                }
              }
            }
          }
        }
        container remote {
          description
            "L2VPN remote peer configuration commands";
          container link {
            description
              "Link information";
            container failure {
              description
                "Failure information";
              leaf notification {
                description
                  "Notify in case of remote link failure";
                type boolean;
                default "true";
              }
            }
          }
        }
        container service {
          description
            "VPWS Service Instance";
          leaf target {
            description
              "Target (remote) VPWS Service Instance identifier";
            type uint32 {
              range "1..16777215";
            }
          }
          leaf source {
            description
              "Source (local) VPWS Service Instance identifier";
            type uint32 {
              range "1..16777215";
            }
          }
        }
        container preferred-path {
          description
            "Preferred path";
          container segment-routing {
            description
              "Segment-routing option";
            container traffic-eng {
              description
                "Segment-routing traffic engineering option";
              container policy {
                description
                  "Set SR traffic engineering policy";
                leaf name {
                  description
                    "SR traffic engineering policy name";
                  type string;
                }
                leaf disable-fallback {
                  description
                    "disable fall back to alternative route";
                  type empty;
                }
              }
            }
          }
        }
        leaf shutdown {
          description
            "Shut down the EVPN VPWS service";
          type empty;
        }
      }
    }
  }

  grouping config-evpn-ethernet-segment-global {
    container evpn-ethernet-segment {
      container evpn {
        list ethernet-segment {
          description
            "Ethernet segment local discriminator value";
          key "es-value";
          leaf es-value {
            description
              "Ethernet segment local discriminator value";
            type uint16 {
              range "1..65535";
            }
          }
          container df-election {
            description
              "Designated forwarder election parameters";
            leaf wait-time {
              type uint8 {
                range "1..10";
              }
              default "3";
            }
          }
          container redundancy {
            description
              "Multi-homing redundancy parameters";
            choice redundancy-choice {
              leaf all-active {
                type empty;
              }
              leaf single-active {
                type empty;
              }
            }
          }
          container identifier {
            description
              "Ethernet Segment Identifier";
            list type {
              description
                "Ethernet Segment Identifier type";
              key "identifier-type";
              leaf identifier-type {
                type uint8 {
                  range "0 | 3";
                }
              }
              choice esi-type-choice {
                leaf hex-string {
                  when "../identifier-type = '0'";
                  description
                    "H.H.H.H.H.H.H.H.H \t9-octet ESI value in hex";
                  type string {
                    pattern '([0-9a-fA-F]{1,2}(.[0-9a-fA-F]{1,2}){8})';
                  }
                }
                leaf system-mac {
                  when "../identifier-type = '3'";
                  description
                    "System MAC address for generating the ESI value";
                  type ios-types:cisco-mac-address-type;
                }
              }
            }
          }
        }
      }
    }
  }

  grouping config-l2vpn-evpn-profile-sub-cmd {
    container default-gateway {
      description
        "Default Gateway parameters";
      leaf advertise {
        description
          "Advertise Default Gateway MAC/IP routes";
        type enumeration {
          enum disable;
          enum enable;
        }
      }
    }
    container flooding-suppression {
      description
        "Suppress flooding of broadcast, multicast, and/or unknown unicast packets";
      leaf address-resolution {
        description
          "Suppress flooding of Address Resolution and Neighbor Discovery Protocol packets";
        type enumeration {
          enum disable;
          enum enable;
        }
      }
    }
    leaf encapsulation {
      description
        "EVPN encap type";
      type enumeration {
        enum vxlan;
        enum mpls;
      }
      default "vxlan";
    }
    leaf evi-base {
      description
        "Evpn instance identifier base";
      type uint16 {
        range "0..65535";
      }
      default "0";
    }
    container ip {
      description
        "IP parameters";
      leaf local-learning {
        description
          "IP local learning";
        type enumeration {
          enum disable;
          enum enable;
        }
      }
    }
    leaf l2vni-base {
      description
        "VxLAN Layer 2 VNI base";
      type uint32 {
        range "4096..16777215";
      }
      default "20000";
    }
    container multicast {
      description
        "Multicast parameters";
      leaf advertise {
        description
          "Advertise L2 multicast capability";
        type enumeration {
          enum disable;
          enum enable;
          enum sync-only;
        }
      }
      leaf intra-es {
        description
          "Enable multicast intra-ES tunnel";
        when "../advertise = 'sync-only'";
        type empty;
      }
    }
    container re-originate {
      description
        "Re-originate route";
      when "../encapsulation = 'vxlan'";
      leaf route-type5 {
        description
          "Re-originate route-type 5";
        type empty;
      }
    }
    leaf local-routing {
      description
        "Vxlan centralized gateway forwarding for routed traffic";
      type enumeration {
        enum disable;
        enum enable;
      }
    }
    container replication-type {
      description
        "EVPN Replication Type";
      choice replication-type-choice {
        default "ingress-case";
        case ingress-case {
          leaf ingress-replication {
            type enumeration {
              enum ingress;
            }
            default "ingress";
          }
        }
        case static-case {
          container static {
            choice address-prefix-choice {
              container address {
                leaf ipv4-address {
                  type inet:ipv4-address;
                }
                leaf ipv6-address {
                  type inet:ipv6-address;
                }
              }
              container prefix {
                leaf ipv4-prefix {
                  type inet:ipv4-prefix;
                }
                leaf ipv6-prefix {
                  type inet:ipv6-prefix;
                }
              }
            }
          }
        }
      }
    }
  }

  grouping config-l2vpn-evpn-profile {
    container l2-profile {
      description
        "EVPN Layer 2 Profile";
      container evpn {
        container profile {
          container default {
            description
              "EVPN L2 default vlan-based profile";
            presence "true";
            uses config-l2vpn-evpn-profile-sub-cmd;
          }
          list profile-name-list {
            key "name";
            leaf name {
              description
                "EVPN L2 profile name";
              type string;
            }
            uses config-l2vpn-evpn-profile-sub-cmd;
          }
        }
      }
    }
  }

  grouping config-l2vpn-evpn-instance {
    container evpn-instance {
      container evpn {
        container instance {
          list instance {
            description
              "evpn instance";
            key "evpn-instance-num";
            leaf evpn-instance-num {
              description
                "evpn instance number";
              type uint16 {
                range "1..65535";
              }
            }
            choice evpn-service-type {
              description
                "Evpn Service type.";
              container point-to-point {
                presence "true";
                uses config-l2vpn-evpn-instance-sub-cmd;
              }
              container vlan-aware {
                presence "true";
                uses config-l2vpn-evpn-instance-sub-cmd;
              }
              container vlan-based {
                presence "true";
                uses config-l2vpn-evpn-instance-sub-cmd;
              }
              container vlan-bundle {
                presence "true";
                uses config-l2vpn-evpn-instance-sub-cmd;
              }
            }
          }
        }
      }
    }
  }

  grouping config-l2vpn-sdwan-main-duplication-grouping {
    container duplication {
      description
        "Duplication detection";
      leaf limit {
        description
          "The number of moves within a specified time interval, default is 5.";
        must '../time' {
          error-message "%Error: Must both configure limit and time.";
        }
        type uint16 {
          range "2..1000";
        }
      }
      leaf time {
        description
          "The duplication timer, unit is second, default is 180.";
        must '../limit' {
          error-message "%Error: Must both configure limit and time.";
        }
        type uint32 {
          range "10..36000";
        }
      }
    }
  }

  grouping config-l2vpn-sdwan-main {
    container sdwan {
      description
        "Global l2vpn sdwan mode configuration";
      container ip {
        description
          "IP parameters";
        uses config-l2vpn-sdwan-main-duplication-grouping;
        container local-learning {
          description
            "IP local learning";
          container limit {
            description
              "Limit number of locally learned IP addresses that can be stored";
            container per-mac {
              description
                "Limit number of IP addresses that can be learned per-MAC";
              leaf ipv4 {
                description
                  "Limit number of IPv4 addresses";
                type uint32 {
                  range "0..32000";
                }
                default "4";
              }
              leaf ipv6 {
                description
                  "Limit number of IPv6 addresses";
                type uint32 {
                  range "0..32000";
                }
                default "12";
              }
            }
          }
          container time {
            description
              "IP local learning timer values";
            leaf down {
              description
                "Down time in minutes";
              type uint32 {
                range "1..1440";
              }
              default "10";
            }
            leaf poll {
              description
                "Polling interval in minutes";
              type uint32 {
                range "1..1440";
              }
              default "1";
            }
            leaf reachable {
              description
                "Reachable lifetime in minutes";
              type uint32 {
                range "1..1440";
              }
              default "5";
            }
            leaf stale {
              description
                "Stale lifetime in minutes";
              type uint32 {
                range "1..1440";
              }
              default "30";
            }
          }
        }
      }
      container mac {
        description
          "MAC parameters";
        uses config-l2vpn-sdwan-main-duplication-grouping;
      }
    }
  }

  grouping config-l2vpn-sdwan-instance-multipoint-grouping {
    container ip {
      description
        "IP parameters";
      leaf local-learning {
        description
          "IP local learning";
        type enumeration {
          enum enable {
            value 1;
          }
          enum disable;
        }
        default "enable";
      }
    }
    leaf flooding-suppression {
      description
        "Suppress flooding of broadcast, multicast, and/or unknown unicast packets";
      type enumeration {
        enum enable {
          value 1;
        }
        enum disable;
      }
      default "enable";
    }
  }

  grouping config-l2vpn-sdwan-instance-default-grouping {
    container active-election {
      description
        "Active election parameters";
      leaf wait-time {
        description
          "Wait time to become active. Unit is second, default is 300.";
        type uint32 {
          range "1..3600";
        }
        default "300";
      }
    }
  }

  grouping config-l2vpn-sdwan-instance {
    container sdwan-instance {
      container sdwan {
        list instance {
          description
            "L2VPN SDWAN instance";
          key "sdwan-instance-num";
          leaf sdwan-instance-num {
            description
              "L2VPN SDWAN instance number, value is in <1..65531>.";
            must 'not (/ios:native/ios:vrf/ios:definition[ios:name=string(current())])' {
              error-message "sdwan instance id and vrf id can not be same";
            }
            type uint32 {
              range "1..65531";
            }
          }
          choice service-type-choice {
            description
              "The choice of service type";
            case point-to-point-case {
              container point-to-point {
                description
                  "Service type as point to point";
                presence "true";
                uses config-l2vpn-sdwan-instance-default-grouping;
              }
            }
            case multipoint-case {
              container multipoint {
                description
                  "Service type as point to multipoint";
                presence "true";
                uses config-l2vpn-sdwan-instance-multipoint-grouping;
                uses config-l2vpn-sdwan-instance-default-grouping;
              }
            }
          }
        }
      }
    }
  }

  grouping config-l2vpn-xconnect-member-group-priority {
    leaf group-name {
      description
        "Configure the cross connect member redundancy group";
      type string;
    }
    leaf priority {
      description
        "Configure the cross connect member priority";
      type uint8 {
        range "0..16";
      }
    }
  }

  grouping config-l2vpn-xconnect-member-encapsulation-template {
    choice encapsulation-template {
      case encapsulation-case {
        leaf encapsulation {
          description
            "Data encapsulation method";
          type enumeration {
            enum mpls;
          }
        }
      }
      case template-case {
        leaf template {
          description
            "template to use for encapsulation and protocol configuration";
          type string;
        }
      }
    }
  }

  grouping config-l2vpn-pseudowire-tlv-template-tlv {
    leaf length {
      description
        "TLV length";
      type uint8 {
        range "1..255";
      }
    }
    choice tlv-length-choice {
      leaf tlv-value-dec-fmt {
        description
          "TLV value in decimal format";
        type uint32 {
          range "1..4294967295";
        }
      }
      leaf dec {
        description
          "TLV value in decimal";
        type uint32 {
          range "1..4294967295";
        }
      }
      leaf hexstr {
        description
          "TLV value in hex string";
        type string {
          pattern '([A-Fa-f0-9][A-Fa-f0-9])+';
        }
      }
      leaf str {
        description
          "TLV value in string";
        type string;
      }
    }
  }

  grouping config-l2vpn-vfi-member-encapsulation-template {
    choice member-encapsulation {
      leaf encapsulation {
        description
          "Data encapsulation method";
        type enumeration {
          enum mpls;
        }
      }
      leaf template {
        description
          "template to use for encapsulation and protocol configuration";
        type string;
      }
    }
  }

  grouping config-l2vpn-vfi-bgp-signaling-rd-rt {
    leaf auto-route-target-boolean {
      description
        "Automatically set a route-target";
      type boolean;
      default "true";
    }
    leaf auto-route-target {
      status obsolete;
      description
        "Automatically set a route-target
         (OBSOLETE, use auto-route-target-boolean)";
      type empty;
    }
    leaf rd {
      description
        "ASN:nn, IP-address:nn or 4BASN:nn VPN Route Distinguisher";
      type ios-types:asn-ip-type;
    }
    container route-target {
      description
        "Route Target VPN Extended Communities";
      leaf rt-value {
        description
          "ASN:nn or IP-address:nn";
        type ios-types:asn-ip-type;
      }
      list both {
        key "rt-value";
        leaf rt-value {
          description
            "ASN:nn or IP-address:nn";
          type ios-types:asn-ip-type;
        }
      }
      list export {
        key "rt-value";
        leaf rt-value {
          description
            "ASN:nn or IP-address:nn";
          type ios-types:asn-ip-type;
        }
      }
      list import {
        key "rt-value";
        leaf rt-value {
          description
            "ASN:nn or IP-address:nn";
          type string;
        }
      }
    }
  }

  grouping config-l2vpn-grouping {
    container pseudowire {
      description
        "Global pseudowire parameters";
      container static-oam {
        description
          "Static PW OAM configuration";
        list class {
          description
            "Static PW OAM class configuration";
          key "pw-nm";
          leaf pw-nm {
            type string;
          }
          container timeout {
            description
              "timeout configurations";
            container refresh {
              description
                "refresh timeout configurations";
              container send {
                description
                  "refresh send timeout configuration";
                leaf interval {
                  type uint32 {
                    range "1..4095";
                  }
                }
              }
              leaf ack {
                description
                  "refresh ack/receive timeout configuration";
                type uint16 {
                  range "0..4095";
                }
              }
            }
          }
          container ack {
            description
              "acknowledgement configuration";
            leaf enable {
              description
                "Enable acknowledgement";
              type empty;
            }
          }
          leaf keepalive {
            description
              "keepalive configuration";
            type uint32 {
              range "1..4095";
            }
          }
          leaf ttl {
            description
              "TTL value for multi-segment PW OAM data";
            type uint8 {
              range "1..255";
            }
          }
        }
      }
      container tlv {
        description
          "Global PW TLV configuration";
        list template {
          description
            "PW TLV Template Keyword";
          key "tlv-nm";
          leaf tlv-nm {
            type string;
          }
          container tlv-config {
            description
              "TLV config command";
            list tlv-list {
              must '(length and tlv-value-dec-fmt) or (length and dec) or (length and hexstr) or (length and str) or (not(length) and not(tlv-value-dec-fmt) and not(dec) and not(hexstr) and not(str))' {
                error-message "tlv-length and tlv-length-choice must be configured";
              }
              key "tlv-type";
              leaf tlv-type {
                description
                  "TLV value in hex format";
                type uint8 {
                  range "1..40";
                }
              }
              uses config-l2vpn-pseudowire-tlv-template-tlv;
            }
          }
          container tlv {
            description
              "TLV config command";
            status obsolete;
            container tlv-type {
              status obsolete;
              leaf type {
                status obsolete;
                type uint8 {
                  range "1..40";
                }
              }
            }
            container tlv-description {
              status obsolete;
              leaf description {
                status obsolete;
                type string;
              }
            }
          }
        }
      }
      container group {
        description
          "Configure pseudowire group parameters";
        status obsolete;
        leaf status {
          description
            "Send pseudowire group status messages";
          status obsolete;
          type empty;
        }
      }
      leaf routing {
        description
          "Configure l2vpn pseudowire routing";
        status obsolete;
        type empty;
      }
    }
    container vfi {
      description
        "Configure a Virtual Forwarding Instance (VFI)";
      list context {
        description
          "Layer2 VPN Context";
        key "vfi-nm";
        leaf vfi-nm {
          description
            "Virtual Forwarding Instance (VFI) name";
          type string;
        }
        container autodiscovery {
          description
            "Auto Discovery mode";
          container bgp {
            description
              "Use BGP for neighbor discovery";
            container signaling {
              description
                "Signaling protocol to use";
              container bgp {
                description
                  "Use BGP signaling and discovery";
                presence "true";
                when 'not(../../../../member/ipv4 or ../../../../member/pseudowire)';
                must 'not(../../../../forward/permit/l2protocol/all)' {
                  error-message "Please unconfigure forward permit l2protocol all before configuring this";
                }
                leaf template {
                  description
                    "Template to be used for autodiscovered pseudowires";
                  type string;
                }
                container control-word {
                  description
                    "Control-word options";
                  choice exclude-include {
                    container exclude {
                      description
                        "Exclude control-word in pseudowire packets";
                      presence "true";
                      leaf negotiate {
                        description
                          "Negotiate control-word in pseudowire packets";
                        type empty;
                      }
                    }
                    container include {
                      description
                        "Include control-word in pseudowire packets";
                      presence "true";
                      leaf negotiate {
                        description
                          "Negotiate control-word in pseudowire packets";
                        type empty;
                      }
                    }
                  }
                }
                container ve {
                  description
                    "Specify VPLS Edge device parameters";
                  leaf id {
                    description
                      "Specify VPLS Edge device ID";
                    type uint16 {
                      range "1..16384";
                    }
                  }
                  leaf range {
                    description
                      "Specify VPLS Edge device ID range";
                    type uint8 {
                      range "11..100";
                    }
                  }
                }
                uses config-l2vpn-vfi-bgp-signaling-rd-rt;
              }
              container ldp {
                description
                  "Use LDP signaling";
                presence "true";
                must 'not(../../../../forward/permit/l2protocol/all)' {
                  error-message "Please unconfigure forward permit l2protocol all before configuring this";
                }
                leaf template {
                  description
                    "Template to be used for autodiscovered pseudowires";
                  type string;
                }
                leaf vpls-id {
                  description
                    "Specify VPLS-ID Extended Community";
                  type ios-types:asn-ip-type;
                }
                uses config-l2vpn-vfi-bgp-signaling-rd-rt;
              }
            }
          }
        }
        container vpn {
          description
            "VPN configuration";
          leaf id {
            description
              "VPN id value";
            type uint32 {
              range "1..4294967295";
            }
          }
        }
        container evpn {
          description
            "Ethernet Virtual Private Network (EVPN)";
          container ethernet-segment {
            description
              "Ethernet segment local discriminator value";
            leaf es-value {
              description
                "Ethernet segment local discriminator value";
              type uint16 {
                range "1..65535";
              }
            }
          }
        }
        leaf evc {
          description
            "EVC Name";
          type string {
            length "1..32";
          }
        }
        leaf mtu {
          description
            "set Maximum Transmission Unit";
          type uint16 {
            range "1500..9180";
          }
        }
        leaf shutdown {
          description
            "Shutdown VFI";
          type empty;
        }
        container status {
          description
            "Pseudowire status capabilities";
          leaf decoupled {
            description
              "Reflect standby status of the attachment circuit as up on the pseudowire";
            type empty;
          }
        }
        container forward {
          description
            "Specify forwarding of types of traffic";
          when '../vpn/id and (not(../autodiscovery/bgp/signaling/bgp) or not(../autodiscovery/bgp/signaling/ldp))';
          container permit {
            description
              "Permit specific traffic type";
            container l2protocol {
              description
                "L2 Protocol BPDUs";
              leaf all {
                description
                  "All types";
                type empty;
              }
            }
          }
        }
        container l2protocol {
          description
            "Configure l2 control protocol processing";
          container forward {
            description
              "forward L2 control protocol packets as data";
            leaf R4 {
              description
                "Reserved Protocol using DA Mac 0180 c200 0004";
              type empty;
            }
            leaf R5 {
              description
                "Reserved Protocol using DA Mac 0180 c200 0005";
              type empty;
            }
            leaf R6 {
              description
                "Reserved Protocol using DA Mac 0180 c200 0006";
              type empty;
            }
            leaf R8 {
              description
                "Reserved Protocol using DA Mac 0180 c200 0008";
              type empty;
            }
            leaf R9 {
              description
                "Reserved Protocol using DA Mac 0180 c200 0009";
              type empty;
            }
            leaf RA {
              description
                "Reserved Protocol using DA Mac 0180 c200 000a";
              type empty;
            }
            leaf RB {
              description
                "Reserved Protocol using DA Mac 0180 c200 000b";
              type empty;
            }
            leaf RC {
              description
                "Reserved Protocol using DA Mac 0180 c200 000c";
              type empty;
            }
            leaf RD {
              description
                "Reserved Protocol using DA Mac 0180 c200 000d";
              type empty;
            }
            leaf RF {
              description
                "Reserved Protocol using DA Mac 0180 c200 000f";
              type empty;
            }
            leaf cdp {
              description
                "Cisco Discovery Protocol";
              type empty;
            }
            leaf dot1x {
              description
                "Dot1x Protocol";
              type empty;
            }
            leaf dtp {
              description
                "Dynamic Trunking Protocol";
              type empty;
            }
            leaf elmi {
              description
                "ELMI Protocol";
              type empty;
            }
            leaf esmc {
              description
                "ESMC Protocol";
              type empty;
            }
            leaf lacp {
              description
                "LACP Protocol";
              type empty;
            }
            leaf lldp {
              description
                "Link Layer Discovery Protocol";
              type empty;
            }
            leaf pagp {
              description
                "Port Aggregation Protocol";
              type empty;
            }
            leaf ptppd {
              description
                "PTP Peer Delay Protocol";
              type empty;
            }
            leaf stp {
              description
                "Spanning Tree Protocol";
              type empty;
            }
            leaf udld {
              description
                "UDLD Protocol";
              type empty;
            }
            leaf vtp {
              description
                "Vlan Trunking Protocol";
              type empty;
            }
          }
        }
        container member {
          description
            "VFI member configuration";
          list ipv4 {
            key "ipv4";
            leaf ipv4 {
              description
                "IP address of the peer";
              type inet:ipv4-address;
            }
            list config-mem-vcid {
              key "mem-vcid";
              leaf mem-vcid {
                description
                  "Enter VC ID value";
                type uint32 {
                  range "1..4294967295";
                }
              }
              uses config-l2vpn-vfi-member-encapsulation-template;
            }
            uses config-l2vpn-vfi-member-encapsulation-template;
          }
          list pseudowire {
            description
              "Pseudowire interface";
            key "pseudowire-number";
            leaf pseudowire-number {
              type uint32 {
                range "1..100000";
              }
            }
            leaf ipv4 {
              description
                "IP address of the peer";
              type inet:ipv4-address;
            }
            leaf mem-vcid {
              description
                "Enter VC ID value";
              type uint32 {
                range "1..4294967295";
              }
            }
            uses config-l2vpn-vfi-member-encapsulation-template;
          }
        }
      }
    }
    container xconnect {
      description
        "Configure a cross connect";
      list context {
        description
          "Layer2 VPN Context";
        key "xc-name";
        leaf xc-name {
          description
            "Configure the cross connect name";
          type string;
        }
        container xc-Mode-config-xconnect {
          leaf description {
            description
              "Description string";
            type string;
          }
          container interworking {
            description
              "Interworking options for the cross connect";
            leaf ethernet {
              description
                "Ethernet interworking";
              type empty;
            }
            leaf ip {
              description
                "IP interworking";
              type empty;
            }
            leaf vlan {
              description
                "VLAN interworking";
              type empty;
            }
            leaf ipv6 {
              description
                "IPV6 interworking";
              type empty;
            }
          }
          container match {
            description
              "Set Xconnect packet matching criteria";
            container protocol {
              description
                "Protocol matching criterion";
              leaf ipv6 {
                description
                  "IPV6";
                type empty;
              }
            }
          }
          container member {
            description
              "Configure the cross connect member";
            list ipv4 {
              key "ipv4";
              leaf ipv4 {
                description
                  "IP address of the peer";
                type inet:ipv4-address;
              }
              list config-ipv4 {
                key "mem-vcid";
                leaf mem-vcid {
                  description
                    "Enter VC ID value";
                  type uint32 {
                    range "1..4294967295";
                  }
                }
                uses config-l2vpn-xconnect-member-encapsulation-template;
                uses config-l2vpn-xconnect-member-group-priority;
              }
              leaf mem-vcid {
                description
                  "Enter VC ID value";
                status obsolete;
                type uint32 {
                  range "1..4294967295";
                }
              }
            }
            list pseudowire {
              description
                "Pseudowire interface";
              key "pseudowire-number";
              leaf pseudowire-number {
                type uint32 {
                  range "1..100000";
                }
              }
              choice config-pseudowire {
                case config-pseudowire-peer {
                  container ipv4 {
                    leaf ipv4 {
                      description
                        "IP address of the peer";
                      type inet:ipv4-address;
                    }
                    leaf mem-vcid {
                      description
                        "Enter VC ID value";
                      type uint32 {
                        range "1..4294967295";
                      }
                    }
                    uses config-l2vpn-xconnect-member-encapsulation-template;
                    uses config-l2vpn-xconnect-member-group-priority;
                  }
                }
                case config-pseudowire-no-peer {
                  container pseudowire-group-priority {
                    uses config-l2vpn-xconnect-member-group-priority;
                  }
                }
              }
            }
            list interface {
              key "interface";
              leaf interface {
                description
                  "Interface name";
                type string;
              }
              choice config-interface {
                case config-interface-service-instance {
                  list service-instance-config {
                    description
                      "Ethernet Service Instance";
                    key "service-instance-id";
                    leaf service-instance-id {
                      description
                        "Service Instance ID";
                      type uint16 {
                        range "1..8000";
                      }
                    }
                    container circuit-type {
                      description
                        "Configure the circuit type";
                      leaf ethernet {
                        description
                          "Ethernet";
                        type empty;
                      }
                      uses config-l2vpn-xconnect-member-group-priority;
                    }
                    uses config-l2vpn-xconnect-member-group-priority;
                  }
                }
                case config-interface-no-service-instance {
                  uses config-l2vpn-xconnect-member-group-priority;
                }
              }
              leaf group {
                description
                  "Configure the cross connect member redundancy group";
                status obsolete;
                type empty;
              }
              leaf service-instance {
                description
                  "Ethernet Service Instance";
                status obsolete;
                type empty;
              }
            }
            leaf Vlan {
              description
                "Vlan interface number";
              status obsolete;
              type uint16 {
                range "1..4094";
              }
            }
          }
          container redundancy {
            description
              "Xconnect redundancy information";
            leaf delay {
              description
                "Enable delay";
              status obsolete;
              type uint8 {
                range "0..180";
              }
            }
            list delay-config {
              must '(delay and disable-delay) or (delay and never) or (not(delay) and not(disable-delay)) or (not(delay) and not(never))' {
                error-message "Please make sure to configure enable-delay along with disable-delay/never ";
              }
              key "group";
              leaf group {
                description
                  "Configure the cross connect member redundancy group";
                type string;
              }
              leaf delay {
                description
                  "Enable delay";
                type uint8 {
                  range "0..180";
                }
              }
              choice disable-delay-never {
                leaf disable-delay {
                  description
                    "Disable delay";
                  type uint8 {
                    range "0..180";
                  }
                }
                leaf never {
                  description
                    "Disallow disable";
                  type empty;
                }
              }
            }
            container predictive {
              description
                "Switch over to backup member without waiting for UP status";
              leaf disabled {
                description
                  "Disable predictive switchover capability for this xconnect";
                type empty;
              }
              leaf enabled {
                description
                  "Enable predictive switchover capability for this xconnect";
                type empty;
              }
            }
            container all-active {
              description
                "Switch packets over all redundant members";
              leaf replicate {
                description
                  "Transmit identical copies of each packet over all redundant members";
                type empty;
              }
            }
          }
          container remote {
            description
              "L2VPN remote peer configuration commands";
            container circuit {
              description
                "Remote peer circuit configuration";
              leaf id-config {
                description
                  "Remote peer circuit ID";
                type uint16 {
                  range "1..4095";
                }
              }
              leaf id {
                description
                  "Remote peer circuit ID";
                status obsolete;
                type empty;
              }
            }
            container link {
              description
                "Link information";
              container failure-v2 {
                description
                  "Failure information";
                leaf notification-boolean {
                  description
                    "Notify in case of remote link failure";
                  type boolean;
                  default "true";
                }
                leaf notification {
                  status obsolete;
                  description
                    "Notify in case of remote link failure
                     (OBSOLETE, use notification-boolean)";
                  type empty;
                }
              }
              leaf failure {
                description
                  "Failure information";
                status obsolete;
                type empty;
              }
            }
          }
          leaf shutdown {
            description
              "Shutdown Xconnect";
            type empty;
          }
        }
      }
    }
    container evpn_cont {
      uses config-l2vpn-evpn-main;
      uses config-l2vpn-evpn-profile;
      uses config-l2vpn-evpn-instance;
      uses config-evpn-ethernet-segment-global;
    }
    container sdwan-l2vpn {
      if-feature "ios-features:sdwan-l2vpn";
      uses config-l2vpn-sdwan-main;
      uses config-l2vpn-sdwan-instance;
    }
  }

  grouping config-l2vpn-config-grouping {
    container l2vpn {
      description
        "Layer2 VPN commands";
      presence "true";
      container logging {
        description
          "Configure logging flags";
        container pseudowire {
          description
            "pseudowire status transition logging";
          leaf status {
            description
              "pseudowire status up/down logging";
            type empty;
          }
        }
        leaf redundancy {
          description
            "xconnect redundancy events";
          type empty;
        }
        leaf vc-state {
          description
            "vc-state transition logging";
          type empty;
        }
      }
      container pseudowire {
        description
          "Configure l2vpn pseudowire parameters";
        container group {
          description
            "Configure pseudowire group parameters";
          leaf status {
            description
              "Send pseudowire group status messages";
            type empty;
          }
        }
        container pseudowire-routing {
          container routing {
            description
              "Configure l2vpn pseudowire routing";
            container switching-point {
              description
                "Configure a switching-point";
              container vcid {
                description
                  "Configure a switching-point vcid range";
                must '(vcid_min and vcid_max) or (not(vcid_min) and not(vcid_max))' {
                  error-message "vcid_min and vcid_max must be configured";
                }
                leaf vcid_min {
                  description
                    "Minimum VCID value";
                  type uint32 {
                    range "1..2147483647";
                  }
                }
                leaf vcid_max {
                  description
                    "Maximum VCID value";
                  type uint32 {
                    range "1..2147483647";
                  }
                }
              }
            }
            container terminating-pe {
              description
                "Configure a terminating-pe";
              leaf tie-breaker {
                description
                  "Configure a terminating-pe tiebreaker";
                type empty;
              }
            }
          }
        }
      }
      container redundancy {
        description
          "Configure L2VPN redundancy parameters";
        container predictive {
          description
            "Switch over to backup member without waiting for UP status";
          leaf enabled {
            description
              "Enable predictive switchover capability for all xconnects";
            type empty;
          }
        }
      }
      leaf router-id {
        description
          "Layer2 router-id value";
        type inet:ipv4-address;
      }
      leaf shutdown {
        description
          "Shutdown Layer2 VPN";
        type empty;
      }
    }
  }

  grouping config-xconnect-grouping {
    container logging {
      container pseudowire {
        leaf status {
          type empty;
        }
      }
      leaf redundancy {
        type empty;
      }
    }
  }

  grouping pseudowire-grouping {
    leaf encapsulation {
      description
        "Data encapsulation method";
      type enumeration {
        enum l2tpv2;
        enum l2tpv3;
        enum mpls;
        enum udp;
      }
    }
    container ip {
      description
        "Specify IP parameters";
      when "../encapsulation = 'l2tpv2' or ../encapsulation = 'l2tpv3'";
      container dfbit {
        description
          "DF bit options for tunnel";
        leaf set {
          description
            "Set the DF bit in the tunnel header";
          type empty;
        }
      }
      container local {
        description
          "Specify local information";
        container interface {
          description
            "Source interface for pseudowire";
          leaf interface-name {
            description
              "Source interface for pseudowire";
            type string;
          }
        }
      }
      container pmtu {
        description
          "Enable Path MTU for tunnel";
        presence "true";
        leaf max {
          description
            "Maximum Path MTU for session";
          type uint16 {
            range "68..65535";
          }
        }
      }
      leaf protocol {
        description
          "Specific IP protocol number to use";
        when "../../encapsulation = 'l2tpv3'";
        type enumeration {
          enum l2tp;
          enum uti;
        }
      }
      container tos {
        description
          "Specify ToS options for IP tunnel header";
        leaf reflect {
          description
            "Reflect IP payload ToS on tunnel";
          type empty;
        }
        leaf value {
          description
            "IP ToS value";
          type uint8;
        }
      }
      leaf ttl {
        description
          "Specify TTL value for IP tunnel header";
        type uint8;
      }
    }
    leaf control-word {
      description
        "Include control-word in pseudowire packets";
      when "../encapsulation = 'mpls'";
      type empty;
    }
    leaf interworking {
      description
        "Interworking options for pseudowire";
      type enumeration {
        enum ethernet;
        enum ip;
        enum vlan;
      }
    }
    container load-balance {
      description
        "Loadbalancing for pseudowire";
      when "../encapsulation = 'mpls'";
      container flow {
        description
          "Enable flow based load balancing for pseudowire";
        presence "true";
        leaf ethernet {
          description
            "Ethernet pseudowire flow classification";
          type enumeration {
            enum dst-mac;
            enum src-dst-mac;
            enum src-mac;
          }
        }
      }
    }
    container monitor {
      description
        "Active monitoring of xconnect peer";
      when "../encapsulation = 'mpls'";
      container peer {
        description
          "Active monitoring of xconnect peer";
        container bfd {
          description
            "BFD active monitoring for the xconnect peer";
          presence "true";
          container local {
            description
              "Specify local endpoint information to map to a BFD session";
            container interface {
              description
                "Source interface for pseudowire";
              uses ios-ifc:interface-grouping;
            }
          }
        }
      }
    }
    container preferred-path {
      description
        "Preferred path";
      container interface {
        description
          "Output Interface";
        choice Tunnel-Tunnel-tp {
          case Tunnel-case {
            leaf Tunnel {
              description
                "Tunnel interface";
              type uint64 {
                range "0..2147483647";
              }
            }
          }
          case Tunnel-tp-case {
            leaf Tunnel-tp {
              description
                "MPLS Transport Profile interface";
              type uint16;
            }
          }
        }
        leaf disable-fallback {
          description
            "disable fall back to alternative route";
          type empty;
        }
      }
      container peer-container {
        leaf peer {
          description
            "Peer Address";
          type union {
            type string;
            type inet:ipv4-address;
          }
        }
        leaf disable-fallback {
          description
            "disable fall back to alternative route";
          type empty;
        }
      }
    }
    container protocol-mpls {
      when "../encapsulation = 'mpls'";
      leaf protocol {
        description
          "Signaling protocol to use";
        type enumeration {
          enum ldp;
          enum none;
        }
      }
    }
    container protocol-l2tpv2 {
      when "../encapsulation = 'l2tpv2'";
      leaf protocol {
        description
          "Signaling protocol to use";
        type enumeration {
          enum l2tpv2;
          enum none;
        }
      }
      leaf class-name {
        description
          "l2tp-class name";
        type leafref {
          path "/ios:native/ios:l2tp-class/ios:name";
        }
      }
    }
    container protocol-l2tpv3 {
      when "../encapsulation = 'l2tpv3'";
      leaf protocol {
        description
          "Signaling protocol to use";
        type enumeration {
          enum l2tpv3;
          enum l2tpv3ietf;
          enum none;
        }
      }
      leaf class-name {
        description
          "l2tp-class name";
        when "../protocol = 'l2tpv3' or ../protocol = 'l2tpv3ietf'";
        type leafref {
          path "/ios:native/ios:l2tp-class/ios:name";
        }
      }
    }
    leaf sequencing {
      description
        "Sequencing options for pseudowire";
      when "../encapsulation = 'mpls' or ../encapsulation = 'l2tpv3'";
      type enumeration {
        enum both;
        enum receive;
        enum resync;
        enum transmit;
      }
    }
    container status {
      description
        "Pseudowire status capabilities";
      presence "true";
      container admin-down {
        description
          "Admin down of Attachment Circuit";
        when "../../encapsulation = 'l2tpv2' or ../../encapsulation = 'l2tpv3'";
        leaf disconnect {
          description
            "Disconnect the session";
          type empty;
        }
      }
      container control-plane {
        description
          "control plane status events";
        leaf route-watch-boolean {
          description
            "listen on the control plane to route-watch events";
          type boolean;
          default "true";
        }
        leaf route-watch {
          status obsolete;
          description
            "listen on the control plane to route-watch events
             (OBSOLETE, use route-watch-boolean)";
          type empty;
        }
      }
      leaf decoupled {
        description
          "Reflect standby status of the attachment circuit as up on the pseudowire";
        type empty;
      }
      container peer {
        description
          "peer status configuration";
        container topology {
          description
            "change status behaviour based on peer topology";
          leaf dual-homed {
            description
              "Our peer(s) are participating in a redundant solution with some form of redundancyprotocol running between the peer routers, Only one of the remote peers will advertise astatus of UP at a time. The other will advertise standby. Change our configuration so we can send a status of UP on both active and redundant pseudowires";
            type empty;
          }
        }
      }
      container redundancy {
        description
          "Xconnect redundancy configuration";
        leaf master {
          description
            "Put the xconnect redundancy group on this node in master mode";
          type empty;
        }
      }
    }
    container switching {
      description
        "Switching TLV on/off for pseudowire";
      when "../encapsulation = 'mpls'";
      leaf tlv-boolean {
        description
          "Switching TLV on/off for pseudowire";
        type boolean;
        default "true";
      }
      leaf tlv {
        status obsolete;
        description
          "Switching TLV on/off for pseudowire
           (OBSOLETE, use tlv-boolean)";
        type empty;
      }
    }
  }

  grouping config-pseudowire-class-grouping {
    uses pseudowire-grouping;
  }

  grouping config-evpn-ethernet-segment {
    container evpn {
      list ethernet-segment {
        description
          "Ethernet segment local discriminator value";
        key "es-value";
        leaf es-value {
          description
            "Ethernet segment local discriminator value";
          type uint16 {
            range "1..65535";
          }
        }
        container df-election {
          description
            "Designated forwarder election parameters";
          leaf wait-time {
            type uint8 {
              range "1..10";
            }
            default "3";
          }
        }
        container redundancy {
          description
            "Multi-homing redundancy parameters";
          choice redundancy-choice {
            leaf all-active {
              type empty;
            }
            leaf single-active {
              type empty;
            }
          }
        }
        leaf sytem-mac {
          description
            "System MAC address for generating the Ethernet Segment ID";
          type string;
        }
        container identifier {
          description
            "Ethernet Segment Identifier";
          list type {
            description
              "Ethernet Segment Identifier type";
            key "identifier-type";
            leaf identifier-type {
              type uint8 {
                range "0 | 3";
              }
            }
            choice esi-type-choice {
              leaf hex-string {
                when "../identifier-type = '0'";
                description
                  "H.H.H.H.H.H.H.H.H \t9-octet ESI value in hex";
                type string {
                  pattern '([0-9a-fA-F]{1,2}(.[0-9a-fA-F]{1,2}){8})';
                }
              }
              leaf system-mac {
                when "../identifier-type = '3'";
                description
                  "System MAC address for generating the ESI value";
                type ios-types:cisco-mac-address-type;
              }
            }
          }
        }
      }
    }
  }

  grouping config-evpn-ethernet-segment-with-auto {
    container evpn {
      choice ethernet-segment-choice {
        case evpn-num-case {
          container ethernet-segment-num {
            list ethernet-segment {
              description
                "Ethernet segment local discriminator value";
              key "es-value";
              leaf es-value {
                description
                  "Ethernet segment local discriminator value";
                type uint16 {
                  range "1..65535";
                }
              }
              container df-election {
                description
                  "Designated forwarder election parameters";
                leaf wait-time {
                  type uint8 {
                    range "1..10";
                  }
                  default "3";
                }
              }
              container redundancy {
                description
                  "Multi-homing redundancy parameters";
                choice redundancy-choice {
                  leaf all-active {
                    type empty;
                  }
                  leaf single-active {
                    type empty;
                  }
                }
              }
              leaf sytem-mac {
                description
                  "System MAC address for generating the Ethernet Segment ID";
                type string;
              }
              container identifier {
                description
                  "Ethernet Segment Identifier";
                list type {
                  description
                    "Ethernet Segment Identifier type";
                  key "identifier-type";
                  leaf identifier-type {
                    type uint8 {
                      range "0 | 3";
                    }
                  }
                  choice esi-type-choice {
                    leaf hex-string {
                      description
                        "H.H.H.H.H.H.H.H.H \t9-octet ESI value in hex";
                      when "../identifier-type = '0'";
                      type string {
                        pattern '([0-9a-fA-F]{1,2}(.[0-9a-fA-F]{1,2}){8})';
                      }
                    }
                    leaf system-mac {
                      description
                        "System MAC address for generating the ESI value";
                      when "../identifier-type = '3'";
                      type ios-types:cisco-mac-address-type;
                    }
                  }
                }
              }
            }
          }
        }
        case evpn-auto-case {
          container ethernet-segment-auto {
            container ethernet-segment {
              description
                "Ethernet segment local discriminator value";
              container auto {
                description
                  "Ethernet segment auto configuration";
                leaf lacp {
                  description
                    "All-active ethernet segment with type 1 ESI";
                  type empty;
                }
                container df-election {
                  description
                    "Designated forwarder election parameters";
                  must '../lacp';
                  leaf wait-time {
                    type uint8 {
                      range "1..10";
                    }
                    default "3";
                  }
                }
              }
            }
          }
        }
      }
      list ethernet-segment {
        status deprecated;
        description
          "Ethernet segment local discriminator value, DEPRECATED";
        key "es-value";
        leaf es-value {
          status deprecated;
          description
            "Ethernet segment local discriminator value, DEPRECATED";
          type uint16 {
            range "1..65535";
          }
        }
        container df-election {
          status deprecated;
          description
            "Designated forwarder election parameters, DEPRECATED";
          leaf wait-time {
            type uint8 {
              range "1..10";
            }
            default "3";
          }
        }
        container redundancy {
          status deprecated;
          description
            "Multi-homing redundancy parameters, DEPRECATED";
          choice redundancy-choice {
            leaf all-active {
              type empty;
            }
            leaf single-active {
              type empty;
            }
          }
        }
        leaf sytem-mac {
          status deprecated;
          description
            "System MAC address for generating the Ethernet Segment ID, DEPRECATED";
          type string;
        }
        container identifier {
          status deprecated;
          description
            "Ethernet Segment Identifier, DEPRECATED";
          list type {
            status deprecated;
            description
              "Ethernet Segment Identifier type, DEPRECATED";
            key "identifier-type";
            leaf identifier-type {
              status deprecated;
              type uint8 {
                range "0 | 3";
              }
            }
            choice esi-type-choice {
              leaf hex-string {
                status deprecated;
                description
                  "H.H.H.H.H.H.H.H.H \t9-octet ESI value in hex, DEPRECATED";
                when "../identifier-type = '0'";
                type string {
                  pattern '([0-9a-fA-F]{1,2}(.[0-9a-fA-F]{1,2}){8})';
                }
              }
              leaf system-mac {
                status deprecated;
                description
                  "System MAC address for generating the ESI value, DEPRECATED";
                when "../identifier-type = '3'";
                type ios-types:cisco-mac-address-type;
              }
            }
          }
        }
      }
    }
  }

  grouping l2tp-class-options {
    leaf authentication {
      description
        "Authenticate the L2TP control connection";
      type empty;
    }
    leaf hello {
      description
        "Set HELLO message interval";
      type uint16 {
        range "0..1000";
      }
      default "60";
    }
    container password {
      description
        "Password for control connection authentication, AVP hiding";
      leaf encryption {
        type enumeration {
          enum 0;
          enum 7;
        }
        default "0";
      }
      leaf password-string {
        description
          "Tunnel password string";
        type string {
          pattern '.*';
        }
      }
    }
    container cookie {
      description
        "Local cookie options";
      leaf size {
        description
          "Local cookie size";
        type uint8 {
          range "4 | 8";
        }
      }
    }
  }

  grouping config-connect-grouping {
    list connect {
      description
        "Configure local connect";
      key "name";
      leaf name {
        type string;
      }
      container connect-config {
        container source-interface {
          description
            "Configure the source interface";
          uses ios:interface-with-dependency-grouping;
          choice connect-interface-choice {
            case interface-without-service-instance {
              container destination-interface {
                uses ios:interface-with-dependency-grouping;
              }
            }
            case interface-with-service-instance {
              container source-service-instance-id {
                leaf service-instance-id {
                  description
                    "Service Instance ID";
                  type uint16 {
                    range "1..8000";
                  }
                }
                container destination-interface {
                  description
                    "Configure the Local connect Destination interface";
                  uses ios:interface-with-dependency-grouping;
                  leaf destination-service-instance-id {
                    description
                      "Service Instance ID";
                    type uint16 {
                      range "1..8000";
                    }
                    mandatory true;
                  }
                }
              }
            }
          }
        }
      }
      container connect-sub-commands {
        container description {
          leaf description {
            description
              "Local Connect description";
            type string {
              pattern '.*';
              length "0..255";
            }
          }
        }
      }
    }
  }

  augment "/ios:native/ios:interface/ios:pseudowire" {
    uses config-interface-pseudowire-grouping {
      if-feature "ios-features:l2vpn";
    }
  }

  augment "/ios:native/ios:interface/ios:FastEthernet" {
    uses config-interface-xconnect-grouping {
      if-feature "ios-features:l2vpn";
    }
  }

  augment "/ios:native/ios:interface/ios:GigabitEthernet" {
    uses config-interface-xconnect-grouping {
      if-feature "ios-features:l2vpn";
    }
  }

  augment "/ios:native/ios:interface/ios:TenGigabitEthernet" {
    uses config-interface-xconnect-grouping {
      if-feature "ios-features:l2vpn";
    }
  }

  augment "/ios:native/ios:interface/ios:FiveGigabitEthernet" {
    uses config-interface-xconnect-grouping {
      if-feature "ios-features:l2vpn";
    }
  }

  augment "/ios:native/ios:interface/ios:AppGigabitEthernet" {
    uses config-interface-xconnect-grouping {
      if-feature "ios-features:l2vpn";
    }
  }

  augment "/ios:native/ios:interface/ios:TwentyFiveGigE" {
    uses config-interface-xconnect-grouping {
      if-feature "ios-features:l2vpn";
    }
  }

  augment "/ios:native/ios:interface/ios:TwoGigabitEthernet" {
    uses config-interface-xconnect-grouping {
      if-feature "ios-features:l2vpn";
    }
  }

  augment "/ios:native/ios:interface/ios:FortyGigabitEthernet" {
    uses config-interface-xconnect-grouping {
      if-feature "ios-features:l2vpn";
    }
  }

  augment "/ios:native/ios:interface/ios:HundredGigE" {
    uses config-interface-xconnect-grouping {
      if-feature "ios-features:l2vpn";
    }
  }

  augment "/ios:native/ios:interface/ios:Port-channel" {
    uses config-interface-xconnect-grouping {
      if-feature "ios-features:l2vpn";
    }
  }

  augment "/ios:native/ios:interface/ios:Vlan" {
    uses config-interface-xconnect-grouping {
      if-feature "ios-features:l2vpn";
    }
  }

  augment "/ios:native/ios:interface/ios:Cellular" {
    uses config-interface-xconnect-grouping {
      if-feature "ios-features:l2vpn";
    }
  }

  augment "/ios:native/ios:interface/ios:FastEthernet/ios-eth:service/ios-eth:instance" {
    uses config-interface-efp-xconnect-grouping {
      if-feature "ios-features:efp";
    }
  }

  augment "/ios:native/ios:interface/ios:GigabitEthernet/ios-eth:service/ios-eth:instance" {
    uses config-interface-efp-xconnect-grouping {
      if-feature "ios-features:efp";
    }
  }

  augment "/ios:native/ios:interface/ios:TenGigabitEthernet/ios-eth:service/ios-eth:instance" {
    uses config-interface-efp-xconnect-grouping {
      if-feature "ios-features:efp";
    }
  }

  augment "/ios:native/ios:interface/ios:FiveGigabitEthernet/ios-eth:service/ios-eth:instance" {
    uses config-interface-efp-xconnect-grouping {
      if-feature "ios-features:efp";
    }
  }

  augment "/ios:native/ios:interface/ios:AppGigabitEthernet/ios-eth:service/ios-eth:instance" {
    uses config-interface-efp-xconnect-grouping {
      if-feature "ios-features:efp";
    }
  }

  augment "/ios:native/ios:interface/ios:TwentyFiveGigE/ios-eth:service/ios-eth:instance" {
    uses config-interface-efp-xconnect-grouping {
      if-feature "ios-features:efp";
    }
  }

  augment "/ios:native/ios:interface/ios:TwoGigabitEthernet/ios-eth:service/ios-eth:instance" {
    uses config-interface-efp-xconnect-grouping {
      if-feature "ios-features:efp";
    }
  }

  augment "/ios:native/ios:interface/ios:FortyGigabitEthernet/ios-eth:service/ios-eth:instance" {
    uses config-interface-efp-xconnect-grouping {
      if-feature "ios-features:efp";
    }
  }

  augment "/ios:native/ios:interface/ios:HundredGigE/ios-eth:service/ios-eth:instance" {
    uses config-interface-efp-xconnect-grouping {
      if-feature "ios-features:efp";
    }
  }

  augment "/ios:native/ios:interface/ios:Port-channel/ios-eth:service/ios-eth:instance" {
    uses config-interface-efp-xconnect-grouping {
      if-feature "ios-features:efp";
    }
  }

  augment "/ios:native/ios:interface/ios:Virtual-PPP" {
    uses config-interface-virtual-ppp-pseudo-grouping {
      if-feature "ios-features:l2vpn";
    }
  }

  augment "/ios:native/ios:interface/ios:FastEthernet" {
    uses config-evpn-ethernet-segment;
  }

  augment "/ios:native/ios:interface/ios:GigabitEthernet" {
    uses config-evpn-ethernet-segment;
  }

  augment "/ios:native/ios:interface/ios:TenGigabitEthernet" {
    uses config-evpn-ethernet-segment;
  }

  augment "/ios:native/ios:interface/ios:FiveGigabitEthernet" {
    uses config-evpn-ethernet-segment;
  }

  augment "/ios:native/ios:interface/ios:AppGigabitEthernet" {
    uses config-evpn-ethernet-segment;
  }

  augment "/ios:native/ios:interface/ios:TwentyFiveGigE" {
    uses config-evpn-ethernet-segment;
  }

  augment "/ios:native/ios:interface/ios:TwoGigabitEthernet" {
    uses config-evpn-ethernet-segment;
  }

  augment "/ios:native/ios:interface/ios:FortyGigabitEthernet" {
    uses config-evpn-ethernet-segment;
  }

  augment "/ios:native/ios:interface/ios:HundredGigE" {
    uses config-evpn-ethernet-segment;
  }

  augment "/ios:native/ios:interface/ios:Port-channel" {
    uses config-evpn-ethernet-segment-with-auto;
  }

  augment "/ios:native/ios:l2" {
    uses config-l2-grouping {
      if-feature "ios-features:l2";
    }
  }

  augment "/ios:native/ios:l2vpn" {
    uses config-l2vpn-grouping {
      if-feature "ios-features:l2vpn";
    }
  }

  augment "/ios:native/ios:l2vpn-config" {
    uses config-l2vpn-config-grouping {
      if-feature "ios-features:l2vpn";
    }
  }

  augment "/ios:native/ios:xconnect" {
    uses config-xconnect-grouping {
      if-feature "ios-features:l2vpn";
    }
  }

  augment "/ios:native/ios:pseudowire-class" {
    uses config-pseudowire-class-grouping {
      if-feature "ios-features:l2vpn";
    }
  }

  augment "/ios:native/ios:l2tp-class" {
    uses l2tp-class-options {
      if-feature "ios-features:l2vpn";
    }
  }

  augment "/ios:native/ios:l2vpn-config" {
    uses config-connect-grouping {
      if-feature "ios-features:l2vpn";
    }
  }
}
