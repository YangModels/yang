module Cisco-IOS-XE-mdns-gateway {
  yang-version 1.1;
  namespace "http://cisco.com/ns/yang/Cisco-IOS-XE-mdns-gateway";
  prefix ios-mdns;

  import cisco-semver {
    prefix cisco-semver;
  }
  import ietf-inet-types {
    prefix inet;
  }
  import Cisco-IOS-XE-native {
    prefix ios;
  }
  import Cisco-IOS-XE-interface-common {
    prefix ios-ifc;
  }
  import Cisco-IOS-XE-features {
    prefix ios-features;
  }
  import Cisco-IOS-XE-vlan {
    prefix ios-vlan;
  }
  import Cisco-IOS-XE-switch {
    prefix ios-sw;
  }
  import Cisco-IOS-XE-types {
    prefix ios-types;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native MDNS Gateway Yang Model.
     Copyright (c) 2018-2020 by Cisco Systems, Inc.
     All rights reserved.";

  revision 2024-07-01 {
    description
      "- Added yang support for query threshold
       - Added default value for statistics and service-cache";
    cisco-semver:module-version "5.3.0";
  }
  revision 2023-11-01 {
    description
      "- Added yang support for remote cache CLIs";
    cisco-semver:module-version "5.2.0";
  }
  revision 2022-11-01 {
    description
      "- Update yang-version to 1.1";
    cisco-semver:module-version "5.1.0";
  }
  revision 2022-07-01 {
    description
      "- Added yang support for service receive purge and query response models
       - Added default support for active response timer
       - Added support for cli service-record-ttl
       - Added support for location under global mdns gateway for wireless";
    cisco-semver:module-version "5.0.0";
  }
  revision 2022-03-01 {
    description
      "- Added yang support for wired service-policy for mDNS flex profiles";
    cisco-semver:module-version "4.2.0";
  }
  revision 2021-11-01 {
    description
      "- Initial revision for 17.7.1
       - Added yang support for service-zone feature
       - Added yang support for controller service-policy feature
       - Added source-interface support under OUT service-list";
    cisco-semver:module-version "4.1.0";
  }
  revision 2021-07-01 {
    description
      "- Split service counts and timers into switch and wireless groupings
       - Added yang support for BCP ipv6 support
       - Added yang support for match all in mdns-sd service-list
       - Changed active-query time to minutes in global and under vlan configuration
       - Added yang support service-mdns-query in global mdns-sd gateway";
    cisco-semver:module-version "4.0.0";
  }
  revision 2021-03-01 {
    description
      "- Added config restrictions for MDNS sd switch ethernet interfaces";
    cisco-semver:module-version "3.0.0";
  }
  revision 2020-11-01 {
    description
      "- Added must restrictions for mode service-peer";
    cisco-semver:module-version "2.0.0";
  }
  revision 2020-07-01 {
    description
      "- Added Yang support for 13 mDNS CLIs (BGP-EVPN)
       - Marked two nodes as obsolete
       - Added support for flex-profile CLI
       - Added 9991 as default port for controller-port
       - Added Yang support for micro location
       - Prepend switchport-config to switchport";
    cisco-semver:module-version "1.2.0";
  }
  revision 2019-11-01 {
    description
      "- Added Yang support for all mDNS CLIs
       - Added regex config";
    cisco-semver:module-version "1.1.0";
  }
  revision 2019-07-01 {
    description
      "Establish semantic version baseline";
    cisco-semver:module-version "1.0.0";
  }
  revision 2018-11-29 {
    description
      "Corrected service-definition description
       and added additional checks in service-list";
  }
  revision 2018-11-07 {
    description
      "Cleanup spelling errors in description statements";
  }
  revision 2018-07-07 {
    description
      "Initial revision";
  }

  grouping mdns-sd-gateway-common-global-grouping {
    leaf sdg-agent {
      description
        "Configure Service Discovery Gateway agent IPv4 address";
      type union {
        type inet:ipv4-address;
        type inet:ipv6-address;
      }
    }
    container source-interface {
      description
        "Configure source interface to communicate with Service Discovery Gateway agent";
      uses ios-ifc:interface-grouping;
    }
    container any-query {
      description
        "Any Query configurations.";
      leaf forward {
        description
          "Enable any query forward to service discovery gateway
           agent.";
        type empty;
      }
    }
    container active-response {
      description
        "Active-response configurations";
      leaf timer {
        description
          "Configure timer for cache active response timer";
        type uint16 {
          range "5..60";
        }
        default "15";
      }
    }
    container mode {
      description
        "To select mode for mdns-sd gateway";
      status obsolete;
      choice mode-type {
        status obsolete;
        leaf service-peer {
          status obsolete;
          description
            "To enable mdns gateway in service-peer mode";
          must "(../../service-announcement-count='50') and
                (../../service-announcement-timer/periodicity='30') and
                (../../service-query-count='50') and
                (../../service-query-timer/periodicity='15')" {
            error-message "Service counts and timers should be set to default";
          }
          type empty;
        }
        leaf sdg-agent {
          status obsolete;
          description
            "To enable mdns gateway in service discovery gateway agent mode";
          if-feature "ios-features:mdns-switch";
          type empty;
        }
      }
    }
    leaf service-announcement-count {
      status obsolete;
      description
        "Maximum Advertisements";
      must "((../mode/service-peer) and (current() <=
            (../service-announcement-timer/periodicity * 20))) or
            (not(../mode/service-peer))";
      type uint16 {
        range "10..500";
      }
      default "50";
    }
    container service-announcement-timer {
      status obsolete;
      description
        "Advertisement announcement timer periodicity in seconds";
      leaf periodicity {
        status obsolete;
        must "((../../mode/service-peer) and (../../service-announcement-count <=
              (current() * 20))) or
              (not(../../mode/service-peer))";
        type uint16 {
          range "5..36000";
        }
        default "30";
      }
    }
    leaf service-query-count {
      status obsolete;
      description
        "Maximum Queries";
      must "((../mode/service-peer) and (current() <=
            (../service-query-timer/periodicity * 20))) or
            (not(../mode/service-peer))";
      type uint16 {
        range "10..500";
      }
      default "50";
    }
    container service-query-timer {
      status obsolete;
      description
        "Query Forward timer periodicity";
      leaf periodicity {
        status obsolete;
        must "((../../mode/service-peer) and (../../service-query-count <=
              (current() * 20))) or
              (not(../../mode/service-peer))";
        type uint16 {
          range "5..36000";
        }
        default "15";
      }
    }
    leaf service-mdns-query {
      description
        "mDNS Query request message processing";
      type enumeration {
        enum all;
        enum ptr;
      }
      default "ptr";
    }
    container active-query-global {
      description
        "mDNS Global Active Query";
      leaf timer {
        description
          "Active Query Periodicity in Minutes";
        type uint16 {
          range "1..120";
        }
        default "30";
      }
    }
    leaf service-record-ttl {
      description
        "Select mode for setting Service Record TTL";
      type enumeration {
        enum enhanced;
        enum original;
      }
      default "enhanced";
    }
    container service-receiver-purge {
      description
        "mDNS service-receiver-purge timer configuration";
      leaf timer {
        description
          "Specify the timer value";
        type uint16 {
          range "30..4500";
        }
        default "120";
      }
    }
    container query-response {
      description
        "mDNS Query Response mode";
      leaf mode {
        description
          "query-response mode";
        must "(not ((current() = 'on-demand') and (../../active-response/timer!=15)))" {
          error-message
            "%Error: active-response timer is not applicable in on-demand mode.
             Please remove active-response timer (‘no active-response timer’) before changing to on-demand mode.";
        }
        type enumeration {
          enum recurring;
          enum on-demand;
        }
        default "recurring";
      }
      leaf threshold {
        description
          "Threshold count for MDNS query-response handling.";
        type uint16 {
          range "5..250";
        }
        default "30";
        units "number of responses";
      }
    }
    leaf remote-cache-enable {
      if-feature "ios-features:mdns-switch";
      description
        "Cache the remote responses from controller";
      type boolean;
      default "true";
    }
    leaf remote-cache-max-limit {
      if-feature "ios-features:mdns-switch";
      description
        "Max entries for the remote cache response DB";
      type uint16 {
        range "100..3000";
      }
      default "1000";
    }
    leaf remote-cache-purge-timer {
      if-feature "ios-features:mdns-switch";
      description
        "Purge timer for the remote cache response DB";
      type uint16 {
        range "30..3600";
      }
      default "300";
    }
  }

  grouping mdns-sd-service-policy-ewlc-grouping {
    leaf location {
      description
        "mDNS Location Based Filtering";
      type enumeration {
        enum lss;
        enum site-tag;
        enum ssid;
        enum ap-name;
        enum ap-location;
        enum regex;
        enum location-group;
      }
    }
    leaf regex-which {
      description
        "Regex based location filter";
      when "../location='regex'";
      type enumeration {
        enum ap-name;
        enum ap-location;
      }
    }
    leaf regex-str {
      description
        "Regex string for location filter";
      when "(../location='regex') and (../regex-which)";
      type string {
        length "1..164";
      }
    }
  }

  grouping mdns-sd-gateway-ewlc-global-grouping {
    container mode-wireless {
      description
        "To select mode for mdns-sd gateway on wireless";
      leaf mode {
        description
          "To enable mdns gateway in service-peer mode";
        type enumeration {
          enum service-peer;
        }
      }
    }
    container srv-ct-wireless {
      description
        "To set service count and timer values for wireless";
      leaf service-announcement-count {
        description
          "Maximum Advertisements";
        must "((../../mode-wireless/mode='service-peer') and (current() <= (../service-announcement-timer/periodicity * 20))) or
              (not(../../mode-wireless/mode='service-peer'))" {
          error-message "%Error: The count and timer should be within range in mode service-peer (count <= timer*20)";
        }
        type uint16 {
          range "10..500";
        }
        default "50";
      }
      container service-announcement-timer {
        leaf periodicity {
          must "((../../../mode-wireless/mode='service-peer') and (../../service-announcement-count <= (current() * 20))) or
                (not(../../../mode-wireless/mode='service-peer'))" {
            error-message "%Error: The count and timer should be within range in mode service-peer (count <= timer*20)";
          }
          type uint16 {
            range "5..36000";
          }
          default "30";
        }
      }
      leaf service-query-count {
        description
          "Maximum Queries";
        must "((../../mode-wireless/mode='service-peer') and (current() <= (../service-query-timer/periodicity * 20))) or
              (not(../../mode-wireless/mode='service-peer'))" {
          error-message "%Error: The count and timer should be within range in mode service-peer (count <= timer*20)";
        }
        type uint16 {
          range "10..500";
        }
        default "50";
      }
      container service-query-timer {
        leaf periodicity {
          must "((../../../mode-wireless/mode='service-peer') and (../../service-query-count <= (current() * 20))) or
                (not(../../../mode-wireless/mode='service-peer'))" {
            error-message "%Error: The count and timer should be within range in mode service-peer (count <= timer*20)";
          }
          type uint16 {
            range "5..36000";
          }
          default "15";
        }
      }
    }
    container active-query {
      status obsolete;
      description
        "mDNS Global Active Query";
      leaf timer {
        status obsolete;
        description
          "Active Query Periodicity in Minutes";
        type uint16 {
          range "15..120";
        }
        default "30";
      }
    }
    container mdns-ap-service-policy {
      description
        "mDNS service policy for mDNS-AP";
      leaf sp-name {
        description
          "mdns service policy name for mdns AP";
        type leafref {
          path "/ios:native/ios-mdns:mdns-sd/ios-mdns:service-policy/ios-mdns:service-policy-name";
        }
      }
    }
    leaf transport {
      description
        "mDNS message processing on a specific transport";
      type enumeration {
        enum both;
        enum ipv4;
        enum ipv6;
      }
      default "ipv4";
    }
    container wireless-global-location {
      description
        "global gateway location config";
      uses mdns-sd-service-policy-ewlc-grouping {
        refine "location" {
          default "lss";
        }
      }
    }
  }

  grouping mdns-sd-gateway-switch-global-grouping {
    container mode-switch {
      description
        "To select mode for mdns-sd gateway on switch";
      leaf mode {
        description
          "To enable mode for mdns-sd gateway";
        type enumeration {
          enum service-peer;
          enum sdg-agent;
        }
        default "sdg-agent";
      }
    }
    container srv-ct-switch {
      description
        "To set service count and timer values for switch";
      leaf service-announcement-count {
        description
          "Maximum Advertisements";
        must "((../../mode-switch/mode='service-peer') and (current() <= (../service-announcement-timer/periodicity * 20))) or
              (not(../../mode-switch/mode='service-peer'))" {
          error-message "%Error: The count and timer should be within range in mode service-peer (count <= timer*20)";
        }
        type uint16 {
          range "10..500";
        }
        default "50";
      }
      container service-announcement-timer {
        leaf periodicity {
          must "((../../../mode-switch/mode='service-peer') and (../../service-announcement-count <= (current() * 20))) or
                (not(../../../mode-switch/mode='service-peer'))" {
            error-message "%Error: The count and timer should be within range in mode service-peer (count <= timer*20)";
          }
          type uint16 {
            range "5..36000";
          }
          default "30";
        }
      }
      leaf service-query-count {
        description
          "Maximum Queries";
        must "((../../mode-switch/mode='service-peer') and (current() <= (../service-query-timer/periodicity * 20))) or
              (not(../../mode-switch/mode='service-peer'))" {
          error-message "%Error: The count and timer should be within range in mode service-peer (count <= timer*20)";
        }
        type uint16 {
          range "10..500";
        }
        default "50";
      }
      container service-query-timer {
        leaf periodicity {
          must "((../../../mode-switch/mode='service-peer') and (../../service-query-count <= (current() * 20))) or
                (not(../../../mode-switch/mode='service-peer'))" {
            error-message "%Error: The count and timer should be within range in mode service-peer (count <= timer*20)";
          }
          type uint16 {
            range "5..36000";
          }
          default "15";
        }
      }
    }
    leaf air-print-helper {
      description
        "Enable or Disable Air Print Helper functionality";
      type enumeration {
        enum enable;
        enum disable;
      }
      default "disable";
    }
    leaf cache-memory-max {
      description
        "Configure the percentage memory for cache";
      type uint16 {
        range "10..100";
      }
    }
    container ingress-client {
      description
        "Ingress Client Packet Tuners";
      container query-reply {
        description
          "query reply count";
        when '/ios:native/ios-mdns:service-export/ios-mdns:mdns-sd/ios-mdns:controller';
        leaf service-count {
          description
            "service count for a query at once";
          type uint16 {
            range "10..200";
          }
        }
      }
      container query-suppression {
        description
          "Ingress Query Suppression";
        leaf enable {
          description
            "Enable Ingress Query Suppression";
          type empty;
        }
        leaf packet-gap {
          description
            "Response frequency for a query";
          type uint16 {
            range "5..60";
          }
        }
      }
    }
    leaf rate-limit {
      description
        "Enable rate limiting of incoming mDNS packets";
      type uint16 {
        range "1..1000";
      }
    }
    container service-type-enumeration {
      leaf period {
        description
          "Service Enumeration period in minutes";
        type uint16 {
          range "15..60";
        }
      }
    }
    container cache-sync {
      description
        "To send cache-sync event towards mDNS service-peer";
      leaf timer {
        description
          "Specify timer value";
        type uint16 {
          range "15..600";
        }
        units "minutes";
      }
    }
  }

  grouping mdns-sd-ewlc-global-grouping {
    container location-filter-wireless {
      list location-filter {
        key "loc-fil-name";
        leaf loc-fil-name {
          description
            "mDNS Location Filter Name";
          type string;
          must "not(.='default-mdns-location-filter')" {
            error-message "Error: Can't config/unconfig location-filter with name 'default-mdns-location-filter'";
          }
        }
        container match {
          presence "true";
          list location-group {
            key "lg-id";
            leaf lg-id {
              must '../role/roles or ../role/none or ../role/all';
              type union {
                type enumeration {
                  enum default;
                  enum all;
                }
                type uint16 {
                  range "1..4096";
                }
              }
            }
            container role {
              description
                "Specify role for location-group to filter";
              leaf-list roles {
                must 'not(../all)';
                type string {
                  length "1..164";
                }
              }
              leaf none {
                must 'not(../all)';
                type empty;
              }
              leaf all {
                must 'not(../roles) and not(../none)';
                type empty;
              }
            }
          }
        }
      }
    }
    list flex-profile {
      description
        "mdns-sd flex-profile configuration";
      key "name";
      leaf name {
        description
          "mDNS Flex profile name";
        type string;
      }
      container update-timer {
        description
          "mDNS Update timers for flex profile";
        leaf service-cache {
          description
            "mDNS service cache update timer";
          type uint16 {
            range "1..100";
          }
          default "1";
        }
        leaf statistics {
          description
            "mDNS statistics update timer";
          type uint16 {
            range "1..100";
          }
          default "1";
        }
      }
      leaf-list wired-vlan-range {
        description
          "mDNS Flex profile wired vlan filter range";
        max-elements 16;
        type uint16 {
          range "1..4094";
        }
      }
      leaf wired-service-policy {
        description
          "mDNS Flex profile wired service policy";
        must '/ios:native/ios-mdns:mdns-sd/ios-mdns:service-policy[ios-mdns:service-policy-name=current()]' {
          error-message "%Error: service-policy does not exist";
        }
        type string {
          length "1..164";
        }
      }
    }
    list wired-filter {
      key "wired-filter-name";
      leaf wired-filter-name {
        description
          "mDNS Wired Filter Name";
        type string;
      }
      container match {
        leaf-list mac {
          description
            "mDNS Service provider MAC address";
          type ios-types:cisco-mac-address-type;
        }
        leaf-list vlan {
          description
            "mDNS vlan number or vlan range, example: 1,3-5,7,9-11";
          type uint16 {
            range "1..4094";
          }
        }
      }
    }
  }

  grouping mdns-sd-switch-global-grouping {
    container service-peer-conf {
      description
        "mDNS service-peer command";
      container service-peer {
        when "(../../gateway/mode-switch/mode='sdg-agent')";
        container group {
          description
            "mDNS service-peer group command";
          list peer-group {
            description
              "Service peer group ID number";
            key "id";
            leaf id {
              type uint16 {
                range "1..1000";
              }
            }
            list service-peer {
              key "ip";
              leaf ip {
                type union {
                  type inet:ipv4-address;
                  type inet:ipv6-address;
                  type string;
                }
              }
              container location-group-obsolete {
                status obsolete;
                leaf location-group-number {
                  status obsolete;
                  must 'not(../all)';
                  type uint16 {
                    range "1..4096";
                  }
                }
                leaf all {
                  status obsolete;
                  must 'not(../location-group-number)';
                  type empty;
                }
                leaf default {
                  status obsolete;
                  type empty;
                }
              }
              list location-group {
                key "lg-num";
                leaf lg-num {
                  must '../role/roles or ../role/none or ../role/all';
                  type union {
                    type enumeration {
                      enum default;
                      enum all;
                    }
                    type uint16 {
                      range "1..4096";
                    }
                  }
                }
                container role {
                  description
                    "Specify user role";
                  leaf-list roles {
                    must 'not(../all)';
                    type string {
                      length "1..164";
                    }
                  }
                  leaf none {
                    must 'not(../all)';
                    type empty;
                  }
                  leaf all {
                    must 'not(../roles) and not(../none)';
                    type empty;
                  }
                }
              }
            }
            list service-policy {
              description
                "mDNS service policy";
              key "policy-name";
              leaf policy-name {
                must '/ios:native/ios-mdns:mdns-sd/ios-mdns:service-policy[ios-mdns:service-policy-name=current()]' {
                  error-message "% service-policy does not exist";
                }
                type string;
              }
            }
          }
        }
      }
    }
    container service-peer {
      status obsolete;
      description
        "This node is obsolete and replaced by service-peer-conf";
      list group {
        status obsolete;
        key "service-peer-grp-name";
        leaf service-peer-grp-name {
          status obsolete;
          type string;
        }
        list service-peer-grp-id {
          status obsolete;
          key "id";
          leaf id {
            status obsolete;
            type uint16 {
              range "1..1000";
            }
          }
          list service-peer {
            status obsolete;
            key "ip";
            leaf ip {
              status obsolete;
              type union {
                type inet:ipv4-address;
                type string;
              }
            }
            container service-group {
              status obsolete;
              leaf-list service-group-number {
                status obsolete;
                must 'not(../all)';
                type union {
                  type enumeration {
                    enum default;
                  }
                  type uint16 {
                    range "1..64";
                  }
                }
              }
              leaf all {
                status obsolete;
                must 'not(../service-group-number)';
                type empty;
              }
            }
          }
        }
      }
    }
    list location-group {
      description
        "Configure mDNS location group";
      key "location-grp-id";
      leaf location-grp-id {
        description
          "Enter location group number";
        type uint16 {
          range "1..4096";
        }
      }
      list vlan {
        description
          "enter vlan number";
        key "vlan-id";
        leaf vlan-id {
          description
            "vlan id";
          must '(/ios:native/ios:vlan/ios-vlan:configuration-entry[ios-vlan:vlan-id=current()]/ios-mdns:mdns-sd/ios-mdns:gateway)' {
            error-message "Snooping must be enabled for the vlan";
          }
          type uint16 {
            range "1..4096";
          }
        }
        leaf description {
          description
            "Location Group description";
          type string;
        }
        container interface {
          description
            "Add interfaces to location-group";
          uses ios-ifc:interface-grouping;
        }
      }
    }
    list location-filter {
      key "loc-fil-name";
      leaf loc-fil-name {
        description
          "mDNS Location Filter Name";
        type string;
        must "not(.='default-mdns-location-filter')" {
          error-message "Error: Can't config/unconfig location-filter with name 'default-mdns-location-filter'";
        }
      }
      container match {
        presence "true";
        container loc_grp_configured {
          status obsolete;
          leaf location-group {
            status obsolete;
            type leafref {
              path "/ios:native/ios-mdns:mdns-sd/ios-mdns:location-group/ios-mdns:location-grp-id";
            }
          }
          leaf vlan {
            status obsolete;
            type leafref {
              path "/ios:native/ios-mdns:mdns-sd/ios-mdns:location-group[ios-mdns:location-grp-id = current()/../location-group]/ios-mdns:vlan/ios-mdns:vlan-id";
            }
          }
        }
        container loc_grp_all {
          status obsolete;
          leaf location-group {
            status obsolete;
            type empty;
          }
          leaf all {
            status obsolete;
            type empty;
          }
          leaf vlan {
            status obsolete;
            must 'not(/ios:native/ios-mdns:mdns-sd/ios-mdns:location-filter/ios-mdns:match/ios-mdns:loc_grp_configured/ios-mdns:vlan = current() or /ios:native/ios-mdns:mdns-sd/ios-mdns:location-filter/ios-mdns:match/ios-mdns:loc_grp_default/ios-mdns:vlan = current())' {
              error-message "%Error: location-group 'all' is allowed only if none of the location-groups are configured for the vlan";
            }
            type uint16 {
              range "1..4096";
            }
          }
        }
        container loc_grp_default {
          status obsolete;
          leaf location-group {
            status obsolete;
            type empty;
          }
          leaf default {
            status obsolete;
            type empty;
          }
          leaf vlan {
            status obsolete;
            must 'not(/ios:native/ios-mdns:mdns-sd/ios-mdns:location-filter/ios-mdns:match/ios-mdns:loc_grp_all/ios-mdns:vlan = current())' {
              error-message "%Error: location-group 'all' is already configured, cannot configure location-group";
            }
            type uint16 {
              range "1..4096";
            }
          }
        }
        list location-group {
          key "lg-id";
          leaf lg-id {
            must "(current() = 'default' or current() = 'all' or
                     (/ios:native/ios-mdns:mdns-sd/ios-mdns:location-group[ios-mdns:location-grp-id = current()]))";
            type union {
              type enumeration {
                enum default;
                enum all;
              }
              type uint16 {
                range "1..4096";
              }
            }
          }
          list vlan {
            key "vlan-id";
            leaf vlan-id {
              must '../role/roles or ../role/none or ../role/all';
              must "(current()/../../lg-id = 'default') or
                      (current()/../../lg-id = 'all') or
                      (/ios:native/ios-mdns:mdns-sd/ios-mdns:location-group[ios-mdns:location-grp-id = current()/../../lg-id]/ios-mdns:vlan/ios-mdns:vlan-id) = current()";
              must "((current()/../../lg-id = 'default') or
                       (/ios:native/ios-mdns:mdns-sd/ios-mdns:location-group[ios-mdns:location-grp-id = current()/../../lg-id]/ios-mdns:vlan/ios-mdns:vlan-id) = current()) and
                       (not (/ios:native/ios-mdns:mdns-sd/ios-mdns:location-filter[ios-mdns:loc-fil-name = current()/../../../../loc-fil-name]/ios-mdns:match/ios-mdns:location-group[ios-mdns:lg-id = 'all'] and
                       /ios:native/ios-mdns:mdns-sd/ios-mdns:location-filter[ios-mdns:loc-fil-name = current()/../../../../loc-fil-name]/ios-mdns:match/ios-mdns:location-group[ios-mdns:lg-id = 'all']/ios-mdns:vlan[ios-mdns:vlan-id = current()])) or
                    current()/../../lg-id = 'all'";
              type uint16 {
                range "1..4096";
              }
            }
            container role {
              description
                "Specify role for location-group to filter";
              leaf-list roles {
                must 'not(../all)';
                type string {
                  length "1..164";
                }
              }
              leaf none {
                must 'not(../all)';
                type empty;
              }
              leaf all {
                must 'not(../roles) and not(../none)';
                type empty;
              }
            }
          }
        }
      }
    }
    list service-group {
      description
        "Configure mDNS service group";
      key "service-group-number";
      leaf service-group-number {
        description
          "Enter service group number";
        type uint8 {
          range "1..64";
        }
      }
      list vlan {
        description
          "vlan number";
        max-elements 1;
        key "vlan";
        leaf vlan {
          description
            "vlan id";
          must '(/ios:native/ios:vlan/ios-vlan:configuration-entry[ios-vlan:vlan-id=current()]/ios-mdns:mdns-sd/ios-mdns:gateway)' {
            error-message "Snooping must be enabled for the vlan";
          }
          type uint16 {
            range "1..4096";
          }
        }
        container interface {
          description
            "Add interfaces to service-group";
          uses ios-ifc:interface-grouping;
        }
      }
    }
    container controller {
      description
        "mDNS controller config";
      list service-policy {
        description
          "controller service policy";
        key "name";
        leaf name {
          description
            "controller service-policy name";
          must "not(.='default-mdns-ctrl-srv-policy')" {
            error-message "Error: Can't config/unconfig ctrl service-policy with name 'default-mdns-ctrl-srv-policy'";
          }
          type string {
            length "1..164";
          }
        }
        leaf service-list {
          description
            "mDNS controller service list";
          type leafref {
            path "/ios:native/ios-mdns:mdns-sd/ios-mdns:controller/ios-mdns:service-list/ios-mdns:name";
          }
        }
      }
      list service-list {
        description
          "controller service list";
        key "name";
        leaf name {
          description
            "controller service list name";
          must "not(.='default-mdns-ctrl-srv-list')" {
            error-message "Error: Can't config/unconfig ctrl service-list with name 'default-mdns-ctrl-srv-list'";
          }
          type string {
            length "1..164";
          }
        }
        container match {
          description
            "Specify service to match";
          list match-other {
            description
              "Specify service to match";
            key "name";
            leaf name {
              description
                "mDNS Service Definition Name";
              type string {
                length "1..164";
              }
              must "not(.='all')" {
                error-message "Error: please use container 'match-all' to configure 'match all'";
              }
            }
            leaf message-type {
              description
                "To set the message type";
              type enumeration {
                enum any;
                enum announcement;
                enum query;
              }
              default "any";
              must "(not((../../match-all/all) and ((../../match-all/message-type='any') or (../../match-all/message-type=.))))" {
                error-message "%Error: Service-list already has match entries hence 'match all' not allowed";
              }
            }
            leaf-list source-interface {
              description
                "Specify source Vlans for services";
              type uint16 {
                range "1..4094";
              }
            }
          }
          container match-all {
            description
              "Specify service to match";
            leaf all {
              description
                "mDNS Service Definition Name";
              type empty;
            }
            leaf message-type {
              description
                "To set the message type";
              type enumeration {
                enum any;
                enum announcement;
                enum query;
              }
              default "any";
              when '../all';
              must "(not((../../match-other/message-type='any') or (../../match-other/message-type=.)))" {
                error-message "%Error: Service-list in already has 'match all' configured";
              }
            }
            leaf-list source-interface {
              description
                "Specify source Vlans for services";
              type uint16 {
                range "1..4094";
              }
            }
          }
        }
      }
    }
  }

  grouping mdns-sd-common-global-grouping {
    container gateway {
      description
        "mDNS Gateway Configuration";
      presence "true";
      uses mdns-sd-gateway-switch-global-grouping {
        if-feature "ios-features:mdns-switch";
      }
      uses mdns-sd-gateway-ewlc-global-grouping {
        if-feature "ios-features:mdns-ewlc";
      }
      uses mdns-sd-gateway-common-global-grouping;
    }
    list service-policy {
      description
        "mDNS Service Policy";
      key "service-policy-name";
      leaf service-policy-name {
        description
          "mDNS Service Policy Name";
        type string {
          length "1..164";
        }
        must "not(.='default-mdns-service-policy')" {
          error-message "Error: Can't config/unconfig service-policy with name 'default-mdns-service-policy'";
        }
      }
      uses mdns-sd-service-policy-ewlc-grouping {
        if-feature "ios-features:mdns-ewlc";
      }
      container service-list-config {
        description
          "mDNS Service List";
        list in {
          description
            "IN Bound Filtering";
          key "service-list-name IN";
          leaf service-list-name {
            description
              "mDNS Service List Name";
            type leafref {
              path "/ios:native/ios-mdns:mdns-sd/ios-mdns:service-list-config/ios-mdns:in/ios-mdns:service-list-name";
            }
          }
          leaf IN {
            type leafref {
              path "/ios:native/ios-mdns:mdns-sd/ios-mdns:service-list-config/ios-mdns:in/ios-mdns:IN";
            }
          }
        }
        list out {
          description
            "OUT Bound Filtering";
          key "service-list-name OUT";
          leaf service-list-name {
            type leafref {
              path "/ios:native/ios-mdns:mdns-sd/ios-mdns:service-list-config/ios-mdns:out/ios-mdns:service-list-name";
            }
          }
          leaf OUT {
            type leafref {
              path "/ios:native/ios-mdns:mdns-sd/ios-mdns:service-list-config/ios-mdns:out/ios-mdns:OUT";
            }
          }
        }
      }
      list service-list {
        status obsolete;
        key "name";
        leaf name {
          status obsolete;
          description
            "mDNS Service List Name";
          type leafref {
            path "/ios:native/ios-mdns:mdns-sd/service-list/service-list-name";
          }
        }
        leaf direction {
          status obsolete;
          description
            "Select Service List Direction IN/OUT";
          type enumeration {
            enum IN;
            enum OUT;
          }
        }
      }
    }
    container service-list-config {
      description
        "mDNS Service List";
      list in {
        description
          "IN Bound Filtering";
        key "service-list-name IN";
        leaf service-list-name {
          description
            "mDNS Service List Name";
          type string {
            length "1..164";
          }
          must "not(.='default-mdns-in-service-list')" {
            error-message "%Error: Can't config/unconfig service-list with name 'default-mdns-in-service-list'";
          }
          must 'not((../../out[service-list-name=current()]))' {
            error-message "%Error: service-list exists with OUT direction";
          }
        }
        leaf IN {
          type enumeration {
            enum IN;
          }
        }
        container match {
          description
            "Specify service to match";
          list match-other {
            description
              "Specify service to match";
            key "name";
            leaf name {
              description
                "mDNS Service Definition Name";
              type string {
                length "1..164";
              }
              must "not(.='all')" {
                error-message "Error: please use container 'match-all' to configure 'match all'";
              }
            }
            leaf message-type {
              description
                "To set the message type";
              type enumeration {
                enum any;
                enum announcement;
                enum query;
              }
              default "any";
              must "(not((../../match-all/all) and ((../../match-all/message-type='any') or (../../match-all/message-type=.))))" {
                error-message "%Error: Service-list already has match entries hence 'match all' not allowed";
              }
            }
          }
          container match-all {
            description
              "Specify service to match";
            leaf all {
              description
                "mDNS Service Definition Name";
              type empty;
            }
            leaf message-type {
              description
                "To set the message type";
              type enumeration {
                enum any;
                enum announcement;
                enum query;
              }
              default "any";
              when '../all';
              must "(not((../../match-other/message-type='any') or (../../match-other/message-type=.)))" {
                error-message "%Error: Service-list in already has 'match all' configured";
              }
            }
          }
        }
      }
      list out {
        description
          "OUT Bound Filtering";
        key "service-list-name OUT";
        leaf service-list-name {
          description
            "mDNS Service List Name";
          type string {
            length "1..164";
          }
          must "not(.='default-mdns-out-service-list')" {
            error-message "%Error: Can't config/unconfig service-list with name 'default-mdns-out-service-list'";
          }
          must 'not((../../in[service-list-name=current()]))' {
            error-message "%Error: service-list exists with IN direction";
          }
        }
        leaf OUT {
          type enumeration {
            enum OUT;
          }
        }
        container match {
          description
            "Specify service to match";
          list match-other {
            description
              "Specify service to match";
            key "name";
            leaf name {
              description
                "mDNS Service Definition Name";
              type string {
                length "1..164";
              }
              must "not(.='all')" {
                error-message "Error: Please use the conatiner 'match-all' to configure 'match all'";
              }
              must 'not((../../match-all/all))' {
                error-message "%Error: Service-list out already has match entries or has 'match all' configured";
              }
            }
            leaf location-filter {
              if-feature "ios-features:mdns-switch";
              description
                "Specify location-filter for Switch";
              must '(/ios:native/ios-mdns:mdns-sd/ios-mdns:location-filter[ios-mdns:loc-fil-name=current()])' {
                error-message "%Error: location filter does not exist";
              }
              type string;
            }
            leaf location-filter-wireless {
              if-feature "ios-features:mdns-ewlc";
              description
                "Specify location-filter for Wireless Controller";
              must '(/ios:native/ios-mdns:mdns-sd/ios-mdns:location-filter-wireless/ios-mdns:location-filter[ios-mdns:loc-fil-name=current()])' {
                error-message "%Error: location filter does not exist";
              }
              type string;
            }
            leaf wired-filter {
              if-feature "ios-features:mdns-ewlc";
              description
                "Specify wired-filter name";
              must '(/ios:native/ios-mdns:mdns-sd/ios-mdns:wired-filter[ios-mdns:wired-filter-name=current()])' {
                error-message "%Error: wired filter does not exist";
              }
              type string;
            }
            leaf-list source-interface {
              if-feature "ios-features:mdns-switch";
              description
                "Specify source Vlans for services";
              type uint16 {
                range "1..4094";
              }
            }
          }
          container match-all {
            description
              "Specify service to match";
            leaf all {
              description
                "mDNS Service Definition Name";
              type empty;
              must '(not(../../match-other/name))' {
                error-message "%Error: Service-list out already has match entries or has 'match all' configured";
              }
            }
            leaf location-filter {
              if-feature "ios-features:mdns-switch";
              description
                "Specify location-filter for Switch";
              must '(/ios:native/ios-mdns:mdns-sd/ios-mdns:location-filter[ios-mdns:loc-fil-name=current()])' {
                error-message "%Error: location filter does not exist";
              }
              type string;
            }
            leaf location-filter-wireless {
              if-feature "ios-features:mdns-ewlc";
              description
                "Specify location-filter for Wireless Controller";
              must '(/ios:native/ios-mdns:mdns-sd/ios-mdns:location-filter-wireless/ios-mdns:location-filter[ios-mdns:loc-fil-name=current()])' {
                error-message "%Error: location filter does not exist";
              }
              type string;
            }
            leaf wired-filter {
              if-feature "ios-features:mdns-ewlc";
              description
                "Specify wired-filter name";
              must '(/ios:native/ios-mdns:mdns-sd/ios-mdns:wired-filter[ios-mdns:wired-filter-name=current()])' {
                error-message "%Error: wired filter does not exist";
              }
              type string;
            }
            leaf-list source-interface {
              if-feature "ios-features:mdns-switch";
              description
                "Specify source Vlans for services";
              type uint16 {
                range "1..4094";
              }
            }
          }
        }
      }
    }
    list service-list {
      status obsolete;
      description
        "mDNS Service List";
      key "service-list-name";
      leaf service-list-name {
        status obsolete;
        description
          "mDNS Service List Name";
        type string {
          length "1..164";
        }
      }
      list direction {
        description
          "Direction IN/OUT for mDNS service-list";
        status obsolete;
        max-elements 1;
        key "dir";
        leaf dir {
          status obsolete;
          description
            "Select direction IN/OUT";
          type enumeration {
            enum IN;
            enum OUT;
          }
        }
        container IN {
          must "../dir = 'IN'" {
            error-message "Configuration allowed for IN direction";
          }
          description
            "IN Bound Filtering";
          status obsolete;
          presence "true";
          list match {
            status obsolete;
            description
              "Specify service to match";
            key "name";
            leaf name {
              status obsolete;
              description
                "mDNS Service Definition Name";
              type string {
                length "1..164";
              }
            }
            leaf message-type {
              status obsolete;
              description
                "To set the message type";
              type enumeration {
                enum any;
                enum announcement;
                enum query;
              }
              default "any";
            }
          }
        }
        container OUT {
          must "../dir = 'OUT'" {
            error-message "Configuration allowed for OUT direction";
          }
          description
            "Out Bound Filtering";
          status obsolete;
          presence "true";
          list match {
            description
              "Specify service to match";
            status obsolete;
            key "name";
            leaf name {
              status obsolete;
              type string {
                length "1..164";
              }
            }
            leaf location-filter {
              status obsolete;
              if-feature "ios-features:mdns-switch";
              description
                "Specify location-filter";
              must '/ios:native/ios-mdns:mdns-sd/ios-mdns:location-filter[ios-mdns:loc-fil-name=current()]' {
                error-message "% location filter does not exist";
              }
              type string;
            }
          }
        }
      }
    }
    list service-definition {
      description
        "mDNS Service Definition";
      key "name";
      leaf name {
        description
          "mDNS Service Definition Name";
        type string {
          length "1..164";
        }
      }
      leaf description {
        description
          "Description of the Custom Service";
        type string {
          length "1..164";
        }
      }
      list service-type {
        key "service-type-name";
        leaf service-type-name {
          description
            "Specify Service-Type String";
          type string {
            length "1..164";
          }
        }
      }
    }
  }

  grouping config-mdns-sd-grouping {
    container mdns-sd {
      description
        "Configure mDNS Service Discovery";
      uses mdns-sd-common-global-grouping;
      uses mdns-sd-switch-global-grouping {
        if-feature "ios-features:mdns-switch";
      }
      uses mdns-sd-ewlc-global-grouping {
        if-feature "ios-features:mdns-ewlc";
      }
    }
  }

  grouping service-export-grouping {
    container service-export {
      description
        "service export";
      container mdns-sd {
        description
          "Controller MDNS configuration";
        list controller {
          description
            "Controller name";
          max-elements 1;
          key "controller-name";
          leaf controller-name {
            type string {
              length "1..164";
            }
          }
          leaf controller-address {
            description
              "Controller Address";
            type union {
              type inet:ipv4-address;
              type inet:ipv6-address;
            }
          }
          leaf controller-port {
            description
              "Controller port where service need to be exported";
            type uint16 {
              range "1..65535";
            }
            default "9991";
          }
          container controller-service-policy {
            description
              "Configure Filter to export";
            leaf csp_name {
              type string {
                length "1..164";
              }
            }
            leaf OUT {
              type empty;
            }
          }
          container controller-source-interface {
            description
              "Configure Source interface to export services";
            uses ios-ifc:interface-grouping;
          }
          leaf global-service-buffer {
            description
              "Global service instance buffer from Controller";
            type enumeration {
              enum disable;
              enum enable;
            }
            default "enable";
          }
        }
      }
    }
  }

  grouping mdns-sd-gateway-common-intf-vlan-grouping {
    container service-policy {
      description
        "mDNS Service Policy";
      leaf name {
        description
          "mDNS Service Policy Name";
        type leafref {
          path "/ios:native/ios-mdns:mdns-sd/ios-mdns:service-policy/ios-mdns:service-policy-name";
        }
      }
    }
  }

  grouping mdns-sd-gateway-switch-common-intf-grouping {
    status obsolete;
    container active-query {
      status obsolete;
      description
        "mDNS Active Query on interface";
      leaf timer {
        status obsolete;
        description
          "Active Query Periodicity in Sec";
        type uint16 {
          range "60..3600";
        }
        default "1800";
      }
    }
    leaf transport {
      description
        "mDNS message processing on a specific transport";
      status obsolete;
      type enumeration {
        enum both;
        enum ipv4;
        enum ipv6;
      }
      default "both";
    }
    leaf service-inst-suffix {
      status obsolete;
      description
        "Configure Service Instance Suffix to append";
      type string {
        length "0..10";
      }
    }
    leaf service-mdns-query {
      status obsolete;
      description
        "mDNS Query request message processing";
      type enumeration {
        enum all;
        enum ptr;
      }
      default "ptr";
    }
  }

  grouping mdns-sd-gateway-switch-intf-vlan-grouping {
    uses mdns-sd-gateway-switch-common-intf-grouping {
      status obsolete;
    }
    container active-query-intf {
      description
        "mDNS Active Query on interface";
      leaf timer {
        description
          "Active Query Periodicity in Sec";
        type uint16 {
          range "60..3600";
        }
      }
    }
    leaf transport-intf {
      description
        "mDNS message processing on a specific transport";
      type enumeration {
        enum both;
        enum ipv4;
        enum ipv6;
      }
      default "both";
    }
    leaf service-inst-suffix-intf {
      description
        "Configure Service Instance Suffix to append";
      type string {
        length "1..10";
      }
    }
    leaf service-mdns-query-intf {
      description
        "mDNS Query request message processing";
      type enumeration {
        enum all;
        enum ptr;
      }
      default "ptr";
    }
  }

  grouping mdns-sd-gateway-intf-vlan-grouping {
    container mdns-sd {
      description
        "mDNS Service Discovery configuration under interface vlan";
      container gateway {
        description
          "mDNS Gateway configuration under interface vlan";
        presence "true";
        uses mdns-sd-gateway-common-intf-vlan-grouping;
        uses mdns-sd-gateway-switch-intf-vlan-grouping {
          if-feature "ios-features:mdns-switch";
        }
      }
    }
  }

  grouping mdns-sd-switch-vlan-config-grouping {
    uses mdns-sd-gateway-common-intf-vlan-grouping;
    uses mdns-sd-gateway-switch-common-intf-grouping {
      status obsolete;
    }
    container source-interface {
      description
        "Configure source interface to communicate with Service Discovery Gateway agent";
      uses ios-ifc:interface-grouping;
    }
    leaf sdg-agent {
      description
        "Configure Service Discovery Gateway agent IPv4/IPv6 address";
      type union {
        type inet:ipv4-address;
        type inet:ipv6-address;
      }
    }
    container service-peer {
      status obsolete;
      description
        "Configure service-peer group";
      leaf group {
        status obsolete;
        description
          "Configure service-peer group name";
        type leafref {
          path "/ios:native/ios-mdns:mdns-sd/ios-mdns:service-peer/ios-mdns:group/ios-mdns:service-peer-grp-name";
        }
      }
    }
    container active-query-vlan {
      description
        "mDNS Active Query on VLAN";
      leaf timer {
        description
          "Active Query Periodicity in Minutes";
        type uint16 {
          range "1..120";
        }
      }
    }
    leaf transport-vlan {
      description
        "mDNS message processing on a specific transport";
      type enumeration {
        enum both;
        enum ipv4;
        enum ipv6;
      }
      default "ipv4";
    }
    leaf service-inst-suffix-vlan {
      description
        "Configure Service Instance Suffix to append";
      type string {
        length "1..10";
      }
    }
    leaf service-mdns-query-vlan {
      description
        "mDNS Query request message processing";
      type enumeration {
        enum all;
        enum ptr;
      }
    }
  }

  grouping mdns-sd-vlan-config-grouping {
    container mdns-sd {
      description
        "mDNS config on vlan config";
      container gateway {
        description
          "Enable mDNS gateway on interface";
        presence "true";
        uses mdns-sd-switch-vlan-config-grouping {
          if-feature "ios-features:mdns-switch";
        }
      }
    }
  }

  grouping mdns-sd-switch-eth-intf-grouping {
    container mdns-sd {
      description
        "mDNS commands";
      presence "true";
      leaf trust {
        description
          "Trust config for not including trunk port in any service-group";
        must '../../ios:switchport-config/ios:switchport/ios-sw:mode/ios-sw:trunk' {
          error-message "Error: Not a trunk port, trust config is not allowed";
        }
        type empty;
      }
    }
  }

  augment "/ios:native" {
    uses config-mdns-sd-grouping;
    uses service-export-grouping {
      if-feature "ios-features:mdns-switch";
    }
  }

  augment "/ios:native/ios:interface/ios:Vlan" {
    uses mdns-sd-gateway-intf-vlan-grouping {
      if-feature "ios-features:vlan";
    }
  }

  augment "/ios:native/ios:vlan/ios-vlan:configuration-entry" {
    uses mdns-sd-vlan-config-grouping;
  }

  augment "/ios:native/ios:interface/ios:GigabitEthernet" {
    uses mdns-sd-switch-eth-intf-grouping {
      if-feature "ios-features:mdns-switch";
    }
  }

  augment "/ios:native/ios:interface/ios:FastEthernet" {
    uses mdns-sd-switch-eth-intf-grouping {
      if-feature "ios-features:mdns-switch";
    }
  }

  augment "/ios:native/ios:interface/ios:TwoGigabitEthernet" {
    uses mdns-sd-switch-eth-intf-grouping {
      if-feature "ios-features:mdns-switch";
    }
  }

  augment "/ios:native/ios:interface/ios:FiveGigabitEthernet" {
    uses mdns-sd-switch-eth-intf-grouping {
      if-feature "ios-features:mdns-switch";
    }
  }

  augment "/ios:native/ios:interface/ios:AppGigabitEthernet" {
    uses mdns-sd-switch-eth-intf-grouping {
      if-feature "ios-features:mdns-switch";
    }
  }

  augment "/ios:native/ios:interface/ios:TenGigabitEthernet" {
    uses mdns-sd-switch-eth-intf-grouping {
      if-feature "ios-features:mdns-switch";
    }
  }

  augment "/ios:native/ios:interface/ios:TwentyFiveGigE" {
    uses mdns-sd-switch-eth-intf-grouping {
      if-feature "ios-features:mdns-switch";
    }
  }

  augment "/ios:native/ios:interface/ios:FortyGigabitEthernet" {
    uses mdns-sd-switch-eth-intf-grouping {
      if-feature "ios-features:mdns-switch";
    }
  }

  augment "/ios:native/ios:interface/ios:HundredGigE" {
    uses mdns-sd-switch-eth-intf-grouping {
      if-feature "ios-features:mdns-switch";
    }
  }
}
