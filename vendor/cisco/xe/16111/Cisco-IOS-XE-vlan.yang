module Cisco-IOS-XE-vlan {
  namespace "http://cisco.com/ns/yang/Cisco-IOS-XE-vlan";
  prefix ios-vlan;

  import ietf-inet-types {
    prefix inet;
  }


  import Cisco-IOS-XE-native {
    prefix ios;
  }

  import Cisco-IOS-XE-vtp {
    prefix ios-vtp;
  }

  import Cisco-IOS-XE-service-routing {
    prefix ios-sr;
  }

  import Cisco-IOS-XE-flow {
    prefix ios-flow;
  }

  import Cisco-IOS-XE-features {
    prefix ios-features;
  }

  import Cisco-IOS-XE-types {
    prefix ios-types;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Virtual LANs (VLAN) Yang Model.
     Copyright (c) 2016-2018 by Cisco Systems, Inc.
     All rights reserved.";

  // =========================================================================
  // REVISION
  // =========================================================================
  revision 2018-11-07 {
      description
      "Cleanup spelling errors in description statements";
  }
  revision 2018-10-27 {
    description
      "Remove type string for vlan id";
  }

  revision 2018-04-23 {
    description
      "Delete the extra call to interface-common-grouping";
  }

  revision 2018-03-13 {
    description
      "Add support for Evpn";
  }
  
  revision 2017-10-02 {
    description
      "Add support for 'ipv6 nd suppress' and 'vlan group *'";
  }

  revision 2017-05-31 {
    description
      "Add vtp-version and vlan name dependency, and service-routing dependency support";
  }

  revision 2017-04-13 {
    description
      "Add service-routing/redistribute support";
  }

  revision 2017-02-07 {
    description
      "Initial revision";
  }



  // interface Vlan *
  grouping config-interface-vlan-grouping {
    // interface vlan / private-vlan
    container private-vlan {
      if-feature ios-features:private-vlan;  
      description
        "Configure private VLAN SVI interface settings";
      leaf mapping {
        description
          "Set the private VLAN SVI interface mapping";
          type string;
      }
    }

    container service-routing {
      description
        "Service Routing in Interface Mode";
      container mdns-sd {
        description
          "Service-Routing mdns-sd configuration in interface mode";
        presence true;
        container redistribute {
          description
            "Redistribution of services";
          leaf mdns-sd {
            description
              "Redistribution of services";
            type empty;
          }
          leaf withdraw-only {
            description
              "Enable redistribution only for service withdraw";   
            type empty;
          }
        }
      }
    }

    container glbp {
      description "Gateway Load Balancing Protocol interface commands";
      list  range {
        key "range";
        leaf range {
          description "Group number";
          type uint16 {
            range "0..1023";
          }
        }
        container forwarder {
          description "Forwarder configuration";
          container preempt {
            description "Overthrow lower priority active forwarders";
            presence true;
            container delay {
              description "Wait before preempting";
              leaf minimum {
                description "Number of seconds for minimum delay";
                type uint16 {
                  range "0..3600";
                }
              }
            }
          }
        }
        container ip {
          description "Enable group and set virtual IP address";
          presence true;
          list ipv4 {
            key "ipv4";
            leaf ipv4 {
              description "Virtual IP address";
              type inet:ipv4-address;
            }
          }
        }
        container preempt {
          description "Overthrow lower priority designated routers";
          presence true;
          container delay {
            description "Wait before preempting";
            leaf minimum {
              description "Number of seconds for minimum delay";
              type uint16 {
                range "0..3600";
              }
            }
          }
        }
        leaf priority {
          description "Priority value";
          type uint8 {
            range "1..255";
          }
        }
        container weighting {
          description "Gateway weighting and tracking";
          list value {
            description "Weighting maximum value";
            key value;
            leaf value {
              type int8;
            }
            leaf upper{
              type int8;
            }
            leaf lower{
              type int8;
            }
          }
          container track {
            description "Interface tracking";
            list  range {
              key "range";
              leaf range {
                description "Tracked object";
                type uint16 {
                  range "1..1000";
                }
              }
              leaf decrement {
                description "Decrement value";
                type uint8 {
                  range "1..255";
                }
              }
            }
          }
        }
        container timers {
          description "Adjust GLBP timers";
          container msec {
            description "Specify hello interval in milliseconds";
            list  range {
              key "range";
              leaf range {
                description "Hello interval in milliseconds";
                type uint16 {
                  range "50..60000";
                }
              }
              leaf range0 {
                description "Hold time in seconds";
                type uint8 {
                  range "1..180";
                }
              }
            }
          }
        }
        leaf name {
          description
            "Redundancy name";
          type string;
        }
      }
    }
  }

  grouping config-vlan-grouping {
    list access-map {
      description "Create vlan access-map or enter vlan access-map command mode";
      key "name";
      leaf name {
          type string;
      }
      leaf value {
        type uint16{
          range "1..65535";
        }
      }
      leaf action {
        description
          "Take the action";
        type enumeration {
          enum "drop";
          enum "forward";
        }
      }
      container match {
        description
          "Match values.";
        container ipv6 {
          description
            "IPv6 based match";
          leaf-list address {
            type string;
          }
        }
        container ip {
          description
            "IP based match";
          leaf-list address {
            type string;
          }
        }
      }
    }
    list configuration {
      description "vlan feature configuration mode";
      key "vlan-id";
      leaf vlan-id {
        description "VLAN ID List Eg. 1-10,15";
        type union {
          type uint16 {
            range "1..4096";
          }
          type string;
        }
      }
      container ip {
        description "ip root chain";
        container flow {
          description "vlan NetFlow configuration commands";
          list monitor {
            description "Apply a Flow Monitor";
            key flow-monitor;
            leaf flow-monitor{
              description "User defined";
              type string;
            }
            leaf input {
              type empty;
            }
            leaf output {
              type empty;
            }
          }
        }
      }
      container ipv6 {
        description "Configure ipv6 dhcp guard";
        container nd {
          description 
            "IPv6 nd configuration commands";
          container suppress {
            description
              "Configure ND suppress on the vlan";
            presence true;
            leaf attach-policy {
              description 
                "Apply a policy for feature ND suppress";
              type string;
            }
          }
        }
        container dhcp {
          description "dhcp feature";
          container guard {
            description "Configure IPv6 DHCP guard for vlan configuration";
            presence true;
            leaf attach-policy {
              description "Apply a policy for feature DHCP Guard";
              type string;
            }
          }
        }
      }
      container member {
        container evpn-instance {
          description
            "Ethernet Virtual Private Network (EVPN)";      
          leaf evpn-instance  {
            type uint16 {
              range "1..65535";
            }
          }
          leaf vni {
            description "VxLAN VNI value";
            type uint32 {
              range "4096..16777215";
            }
          }
       }
       leaf vni {
         description "VxLAN VNI value";
         type uint32 {
           range "4096..16777215";
         }
       }
     }
    }
    list filter {
      description "Apply a VLAN Map";
      key "word";
      leaf word {
        type string;
      }
      leaf vlan-list {
        description "VLANs to apply filter to";
        type union {
          type uint16 {
            range "1..4094";
          }
          type string;
        }
      }
    }
    container accounting {
      description
        "VLAN accounting configuration";
      presence "true";
      leaf input {
        description
          "Input accounting";
        type empty;
      }
      leaf output {
        description
          "Output accounting";
        type empty;
      }
    }
    container internal {
      description
        "internal VLAN";
      container allocation {
        description
          "internal VLAN allocation";
        leaf policy {
          type enumeration {
            enum "ascending";
            enum "descending";
          }
        }
      }
    }
    container dot1q {
      description
        "dot1q parameters";
      container tag {
        description
          "tag parameters";
        leaf native {
          description
            "tag native vlan";
          type empty;
        }
      }
    }
    container access-log {
      description
        "Configure VACL logging";
      leaf maxflow {
        description
          "Set vacl logging maximum flow number";
        type uint16 {
          range "0..2048";
        }
      }
      leaf ratelimit {
        description
          "Set vacl logging rate limiter";
        type uint16 {
          range "10..5000";
        }
      }
      leaf threshold {
        description
          "Set vacl log-update threshold";
        type uint32 {
          range "0..2147483647";
        }
      }
    }
    list group {
      description 
        "Create a vlan group";
      key "name";
      leaf name {
        description
          "Group name starts with alphabet";
        type string;
      }
      list vlan-list {
        description
          "List of vlans in this group";
        key "vlan-id";
        leaf vlan-id {
          description
            "a single VLAN id (allowed value range 1-4094)" +
            "or Comma-separated VLAN id range." +
            "e.g. 99 or 1-30 or  1-20,30,40-50";
          type union {
            type uint16 {
              range "1..4094";
            }
            type ios-types:range-string;
          }
        }   
      }
    }  
    list vlan-list {
      key "id";
      leaf id {
        description
          "a single VLAN id (allowed value range 1-4094)" +
          "or Comma-separated VLAN id range." +
          "e.g. 99 or 1-30 or  1-20,30,40-50";
        type uint16 {
          range "1..4094";
        }
      }
      leaf remote-span {
        description
          "Configure as Remote SPAN VLAN";
        type empty;
      }
      container private-vlan {
        if-feature ios-features:private-vlan;
        description
          "Configure a private VLAN";
        leaf primary {
          description
            "Configure the VLAN as a primary private VLAN";
          type empty;
        }
        leaf association {
          description
            "Configure association between private VLANs";
          type string;
        }
        leaf community {
        description
          "Configure the VLAN as a community private VLAN";
        type empty;
        }
        leaf isolated {
          description
            "Configure the VLAN as an isolated private VLAN";
          type empty;
        }
      }
      leaf name {
        description
          "Ascii name of the VLAN";
        
        type string {
          length "1..128";
        }
        must "/ios:native/ios:vtp/ios-vtp:version = 3 or string-length(.) <= 32";
      }
      leaf state {
        description
          "Operational state of the VLAN";
        type enumeration {
          enum "active";
          enum "suspend";
        }
      }
      container lldp {
        leaf run {
          type empty;
        }
      }
      leaf uni-vlan {
        description
          "Configure a UNI VLAN";
        type enumeration {
          enum "community";
          enum "isolated";
        }
      }
    }
  }

  /////////////////////////////////////////////////////////
  // native / vlan
  /////////////////////////////////////////////////////////
  augment "/ios:native/ios:vlan" {
    uses config-vlan-grouping;
  }

  /////////////////////////////////////////////////////////
  // native / interface / Vlan
  /////////////////////////////////////////////////////////
  augment "/ios:native/ios:interface/ios:Vlan" {
    uses config-interface-vlan-grouping {
      if-feature ios-features:vlan;
    }
  }
}
