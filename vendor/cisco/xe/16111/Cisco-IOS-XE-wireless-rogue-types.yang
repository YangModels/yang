module Cisco-IOS-XE-wireless-rogue-types {
  yang-version 1;
  namespace "http://cisco.com/ns/yang/Cisco-IOS-XE-wireless-rogue-types";
  prefix wireless-rogue-types;

  import Cisco-IOS-XE-wireless-enum-types {
    prefix wireless-enum-types;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for wireless rogue data types.
     Copyright (c) 2016-2018 by Cisco Systems, Inc.
     All rights reserved.";

  revision 2018-10-29 {
    description
      "- validation for class type custom
       - Cleaned up spelling errors in descriptions.";
    reference "5.0.0";
  }
  revision 2018-05-18 {
    description
      "Added validation";
    reference "4.0.0";
  }
  revision 2018-03-22 {
    description
      "Add encryption indicator and new defaults";
    reference "3.0.0";
  }
  revision 2018-01-24 {
    description
      "The first generally available version";
    reference "2.0.0";
  }
  revision 2017-05-05 {
    description
      "Initial revision";
    reference "1.0.0";
  }

  grouping st-rule-data-cfg {
    description
      "Rogue rule types for Config";
    leaf class-type {
      type wireless-enum-types:rogue-class-type;
      must "(../enable = 'false') or (../class-type = 'rogue-classtype-friendly' and (../state = 'rogue-state-trusted' or ../state = 'rogue-state-alert' or ../state = 'rogue-state-acknowledged')) or (../class-type = 'rogue-classtype-malicious' and (../state = 'rogue-state-contained' or ../state = 'rogue-state-alert')) or (../class-type = 'rogue-classtype-custom' and (../state = 'rogue-state-contained' or ../state = 'rogue-state-alert')) or (../class-type = 'rogue-classtype-unclassified' and ../state = 'rogue-state-deleted')" {
        error-message "Please define a valid class/state classification";
        error-app-tag "must-violation";
      }
      default "rogue-classtype-unclassified";
      description
        "Classification type";
    }
    leaf state {
      type wireless-enum-types:rogue-state;
      description
        "Rogue state";
    }
    leaf severity-score {
      when "(../class-type = 'rogue-classtype-custom')";
      type uint32 {
        range "1 .. 100";
      }
      description
        "Severity score";
    }
    leaf class-type-custom-name {
      when "(../class-type = 'rogue-classtype-custom')";
      type string;
      description
        "Custom name of the classification";
    }
    leaf match-op {
      type wireless-enum-types:apf-rogue-rule-rule-match-op;
      must "../match-op = 'rule-match-any' or ../match-op = 'rule-match-all'" {
        error-message "Match operation can be ALL or ANY";
        error-app-tag "must-violation";
      }
      default "rule-match-any";
      description
        "Match operation";
    }
    leaf priority-num {
      type int32 {
        range "1 .. 512";
      }
      mandatory true;
      description
        "priority number for the rogue rule";
    }
    leaf enable {
      type boolean;
      default "false";
      description
        "Enable the rule";
    }
  }

  grouping st-rule-condition-cfg {
    description
      "Rouge rule for conditional config";
    leaf rssi {
      type int32 {
        range "-128 .. 0";
      }
      description
        "Receiving signal strength indicator";
    }
    leaf client-count {
      type uint32 {
        range "1 .. 10";
      }
      description
        "Number of client present";
    }
    leaf no-encryption {
      type boolean;
      default "false";
      description
        "no encryption";
    }
    leaf managed-ssid {
      type boolean;
      default "false";
      description
        "Status of managed ssid";
    }
    leaf duration {
      type uint32 {
        range "0 .. 3600";
      }
      description
        " duration (0,3600)";
    }
    leaf any-encryption {
      type boolean;
      description
        "any type of encryption";
    }
    leaf wpa-encryption {
      type boolean;
      description
        "WPA encryption";
    }
    leaf wpa2-encryption {
      type boolean;
      description
        "WPA2 encryption";
    }
  }

  grouping st-rule-data-op {
    description
      "Rogue rule types for oper data";
    leaf hit-cnt {
      type uint32;
      description
        "Number of rule hit";
    }
  }
}
