module Cisco-IOS-XE-route-map {
  namespace "http://cisco.com/ns/yang/Cisco-IOS-XE-route-map";
  prefix ios-route-map;

  import ietf-inet-types {
    prefix inet;
  }


  import Cisco-IOS-XE-types {
    prefix ios-types;
  }

  import Cisco-IOS-XE-interface-common {
    prefix ios-ifc;
  }

  import Cisco-IOS-XE-native {
    prefix ios;
  }

  import Cisco-IOS-XE-features {
    prefix ios-features;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Route Map Yang model.
     Copyright (c) 2016-2018 by Cisco Systems, Inc.
     All rights reserved.";

  // =========================================================================
  // REVISION
  // =========================================================================
  revision 2019-03-06 {
    description
      "Fixed route-map set community configuration";
  }
  revision 2018-12-06 {
    description
      "Added Support of color extended community";
  }
  revision 2018-12-01 {
    description
      "Removed choice option from set ip nexthop so that multiple \
       options can be configured at same time";
  }
  revision 2018-11-13 {
    description
      "Change \ to + in multi-line descriptions as it causes NSO compile error";
  }
  revision 2018-08-30 {
    description
      "Added support for set nlri and set attribute-set";
  }
  revision 2018-08-10 {
    description
      "Added support for multiple IPv4 next-hop (set ip next-hop)";
  }
  revision 2018-05-02 {
    description
      "Add omp and nat-route to source-protocol matching";
  }
  revision 2018-03-08 {
    description
      "Add tailf:cli-flat-list-syntax to route-map/match-preference";
  }
  revision 2018-01-08 {
    description
      "Revise modeling for set metric";
  }

  revision 2017-10-20 {
    description
      "Add model omp-tag for set and match";
  }

  revision 2017-07-27 {
    description
      "Add model for set ip next-hop verify-availability" +
      "<ipaddr> <range> track <range>";
  }
  revision 2017-06-07 {
    description
      "Add model for named ordering route-map enable";
  }
  revision 2017-02-07 {
    description
      "Initial revision";
  }

  grouping config-named-ordering-route-map-grouping {
    container named-ordering-route-map {
      description
        "named ordering route-map enable";
      leaf enable {
        description
	  "named ordering enable";
        type empty;
      }
    }
  }

  grouping next-hop-address-grouping {
    container next-hop {
      description
        "Next hop along path";
      leaf-list address {
        type inet:ipv4-address;
      }
    }
  }

  grouping ip-access-list-grouping {
    leaf-list access-list {
      type ios-types:exp-acl-type;
    }
    leaf-list prefix-list {
      description
        "Match entries of prefix-lists";
      type string;
    }
  }

  grouping ipv6-access-list-grouping {
    leaf access-list {
      type string {
        pattern "[a-zA-Z].*";
      }
    }
    leaf prefix-list {
      description
        "IPv6 prefix-list";
      type string;
    }
  }

  grouping route-map-community-grouping {
    list community-id {
      key "community-id cost-value";
      leaf community-id {
        description
          "Community ID";
        type uint8 {
          range "0..255";
        }
      }
      leaf cost-value {
        description
          "Cost Value (No-preference Cost = 2147483647)";
        type uint32 {
          range "0..4294967295";
        }
      }
    }
  }

  grouping config-route-map-common-grouping {
      // route-map * / description
      leaf description {
        description
          "Route-map comment";
        type string;
      }

      // route-map * / set
      container set {
        description
          "Set values in destination routing protocol";
        container aigp-metric {
          description
            "accumulated metric value";
          leaf value {
            description
              "manual value";
            type uint32 {
              range "0..4294967295";
            }
          }
          leaf igp-metric {
            description
              "metric value from rib";
            type empty;
          }
        }
        // route-map * / set as-path
        container as-path {
          description
            "Prepend string for a BGP AS-path attribute";
          container prepend {
            description
              "Prepend to the as-path";
            container as-container {
              leaf as-number {
                description
                  "<1-65535>;;AS number";
                type string;
              }
            }
            container last-as-cont {
              leaf last-as {
                type uint16 {
                  range "1..10";
                }
              }
            }
          }
          container tag {
            description
              "Set the tag as an AS-path attribute";
            presence "tag";
          }
        }
	// route-map * / set attribute-set
	leaf attribute-set {
	  description
	    "TE Profile name";
	  type string;
	}
        // route-map * / set automatic-tag
        leaf automatic-tag {
          description
            "Automatically compute TAG value";
          type empty;
        }
        // route-map * /set clns
        container clns {
          description
            "OSI summary address";
          uses next-hop-address-grouping;
        }
        // route-map * / set community
        container community {
          description
            "BGP community attribute";
          choice community-well-known-choice {
            leaf none {
              description
                "No community attribute";
              type empty;
            }
            container community-well-known {
              leaf-list community-list {
                ordered-by user;
                type union {
                  type ios-types:community-number-type;
                  type ios-types:community-well-known-add-type;
                }
              }
            }
          }
        }
        // route-map * / set comm-list
        container comm-list {
          description
            "set BGP community list (for deletion)";
          choice comm-list-choice {
            leaf comm-list-standard {
              type uint16 {
                range "1..99";
              }
            }
            leaf comm-list-expanded {
              type uint16 {
                range "100..500";
              }
            }
            leaf comm-list-name {
              type string;
            }
          }
          leaf delete {
            description
              "Delete matching communities";
            type empty;
          }
        }
        container dampening {
          description
            "Set BGP route flap dampening parameters";
          list dampening-list {
            key "half-life-penalty restart-penalty suppress-penalty max-suppress-penalty";
            leaf half-life-penalty {
              description
                "half-life time for the penalty";
              type uint8 {
                range "1..45";
              }
            }
            leaf restart-penalty {
              description
                "penalty to start reusing a route";
              type uint16 {
                range "1..20000";
              }
            }
            leaf suppress-penalty {
              description
                "penalty to start suppressing a route";
              type uint16 {
                range "1..20000";
              }
            }
            leaf max-suppress-penalty {
              description
                "Maximum duration to suppress a stable route";
              type uint8 {
                range "1..255";
              }
            }
          }
        }
        container default {
          container interface {
            description
              "SPAN source interface";
            uses ios-ifc:interface-grouping;
          }
        }
        container extcomm-list {
          description
            "Set BGP/VPN extended community list (for deletion)";
          list ext-range {
            key "comm-list-num";
            leaf comm-list-num {
              description
                "Extended community-list number (expanded)";
              type uint16 {
                range "1..500";
              }
            }
            leaf delete {
              description
                "Delete matching extended communities";
              type empty;
            }
          }
          list excomm-list-name {
            key "name";
            leaf name {
              description
                "extcommunity-list name";
              type string;
            }
            leaf delete {
              type empty;
            }
          }
        }
        // route-map * / set extcommunity
        container extcommunity {
          description
            "BGP extended community attribute";
          leaf color {
            description
             "Color Extended Community";
            type uint32 {
              range "1..4294967295";
            }
          }
          container cost {
            description
              "Cost extended community";
            uses route-map-community-grouping;
            container igp {
              description
                "Compare following IGP cost comparison";
              uses route-map-community-grouping;
            }
            container pre-bestpath {
              description
                "Compare before all other steps in bestpath calculation";
              uses route-map-community-grouping;
            }
          }
          container rt {
            description
              "Route Target extended community";
            leaf-list asn-nn {
              ordered-by user;
              type union {
                type ios-types:asn-ip-type;
                type enumeration {
                  enum "additive" {
                  }
                }
              }
            }
            container range {
              description
                "Specify a range of extended community";
              leaf lower-limit {
                description
                  "VPN extended community lower limit";
                type ios-types:asn-ip-type;
              }
              leaf high-limit {
                description
                  "VPN extended community high limit";
                type ios-types:asn-ip-type;
              }
              leaf additive {
                description
                  "Add to the existing extcommunity";
                type empty;
              }
            }
          }
          container soo {
            description
              "Site-of-Origin extended community";
            leaf asn-nn {
              type ios-types:asn-ip-type;
            }
          }
          container vpn-distinguisher {
            description
              "VPN Distinguisher";
            leaf asn-nn {
              type ios-types:asn-ip-type;
            }
            container range {
              description
                "Specify a range of extended community";
              leaf lower-limit {
                description
                  "VPN extended community lower limit";
                type ios-types:asn-ip-type;
              }
              leaf high-limit {
                description
                  "VPN extended community high limit";
                type ios-types:asn-ip-type;
              }
              leaf additive {
                description
                  "Add to the existing extcommunity";
                type empty;
              }
            }
          }
        }
        // route-map * / set global
        leaf global {
          type empty;
        }
        // route-map * / set interface
        container interface {
          uses ios-ifc:interface-grouping;
        }
        // route-map * / set ip
        container ip {
          description
            "IP specific information";
          container address {
            description
              "Specify IP address";
            leaf prefix-list {
              description
                "Specify prefix-list";
              type string;
            }
          }
          container default {
            description
              "Set default information";
            container global {
              description
                "global routing table";
              uses next-hop-address-grouping;
            }
            uses next-hop-address-grouping;
            container vrf {
              description
                "VRF name";
              list vrfs {
                key "vrf";
                leaf vrf {
                  description
                    "WORD;;VRF name";
                  type string;
                }
                uses next-hop-address-grouping;
              }
            }
          }
          leaf df {
            type uint8 {
              range "0..1";
            }
          }
          container global {
            description
              "global routing table";
            uses next-hop-address-grouping;
          }
          container next-hop {
            description
              "Next hop address";
            leaf-list address {
              type inet:ipv4-address;
            }
            container dynamic {
              description
                "application dynamically sets next hop";
              leaf dhcp {
                description
                  "DHCP learned next hop";
                type empty;
              }
            }
            container encapsulate {
              description
                "Encapsulation profile for VPN nexthop";
              leaf l3vpn {
                description
                  "L3VPN";
                type string;
              }
            }
            leaf peer-address {
              description
                "Use peer address (for BGP only)";
              type empty;
            }
            container recursive {
              description
                "Recursive next-hop";
              leaf ipv4 {
                description
                  "IP address of recursive next hop";
                type inet:ipv4-address;
              }
              leaf global {
                description
                  "IP address of recursive next hop";
                type inet:ipv4-address;
              }
              container vrf {
                description
                  "VRF name";
                list vrfs {
                  key "vrf";
                  leaf vrf {
                    description
                      "VRF name";
                    type string;
                  }
                  leaf ipv4 {
                    description
                      "IP address of recursive next hop";
                    type inet:ipv4-address;
                  }
                }
              }
            }
            leaf self {
              description
                "Use self address (for BGP only)";
              type empty;
            }
            container verify-availability {
              description
                "Verify if nexthop is reachable";
              presence "true";
              list ipv4 {
                key "ipv4";
                leaf ipv4 {
                  description
                    "IP address of next hop";
                  type inet:ipv4-address;
                }
                leaf range {
                  type uint16 {
                    range "1..65535";
                  }
                }
                leaf track {
                  description
                    "set the next hop depending on the state" +
                     "of a tracked object";
                  type uint16 {
                     range "1..1000";
                  }
                } 
              }
            }
          }
          container precedence {
            description
              "Set precedence field";
            presence "true";
            leaf precedence-value {
              type uint8 {
                range "0..7";
              }
            }
            leaf precedence-fields {
              type enumeration {
                enum "critical";
                enum "flash";
                enum "flash-override";
                enum "immediate";
                enum "internet";
                enum "network";
                enum "priority";
                enum "routine";
              }
            }
          }
          container qos-group {
            description
              "Set QOS Group ID";
            presence "true";
            leaf qos-id {
              type uint8 {
                range "0..99";
              }
            }
          }
          container tos {
            description
              "Set type of service field";
            presence "true";
            leaf service-value {
              type uint8 {
                range "0..15";
              }
            }
            leaf tos-fields {
              type enumeration {
                enum "max-reliability";
                enum "max-throughput";
                enum "min-delay";
                enum "min-monetary-cost";
                enum "normal";
              }
            }
          }
          container vrf {
            description
              "VRF name";
            list vrfs {
              key "vrf";
              leaf vrf {
                description
                  "WORD;;VRF name";
                type string;
              }
              uses next-hop-address-grouping;
            }
          }
        }
        // route-map * / set ipv6
        container ipv6 {
          description
            "IPv6 specific information";
          container address {
            description
              "IPv6 address";
            leaf-list prefix-list {
              description
                "IPv6 prefix-list";
              type string;
            }
          }
          container default {
            description
              "Set default information";
            container global {
              description
                "global routing table";
              leaf next-hop {
                description
                  "Next hop along path";
                type inet:ipv6-address;
              }
            }
            container next-hop {
              description
                "Next hop along path";
              list ipv6s {
                key "ipv6";
                leaf ipv6 {
                  description
                    "Default next hop IPv6 address";
                  type inet:ipv6-address;
                }
              }
              leaf next-hop-address {
                type inet:ipv6-address;
              }
            }
            list dvrf {
              key "dvrf";
              leaf dvrf {
                description
                  "VRF name";
                type string;
              }
              list dvrf0 {
                key "dvrf0";
                leaf dvrf0 {
                  description
                    "VRF name";
                  type string;
                }
                leaf next-hop {
                  description
                    "Next hop along path";
                  type empty;
                }
              }
            }
          }
          container global {
            description
              "global routing table";
            container next-hop {
              description
                "IPv6 Next hop";
              list nh-ipv6 {
                key "nh-ipv6";
                leaf nh-ipv6 {
                  description
                    "Next hop address";
                  type inet:ipv6-address;
                }
                leaf nh-ipv60 {
                  description
                    "Next hop address";
                  type inet:ipv6-address;
                }
              }
              leaf verify-availability {
                description
                  "Next hop address";
                type inet:ipv6-address;
              }
            }
          }
          container next-hop {
            description
              "IPv6 Next hop";
            list nha-ipv6 {
              key "nha-ipv6";
              leaf nha-ipv6 {
                description
                  "Next hop address";
                type inet:ipv6-address;
              }
              list nha-ipv60 {
                key "nha-ipv60";
                leaf nha-ipv60 {
                  description
                    "Next hop address";
                  type inet:ipv6-address;
                }
                leaf nh-ipv6 {
                  description
                    "Next hop address";
                  type inet:ipv6-address;
                }
              }
            }
            container encapsulate {
              description
                "Encapsulation profile for VPN nexthop";
              leaf l3vpn {
                description
                  "Encapsulation profile name";
                type string;
              }
            }
            leaf peer-address {
              description
                "Use peer address (for BGP only)";
              type empty;
            }
            leaf recursive {
              description
                "IPv6 address of recursive next-hop";
              type inet:ipv6-address;
            }
            container verify-availability {
              description
                "Verify if nexthop is reachable";
              list va-ipv6 {
                key "va-ipv6";
                leaf va-ipv6 {
                  description
                    "Next hop address";
                  type inet:ipv6-address;
                }
                leaf seq-nh {
                  description
                    "Sequence to insert into next-hop list";
                  type uint16 {
                    range "1..65535";
                  }
                }
              }
            }
          }
          leaf precedence {
            description
              "Precedence value";
            type uint8 {
              range "0..7";
            }
          }
          list bvrf {
            key "bvrf";
            leaf bvrf {
              description
                "VRF name";
              type string;
            }
            list bvrf0 {
              key "bvrf0";
              leaf bvrf0 {
                description
                  "VRF name";
                type string;
              }
              container next-hop {
                description
                  "IPv6 Next hop";
                leaf bipv6 {
                  description
                    "Next hop address";
                  type inet:ipv6-address;
                }
                leaf verify-availability {
                  description
                    "Verify if nexthop is reachable";
                  type empty;
                }
              }
            }
          }
        }
        // route-map * / set level
        container level {
          description
            "Where to import route";
          leaf level-1 {
            description
              "Import into a level-1 area";
            type empty;
          }
          leaf level-1-2 {
            description
              "Import into level-1 and level-2";
            type empty;
          }
          leaf level-2 {
            description
              "Import into level-2 sub-domain";
            type empty;
          }
          leaf nssa-only {
            description
              "Import only into OSPF NSSA areas and don't propagate";
            type empty;
          }
        }
        // route-map * / set lisp
        container lisp {
          description
            "Locator ID Separation Protocol specific information";
          leaf locator-set {
            description
              "The name of the locator set";
            type string;
          }
        }
        leaf local-preference {
          description
            "Preference value";
          type uint32 {
            range "0..4294967295";
          }
        }
        // route-map * / set metric
        container metric {
          description
            "Metric value for destination routing protocol";
          choice metric-choice {
            case relative-value {
              leaf metric-change {
                description
                  "+/-<metric>;;Add or subtract metric";
                type string {
                  pattern "(\\+|-)\\d{1,10}";
                }
              }
            }
            case absolute-values {
              container values {
                leaf value {
                  description
                    "Metric value or Bandwidth in Kbits per second";
                  type uint32;
                }
                leaf delay {
                  description
                    "EIGRP delay metric, in 10 microsecond units";
                  when "../value";
                  type string {
                    pattern "(\\+|-)?\\d{1,10}";
                  }
                }
                leaf reliability {
                  description
                    "EIGRP reliability metric where 255 is 100% reliable";
                  when "../delay";
                  must "../loading and ../MTU";
                  type uint8;
                }
                leaf loading {
                  description
                    "EIGRP Effective bandwidth metric (Loading) where 255 is 100% loaded";
                  when "../delay";
                  must "../reliability and ../MTU";
                  type uint8 {
                    range "1..255";
                  }
                }
                leaf MTU {
                  description
                    "EIGRP MTU of the path";
                  when "../delay";
                  must "../reliability and ../loading";
                  type uint32 {
                    range "1..4294967295";
                  }
                }
              }
            }
          }
        }
        leaf metric-type {
          description
            "Type of metric for destination routing protocol";
          type enumeration {
            enum "external";
            enum "internal";
            enum "type-1";
            enum "type-2";
          }
        }
        leaf mpls-label {
          description
            "Set MPLS label for prefix";
          type empty;
        }
	// route-map * / set nlri
        container nlri {
          description
            "BGP NLRI type";
	  leaf unicast {
	    description
	      "Used in unicast RIB";
	    type empty;
	  }
	  leaf multicast {
	    description
	      "Used in multicast RIB";
	    type empty;
	  }
        }
        // route-map * / set weight
        leaf weight {
          description
            "BGP weight for routing table";
          type uint32 {
            range "0..65535";
          }
        }
        // route-map * / set omp-tag 
        leaf omp-tag {
          if-feature ios-features:omp;
          description
            "OMP tag value for destination routing protocol";
          type uint32;
        }
        // route-map * / set origin
        container origin {
          description
            "BGP origin code";
          leaf origin-value {
            type enumeration {
              enum "igp" {
              }
              enum "incomplete" {
              }
            }
          }
          leaf egp {
            description
              "remote EGP";
            type uint32 {
              range "0..65535";
            }
          }
        }
        container tag {
          description
            "Tag value for destination routing protocol";
          leaf tag-val {
            description
              "Tag value";
            type uint32 {
              range "0..4294967295";
            }
          }
          leaf tag-ipv4 {
            description
              "Tag value(dotted decimal format)";
            type inet:ipv4-address;
          }
        }
        leaf traffic-index {
          description
            "Bucket number";
          type uint8 {
            range "1..64";
          }
        }
        leaf vrf {
          description
            "VPN Routing/Forwarding instance name";
          type string;
        }
      }
      // route-map * / match
      container match {
        description
          "Match values from routing table";
        container additional-paths {
          description
            "BGP Add-Path match policies";
          container advertise-set {
            description
              "BGP Add-Path advertise-set policy";
            container all {
              description
                "BGP Add-Path advertise all paths";
              presence "true";
              leaf best {
                description
                  "BGP Add-Path best n paths to advertise";
                type uint8 {
                  range "1..3";
                }
              }
              leaf best-range {
                description
                  "BGP Add-Path best paths to advertise (lower limit)";
                type uint8 {
                  range "1..3";
                }
              }
              container group-best {
                description
                  "BGP Add-Path advertise group-best path";
                presence "true";
                leaf best {
                  description
                    "BGP Add-Path advertise best n paths";
                  type empty;
                }
                leaf best-range {
                  description
                    "BGP Add-Path advertise best paths (range m to n)";
                  type empty;
                }
              }
            }
            container best {
              description
                "BGP Add-Path advertise best n paths";
              list best-range {
                key "best-range";
                leaf best-range {
                  description
                    "BGP Add-Path best n paths to advertise";
                  type uint8 {
                    range "1..3";
                  }
                }
                leaf all {
                  description
                    "BGP Add-Path advertise all paths";
                  type empty;
                }
                leaf group-best {
                  description
                    "BGP Add-Path advertise group-best path";
                  type empty;
                }
              }
            }
            container best-range {
              description
                "BGP Add-Path advertise best paths (range m to n)";
              list adv-path {
                key "adv-path";
                leaf adv-path {
                  description
                    "BGP Add-Path best paths to advertise (lower limit)";
                  type uint8 {
                    range "1..3";
                  }
                }
                leaf adv-path0 {
                  description
                    "BGP Add-Path best paths to advertise (upper limit)";
                  type uint8 {
                    range "1..3";
                  }
                }
              }
            }
            container group-best {
              description
                "BGP Add-Path advertise group-best path";
              presence "true";
              leaf all {
                description
                  "BGP Add-Path advertise all paths";
                type empty;
              }
              leaf best {
                description
                  "BGP Add-Path best n paths to advertise";
                type uint8 {
                  range "1..3";
                }
              }
              leaf best-range {
                description
                  "BGP Add-Path best paths to advertise (lower limit)";
                type uint8 {
                  range "1..3";
                }
              }
            }
          }
        }
        container as-path {
          description
            "Match BGP AS path list";
          leaf-list access-list {
            description
              "AS path access-list";
            type uint16 {
              range "1..500";
            }
          }
        }
        // route-map * / match clns
        container clns {
          description
            "CLNS information";
          leaf-list name {
            description
              "Named clna list";
            type string;
          }
        }
        // route-map * / match community
        container community {
          description
            "Match BGP community list";
          leaf-list name {
            description
              "Named Access List";
            type string;
          }
        }
        // route-map * / match extcommunity
        container extcommunity {
          description
            "Match BGP/VPN extended community list";
          leaf-list name {
            description
              "Named Access List";
            type string;
          }
        }
        // route-map * / match interface
        container interface {
          description
            "SPAN source interface";
          leaf-list interface {
            type string;
          }
        }
        // route-map * / match ip
        container ip {
          description
            "IP specific information";
          container address {
            description
              "Match address of route or match packet";
            uses ip-access-list-grouping;
          }
          container flowspec {
            description
              "Match address of route";
            container dest-pfx {
              description
                "Match dest prefix component of flowspec prefix";
              uses ip-access-list-grouping;
            }
            container src-pfx {
              description
                "Match source prefix component of flowspec prefix";
              uses ip-access-list-grouping;
            }
          }
          container next-hop {
            description
              "Match next-hop address of route";
            uses ip-access-list-grouping;
          }
          container redistribution-source {
            description
              "route redistribution source (EIGRP only)";
            uses ip-access-list-grouping;
          }
          container route-source {
            description
              "Match advertising source address of route";
            uses ip-access-list-grouping;
          }
        }
        // route-map * / match ipv6
        container ipv6 {
          description
            "IPv6 specific information";
              //next-hop
              //route-source
          container address {
            description
              "Match address of route";
            uses ipv6-access-list-grouping;
          }
          container flowspec {
            description
              "Match address of route";
            container dest-pfx {
              description
                "Match dest prefix component of flowspec prefix";
              uses ipv6-access-list-grouping;
            }
            container src-pfx {
              description
                "Match source prefix component of flowspec prefix";
              uses ipv6-access-list-grouping;
            }
          }
          container next-hop {
            description
              "Match next-hop address of route";
            uses ipv6-access-list-grouping;
          }
          container route-source {
            description
              "Match advertising source address of route";
            uses ipv6-access-list-grouping;
          }
        }
        //route-map * / match length
        container length {
          description
            "Packet length";
          list lengths {
            key "min-len max-len";
            leaf min-len {
              description
                "Minimum packet length";
              type uint32 {
                range "0..2147483647";
              }
            }
            leaf max-len {
              description
                "Maximum packet length";
              type uint32 {
                range "0..2147483647";
              }
            }
          }
        }
        container local-preference {
          description
            "Local preference for route";
          leaf-list values {
            type uint32 {
              range "0..4294967295";
            }
          }
        }
        container mdt-group {
          description
            "Match routes corresponding to MDT group";
          leaf-list name {
            description
              "IP Access List";
            type string;
          }
        }
        // route-map * / match metric
        container metric {
          description
            "Match metric of route";
          leaf metric-value {
            type string;
          }
          leaf external {
            description
              "match route using external protocol metric";
            type string;
          }
        }
        leaf mpls-label {
          description
            "Match routes which have MPLS labels";
          type empty;
        }
        container policy-list {
          description
            "Match IP policy list";
          leaf-list policy-map-names {
            description
              "IP Policy map name";
            type string;
          }
        }
        leaf omp-tag {
          if-feature ios-features:omp;
          description
            "OMP Tag value for route match";
          type uint32;
        }
        container route-type {
          description
            "Match route-type of route";
          container external {
            description
              "external route (BGP, EIGRP and OSPF type 1/2)";
            presence "true";
            leaf type-1 {
              description
                "OSPF external type 1 route";
              type empty;
            }
            leaf type-2 {
              description
                "OSPF external type 2 route";
              type empty;
            }
          }
          leaf internal {
            description
              "internal route (including OSPF intra/inter area)";
            type empty;
          }
          leaf level-1 {
            description
              "IS-IS level-1 route";
            type empty;
          }
          leaf level-2 {
            description
              "IS-IS level-2 route";
            type empty;
          }
          leaf local {
            description
              "locally generated route";
            type empty;
          }
          container nssa-external {
            description
              "nssa-external route (OSPF type 1/2)";
            presence "true";
            leaf type-1 {
              description
                "OSPF external type 1 route";
              type empty;
            }
            leaf type-2 {
              description
                "OSPF external type 2 route";
              type empty;
            }
          }
        }
        container rpki {
          description
            "Match RPKI state of route";
          leaf invalid {
            description
              "RPKI Invalid State";
            type empty;
          }
          leaf not-found {
            description
              "RPKI Not Found State";
            type empty;
          }
          leaf valid {
            description
              "RPKI Valid State";
            type empty;
          }
        }
        container source-protocol {
          description
            "Match source-protocol of route";
          presence "true";
          leaf-list bgp {
            description
              "Border Gateway Protocol (BGP)";
            type ios-types:bgp-as-number-type;
          }
          leaf connected {
            description
              "Connected";
            type empty;
          }
          leaf-list eigrp {
            description
              "Border Gateway Protocol (BGP)";
            type string;
          }
          leaf isis {
            description
              "ISO IS-IS";
            type empty;
          }
          leaf lisp {
            description
              "Locator ID Separation Protocol (LISP)";
            type empty;
          }
          leaf mobile {
            description
              "Mobile routes";
            type empty;
          }
          leaf-list ospf {
            description
              "Open Shortest Path First (OSPF)";
            type string;
          }
          leaf-list ospfv3 {
            description
              "OSPFv3";
            type string;
          }
          leaf rip {
            description
              "Routing Information Protocol (RIP)";
            type empty;
          }
          leaf static {
            description
              "Static routes";
            type empty;
          }
          leaf omp {
            if-feature ios-features:omp;
            description
              "Overlay Management Protocol (OMP)";
            type empty;
          }
          leaf nat-route {
            if-feature ios-features:sdwan;
            description
              "NAT Route Protocol";
            type empty;
          }
        }
        container tag {
          description
            "Match tag of route";
          leaf-list tag_value {
            description
              "Tag value";
            type uint32 {
              range "0..4294967295";
            }
          }
          leaf-list ipv4-address {
            description
              "<A.B.C.D>;;Tag value(dotted decimal format)";
            type inet:ipv4-address;
          }
          container list {
            description
              "Route Tag List";
            leaf-list tag-names {
              description
                "Tag list name";
              type string;
            }
          }
        }
        leaf track {
          description
            "tracking object";
          type uint16 {
            range "1..1000";
          }
        }
      }
  }
  grouping config-route-map-grouping {
    list route-map-seq {

      key "ordering-seq";
      leaf ordering-seq {
        description "Ordering seq tag";
        type string;
      }

      // route-map * permit
      // route-map * deny
      leaf operation {
        type enumeration {
          enum "deny" {
          }
          enum "permit" {
          }
        }
      }

      // route-map * #
      leaf sequence {
        type uint16 {
          range "0..65535";
        }
      }
      uses config-route-map-common-grouping; 
    }
    list route-map-without-order-seq {
      key "seq_no";
      leaf seq_no {
        type uint16 {
          range "0..65535";
        }
      }
      leaf operation {
        type enumeration {
          enum "deny" {
          }
          enum "permit" {
          }
        }
      }
      uses config-route-map-common-grouping; 
    }
  }

  /////////////////////////////////////////////////////////
  // native
  /////////////////////////////////////////////////////////
  augment "/ios:native" {
    uses config-named-ordering-route-map-grouping;
  }

  /////////////////////////////////////////////////////////
  // native / route-map
  /////////////////////////////////////////////////////////
  augment "/ios:native/ios:route-map" {
    uses config-route-map-grouping;
  }
}
