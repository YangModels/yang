module Cisco-IOS-XE-vrf-oper {
  yang-version 1;
  namespace "http://cisco.com/ns/yang/Cisco-IOS-XE-vrf-oper";
  prefix vrf-ios-xe-oper;

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for IOS-XE VRF operational data.";

  revision 2018-09-10 {
    description
      "Initial revision";
    reference "1.0.0";
  }

  typedef vrf-af {
    type enumeration {
      enum "ipv4-unicast" {
        value 0;
        description
          "Address family ipv4 unicast";
      }
      enum "ipv6-unicast" {
        value 1;
        description
          "Address family ipv6 unicast";
      }
      enum "ipv4-multicast" {
        value 2;
        description
          "Address family ipv4 multicast";
      }
      enum "ipv6-multicast" {
        value 3;
        description
          "Address family ipv6 multicast";
      }
    }
    description
      "VRF address family types";
  }

  grouping vrf-af-entry {
    description
      "VRF address family operational data";
    leaf address-family {
      type vrf-ios-xe-oper:vrf-af;
      description
        "Address family enabled on this VRF";
    }
  }

  grouping vrf-entry {
    description
      "VRF entry to store operational data";
    leaf vrf-name {
      type string;
      description
        "Unique name of this VRF";
    }
    leaf-list interface {
      type string;
      ordered-by user;
      description
        "List of interfaces using this VRF";
    }
    list address-family-entry {
      description
        "List of address family data for this VRF";
      uses vrf-ios-xe-oper:vrf-af-entry;
    }
  }

  container vrf-oper-data {
    config false;
    description
      "VRF operational data";
    list vrf-entry {
      key "vrf-name";
      description
        "VRF entries";
      uses vrf-ios-xe-oper:vrf-entry;
    }
  }
}
