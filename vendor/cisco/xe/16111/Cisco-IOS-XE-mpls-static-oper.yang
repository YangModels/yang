module Cisco-IOS-XE-mpls-static-oper {
  yang-version 1;
  namespace "http://cisco.com/ns/yang/Cisco-IOS-XE-mpls-static-oper";
  prefix mpls-static-ios-xe-oper;

  import ietf-inet-types {
    prefix inet;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for MPLS static operational data.
     Copyright (c) 2017-2018 by Cisco Systems, Inc.
     All rights reserved.";

  revision 2019-01-14 {
    description
      "Initial revision";
    reference "1.0.0";
  }

  typedef local-label-state {
    type enumeration {
      enum "local-label-non-existent" {
        value 0;
        description
          "Non existent";
      }
      enum "local-label-allocated" {
        value 1;
        description
          "Allocated";
      }
      enum "local-label-delete-pending" {
        value 2;
        description
          "Delete pending";
      }
      enum "local-label-allocate-pending" {
        value 3;
        description
          "Allocate pending";
      }
    }
    description
      "Describes supported local label state";
  }

  typedef remote-label-flag {
    type bits {
      bit remote-label-nexthop-is-peer {
        position 0;
        description
          "Nexthop is a TDP/LDP peer";
      }
      bit remote-label-nexthop-checked {
        position 1;
        description
          "The binding nexthop is checked to be a routing nexthop";
      }
    }
    description
      "Describes supported remote label flag";
  }

  typedef label-type-flag {
    type bits {
      bit label-type-normal {
        position 0;
        description
          "Normal MPLS label";
      }
      bit label-type-ietf-reserved {
        position 1;
        description
          "IETF reserved label";
      }
      bit label-type-tag-switch-reserved {
        position 2;
        description
          "TAG switch reserved label";
      }
      bit label-type-generic-reserved {
        position 3;
        description
          "Generic reserved label";
      }
    }
    description
      "Describes supported label type flag";
  }

  grouping remote-label-binding {
    description
      "Information of remote label binding";
    leaf type {
      type mpls-static-ios-xe-oper:label-type-flag;
      description
        "Label type";
    }
    leaf label {
      type uint32;
      description
        "Label value";
    }
    leaf remote-ldpid {
      type string;
      description
        "Remote LDP Identifier, only valid when peer is a LDP neighbor";
    }
    leaf flag {
      type mpls-static-ios-xe-oper:remote-label-flag;
      description
        "Remote label binding flags";
    }
  }

  grouping binding-key {
    description
      "Information of label binding table search key";
    leaf table-id {
      type uint32;
      description
        "routing table Identifier";
    }
    leaf fec {
      type inet:ip-prefix;
      description
        "Forwarding Equivalence Class: IP prefix";
    }
  }

  grouping binding {
    description
      "Information of MPLS static label binding";
    leaf local-label {
      type uint32;
      description
        "Local label value";
    }
    leaf local-label-type {
      type mpls-static-ios-xe-oper:label-type-flag;
      description
        "Local label type";
    }
    leaf local-label-state {
      type mpls-static-ios-xe-oper:local-label-state;
      description
        "Local label state";
    }
    list remote-binding {
      description
        "Remote label bindings";
      uses mpls-static-ios-xe-oper:remote-label-binding;
    }
  }

  container mpls-static-oper-data {
    config false;
    description
      "MPLS static operational data";
    list mpls-static-binding {
      key "table-id fec";
      description
        "Information of MPLS static label binding";
      uses mpls-static-ios-xe-oper:binding-key;
      uses mpls-static-ios-xe-oper:binding;
    }
  }
}
