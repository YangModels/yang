module Cisco-IOS-XE-wireless-tunnel-types {
  yang-version 1;
  namespace "http://cisco.com/ns/yang/Cisco-IOS-XE-wireless-tunnel-types";
  prefix wireless-tunnel-types;

  organization
    "Cisco Systems, Inc.";
  contact
    "Cisco Systems, Inc.
     Customer Service
     
     Postal: 170 W Tasman Drive
     San Jose, CA 95134
     
     Tel: +1 1800 553-NETS
     
     E-mail: cs-yang@cisco.com";
  description
    "Model for managing tunnel configurations
     Copyright (c) 2018 by Cisco Systems, Inc.
     All rights reserved.";

  revision 2018-11-01 {
    description
      "Initial revision";
    reference "1.0.0";
  }

  grouping st-tunnel-profile-base {
    description
      "Configuration of wireless tunnel profile";
    leaf status {
      type boolean;
      default "false";
      description
        "Whether tunnel profile is enabled";
    }
    leaf aaa-override {
      type boolean;
      default "false";
      description
        "Whether AAA override is enabled";
    }
    leaf aaa-proxy {
      type boolean;
      default "false";
      description
        "Whether AAA proxy is enabled";
    }
    leaf aaa-accounting-proxy {
      type boolean;
      description
        "Whether AAA accounting proxy is enabled";
    }
    leaf opt82-enable {
      type boolean;
      description
        "Whether DHCP-opt82 is enabled";
    }
    leaf opt82-ascii {
      type boolean;
      description
        "Whether DHCP-opt82 format is ASCII. Binary if false";
    }
    leaf opt82-delimiter {
      type string {
        length "0 .. 1";
      }
      description
        "DHCP-op82 Delimiter character";
    }
  }

  grouping st-tunnel-rule-base {
    description
      "Configuration of wireless tunnel rule";
    leaf realm {
      type string;
      description
        "The rule realm to match with";
    }
    leaf vlan-id {
      type uint32 {
        range "1 .. 4094";
      }
      description
        "The rule VLAN";
    }
    leaf domain-name {
      type string;
      description
        "The rule's destination domain name";
    }
  }
}
