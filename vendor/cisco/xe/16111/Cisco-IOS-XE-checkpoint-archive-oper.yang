module Cisco-IOS-XE-checkpoint-archive-oper {
  yang-version 1;
  namespace "http://cisco.com/ns/yang/Cisco-IOS-XE-checkpoint-archive-oper";
  prefix checkpoint-archive-ios-xe-oper;

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions for
     monitoring the checkpoint archives in a Network Element.
     Copyright (c) 2016-2017 by Cisco Systems, Inc.
     All rights reserved.";

  revision 2018-10-29 {
    description
      "Cleaned up spelling errors in descriptions.";
    reference "2.1.0";
  }
  revision 2017-04-01 {
    description
      "Top level container name change";
    reference "2.0.0";
  }
  revision 2017-02-07 {
    description
      "Initial revision";
    reference "1.0.0";
  }

  grouping archive {
    description
      "Archive information";
    leaf number {
      type uint16;
      description
        "The archive number";
    }
    leaf name {
      type string;
      description
        "The name of the archive";
    }
  }

  grouping checkpoint-archive {
    description
      "Checkpoint archive information";
    leaf max {
      type uint8;
      description
        "The maximum number of archives";
    }
    leaf current {
      type uint8;
      description
        "The current number of archives";
    }
    leaf recent {
      type string;
      description
        "The most recent archive";
    }
    container archives {
      description
        "Archive information";
      list archive {
        key "number";
        description
          "List of archives";
        uses checkpoint-archive-ios-xe-oper:archive;
      }
    }
  }

  container checkpoint-archives {
    config false;
    description
      "Contents of the checkpoint archive information base";
    uses checkpoint-archive-ios-xe-oper:checkpoint-archive;
  }
}
