module cisco-xe-routing-isr-openconfig-platform-deviation {
  // namespace
  namespace "http://openconfig.net/yang/cisco-xe-routing-isr-openconfig-platform-deviation";

  prefix cisco-xe-routing-isr-oc-platform-devs;

  import openconfig-platform {
    prefix oc-platform;
  }

  import openconfig-alarms {
    prefix oc-alarms;
  }

  import openconfig-interfaces {
    prefix oc-if;
  }

  organization
    "Cisco Systems, Inc.";

  contact
    " Cisco Systems, Inc.
    Customer Service

    Postal: 170 W Tasman Drive
    San Jose, CA 95134

    Tel: +1 1800 553-NETS

    E-mail: cs-yang@cisco.com";

  description
    "This module defines deviation statements for openconfig-platform module for IOS XE Routing ISR devices.";

  revision 2010-10-09 {
    description
      "Add deviations to remove openconfig-platform features not implemented on IOS XE ISR devices";
 
    reference
      "RFC 6020: YANG - A Data Modeling Language for the
       Network Configuration Protocol (NETCONF)";
  }

 deviation "/oc-platform:components" {
      deviate not-supported; 
      description
        "oc-platform not supported.";
  }

 deviation "/oc-if:interfaces/oc-if:interface/oc-if:state/oc-platform:hardware-port" {
      deviate not-supported; 
      description
        "oc-platform hardware-port not supported.";
  }

}
