module Cisco-IOS-XE-rpc {
  namespace "http://cisco.com/ns/yang/Cisco-IOS-XE-rpc";
  prefix ios-xe-rpc;


  import ietf-inet-types {
    prefix inet;
  }

  import Cisco-IOS-XE-types {
	  prefix ios-types;
  }

  organization "Cisco Systems";

  contact
    <mailto:cs-yang@cisco.com>;

  description
    "NED RPC YANG module for IOS
     Copyright (c) 2016-2018 by Cisco Systems, Inc.
     All rights reserved.";

  // =========================================================================
  // REVISION
  // =========================================================================
  revision 2018-11-25 {
    description
      "Exec command to send AMP file analysis apikey";
  }


  revision 2018-11-07 {
    description
      "Cleanup spelling errors in description statements";
  }  
  revision 2018-11-06 {
    description
      "Add UTD database update EXEC command";
  }

  revision 2018-10-29 {
    description
      "Added range-string for debug ipsec command";
  }
 
  revision 2018-10-12 {
    description
      "Added crypto pki debug and exec commands";
  } 

  revision 2018-10-02 {
    description
      "Add unmount command in existing hw-module chain";
  }

  revision 2018-10-01 {
    description
      "Add IPSEC no debug exec commands";
  } 
  
  revision 2018-09-20 {
    description
      "Add IPSEC debug exec commands";
  } 
  revision 2018-08-17 {
    description
      "Added cts credential * and clear cts * commands";
  }
  revision 2018-08-05 {
    description 
      "Add License Install Commands";
  }
  revision 2018-08-01 {
    description
      "Add UTD clear commands";
  }
  revision 2018-07-30 {
    description 
      "Add hw-module commands";
  }
  revision 2018-06-18 {
    description 
      "Update UTD signature update EXEC command to include local file support";
  }
  revision 2018-05-21 {
    description 
      "Add Umbrella clear commands";
  }      
  revision 2018-04-18 {
    description 
      "Add ZBFW clear commands";
  }
  revision 2018-03-14 {
    description 
      "Add UTD signature update EXEC command";
  }
  revision 2017-12-18 {
    description 
      "Add GIR start maintenance and stop maintenance EXEC commands";
  }
  revision 2017-12-06 {
    description 
      "Add Viptela clear aaa local user lockout username <> command";
  }
  revision 2017-11-27 {
    description 
      "Add Viptela clear and release commands";
  }
  revision 2017-11-21 {
    description 
      "Clear flow commands";
  }
  revision 2017-11-14 {
    description
      "Add app-hosting and guestshell EXEC commands";
  }
  revision 2017-11-04 {
    description
      "Add reason to reload";
  }
  revision 2017-10-12 {
    description
      "Added more nodes to the license RPC";
  }
  revision 2017-10-10 {
    description
      "Add copy and delete EXEC commands";
  }
  revision 2017-09-21 {
    description
      "Add virtual-service EXEC commands";
  }
  revision 2017-08-28 {
    description
      "Added the force option to the reload RPC";
  }
  revision 2017-07-13 {
    description 
      "Added service sd-avc CLI";
  }
  revision 2017-02-07 {
    description
      "Initial revision";
  }

  grouping cisco-xe-rpc-output {
    description 
      "Used to return output from RPCs";
    leaf result {
      type string;
      description 
        "Output returned by the network element";
    }
  }

  grouping utd-username-password-grouping {
    leaf username {
      description
        "Provide the username for authentication";
      mandatory true;
      type string;
    }
    leaf password {
      description
        "Provide the password for authentication";
      mandatory true;
      type string;
    }
  }

  grouping clear-cts-counters-ip-grouping {
    choice ip-choice {
      case ipv6-case {
        leaf ipv6 {
          description "Protocol Version - IPv4";
          type empty;
        }
      }
      case ipv4-case {
        leaf ipv4 {
          description "Protocol Version - IPv6";
          type empty;
        }
      }
    }
  }
 
  grouping clear-cts-source-destination-grouping { 
    choice from_to-choice {
      case security_tag-case {
        leaf security_tag {
          description "Security Group Tag";
          type uint16 {
            range "0..65519";
          }
        }
        choice ip-choice {
          case ipv6-case {
            leaf ipv6 {
              description "Protocol Version - IPv6";
              when "../security_tag";
              type empty;
            }
          }
          case ipv4-case {
            leaf ipv4 {
              description "Protocol Version - IPv4";
              when "../security_tag";
              type empty;
            }
          }
        }
      }
      case unknown-case {
        container unknown {
          description " Unknown Destination Group";
          presence true;
          uses clear-cts-counters-ip-grouping;
        }
      }
    }
  }

  grouping debug-level-grouping {
    container level {
      choice level-choice {
        case error-case {
          leaf error{
            description "Enable error debug";
            type empty;
          }
        }
        case info-case {
          leaf info{
              description "Enable info debug";
              type empty;
          }
        }
        case verbose-case {
          leaf verbose{
              description "Enable verbose debug";
              type empty;
          }
        }
        case warning-case {
          leaf warning{
              description "Enable warning debug";
              type empty;
          }
        }
      }
    }
  }



  rpc switch {
    input {
      leaf _switch-number {
        mandatory true;
        type uint8 {
          range "1..9";
         }
      }
      choice pri-renum-stack {
        mandatory true;
        case priority-case {
        leaf priority {
	  description 
	    "<1-15>  Switch Priority";
          type uint8 {
	    range "1..15";
          }
        }
	}
	case renumver-case {
        leaf renumber {
	  description 
	    "<1-9>  New number of the Switch";
          type uint8 {
	    range "1..9";
          }
        }
	}
	case stack-case {
	container statck {
          leaf port {
	    description 
	      "<1-2>  Stack port number to enable/disable";
            type uint8 {
	      range "1..2";
            }
          }
          }
        }
      }
    }
    output {
      uses cisco-xe-rpc-output; 
    }
  }
  rpc default {
    description 
      "Set a command to its defaults";
    input {
      choice default-choice {
        mandatory true;
        case interface-case {
          leaf interface {
            description 
	      "Select an interface to configure";
            type string {
              pattern "[A-Za-z]([\w/.-]+)";
            }

          }
        }
      }
    }
    output {
      uses cisco-xe-rpc-output; 
    }
  }
  rpc clear {
    description 
      "Clear";
    input {
      choice clear-choice {
        mandatory true;
        case interface-case {
          leaf interface {
            description 
              "Select an interface to clear";
            type string {
              pattern "[A-Za-z]([\w/.-]+)";
            }
          }
        }
        case count-case {
          leaf count {
            description 
              "Select an interface to clear";
            type string {
              pattern "[A-Za-z]([\w/.-]+)";
            }
          }
        }
        case flow-case {
          container flow {
            description "Flow monitor clear commands";
            choice flow-choice {
              case monitor-case {
                container monitor {
                  leaf name {
                    mandatory true;
                    type string;
                  }
                  choice monitor-option {
                    leaf force-export {
                      type empty;
                    }
                    leaf statistics {
                      type empty;
                    }
                    container cache {
                      leaf force-export {
                        type empty;
                      }
                    }
                  }
                }
              }
               case export-case {
                container exporter {
                  leaf name {
                    type string;
                  }
                  leaf statistics {
                    type empty;
                  }
                }
              }
            }
          } 
        }
        case ip-case {
          container ip {
            choice ip-protocol {
              case dhcp-case {
                container dhcp {
                  description
                    "Delete items from the DHCP database";
                  container binding {
                    description
                      "DHCP address bindings";
                    leaf vrf {
                      description 
                        "DHCP vrf bindings";
                      type string;
                    }
                    leaf _all {
                      description 
                        "Clear all automatic bindings";
                      mandatory true;
                      type string {
                        pattern "[*]";
                      }
                    }
                  }
                }
              }
              case ospf-case {
                container ospf {
                  leaf _id {
                    description
                      "Process ID number";
                    type uint16;
                  }
                  leaf process {
                    description
                      "Reset OSPF process";
                    type empty;
                  }
                }
              }
              case bgp-case {
                container bgp {
                  description
                    "Clear BGP connections";
                  leaf _peer-address {
                    description
                      "BGP neighbor address to clear";
                    type union {
                      type inet:ipv4-address;
                      type inet:ipv6-address;
                    }
                  }
                  leaf vrf {
                    description
                      "Select a VPN Routing/Forwarding instance";
                    type string;
                  }
                }
              }
            }
          }
        }
        case arp-cache-case {
          container arp-cache {
            description 
              "Clear the entire ARP cache";
            presence true;
            leaf vrf {
              description 
                "Clear entries for a VPN Routing/Forwarding instance";
              type string;
            }
            leaf interface {
              description
                "Clear the entire ARP cache on the interface";
              type string {
                pattern "[A-Za-z]([\w/.-]+)";
              }
            }
            leaf _ip {
              description 
                "IP address";
              type inet:ipv4-address;
            }
          }
        }
        case aaa-case {
          container aaa {
            description
              "Clear AAA values";
            container local {
              description
                "Clear AAA local method options";
              container user {
                description
                  "Clear local AAA users";
                container lockout {
                  description
                    "Clear locked out local AAA users";
                  leaf username {
                    description
                      "Username of the locked-user";
                    type string;
                  }
                }
              }
            }
          }
        }
        case platform-case {
          container platform {
            description
              "Clear platform information";
            container hardware {
              description
                "Clear platform hardware information";
              container qfp {
                description
                  "Quantum Flow Processor";
                container active {
                  description
                    "Active instance";
                  container feature {
                    description
                      "Clear features";
                    choice feature-choice {
                      container firewall {
                        description
                          "Clear QFP Firewall";
                        leaf drop {
                          description
                           "Clear firewall drop counters";
                          type empty;
                        }
                      }
                      container umbrella {
                         description
                           "Clear QFP Umbrella";
                           container datapath {
                              description
                                "Clear Umbrella datapath";
                              leaf stats {
                                 description
                                   "Clear Umbrella datapath stats";
                                   type empty;
                              }
                           }
                      }
                      container utd {
                        description
                          "Clear QFP UTD";
                        container stats {
                          description
                            "Clear UTD statistics";
                          choice stats-choice {
                            case all {
                              leaf _all {
                                type empty;
                              }
                            }
                            case default {
                              container default {
                                description
                                  "Default Context";
                                leaf context {
                                  description
                                    "Default Context";
                                  type empty;
                                }
                              }
                            }
                            case divert {
                              leaf divert {
                                description
                                  "Clear AppNav Redirect Statistics";
                                type empty;
                              }
                            }
                            case drop {
                              leaf drop {
                                description
                                  "Clear Drop Statistics";
                                type empty;
                              }
                            }
                            case general {
                              leaf general {
                                description
                                  "Clear General Statistics";
                                type empty;
                              }
                            }
                            case sn {
                              leaf sn {
                                description
                                  "Clear AppNav Service Node Statistics";
                                type empty;
                              }
                            }
                            case summary {
                              leaf summary {
                                description
                                  "Clear Summary Statistics";
                                type empty;
                              }
                            }
                            case vrf {
                              container vrf {
                                description
                                  "Clear VRF Statistics";
                                choice vrf-choice {
                                  case default-context {
                                    container default {
                                      description
                                        "Default Context";
                                      leaf context {
                                        description
                                          "Default Context";
                                        type empty;
                                      }
                                    }
                                  }
                                  case global {
                                    leaf global {
                                      description
                                        "Global domain";
                                      type empty;
                                    }
                                  }
                                  case id {
                                    leaf id {
                                      description
                                        "Clear VRF statistics by id";
                                      type uint16 {
                                        range "0..4096";
                                      }
                                    }
                                  }
                                  case name {
                                    leaf name {
                                      description
                                        "Clear VRF statistics by name";
                                      type string {
                                        length "1..32";
                                      }
                                    }
                                  }
                                }
                              }
                            }
                          }
                        }
                      }
                    }
                  }
                }
              }
            }
          }
        }
        case utd-case {
          container utd {
            description
              "Clear Unified Threat Defense information";
            container engine {
              description
                "Clear information about the UTD engine";
              container standard {
                description
                  "Clear information about the standard engine";
                choice utd-eng-std-choice {
                  container logging {
                    description
                      "Clear logging information/logs from the container";
                    leaf events {
                      description
                        "Clear engine logging events from the container";
                      type empty;
                    }
                  }
                  container statistics {
                    description
                      "Clear the engine statistics from the container";
                    choice stats-choice {
                      container daq {
                        description
                          "Clear statistics for DAQ from the container";
                        choice daq-choice {
                          case all {
                            leaf _all {
                              type empty;
                            }
                          }
                          case vrf {
                            container vrf {
                              description
                                "Specify VRF for the stats";
                              choice vrf-choice {
                                case global {
                                  leaf global {
                                    description
                                      "Global VRF";
                                    type empty;
                                  }
                                }
                                case name {
                                  leaf name {
                                    description
                                      "VRF name";
                                    type string {
                                      length "1..32";
                                    }
                                  }
                                }
                              }
                            }
                          }
                        }
                      }
                      container url-filtering {
                        description
                          "Clear statistics for url filtering from the container";
                        choice url-filtering-choice {
                          case all {
                            leaf _all {
                              type empty;
                            }
                          }
                          case vrf {
                            container vrf {
                              description
                                "Specify VRF for the stats";
                              choice vrf-choice {
                                case global {
                                  leaf global {
                                    description
                                      "Global VRF";
                                    type empty;
                                  }
                                }
                                case name {
                                  leaf name {
                                    description
                                      "VRF name";
                                    type string {
                                      length "1..32";
                                    }
                                  }
                                }
                              }
                            }
                          }
                        }
                      }
                    }
                  }
                }
              }
            }
          }
        }
        case zone-pair-case {
          container zone-pair {
            description
              "Clear zone-pair";
            leaf counter {
              description
                "Zone-pair counters";
              type empty;
            }
          }
        }
        case cts-case {
          container cts {
            description "Cisco Trusted Security commands";
            choice cts-choice {
              case counter-case {
                container counter {
                  description "Clear a CTS interface's counters or all counters";
                  presence true;
                  leaf interface {
                     description "GigabitEthernet IEEE 802.3z";    
                     type string;
                  }
                }
              }
              case credentials-case {
                leaf credentials {
                  description "Clear all CTS credentials, including all PACs";
                  type empty;
                }
              }
              case environment-data-case {
                leaf environment-data {
                  description "Clear CTS Environment Data";
                  type empty;
                }
              }
              case pac-case {
                container pac {
                  description "Clear a PAC or all PACs from the keystore";
                  choice pac-choice {
                    case A-ID-case {
                      leaf A-ID {
                        description "Specify A-ID of a PAC to be removed from the key store";
                        type string;
                      }
                    }
                    case all-case {
                      leaf all {
                        description "Clear all PACs on the device";
                        type empty;
                      }
                    }
                  }
                }
              }
              case role-based-case {
                container role-based {
                  description "Role-based Access Control information";
                  container counters {
                    description "Display role-based access control statistics per <SGT, DGT> cell";
                    presence true;
                    choice counters-choice {
                      case default-case {
                        container default {
                          description "Default policy counters";
                          presence true;
                          uses clear-cts-counters-ip-grouping;
                        }
                      }
                      case ipv4-case {
                        leaf ipv4 {
                          description "Protocol Version - IPv4";
                          type empty;
                        }
                      }
                      case ipv6-case {
                        leaf ipv6 {
                            description "Protocol Version - IPv4";
                            type empty;
                        }
                      }
                      case from-case {
                        container from {
                          description "Source Group";
                          uses clear-cts-source-destination-grouping;
                        }
                        container to {
                          description "Destination Group";
                          uses clear-cts-source-destination-grouping;
                        }
                      }
                    } 
                  }
                }
              }
              case server-case {
                leaf server {
                  description " Remove the specified authentication server";
                  type inet:ipv4-address;
                }
              }
              case sxp-case {
                container sxp {
                  description "Clear the SXP counters";
                  leaf filter-counters {
                    type empty;
                  }
                } 
              } 
            }
          }
        }
      }
    }
    output {
      uses cisco-xe-rpc-output; 
    }
  }
  rpc release {
    description 
      "Release a resource";
    input {
      leaf dhcp {
        description
	  "Release a dhcp lease (an interface)";
        type string;
      }
    }
    output {
      uses cisco-xe-rpc-output;
    }
  }
  rpc reload {
    description 
      "Halt and perform a cold restart";
    input {
      leaf force {
        description "Force a restart even if there is unsaved config";
        type boolean;
      }
      leaf reason {
        description "Reload reason";
        type string;
      }
    }
    output {
      uses cisco-xe-rpc-output; 
    }
  }
rpc cellular {
    input {
      leaf _if-name {
          type string;
      }
      container lte {
        choice action {
          case tech  {
            container technology {
              choice action {
                case lte {
                   leaf lte {
                     type empty;
                   }
                }
                case auto {
                  leaf auto {
                    type empty;
                  }
                }
                case umts {
                  leaf umts {
                    type empty;
                  }
                }
              }
            }
          }
          case modem-reset {
              leaf modem-reset {
                  type empty;
              }
          }
          case profile {
            container profile {
               choice prof {
                  case delete  {
                    description "Cellular Profile configuration";
                    container delete {
                      description "Delete a Profile";
                        leaf _profile-id {
                          description "Profile ID";
                          type uint8 {
                            range "1..16";
                          }
                        }
                    }
                  }
                  case create {
                    container create {
                      description "Create a Profile";
                      leaf _profile-id {
                        description "Profile ID";
                        type uint8 {
                          range "1..16";
                        }
                      }
                      leaf _prof_name {
                        description "Profile name";
                        type string;
                      }
                      choice auth {
                        case none {
                          leaf none {
                            type empty;
                          }
                        }
                        case chap {
                          leaf chap {
                            type empty;
                          }
                        }
                        case pap {
                          leaf pap {
                            type empty;
                          }
                        }
                        case pap_chap {
                          leaf pap_chap {
                            type empty;
                          }
                        }
                      }
                      leaf _user_name {
                        description "Username for authentication";
                        type string;
                      }
                      leaf _password {
                        description "Password for authentication";
                        type string;
                      }
                      choice pdn {
                        case ipv4 {
                          leaf ipv4 {
                            type empty;
                          }
                        }
                        case ipv6 {
                          leaf ipv6 {
                            type empty;
                          }
                        }
                        case ipv4v6 {
                          leaf ipv4v6 {
                            type empty;
                          }
                        }
                      }
                    }
                  }
                }
              }
            }
          }
        }
      }
    output {
      uses cisco-xe-rpc-output;
    }
  }

  rpc license {
    input {
      choice license-command-choice {
        case licese-smart  {
          container smart {
            choice smart-choice {
	      case register-case {
	        container register {
	          leaf idtoken {
	            mandatory true;
	            type string;
	          }
	          leaf force {
	            description "Forcefully register";
                    type empty;
                  }
                }
	      }
	      case deregister-case {
	        leaf deregister {
	          type empty;
                }
	      }
	      case renew-case {
	        container renew {
                  choice renew-choice {
	            mandatory true;
	            leaf ID {
	              type empty;
                    }
	            leaf auth {
	              type empty;
                    }
                  }
	        }
	      }
	    }
          }
        }
        case license-install {
          leaf install {
            description
	      "Install license information";
            type string {
              pattern "(((bootflash:)|(flash:)|(ftp:)|(http:)|(https:)|(nvram:)|(param:)|(scp:)|(syslog)|(system:)|(tftp:)|(tmpsys:)).*)";
            }
          }
        }
        case license-clear {
          leaf clear {
            description
	      "Clear license information. Feature name to clear";
            type string;
          }
        }
      }
    }
    output {
      uses cisco-xe-rpc-output; 
    }
  }

  rpc service {
    description "SD-AVC service management";
    input {
      container sd-avc {
        choice sd-avc-choice {
          mandatory true;
          case activate-case {
            leaf activate {
              type empty;
            }
          }
          case configure-case {
            container configure {
              container gateway {
                leaf interface {
                  type string; 
                }
                leaf service-ip {
                  type inet:ipv4-address; 
                }
                leaf activate {
                  type empty;
                }
              }
            }
          }
          case connect-case {
            leaf connect {
              type empty;
            }
          }
          case help-case {
            leaf help {
              type empty;
            }
          }
          case deactivate-case {
            leaf deactivate {
              type empty;
            }
          }
          case install-case {
            container install {
              leaf package {
                type string;
              }
            }
          }
          case status-case {
            leaf status {
             type empty;
            }
          }
          case unconfigure-case {
            leaf unconfigure {
              type empty;
            }
          }
          case uninstall-case {
            leaf uninstall {
              type empty;
            }
          } 
          case upgrade-case {
            container upgrade {
              leaf package {
                type string;
              }
            }
          }
        }
      }
    }
    output {
      uses cisco-xe-rpc-output;
    }
  }
  rpc virtual-service {
    description
      "Virtual-service management";
    input {
      choice operation {
        mandatory true;
        container install {
          leaf name {
             type string;
           }
           leaf package {
             type string;
           }
           leaf media {
             type string;
           }
         }
         container uninstall {
          leaf name {
            type string;
          }
        }
        container upgrade {
          leaf name {
            type string;
          }
          leaf package {
            type string;
          }
        }
      }
    }
    output {
      uses cisco-xe-rpc-output;
    }
  }
  rpc copy {
    description
      "Copy from one file to another";
    input {
      leaf _source {
        mandatory true;
        type string {
          pattern "((((bootflash:)|(harddisk:)|(flash:)|(nvram:)|(ftp:)|(http:)|(https:)|(scp:)|(tftp:)).*)|((running-config)|(startup-config)))";
        }
      }
      leaf _destination {
        mandatory true;
        type string {
          pattern "((((bootflash:)|(harddisk:)|(flash:)|(nvram:)|(ftp:)|(http:)|(https:)|(scp:)|(tftp:)).*)|((running-config)|(startup-config)))";
        }
      }
    }
    output {
      uses cisco-xe-rpc-output;
    }
  }
  rpc delete {
    description
      "Delete a file";
    input {
      leaf _filename {
        mandatory true;
        type string {
          pattern "(((bootflash:)|(harddisk:)|(flash:)|(nvram:)).*)";
        }
      }
    }
    output {
      uses cisco-xe-rpc-output;
    }
  }
  rpc app-hosting {
    description
      "App-hosting management";
    input {
      choice lifecycle {
        mandatory true;
        container install {
          leaf appid {
            type string;
          }
          leaf package {
            type string;
          }
        }
        container uninstall {
          leaf appid {
            type string;
          }
        }
        container activate {
          leaf appid {
            type string;
          }
        }
        container deactivate {
          leaf appid {
            type string;
          }
        }
        container start {
          leaf appid {
            type string;
          }
        }
        container stop {
          leaf appid {
            type string;
          }
        }
      }
    }
    output {
      uses cisco-xe-rpc-output;
    }
  }
  rpc guestshell {
    description
      "guestshell managementshell";
    input {
      choice action {
        mandatory true;
        case destroy-case {
          leaf destroy {
            description "Destroy guestshell";
            type empty;
          }
        }
        case disable-case {
          leaf disable {
            description "Disable guestshell";
            type empty;
          }
        }
        case enable-case {
          leaf enable {
            description "Enable guestshell";
            type empty;
          }
        }
      }
    }
    output {
      uses cisco-xe-rpc-output;
    }
  }
  rpc start {
    description "Start system operations";
    input {
      leaf maintenance {
        description "GIR start maintenance mode";
        type empty;
      }
    }
    output {
      uses cisco-xe-rpc-output;
    }
  }
  rpc stop {
    description "Stop system operations";
    input {
      leaf maintenance {
        description "GIR stop maintenance mode";
        type empty;
      }
    }
    output {
      uses cisco-xe-rpc-output;
    }
  }
  rpc utd {
    description "Unified Threat Defense commands";
    input {
      choice feature {
        case feature-threat {
          container threat-inspection {
            description
              "IPS/IDS related commands";
            container signature {
              description
                "Provide actions to be taken for signatures";
              choice method {
                container _saved {
                  leaf update {
                    description
                      "Update the IPS/IDS signature rules";
                    mandatory true;
                    type empty;
                  }
                }
                container _manual {
                  container update {
                    description
                      "Update the IPS/IDS signature rules";
                    choice type {
                      container file {
                        description
                          "Perform an update of the signature package using a local file";
                        leaf _filename {
                          mandatory true;
                          type string;
                        }
                      }
                      container server {
                        description
                          "Provide config options for the signature update server";
                        choice type {
                          container cisco {
                            description
                              "Use Cisco site to provide updates";
                            uses utd-username-password-grouping;
                          }
                          container url {
                            description
                              "Enter the complete URL for the path to the update server";
                            choice url-uname-passwd {
                              container _credentials {
                                leaf _url {
                                  mandatory true;
                                  type string;
                                }
                                uses utd-username-password-grouping;
                              }
                              container _no-credentials {
                                leaf _url {
                                  mandatory true;
                                  type string;
                                }
                              }
                            }
                          }
                        }
                      }
                    }
                  }
                }
              }
            }
          }
        }
        case feature-webfltr {
          container web-filter {
            description
              "Web-filter related commands";
            container database {
              description
                "Provide actions to be taken for the web-filter database";
              leaf update {
                description
                  "Update the web-filter database";
                mandatory true;
                type empty;
              }
            }
          }
        }
	case feature-file-inspection {
	  container file-inspection {
	    description 
	      "UTD file inspection commands";
	    container analysis {
	      description
	        "UTD file analysis related commands";
	      leaf apikey {
	        description
		  "Provide UTD file analysis apikey";
		mandatory true;
		type string {
		  length 1..128;
		}
	      }
	    }
	  }
	}
      }
    }
    output {
      uses cisco-xe-rpc-output;
    }
  }
  rpc hw-module {
    description "Control of individual components in the system";
    input {
      container switch {
        description
          "Switch in the system";
        leaf _switch-number {
          description
            "Switch number in the Stack (Refer to show switch CLI)";
          type uint8 {
            range "1..8";
          }
        }
        container usbflash1 {
          description
            "USB SSD";
          choice umount_sec {
            mandatory true;
            case unmount-case {
              leaf unmount {
                description
                  "unmount on usbflash1";
                  type empty;
              }
            }
            case security-case {
              container security {
                description
                  "Security on usbflash1";
                choice security-choice {
                  mandatory true;
                  case enable-case {
                    container enable {
                      description
                        "Enable security on usbflash1";
                      presence true;
                      leaf password {
                        description
                          "Enter password for enabling security on usbflash1";
                        type string;
                      }
                    }
                  }
                  case disable-case { 
                    container disable {
                      description
                        "Disable security on usbflash1";
                      presence true;
                      leaf password {
                        description
                          "Enter password for Disabling security on usbflash1";
                        type string;
                      }
                    }  
                  }
                  case unlock-case { 
                    container unlock {
                      description
                        "Unlock security on usbflash1";
                      presence true;
                      leaf password {
                        description
                          "Enter password for unlock security on usbflash1";
                        type string;
                      }
                    }  
                  }
                }
              }
            }
          }
        }
      }
    }
    output {
      uses cisco-xe-rpc-output;
    }
  }
  rpc cts {
    description "Cisco Trusted Security Exec Commands";
    input {
      container credentials {
        description "Insert CTS device ID and password into the keystore";
        leaf id {
          description "Specify the CTS device ID for this switch or router(upto 32 char)";
          type string {
            length "1..24";
          }
        }
        leaf password {
          description "specify this device's CTS password(upto 24 char)";
          when "../id";
          type string;
        }
      }
    }
    output {
        uses cisco-xe-rpc-output;
    }
  }

  rpc debug {
    description "Debug";
    input {
      choice debug-choice {
        mandatory true;
        case platform-case {
          container platform {
            description "Debug platform information";
            container condition {
              choice condition-choice {
                case start-case {
                  leaf start {
                    description "Start conditional debug";
                    type empty;
                  }
                }
                case stop-case {
                  leaf stop {
                    description "Stop conditional debug";
                    type empty;
                  }
                }
                case feature-case {
                  container feature {
                    description "For a specific feature";
                    container ipsec {
                      description "IPSEC feature";
                      container dataplane {
                        description "packet/flow information";
                        choice dataplane-debug-choice {
                          case submode-case {
                            container submode {
                              description "submode information";
                              choice submode-choice {
                                case all-case {
                                  container all {
                                    description "ipsec all submode";
                                    uses debug-level-grouping;
                                  } 
                                }
                                case cce-case {
                                  container cce {
                                    description "ipsec cce submode";
                                    uses debug-level-grouping;
                                  }
                                }
                                case pkt-dump {
                                  container pkt-dump {
                                    description "ipsec pkt-dump submode";
                                    uses debug-level-grouping;
                                  }
                                }
                              }
                              }
                            }
                            case droptype-case {
                              leaf droptype {
                                description "Set debug droptype";
                                type union {
                                  type uint8 {
                                    range "1..113";
                                  }
                                  type ios-types:range-string;
                                }
                              }
                            }
                                
                            case pktcorrupt-case {
                              leaf pktcorrupt { 
                                description "Set debug pkt corruption";
                                type uint8 {
                                  range "1..255";
                                }
                              }
                            }
                          }
                        }
                      }
                    }
                  }
                }
              }
            }
          }
       }
       container crypto {
         description "Cryptographic subsystem";
            container pki {
             description "PKI debugging information";
             leaf API {
               description "PKI API debugging information";
               type empty;
             }
             leaf callbacks {
               description "PKI callbacks debugging information";
               type empty;
             }
             leaf messages {
              description "PKI messages debugging information";
              type empty;
            }
             leaf scep {
              description "PKI scep debugging information";
              type empty;
            }
             container server {
               description "PKI server debugging information";
               presence true;
                  leaf performance {
                  description "PKI server performance debugging information";
                  type empty;
               }
             }
             container transactions {
              description "PKI transaction debugging information";
              presence true;
              leaf performance {
                description "PKI transaction performance debugging information";
                type empty;
              }
            }
             leaf validation {
              description "PKI validation debugging information";
              type empty;
            }
           }
           leaf est-client {
               description "EST client debugging information";
             type empty;
           }
           leaf ha {
             description "PKI HA debugging information";
             type empty;
           }
        }
      }
                                  
      output {
        uses cisco-xe-rpc-output;
      }
  }
  rpc no {
    description "no";
      
    input {
      choice no-case {
        case debug-case {
          container debug {
            choice debug-choice {
              mandatory true;
              case platform-case {
                container platform {
                  description "Debug platform information";
                  container condition {
                    choice condition-choice {
                      case start-case {
                        leaf start {
                          description "Start conditional debug";
                          type empty;
                        }
                      }
                      case stop-case {
                        leaf stop {
                          description "Stop conditional debug";
                          type empty;
                        }
                      }
                      case feature-case {
                        container feature {
                          description "For a specific feature";
                          container ipsec {
                            description "IPSEC feature";
                            container dataplane {
                              description "packet/flow information";
                              choice dataplane-debug-choice {
                                case submode-case {
                                  container submode {
                                    description "submode information";
                                    choice submode-choice {
                                      case all-case {
                                        container all {
                                          description "ipsec all submode";
                                          uses debug-level-grouping;
                                        } 
                                      }
                                      case cce-case {
                                        container cce {
                                          description "ipsec cce submode";
                                          uses debug-level-grouping;
                                        }
                                      }
                                      case pkt-dump {
                                        container pkt-dump {
                                          description "ipsec pkt-dump submode";
                                          uses debug-level-grouping;
                                        }
                                      }
                                    }
                                  }
                                }
                                case droptype-case {
                                  leaf droptype {
                                    description "Set debug droptype";
                                    type empty;
                                  }
                                }
                                case pktcorrupt-case {    
                                  leaf pktcorrupt { 
                                    description "Set debug pkt corruption";
                                    type empty;
                                  }
                                }
                              }
                            }
                          }
                        }
                      }
                    }
                  }
                }
              }
            }
          }
        }
      }
    }
    
    output {
      uses cisco-xe-rpc-output;
    }
  }                  
  rpc crypto {
    description "Encryption related commands";
    input {
      container pki {
        description "Public key components";
        choice subcommand {
          case benchmark {
            container benchmark {
              description "Benchmark commands";
              leaf start {
                 description "Collection limit";
                type uint16 {
                  range "0..9990";
                }
              }
              leaf wrap {
                description "Wrap data to the start of buffer";
                when "../start";
                type empty;
              }
              leaf stop {
                description "stop collecting benchmark data";
                type empty;
              }
            }
          }
          case crl {
            container crl {
              description "CRL command";
              leaf refresh-cache {
                description "Refresh the CRL in cache";
                type empty;
              }
            }
          }
          case server {
            container server {
              description "Server command";
              leaf _name {
                description "server name";
                mandatory true;
                type string;
              }
              container grant {
                description "Grant enrollment requests";
                leaf _id {
                  description "Enrollment id";
                  type uint16 {
                     range "1..999";
                  }
                }
                leaf all {
                  description "Grant all pending requests";
                  type empty;
                }
              }
              container password {
                description "One time password for SCEP enrollment";
                container generate {
                  description "Generate password";
                  presence true;
                  leaf _minutes {
                    description "Validity in minutes";
                    type uint16 {
                      range "1..1440";
                    }
                  }
                }
              }
              container reject {
                description "Reject enrollment requests";
                leaf _id {
                  description "Enrollment id";
                  type uint16 {
                    range "1..999";
                  }
                }
                leaf all {
                  description "Reject all pending requests";
                  type empty;
                }
              }
              container remove {
                description "Remove enrollment requests";
                leaf _id {
                  description "Enrollment id";
                  type uint16 {
                    range "1..999";
                  }
                }
                leaf all {
                  description "Remove all pending requests";
                  type empty;
                }
              }
              container request {
                description "Retrieve an enrollment request";
                container pkcs10 {
                  description "PKCS10 enrollment request";
                  leaf _location {
                    description "Retrieval location";
                    type enumeration {
                      enum "bootflash:";
                      enum "cns:";
                      enum "disk0:";
                      enum "disk1:";
                      enum "flash:";
                      enum "ftp:";
                      enum "http:";
                      enum "https:";
                      enum "null:";
                      enum "nvram:";
                      enum "pram:";
                      enum "rcp:";
                      enum "scep";
                      enum "scp:";
                      enum "sftp:";
                      enum "system:";
                      enum "tar:";
                      enum "terminal";
                      enum "tftp:";
                      enum "tmpsys:";
                      enum "tti";
                      enum "unix:";
                      enum "webui:";
                    }
                  }
                  choice format {
                    case base64 {
                      leaf base64 {
                        description "output in base64 format";
                        type empty;
                      }
                    }
                    case pem {
                      leaf pem {
                        description "output in pem format";
                        type empty;
                      }
                    }
                    case hex {
                      container hex {
                        description "output in hex format";
                        presence true;
                        leaf _tid {
                          description "Transaction ID";
                          type string;
                        }
                        leaf _nonce {
                          description "nonce";
                          type string;
                        }
                        leaf _rid {
                          description "Request ID";
                          type uint16 {
                             range "1..999";
                          } 
                        }
                      }
                    }         
                  } 
                }
              }
              leaf revoke {
                description "revoke certificate";
                type string {
                  pattern '([0-9a-fA-FxX]+)';
                }
              }
              leaf unrevoke {
                description "unrevoke certificate";
                type string {
                  pattern '([0-9a-fA-FxX]+)';
                }
              }
              leaf start {
                description "Start server";
                type empty;
              }
              leaf stop {
                description "Stop server";
                type empty;
              }
              container trim {
                description "Trim the CRL based on expired certificates";
                leaf url {
                  description "location of expired certs file";
                  type enumeration {
                    enum "bootflash:";
                    enum "cns:";
                    enum "disk0:";
                    enum "disk1:";
                    enum "flash:";
                    enum "ftp:";
                    enum "http:";
                    enum "https:";
                    enum "null:";
                    enum "nvram:";
                    enum "pram:";
                    enum "rcp:";
                    enum "scp:";
                    enum "sftp:";
                    enum "system:";
                    enum "tar:";
                    enum "tftp:";
                    enum "tmpsys:";
                    enum "unix:";
                    enum "webui:";
                  } 
                }
                leaf verbose {
                  type empty;
                }
              }
            }
          }
        }
      }
    }
    output {
        uses cisco-xe-rpc-output;
    }
  }  

}
