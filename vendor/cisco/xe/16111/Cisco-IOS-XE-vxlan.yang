module Cisco-IOS-XE-vxlan {
  namespace "http://cisco.com/ns/yang/Cisco-IOS-XE-vxlan";
  prefix ios-vxlan;

  import ietf-inet-types {
    prefix inet;
  }


  import Cisco-IOS-XE-native {
    prefix ios;
  }

  import Cisco-IOS-XE-types {
    prefix ios-types;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE Virtual Extensible Local Area Network (VXLAN) Yang Model.
     Copyright (c) 2018 by Cisco Systems, Inc.
     All rights reserved.";

  // =========================================================================
  // REVISION
  // =========================================================================
  revision 2018-10-15 {
     description
       "Initial revision";
  }

  grouping config-vxlan-grouping {
    container udp {
      leaf port {
        description
          "VxLAN dataplane UDP destination port for global";
        type uint16 {
          range "1024..65535";
        }
      }
    }
  }

  /////////////////////////////////////////////////////////
  // vxlan
  /////////////////////////////////////////////////////////
  augment "/ios:native/ios:vxlan" {
    uses config-vxlan-grouping;
  }

}
