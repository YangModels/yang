module Cisco-IOS-XE-wireless-mesh-cfg {
  yang-version 1;
  namespace "http://cisco.com/ns/yang/Cisco-IOS-XE-wireless-mesh-cfg";
  prefix wireless-mesh-cfg;

  import Cisco-IOS-XE-wireless-enum-types {
    prefix wireless-enum-types;
  }
  import Cisco-IOS-XE-wireless-types {
    prefix wireless-types;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Wireless Mesh Configuration
     Copyright (c) 2017-2018 by Cisco Systems, Inc.
     All rights reserved.";

  revision 2018-10-29 {
    description
      "Cleaned up spelling errors in descriptions.";
    reference "3.1.0";
  }
  revision 2018-05-01 {
    description
      "- Remove certain leafs from st-mesh-config
       - Remove certain leafs from st-mesh-profile
       - Remove grouping st-mesh-data-rate";
    reference "3.0.0";
  }
  revision 2018-01-24 {
    description
      "The first generally available version";
    reference "2.0.0";
  }
  revision 2017-10-06 {
    description
      "Initial revision";
    reference "1.0.0";
  }

  grouping st-mesh-config {
    description
      "This contains all attributes for mesh global config";
    leaf assoc-count-alarm-thresh {
      type uint32 {
        range "1 .. 30";
      }
      default "10";
      description
        "Threshold value for cumulative Association Count at parent mesh AP for generating Mesh Alarm";
    }
    leaf high-snr-alarm-thresh {
      type uint32 {
        range "31 .. 100";
      }
      default "60";
      description
        "Threshold value for higher SNR on backhaul link of a child mesh AP for generating Mesh Alarm";
    }
    leaf low-snr-alarm-thresh {
      type uint32 {
        range "1 .. 30";
      }
      default "12";
      description
        "Threshold value for lower SNR on backhaul link of a child mesh AP for generating Mesh Alarm";
    }
    leaf max-map-children-alarm-thresh {
      type uint32 {
        range "1 .. 50";
      }
      default "10";
      description
        "Threshold value for number of children MAPs on a parent MAAP for generating Mesh Alarm";
    }
    leaf max-rap-children-alarm-thresh {
      type uint32 {
        range "1 .. 50";
      }
      default "20";
      description
        "Threshold value for number of children MAPs on a parent RAP for generating Mesh Alarm";
    }
    leaf max-hop-alarm-thresh {
      type uint32 {
        range "1 .. 16";
      }
      default "4";
      description
        "Threshold value for number of hops from the MAP node to the RAP node for generating Mesh Alarm";
    }
    leaf parent-change-count-alarm-thresh {
      type uint32 {
        range "1 .. 30";
      }
      default "3";
      description
        "Threshold value for the number of times a child Mesh node changes its parent for generating Mesh Alarm";
    }
    leaf bhaul-rrm-enabled {
      type boolean;
      default "false";
      description
        "This value indicates if RRM should be enabled or not in the backhaul radio of a root Mesh AP, which does not have any child Mesh APs";
    }
    leaf bhaul-bdomain-chan-used {
      type boolean;
      default "false";
      description
        "This value indicates whether UNII B domain channels are enabled or not in the backhaul radio of Mesh Access Points";
    }
    leaf cac-enabled {
      type boolean;
      default "false";
      description
        "This value indicates whether Call Admission Control is enabled or not for the Mesh Access Points";
    }
    leaf psk-prov-mode {
      type boolean;
      default "false";
      description
        "This value indicates whether PSK provisioning is enabled or not for the Mesh AP";
    }
    leaf default-psk {
      type boolean;
      default "false";
      description
        "Whether default psk is enabled or not for the Mesh AP";
    }
    leaf psk-inuse-index {
      type uint8 {
        range "1 .. 5";
      }
      default "1";
      description
        "This value indicates the PSK in-use key index";
    }
    leaf rap-channel-sync-enabled {
      type boolean;
      default "false";
      description
        "This value indicates whether syncing of Mesh root AP channels across mobility group is enabled or not for Mesh";
    }
    leaf eth-bridging-bpdu-allowed {
      type boolean;
      default "false";
      description
        "This value indicates whether we should allow BPDU packets on the Mesh network when Ethernet bridging is enabled";
    }
    leaf public-safety-enabled {
      type boolean;
      default "false";
      description
        "This value indicates whether public safety band is enabled or not";
    }
  }

  grouping st-mesh-data-rate {
    description
      "This value indicates the Mesh backhaul data rate";
    leaf type {
      type wireless-types:mesh-bhaul-data-rate-type;
      default "mesh-bhaul-rate-auto";
      description
        "This value indicates the backhaul date rate type(auto, 802.11abg, 802.11n, 802.11ac)";
    }
    leaf rate {
      type wireless-types:mesh-dot11abg-data-rate;
      default "data-rate-auto";
      description
        "This value indicates enum value for Mesh backhaul 802.11 tx rate in kbps";
    }
    leaf dot11n-mcs-index {
      type uint8 {
        range "0 .. 31";
      }
      default "0";
      description
        "This value indicates Mesh backhaul tx rate 802.11n mcs index";
    }
    leaf dot11ac-mcs-index {
      type uint8 {
        range "0 .. 9";
      }
      default "0";
      description
        "This value indicates Mesh backhaul tx rate 802.11ac mcs index";
    }
    leaf spatial-stream {
      type uint8 {
        range "1 .. 4";
      }
      default "1";
      description
        "This value indicates Mesh backhaul tx rate 802.11ac spatial stream";
    }
  }

  grouping st-mesh-profile {
    description
      "This value indicates the description of the Mesh profile";
    leaf profile-name {
      type string;
      description
        "This value indicates the name of Mesh profile";
    }
    leaf description {
      type string;
      default "";
      description
        "This value indicates the name of the Mesh profile description";
    }
    leaf amsdu-enabled {
      type boolean;
      default "true";
      description
        "This value indicates whether A-MSDU is enabled or not on the backhaul radio of Mesh AP";
    }
    leaf bg-scan-enabled {
      type boolean;
      default "false";
      description
        "This value indicates whether background scanning is enabled or not on the backhaul radio of Mesh AP";
    }
    leaf ccn-mode {
      type boolean;
      default "false";
      description
        "This value indicates whether a parent Mesh AP should send Channel change notification for children mesh APs";
    }
    leaf bhaul-client-access {
      type boolean;
      default "false";
      description
        "This value indicates whether Client Access is enabled or not on the Backhaul Radio of the Mesh AP";
    }
    leaf eth-vlan-transparent {
      type boolean;
      default "true";
      description
        "This value indicates whether Ethernet bridging on Mesh APs should use vlan configuration or not";
    }
    leaf full-sector-dfs {
      type boolean;
      default "true";
      description
        "This value indicates whether full sector DFS feature is enabled or not on the Mesh network";
    }
    leaf ids-state-enabled {
      type boolean;
      default "false";
      description
        "This value indicates whether Mesh AP should send the IDS, rogue reports to WLC";
    }
    leaf multicast-mode {
      type wireless-types:mesh-multicast-mode;
      default "mesh-multicast-mode-inout";
      description
        "This value indicates the multicast mode over mesh network for Ethernet bridged multicast traffic";
    }
    leaf range {
      type uint32 {
        range "150 .. 132000";
      }
      default "12000";
      description
        "This value indicates the maximum range between outdoor root and mesh Access Points";
    }
    leaf security-mode {
      type wireless-types:mesh-security-mode;
      default "mesh-security-mode-eap";
      description
        "This value indicates the security method used for Mesh Access Points";
    }
    leaf conv-method {
      type wireless-types:mesh-convergence-method;
      default "mesh-convergence-standard";
      description
        "This value indicates Convergence method used in the Mesh Access Points";
    }
    leaf lsc-only-auth {
      type boolean;
      default "false";
      description
        "This value indicates whether LSC Authentication is enabled or not for the Mesh AP";
    }
    leaf bridgegroupname {
      type string;
      default "";
      description
        "This value indicates if strict matching of bridge group name is enabled for Mesh Access Points for parent selection";
    }
    leaf bgn-strict-match-enabled {
      type boolean;
      default "false";
      description
        "This value indicates whether Ethernet bridging is enabled or not for Mesh Access Points";
    }
    leaf eth-bridging-enabled {
      type boolean;
      default "false";
      description
        "This value indicates whether Ethernet bridging is enabled or not for Mesh Access Points";
    }
    leaf battery-state-enabled {
      type boolean;
      default "true";
      description
        "This value indicates whether external battery state is enabled or not for the Mesh Access Point";
    }
    leaf authorization-method {
      type string;
      default "";
      description
        "AAA method for the mesh access point authorization";
    }
    leaf authentication-method {
      type string;
      default "";
      description
        "AAA method for the mesh access point authentication";
    }
    container bhaul-tx-rate-dot11bg {
      description
        "Mesh backhaul tx rate for 2.4ghz radio backhaul";
      uses wireless-mesh-cfg:st-mesh-data-rate;
    }
    container bhaul-tx-rate-dot11a {
      description
        "Mesh backhaul tx rate for 5ghz radio backhaul";
      uses wireless-mesh-cfg:st-mesh-data-rate;
    }
  }

  grouping st-mesh-psk {
    description
      "This contains all attributes for mesh psk config";
    leaf index {
      type uint8 {
        range "1 .. 5";
      }
      description
        "This value indicates the key index";
    }
    leaf psk-key {
      type string;
      default "";
      description
        "This values indicates the psk key";
    }
    leaf psk-key-type {
      type wireless-enum-types:crypt-type;
      default "clear";
      description
        "This values indicates the type of the key";
    }
    leaf description {
      type string;
      default "";
      description
        "This value indicates the description of the psk key";
    }
  }

  container mesh-cfg-data {
    description
      "This contains all attributes for mesh config";
    container mesh {
      presence "mesh";
      description
        "This contains all attributes for mesh global config";
      uses wireless-mesh-cfg:st-mesh-config;
    }
    container mesh-profiles {
      description
        "Mesh profiles configuration";
      list mesh-profile {
        key "profile-name";
        description
          "This contains all attributes for mesh profile config";
        uses wireless-mesh-cfg:st-mesh-profile;
      }
    }
    container mesh-psks {
      description
        "Mesh psk config";
      list mesh-psk {
        key "index";
        description
          "This contains all attributes for the mesh psk config";
        uses wireless-mesh-cfg:st-mesh-psk;
      }
    }
  }
}
