module Cisco-IOS-XE-cellwan-oper {
  yang-version 1;
  namespace "http://cisco.com/ns/yang/Cisco-IOS-XE-cellwan-oper";
  prefix cellwan-ios-xe-oper;

  import ietf-inet-types {
    prefix inet;
  }
  import ietf-yang-types {
    prefix yang;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for cellwan operational data.
     Copyright (c) 2018 by Cisco Systems, Inc.
     All rights reserved.";

  revision 2018-10-29 {
    description
      "Cleaned up spelling errors in descriptions.";
    reference "1.2.0";
  }
  revision 2018-05-18 {
    description
      "Addition of Cellular Sim Security, GPS and SMS data";
    reference "1.1.0";
  }
  revision 2018-05-01 {
    description
      "Initial revision";
    reference "1.0.0";
  }

  typedef modem-status {
    type enumeration {
      enum "modem-status-offline" {
        value 0;
        description
          "Modem is in Offline state";
      }
      enum "modem-status-online" {
        value 1;
        description
          "Modem is in Online state";
      }
      enum "modem-status-low-power" {
        value 2;
        description
          "Modem is in Low Power Mode state";
      }
      enum "modem-status-power-off" {
        value 3;
        description
          "Modem is in power off state";
      }
      enum "modem-status-boot-ready" {
        value 4;
        description
          "Modem is in boot ready state";
      }
      enum "modem-status-unknown" {
        value 5;
        description
          "Modem is in unknown state";
      }
    }
    description
      "Modem status indicates the current state of cellular modem";
  }

  typedef cw-radio-power-status {
    type enumeration {
      enum "radio-power-mode-online" {
        value 0;
        description
          "Cellular modem is in online radio mode";
      }
      enum "radio-power-mode-low-power" {
        value 1;
        description
          "Cellular modem is in low power radio mode";
      }
      enum "radio-power-mode-factory-test" {
        value 2;
        description
          "Cellular modem is in factory test radio mode";
      }
      enum "radio-power-mode-offline" {
        value 3;
        description
          "Cellular modem is in offline radio mode";
      }
      enum "radio-power-mode-reset" {
        value 4;
        description
          "Cellular modem is in reset radio mode";
      }
      enum "radio-power-mode-off" {
        value 5;
        description
          "Cellular modem is in off radio mode";
      }
      enum "radio-power-mode-persistent-low-power" {
        value 6;
        description
          "Cellular modem is in persistent low power radio mode";
      }
    }
    description
      "Radio power status indicates the current radio power mode of cellular modem";
  }

  typedef radio-bandwidth {
    type enumeration {
      enum "bandwidth-1-dot-4-mhz" {
        value 0;
        description
          "Cellular radio bandwidth is 1.4 MHz";
      }
      enum "bandwidth-3-mhz" {
        value 1;
        description
          "Cellular radio bandwidth is 3 MHz";
      }
      enum "bandwidth-5-mhz" {
        value 2;
        description
          "Cellular radio bandwidth is 5 MHz";
      }
      enum "bandwidth-10-mhz" {
        value 3;
        description
          "Cellular radio bandwidth is 10 MHz";
      }
      enum "bandwidth-15-mhz" {
        value 4;
        description
          "Cellular radio bandwidth is 15 MHz";
      }
      enum "bandwidth-20-mhz" {
        value 5;
        description
          "Cellular radio bandwidth is 20 MHz";
      }
      enum "bandwidth-invalid" {
        value 6;
        description
          "Cellular radio bandwidth is invalid";
      }
      enum "bandwidth-unknown" {
        value 7;
        description
          "Cellular radio bandwidth is unknown";
      }
    }
    description
      "Radio bandwidth indicates the current cellular radio bandwidth selected in MHz";
  }

  typedef modem-technology {
    type enumeration {
      enum "cdma-evdo-1x-rtt" {
        value 0;
        description
          "Modem technology selected is CDMA (Code Division Multiple Access) / 
             EVDO (Evolution-Data Optimized) / 
             1xRTT (Single carrier (1x) radio transmission technology)";
      }
      enum "gsm-umts-gprs" {
        value 1;
        description
          "Modem technology selected is GSM (Global System for Mobile Communications) 
             / UMTS (Universal Mobile Telecommunications Service) 
             / GPRS (General Packet Radio Service)";
      }
      enum "tech-unknown" {
        value 2;
        description
          "Modem technology selected is unknown";
      }
    }
    description
      "Modem technology indicates the current cellular technology selected";
  }

  typedef rat-preference {
    type enumeration {
      enum "lte-radio-tech-no-svc" {
        value 0;
        description
          "Radio technology preference is no svc";
      }
      enum "lte-radio-tech-cdma-1-xrtt" {
        value 1;
        description
          "Radio technology preference is CDMA (Code Division Multiple Access) 
           / 1xRTT (Single carrier (1x) radio transmission technology)";
      }
      enum "lte-radio-tech-cdma-evdo" {
        value 2;
        description
          "Radio technology preference is CDMA (Code Division Multiple Access) 
           / EVDO (Evolution-Data Optimized) ";
      }
      enum "lte-radio-tech-amps" {
        value 3;
        description
          "Radio technology preference is AMPS (Advanced Mobile Phone Service)";
      }
      enum "lte-radio-tech-gsm" {
        value 4;
        description
          "Radio technology preference is GSM (Global System for Mobile Communications)";
      }
      enum "lte-radio-tech-umts" {
        value 5;
        description
          "Radio technology preference is UMTS (Universal Mobile Telecommunications Service)";
      }
      enum "lte-radio-tech-wlan" {
        value 6;
        description
          "Radio technology preference is WLAN (wireless local area network)";
      }
      enum "lte-radio-tech-gprs" {
        value 7;
        description
          "Radio technology preference is GPRS (General Packet Radio Service)";
      }
      enum "lte-radio-tech-lte" {
        value 8;
        description
          "Radio technology preference is LTE (Long-Term Evolution)";
      }
      enum "lte-radio-tech-auto" {
        value 9;
        description
          "Radio technology preference is AUTO ";
      }
      enum "lte-radio-tech-hybrid-cdma" {
        value 10;
        description
          "Radio technology preference is Hybrid CDMA (Hybrid Code Division Multiple Access)";
      }
      enum "lte-radio-tech-wcdma" {
        value 11;
        description
          "Radio technology preference is WCDMA (Wideband Code Division Multiplexing Access)";
      }
      enum "lte-radio-tech-gwl" {
        value 12;
        description
          "Radio technology preference is GWL ";
      }
      enum "lte-radio-tech-edge" {
        value 13;
        description
          "Radio technology preference is EDGE (Enhanced Data rates for GSM Evolution)";
      }
      enum "lte-radio-tech-hsdpa-n-wcdma" {
        value 14;
        description
          "Radio technology preference is HSDPA (High Speed Downlink Packet Access)
           & WCDMA (Wideband Code Division Multiplexing Access)";
      }
      enum "lte-radio-tech-wcdma-n-hsupa" {
        value 15;
        description
          "Radio technology preference is WCDMA (Wideband Code Division Multiplexing Access)
             & HSUPA (High Speed Uplink Packet Access)";
      }
      enum "lte-radio-tech-hsdpa-n-hsupa" {
        value 16;
        description
          "Radio technology preference is HSDPA (High Speed Downlink Packet Access)
             & HSUPA (High Speed Uplink Packet Access)";
      }
      enum "lte-radio-tech-hsdpa-plus-n-wcdma" {
        value 17;
        description
          "Radio technology preference is HSDPA+ (High Speed Downlink Packet Access plus) 
             & WCDMA (Wideband Code Division Multiplexing Access)";
      }
      enum "lte-radio-tech-hsdpa-plus-n-hsupa" {
        value 18;
        description
          "Radio technology preference is HSDPA+ (High Speed Downlink Packet Access plus)
             & HSUPA (High Speed Uplink Packet Access)";
      }
      enum "lte-radio-tech-dc-hsdpa-plus-n-wcdma" {
        value 19;
        description
          "Radio technology preference is 
             DC HSDPA+ (Dual Carrier High Speed Downlink Packet Access plus) 
             & WCDMA (Wideband Code Division Multiplexing Access)";
      }
      enum "lte-radio-tech-dc-hsdpa-plus-n-hsupa" {
        value 20;
        description
          "Radio technology preference is 
             DC HSDPA+ (Dual Carrier High Speed Downlink Packet Access plus) 
             & HSUPA (High Speed Uplink Packet Access)";
      }
      enum "lte-radio-tech-null-bearer" {
        value 21;
        description
          "Radio technology preference is Null Bearer ";
      }
      enum "lte-radio-tech-unknown" {
        value 22;
        description
          "Radio technology preference is Unknown ";
      }
      enum "lte-radio-tech-no-change" {
        value 23;
        description
          "Radio technology preference is unchanged ";
      }
    }
    description
      "RAT preference indicates the current radio technology preference";
  }

  typedef rat-technology {
    type enumeration {
      enum "system-mode-none" {
        value 0;
        description
          "Radio technology selected is none";
      }
      enum "system-mode-gprs" {
        value 1;
        description
          "Radio technology selected is GPRS (General Packet Radio Service)";
      }
      enum "system-mode-edge" {
        value 2;
        description
          "Radio technology selected is EDGE (Enhanced Data rates for GSM Evolution)";
      }
      enum "system-mode-umts" {
        value 3;
        description
          "Radio technology selected is UMTS (Universal Mobile Telecommunications System)";
      }
      enum "system-mode-hsdpa" {
        value 4;
        description
          "Radio technology selected is HSDPA (High Speed Downlink Packet Access)";
      }
      enum "system-mode-hsupa" {
        value 5;
        description
          "Radio technology selected is HSUPA (High Speed Uplink Packet Access)";
      }
      enum "system-mode-hspa" {
        value 6;
        description
          "Radio technology selected is HSPA (High Speed Packet Access)";
      }
      enum "system-mode-hspa-plus" {
        value 7;
        description
          "Radio technology selected is HSPA+ (Evolved High Speed Packet Access)";
      }
      enum "system-mode-lte-fdd" {
        value 8;
        description
          "Radio technology selected is LTE-FDD (Long Term Evolution-Frequency Division Duplex)";
      }
      enum "system-mode-lte-tdd" {
        value 9;
        description
          "Radio technology selected is LTE-TDD(Long Term Evolution-Time Division Duplex)";
      }
      enum "system-mode-lte-e-hrpd-1x-rtt" {
        value 10;
        description
          "Radio technology selected is LTE (Long Term Evolution) /
             eHRPD (Evolved High Rate Packet Data) /
             1xRTT (Single carrier (1x) radio transmission technology)";
      }
      enum "system-mode-lte-e-hrpd-evdo" {
        value 11;
        description
          "Radio technology selected is LTE (Long Term Evolution) / 
             eHRPD (Evolved High Rate Packet Data) / 
             EVDO (Evolution-Data Optimized) ";
      }
      enum "system-mode-evdo" {
        value 12;
        description
          "Radio technology selected is EVDO (Evolution-Data Optimized)";
      }
      enum "system-mode-evdo-reva" {
        value 13;
        description
          "Radio technology selected is EVDO (Evolution-Data Optimized) / 
             REVA (Evolution Data Optimized - Rev A)";
      }
      enum "system-mode-hsdpa-n-wcdma" {
        value 14;
        description
          "Radio technology selected is HSDPA (High Speed Downlink Packet Access) 
             & WCDMA (Wideband Code Division Multiple Access)";
      }
      enum "system-mode-wcdma-n-hsupa" {
        value 15;
        description
          "Radio technology selected is WCDMA (Wideband Code Division Multiple Access)
             & HSUPA (High Speed Uplink Packet Access) ";
      }
      enum "system-mode-hsdpa-n-hsupa" {
        value 16;
        description
          "Radio technology selected is HSDPA (High Speed Downlink Packet Access) 
             & HSUPA (High Speed Uplink Packet Access) ";
      }
      enum "system-mode-hsdpa-plus-n-wcdma" {
        value 17;
        description
          "Radio technology selected is HSDPA+ (High Speed Downlink Packet Access plus) 
             & WCDMA (Wideband Code Division Multiple Access)";
      }
      enum "system-mode-hsdpa-plus-n-hsupa" {
        value 18;
        description
          "Radio technology selected is HSDPA+ (High Speed Downlink Packet Access plus) 
             & HSUPA (High Speed Uplink Packet Access) ";
      }
      enum "system-mode-dc-hsdpa-plus-n-wcdma" {
        value 19;
        description
          "Radio technology selected is 
             DC HSDPA+ (Dual Carrier High Speed Downlink Packet Access plus) 
             & WCDMA (Wideband Code Division Multiple Access)";
      }
      enum "system-mode-dc-hsdpa-plus-n-hsupa" {
        value 20;
        description
          "Radio technology selected is 
             DC HSDPA+ (Dual Carrier High Speed Downlink Packet Access plus)
             & HSUPA (High Speed Uplink Packet Access)";
      }
      enum "sysyem-mode-null-bearer" {
        value 21;
        description
          "Radio technology selected is null bearer";
      }
      enum "system-mode-unknown" {
        value 22;
        description
          "Radio technology selected is unknown";
      }
    }
    description
      "RAT technology indicates the current radio technology selected";
  }

  typedef service-status {
    type enumeration {
      enum "service-status-normal" {
        value 0;
        description
          "Cellular Network status is in normal state";
      }
      enum "service-status-emergency" {
        value 1;
        description
          "Cellular Network status is in emergency state";
      }
      enum "service-status-no-service" {
        value 2;
        description
          "Cellular Network status is in no service state";
      }
      enum "service-status-unknown" {
        value 3;
        description
          "Cellular Network status is in unknown state";
      }
    }
    description
      "Service status indicates the current network service for cellular modem";
  }

  typedef modem-service {
    type enumeration {
      enum "service-type-circuit-switched" {
        value 0;
        description
          "Cellular Network service type is circuit-switched";
      }
      enum "service-type-packet-switched" {
        value 1;
        description
          "Cellular Network service type is packet-switched";
      }
      enum "service-type-combined" {
        value 2;
        description
          "Cellular Network service type is combined";
      }
      enum "service-type-invalid" {
        value 3;
        description
          "Cellular Network service type is invalid";
      }
      enum "service-type-unknown" {
        value 4;
        description
          "Cellular Network service type is unknown";
      }
    }
    description
      "Modem service indicates the current network service type for cellular modem";
  }

  typedef lte-ca {
    type enumeration {
      enum "lte-ca-deconfigured" {
        value 0;
        description
          "LTE carrier aggregation is deconfigured";
      }
      enum "lte-ca-deactivated" {
        value 1;
        description
          "LTE carrier aggregation is deactivated";
      }
      enum "lte-ca-activated" {
        value 2;
        description
          "LTE carrier aggregation is activated";
      }
      enum "lte-ca-unsupported" {
        value 3;
        description
          "LTE carrier aggregation is unsupported";
      }
    }
    description
      "LTE CA indicates the LTE carrier aggregation status for cellular modem";
  }

  typedef reg-state {
    type enumeration {
      enum "reg-status-not-registered" {
        value 0;
        description
          "Cellular Network is in not registered state";
      }
      enum "reg-status-registered" {
        value 1;
        description
          "Cellular Network is in registered state";
      }
      enum "reg-status-searching" {
        value 2;
        description
          "Cellular Network is in searching state";
      }
      enum "reg-status-registration-denied" {
        value 3;
        description
          "Cellular Network is in registration denied state";
      }
      enum "reg-status-unsupported" {
        value 4;
        description
          "Cellular Network is in unsupported state";
      }
    }
    description
      "Registration state indicates the current cellular network registration state";
  }

  typedef packet-sess-status {
    type enumeration {
      enum "packet-session-status-inactive" {
        value 0;
        description
          "Cellular packet session status is inactive";
      }
      enum "packet-session-status-active" {
        value 1;
        description
          "Cellular packet session status is active";
      }
    }
    description
      "Packet Session Status indicates the Cellular packet session state";
  }

  typedef profile-scope {
    type enumeration {
      enum "scope-global" {
        value 0;
        description
          "IP address scope is Global";
      }
      enum "scope-link" {
        value 1;
        description
          "IP address scope is Link";
      }
    }
    description
      "Profile Scope indicates the IP address scope";
  }

  typedef cellwan-chv1-sim-status {
    type enumeration {
      enum "chv1-verify-disabled" {
        value 0;
        description
          "SIM card holder verification (CHV1) disabled";
      }
      enum "chv1-verify-enabled" {
        value 1;
        description
          "SIM card holder verification (CHV1) enabled";
      }
      enum "chv1-verify-pending" {
        value 2;
        description
          "SIM card holder verification (CHV1) pending";
      }
    }
    description
      "Cellular modem SIM card holder verification (CHV1) status";
  }

  typedef cellwan-sim-status {
    type enumeration {
      enum "sim-status-ok" {
        value 0;
        description
          "Cellular modem SIM status is inserted";
      }
      enum "sim-status-not-inserted" {
        value 1;
        description
          "Cellular modem SIM is not inserted";
      }
      enum "sim-status-removed" {
        value 2;
        description
          "Cellular modem SIM is in removed state";
      }
      enum "sim-status-init-failure" {
        value 3;
        description
          "Cellular modem SIM is in initialization failure state";
      }
      enum "sim-status-general-failure" {
        value 4;
        description
          "Cellular modem SIM is in general failure state";
      }
      enum "sim-status-locked" {
        value 5;
        description
          "Cellular modem SIM is in locked state";
      }
      enum "sim-status-chv1-blocked" {
        value 6;
        description
          "Cellular modem SIM is in chv1 (Card Holder Verification) blocked state";
      }
      enum "sim-status-chv2-blocked" {
        value 7;
        description
          "Cellular modem SIM is in chv2 (Card Holder Verification) blocked state";
      }
      enum "sim-status-chv1-rejected" {
        value 8;
        description
          "Cellular modem SIM is in chv1 (Card Holder Verification) rejected state";
      }
      enum "sim-status-chv2-rejected" {
        value 9;
        description
          "Cellular modem SIM is in chv2 (Card Holder Verification) rejected state";
      }
      enum "sim-status-mep-locked" {
        value 10;
        description
          "Cellular modem SIM is in MEP (Mobile Equipment Personalization) locked state";
      }
      enum "sim-status-network-reject" {
        value 11;
        description
          "Cellular modem SIM is in network reject state";
      }
      enum "sim-status-unknown" {
        value 12;
        description
          "Cellular modem SIM is in unknown state";
      }
    }
    description
      "Cellular modem SIM status";
  }

  typedef cellwan-sim-user-op {
    type enumeration {
      enum "sim-user-op-none" {
        value 0;
        description
          "Cellular modem SIM user operation is in None state";
      }
      enum "sim-user-op-chv1" {
        value 1;
        description
          "Cellular modem SIM user is in CHV1 (Card Holder Verification) state";
      }
      enum "sim-user-op-chv2" {
        value 2;
        description
          "Cellular modem SIM user is in CHV2 (Card Holder Verification) state";
      }
      enum "sim-user-op-unblock-chv1" {
        value 3;
        description
          "Cellular modem SIM user is in Unblocked CHV1 (Card Holder Verification) state";
      }
      enum "sim-user-op-unblock-chv2" {
        value 4;
        description
          "Cellular modem SIM user is in Unblocked CHV2 (Card Holder Verification) state";
      }
      enum "sim-user-op-mep" {
        value 5;
        description
          "Cellular modem SIM user is in MEP (Mobile Equipment Personalization) state";
      }
      enum "sim-user-op-unknown" {
        value 6;
        description
          "Cellular modem SIM user operation is in Unknown state";
      }
    }
    description
      "Cellular modem SIM user operation status";
  }

  typedef cwan-gps-feature-state {
    type enumeration {
      enum "gps-disabled" {
        value 0;
        description
          "Cellular modem GPS feature state is Disabled";
      }
      enum "gps-enabled" {
        value 1;
        description
          "Cellular modem GPS feature state is Enabled";
      }
    }
    description
      "Cellular modem GPS feature state status";
  }

  typedef cwan-gps-port-selected {
    type enumeration {
      enum "dedicated-gps-port" {
        value 0;
        description
          "Cellular modem dedicated GPS port selected";
      }
      enum "div-gps-port" {
        value 1;
        description
          "Cellular modem DIV port selected for GPS";
      }
      enum "voltage-no-bias-gps-port" {
        value 2;
        description
          "Cellular modem voltage no-bias port selected for GPS";
      }
      enum "gps-port-none" {
        value 3;
        description
          "Cellular modem none port selected for GPS";
      }
    }
    description
      "Cellular modem GPS port selection status";
  }

  typedef cwan-gps-state {
    type enumeration {
      enum "gps-state-disabled" {
        value 1;
        description
          "Cellular modem is in GPS disabled state";
      }
      enum "gps-state-acquiring" {
        value 2;
        description
          "Cellular modem is in GPS acquiring state";
      }
      enum "gps-state-enabled" {
        value 3;
        description
          "Cellular modem is in GPS enabled state";
      }
      enum "gps-loc-error" {
        value 4;
        description
          "Cellular modem is in GPS location error state";
      }
    }
    description
      "Cellular modem GPS state";
  }

  typedef cwan-gps-mode-selected {
    type enumeration {
      enum "gps-mode-disable" {
        value 0;
        description
          "Cellular modem GPS mode is disabled";
      }
      enum "gps-mode-standalone" {
        value 1;
        description
          "Cellular modem GPS mode is standalone";
      }
      enum "gps-mode-mbased" {
        value 2;
        description
          "Cellular modem GPS mode is ms-based";
      }
      enum "gps-mode-msassist" {
        value 3;
        description
          "Cellular modem GPS mode is ms-assist";
      }
    }
    description
      "Cellular modem GPS mode selection status";
  }

  grouping cellwan-hardware-entry {
    description
      "Cellular modem hardware status entry details";
    leaf cellular-interface {
      type string;
      description
        "Cellular interface";
    }
    leaf cellular-firmware-version {
      type string;
      description
        "Cellular Modem firmware version";
    }
    leaf cellular-firmware-build-time {
      type string;
      description
        "Cellular Modem firmware build time";
    }
    leaf cellular-hardware-version {
      type string;
      description
        "Cellular Modem hardware version";
    }
    leaf cellular-device-model {
      type string;
      description
        "Cellular Modem device model type";
    }
    leaf cellular-imsi {
      type string;
      description
        "Cellular Modem IMSI";
    }
    leaf cellular-imei {
      type string;
      description
        "Cellular Modem IMEI";
    }
    leaf cellular-iccid {
      type string;
      description
        "Cellular Modem ICCID";
    }
    leaf cellular-msisdn {
      type string;
      description
        "Cellular Modem MSISDN";
    }
    leaf cellular-fsn {
      type string;
      description
        "Cellular Modem FSN";
    }
    leaf cellular-modem-status {
      type cellwan-ios-xe-oper:modem-status;
      description
        "Cellular Modem Status";
    }
    leaf cellular-modem-temperature {
      type int16;
      description
        "Cellular Modem temperature";
    }
    leaf cellular-pri-skuid {
      type string;
      description
        "Cellular Modem PRI sku id";
    }
    leaf cellular-pri-version {
      type string;
      description
        "Cellular Modem PRI version";
    }
    leaf cellular-carrier {
      type string;
      description
        "Cellular Modem carrier";
    }
    leaf cellular-oem-pri-version {
      type string;
      description
        "Cellular Modem OEM PRI version";
    }
  }

  grouping cellwan-radio-entry {
    description
      "Cellular modem radio status entry details";
    leaf cellular-interface {
      type string;
      description
        "Cellular interface";
    }
    leaf technology {
      type cellwan-ios-xe-oper:modem-technology;
      description
        "Cellular modem technology";
    }
    leaf radio-power-mode {
      type cellwan-ios-xe-oper:cw-radio-power-status;
      description
        "Cellular modem radio power mode";
    }
    leaf radio-rx-channel {
      type uint32;
      description
        "Cellular radio receive (Rx) channel number";
    }
    leaf radio-tx-channel {
      type uint32;
      description
        "Cellular radio transmit (Tx) channel number";
    }
    leaf radio-band {
      type uint32;
      description
        "Cellular radio band number";
    }
    leaf bandwidth {
      type cellwan-ios-xe-oper:radio-bandwidth;
      description
        "Cellular radio bandwidth in MHz";
    }
    leaf radio-rssi {
      type int16;
      description
        "Cellular RSSI - Received Signal Strength Indication in dBm";
    }
    leaf radio-rsrp {
      type int16;
      description
        "Cellular RSRP - Reference Signal Received Power in dBm";
    }
    leaf radio-rsrq {
      type int8;
      description
        "Cellular RSRQ - Reference Signal Received Quality in dB";
    }
    leaf radio-snr {
      type decimal64 {
        fraction-digits 2;
      }
      description
        "Cellular SNR - Signal to Noise Ratio in dB";
    }
    leaf radio-rat-preference {
      type cellwan-ios-xe-oper:rat-preference;
      description
        "Cellular Radio Access Technology preference";
    }
    leaf radio-rat-selected {
      type cellwan-ios-xe-oper:rat-technology;
      description
        "Cellular Radio Access Technology selected";
    }
  }

  grouping cellwan-network-entry {
    description
      "Cellular modem network status entry details";
    leaf cellular-interface {
      type string;
      description
        "Cellular interface";
    }
    leaf cellular-modem-time {
      type yang:date-and-time;
      description
        "Current Cellular modem time";
    }
    leaf radio-access-technology-selected {
      type cellwan-ios-xe-oper:rat-technology;
      description
        "Cellular Radio Access Technology selected";
    }
    leaf current-service-status {
      type cellwan-ios-xe-oper:service-status;
      description
        "Cellular network current service status";
    }
    leaf current-system-identifier {
      type uint16;
      description
        "Cellular modem current system identifier";
    }
    leaf current-network-identifier {
      type uint16;
      description
        "Cellular modem current network identifier";
    }
    leaf current-service-type {
      type cellwan-ios-xe-oper:modem-service;
      description
        "Cellular network current service type";
    }
    leaf current-roaming-status {
      type string;
      description
        "Cellular network current roaming status";
    }
    leaf network-selection-mode {
      type string;
      description
        "Cellular network selection mode";
    }
    leaf network-name {
      type string;
      description
        "Cellular current network name";
    }
    leaf mobile-country-code {
      type uint16;
      description
        "Cellular network mobile country code";
    }
    leaf mobile-network-code {
      type uint16;
      description
        "Cellular modem mobile network code";
    }
    leaf packet-switch-domain-state {
      type string;
      description
        "Cellular packet switched (PS) domain state";
    }
    leaf lte-carrier-aggregation {
      type cellwan-ios-xe-oper:lte-ca;
      description
        "Cellular LTE carrier aggregation (CA) state";
    }
    leaf registration-state {
      type cellwan-ios-xe-oper:reg-state;
      description
        "Cellular network registration state";
    }
    leaf emm-state {
      type string;
      description
        "Cellular network EMM registration state";
    }
    leaf emm-substate {
      type string;
      description
        "Cellular network EMM sub-state";
    }
    leaf location-area-code {
      type uint16;
      description
        "Cellular network location area code";
    }
    leaf tracking-area-code {
      type uint16;
      description
        "Cellular network tracking area code";
    }
    leaf cell-id {
      type uint64;
      description
        "Cellular network cell ID";
    }
    leaf negotiated-network-mtu {
      type uint16;
      description
        "Cellular modem negotiated network MTU size";
    }
  }

  grouping cellwan-connection-entry {
    description
      "Cellular modem connection status entry details";
    leaf cellular-interface {
      type string;
      description
        "Cellular interface";
    }
    leaf active-profile {
      type uint64;
      description
        "Cellular modem active profile number";
    }
    leaf cellular-packet-status {
      type cellwan-ios-xe-oper:packet-sess-status;
      description
        "Cellular modem packet session status";
    }
    leaf tx-packets {
      type uint64;
      description
        "Cellular data packets transmitted";
    }
    leaf rx-packets {
      type uint64;
      description
        "Cellular data packets received";
    }
    leaf tx-bytes {
      type uint64;
      description
        "Cellular data bytes transmitted";
    }
    leaf rx-bytes {
      type uint64;
      description
        "Cellular data bytes received";
    }
    leaf ipv4-addr {
      type inet:ip-address;
      description
        "Cellular interface IPv4 Address";
    }
    leaf ipv6-addr {
      type inet:ip-address;
      description
        "Cellular interface IPv6 Address";
    }
    leaf ipv4-dns-pri {
      type inet:ip-address;
      description
        "Cellular interface primary IPv4 DNS Address";
    }
    leaf ipv4-dns-sec {
      type inet:ip-address;
      description
        "Cellular interface secondary IPv4 DNS Address";
    }
    leaf ipv6-dns-pri {
      type inet:ip-address;
      description
        "Cellular interface primary IPv6 DNS Address";
    }
    leaf ipv6-dns-sec {
      type inet:ip-address;
      description
        "Cellular interface secondary IPv6 DNS Address";
    }
    leaf scope {
      type cellwan-ios-xe-oper:profile-scope;
      description
        "Cellular interface profile IP address scope";
    }
  }

  grouping cellwan-security-entry {
    description
      "Cellular modem SIM security status entry details";
    leaf cellular-interface {
      type string;
      description
        "Cellular interface";
    }
    leaf active-sim {
      type int8;
      description
        "Cellular modem active SIM slot status";
    }
    leaf sim-num-switchover {
      type uint32;
      description
        "Cellular modem SIM switchover attempts";
    }
    leaf chv1-status {
      type cellwan-ios-xe-oper:cellwan-chv1-sim-status;
      description
        "Cellular SIM Card Holder Verification (CHV1) status";
    }
    leaf sim-status {
      type cellwan-ios-xe-oper:cellwan-sim-status;
      description
        "Cellular SIM status";
    }
    leaf sim-oper {
      type cellwan-ios-xe-oper:cellwan-sim-user-op;
      description
        "Cellular SIM user operation";
    }
    leaf num-retries {
      type int8;
      description
        "Cellular SIM number of CHV1 retries remaining";
    }
  }

  grouping cellwan-sms-entry {
    description
      "Cellular modem SMS entry details";
    leaf cellular-interface {
      type string;
      description
        "Cellular interface";
    }
    leaf in-sms-count {
      type uint16;
      description
        "Number of incoming SMS stored in Cellular modem";
    }
    leaf in-sms-archived {
      type uint16;
      description
        "Number of incoming SMS archived in Cellular modem";
    }
    leaf in-sms-deleted {
      type uint16;
      description
        "Number of incoming SMS deleted in Cellular modem";
    }
    leaf in-sms-max {
      type uint16;
      description
        "Number of SIM/modem SMS record allocated";
    }
    leaf in-sms-used {
      type uint16;
      description
        "Number of SIM/modem SMS record used";
    }
    leaf sms-callback-count {
      type uint16;
      description
        "Number of SMS triggered data callback";
    }
    leaf in-sms-arch-count {
      type uint16;
      description
        "Number of successful archive on in SMS";
    }
    leaf in-sms-arch-error-count {
      type uint16;
      description
        "Number of failed archive on in SMS";
    }
    leaf out-sms-count {
      type uint16;
      description
        "Number of outgoing SMS successfully sent";
    }
    leaf out-sms-error-count {
      type uint16;
      description
        "Number of outgoing SMS send failure";
    }
    leaf out-sms-pending {
      type uint16;
      description
        "Number of outgoing SMS pending";
    }
    leaf out-sms-arch-count {
      type uint16;
      description
        "Number of successful archive out in SMS";
    }
    leaf out-sms-arch-error-count {
      type uint16;
      description
        "Number of failed archive on out SMS";
    }
  }

  grouping cellwan-gps-entry {
    description
      "Cellular modem GPS status entry details";
    leaf cellular-interface {
      type string;
      description
        "Cellular interface";
    }
    leaf gps-feature-state {
      type cellwan-ios-xe-oper:cwan-gps-feature-state;
      description
        "Cellular modem GPS feature state status";
    }
    leaf port-selected {
      type cellwan-ios-xe-oper:cwan-gps-port-selected;
      description
        "Cellular modem GPS port selection status";
    }
    leaf state {
      type cellwan-ios-xe-oper:cwan-gps-state;
      description
        "Cellular modem GPS state status";
    }
    leaf mode-selected {
      type cellwan-ios-xe-oper:cwan-gps-mode-selected;
      description
        "Cellular modem GPS mode selection status";
    }
    leaf latitude {
      type string;
      description
        "Cellular modem GPS latitude details";
    }
    leaf longitude {
      type string;
      description
        "Cellular modem GPS longitude details";
    }
    leaf timestamp {
      type yang:date-and-time;
      description
        "Cellular modem GPS timestamp details";
    }
  }

  container cellwan-oper-data {
    config false;
    description
      "Cellwan operational data";
    list cellwan-hardware {
      key "cellular-interface";
      description
        "Cellwan modem hardware data";
      uses cellwan-ios-xe-oper:cellwan-hardware-entry;
    }
    list cellwan-radio {
      key "cellular-interface";
      description
        "Cellwan modem radio data";
      uses cellwan-ios-xe-oper:cellwan-radio-entry;
    }
    list cellwan-network {
      key "cellular-interface";
      description
        "Cellwan modem network data";
      uses cellwan-ios-xe-oper:cellwan-network-entry;
    }
    list cellwan-connection {
      key "cellular-interface";
      description
        "Cellwan modem connection data";
      uses cellwan-ios-xe-oper:cellwan-connection-entry;
    }
    list cellwan-security {
      key "cellular-interface";
      description
        "Cellwan modem sim security data";
      uses cellwan-ios-xe-oper:cellwan-security-entry;
    }
    list cellwan-sms {
      key "cellular-interface";
      description
        "Cellwan modem sms data";
      uses cellwan-ios-xe-oper:cellwan-sms-entry;
    }
    list cellwan-gps {
      key "cellular-interface";
      description
        "Cellwan modem gps data";
      uses cellwan-ios-xe-oper:cellwan-gps-entry;
    }
  }
}
