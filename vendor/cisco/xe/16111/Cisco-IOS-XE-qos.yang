module Cisco-IOS-XE-qos {
  namespace "http://cisco.com/ns/yang/Cisco-IOS-XE-qos";
  prefix ios-qos;


  import Cisco-IOS-XE-native {
    prefix ios;
  }

  import Cisco-IOS-XE-features {
    prefix ios-features;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Quality of Service (QoS) Yang Model.
     Copyright (c) 2016 by Cisco Systems, Inc.
     All rights reserved.";

  // =========================================================================
  // REVISION
  // =========================================================================
  revision 2017-02-07 {
    description
      "Initial revision";
  }


  grouping queue-size-grouping {
    leaf queue-size-1 {
      type uint8 {
        range "1..100";
      }
    }
    leaf queue-size-2 {
      type uint8 {
        range "1..100";
      }
    }
    leaf queue-size-3 {
      type uint8 {
        range "1..100";
      }
    }
    leaf queue-size-4 {
      type uint8 {
        range "1..100";
      }
    }
    leaf queue-size-5 {
      type uint8 {
        range "1..100";
      }
    }
    leaf queue-size-6 {
      type uint8 {
        range "1..100";
      }
    }
    leaf queue-size-7 {
      type uint8 {
        range "1..100";
      }
    }
    leaf queue-size-8 {
      type uint8 {
        range "1..100";
      }
    }
  }

  grouping config-interface-wrr-queue-grouping {
    //unused /native/interface/wrr-queue   
    container wrr-queue {
      description
        "Configure weighted round-robin xmt queues";
      container bandwidth {
        description
          "Configure WRR minimum bandwidth with weights or percentages";
        
        choice bandwidth-choice {
          case a {
            leaf weight-1 {
              type uint8 {
            range "0..255";
              }
            }
            leaf weight-2 {
              type uint8 {
            range "0..255";
              }
            }
            leaf weight-3 {
              type uint8 {
            range "0..255";
              }
            }
            leaf weight-4 {
              type uint8 {
            range "0..255";
              }
            }
            leaf weight-5 {
              type uint8 {
            range "0..255";
              }
            }
            leaf weight-6 {
              type uint8 {
            range "0..255";
              }
            }
            leaf weight-7 {
              type uint8 {
            range "0..255";
              }
            }
          }
          case b {
            container percent {
              
              leaf percent-1 {
                type uint8 {
                  range "0..100";
                }
              }
              leaf percent-2 {
                type uint8 {
                  range "0..100";
                }
              } 
              leaf percent-3 {
                type uint8 {
                  range "0..100";
                }
              }
              leaf percent-4 {
                type uint8 {
                  range "0..100";
                }
              }
              leaf percent-5 {
                type uint8 {
                  range "0..100";
                }
              }
              leaf percent-6 {
                type uint8 {
                  range "0..100";
                }
              }
              leaf percent-7 {
                type uint8 {
                  range "0..100";
                }
              }
            }
          }
        }
      }
      list cos-map {
        description
          "Configure cos-map for a queue threshold";
        
        key "queue-id threshold-id";
        leaf queue-id {
          type uint8 {
            range "1..3";
          }
        }
        leaf threshold-id {
          type uint8 {
            range "1..8";
          }
        }
        leaf-list cos-values {
          max-elements "8";
          type uint8 {
            range "0..7";
          }
        }
      }
      container queue-limit {
        description
          "Configure queue-limit";
        
        leaf weight-a {
          type uint8 {
            range "0..100";
          }
        }
        leaf weight-b {
          type uint8 {
            range "0..100";
          }
        }
        leaf weight-c {
          type uint8 {
            range "0..100";
          }
        }
      }
      container random-detect {
        description
          "Configure random-detect";
        list max-threshold {
          description
            "Max threshold for WRED";
          
          key "id";
          leaf id {
            type uint8 {
              range "1..3";
            }
          }
          uses queue-size-grouping;
        }
        list min-threshold {
          description
            "Min threshold for WRED";
          
          key "id";
          leaf id {
            type uint8 {
              range "1..3";
            }
          }
          uses queue-size-grouping;
        }
      } 
      list threshold {
        description
          "Configure queue tail-drop thresholds";
        
        key "id";
        leaf id {
          type uint8 {
            range "1..3";
          }
        }
        uses queue-size-grouping;
      }
    }
  }

  grouping config-qos-grouping {
    // TODO trim candidate
    container account {
      description
        "Additional lengths to be accounted by QoS Features";
      container layer-all  {
        description
          "All layers, including L1";
        leaf encapsulation {
          description
            "Account Layer 1 Encapsulation when applying QoS features";
          type empty;
        }
      }

      container layer2 {
        description
          "Accounting Layer 2 headers";
        container encapsulation {
          description
            "Account Layer 2 Encapsulation when applying QoS features";
          leaf arpa {
            description
              "ARPA Encapsulation Size (18 bytes)";
            type empty;
          }
          leaf dot1q {
            description
              "IEEE 802.1q Encapsulation Size (22 bytes)";
            type empty;
          }
          leaf isl {
            description
              "ISL Encapsulation Size (48 bytes)";
            type empty;
          }

          container length {
            description
              "Layer2 Encapsulation length in bytes";
            presence true;

            leaf byte-length {
              description
                "Layer2 Encapsulation length in bytes, <0-0>";
              type int8;
            }
          }
        }
      }
    }

    // TODO trim candidate
    container control-packets {
      description
        "Enable QoS on control packets";
      presence true;

      leaf bpdu-range {
        description
          "Enable QoS on BPDU-range packets";
        type empty;
      }

      leaf cdp-vtp {
        description
          "Enable QoS on CDP and VTP packets";
        type empty;
      }

      leaf eapol {
        description
          "Enable QoS on EAPOL packets";
        type empty;
      }

      leaf lldp {
        description
          "Enable QoS on LLDP packets";
        type empty;
      }

      leaf protocol-tunnel {
        description
          "Enable QoS on protocol tunneled packets";
        type empty;
      }
      leaf sstp {
        description
          "Enable QoS on SSTP packets";
        type empty;
      }
    }

    container preserve {
      description
        "Preserve packet header bits";

      container marking  {
        description
          "Preserve cos/tos header bits";
        leaf hipriority {
          description
            "Preserve marking in high priority generated control packets";
          type empty;
        }
      }

      container mpls {
        description
          "Preserve MPLS packet header bits";
        leaf exp {
          description
            "Preserve MPLS EXP packet header bits";
          type empty;
        }
      }
    }

    container trace {
      description
        "QoS trace log settings";

      container resize {
        description
          "resize trace log";

        leaf size {
          description
            "buffer size in bytes";
          type int32;
        }

        leaf all {
          description
            "all trace logs";
          type int32;
        }

        leaf error   {
          description
            "error trace log";
          type int32;
        }

        leaf event {
          description
            "event trace log";
          type int32;
        }

        leaf warning {
          description
            "warning trace log";
          type int32;
        }
      }
    }

    leaf diffservmib {
      description
        "RFC3289 support for QoS policy-maps";
      type empty;
    }

    container queue-softmax-multiplier {
      if-feature ios-features:qos-qsm;
      description
        "global multiplier(%) for queue soft buffer maximal size";
      leaf value {
        description
          "multiplier(%) 100 - 1200";
        type int16 {
          range "100..1200";
        }
      }
    }
  }

  grouping config-table-map-grouping {
    leaf default {
      description
        "the default behavior for setting value not found in the table map";
      type union {
        type uint8 {
          range "0..63";
        }
        type enumeration {
          enum "copy";
          enum "ignore";
        }
      }
    }
    // table-map * / map from * to *
    list map {
      description
        "map to-value from from-value";
      key "from to";
      leaf from {
        description
          "map from value";
        type uint8 {
          range "0..63";
        }
      }
      leaf to {
        description
          "map to value";
        type uint8 {
          range "0..63";
        }
      }
    }
  }

  /////////////////////////////////////////////////////////
  // native / qos *
  /////////////////////////////////////////////////////////
  augment "/ios:native/ios:qos" {
    uses config-qos-grouping;
  }

  /////////////////////////////////////////////////////////
  // native / table-map *
  /////////////////////////////////////////////////////////
  augment "/ios:native/ios:table-map" {
    uses config-table-map-grouping {
      if-feature ios-features:table-map;
    }
  }
}//module
