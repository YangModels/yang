module cisco-xe-switching-openconfig-system-deviation {
  // namespace
  namespace "http://openconfig.net/yang/cisco-xe-switching-openconfig-system-deviation";

  prefix cisco-xe-switching-oc-system-devs;

  import openconfig-system {
    prefix oc-sys;
  }

  organization
    "Cisco Systems, Inc.";

  contact
    " Cisco Systems, Inc.
    Customer Service

    Postal: 170 W Tasman Drive
    San Jose, CA 95134

    Tel: +1 1800 553-NETS

    E-mail: cs-yang@cisco.com";

  description
    "This module defines deviation statements for openconfig-system module for IOS XE Routing platforms.";

  revision 2017-11-27 {
    description
      "Add deviations to remove openconfig-system features not implemented on IOS XE Routing platforms";
 
    reference
      "RFC 6020: YANG - A Data Modeling Language for the
       Network Configuration Protocol (NETCONF)";
  }

  deviation "/oc-sys:system/oc-sys:config" {
      deviate not-supported; 
      description
        "oc-system config not supported on IOS XE Routing platforms";
  }

  deviation "/oc-sys:system/oc-sys:state/oc-sys:hostname" {
      deviate not-supported; 
      description
        "oc-system state/hostname not supported on IOS XE Routing platforms";
  }

  deviation "/oc-sys:system/oc-sys:clock" {
      deviate not-supported; 
      description
        "oc-system clock not supported on IOS XE Routing platforms";
  }

  deviation "/oc-sys:system/oc-sys:dns" {
      deviate not-supported; 
      description
        "oc-system dns not supported on IOS XE Routing platforms";
  }

  deviation "/oc-sys:system/oc-sys:ntp" {
      deviate not-supported; 
      description
        "oc-system ntp not supported on IOS XE Routing platforms";
  }

  deviation "/oc-sys:system/oc-sys:telnet-server" {
      deviate not-supported; 
      description
        "oc-system telnet-server not supported on IOS XE Routing platforms";
  }

  deviation "/oc-sys:system/oc-sys:ssh-server" {
      deviate not-supported; 
      description
        "oc-system ssh-server not supported on IOS XE Routing platforms";
  }

  deviation "/oc-sys:system/oc-sys:aaa" {
      deviate not-supported; 
      description
        "oc-system aaa not supported on IOS XE Routing platforms";
  }

  deviation "/oc-sys:system/oc-sys:logging" {
      deviate not-supported; 
      description
        "oc-system logging not supported on IOS XE Routing platforms";
  }

  deviation "/oc-sys:system/oc-sys:memory" {
      deviate not-supported; 
      description
        "oc-system memory not supported on IOS XE Routing platforms";
  }

  deviation "/oc-sys:system/oc-sys:processes" {
      deviate not-supported; 
      description
        "oc-system processes state args not supported on IOS XE Routing platforms";
  }

}
