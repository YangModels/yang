module cisco-xe-switching-openconfig-vlan-deviation {

  namespace "http://cisco.com/ns/yang/cisco-xe-switching-openconfig-vlan-deviation";

  prefix cisco-xe-switching-oc-vlan-devs;
  
  import openconfig-interfaces { 
    prefix oc-if; 
  }
 
  import openconfig-vlan { 
    prefix oc-vlan; 
  }

  import cisco-xe-openconfig-vlan-ext {
    prefix oc-vlan-ext;
  }

  organization "Cisco Systems";

  description
     "Deviation YANG module for Openconfig-vlan for IOS XE Switching platforms
      Copyright (c) 2017 by Cisco Systems, Inc.
      All rights reserved.";

  revision 2017-03-17 {
     description "Initial revision";
  }


  deviation "/oc-vlan:vlans/oc-vlan:vlan/oc-vlan:members/oc-vlan:member" +
            "/oc-vlan:interface-ref/oc-vlan:state/oc-vlan:subinterface" {
    deviate not-supported;
  }

  deviation "/oc-vlan:vlans/oc-vlan-ext:default-vlan/oc-vlan-ext:ports" +
            "/oc-vlan-ext:subinterface" {
    deviate not-supported;
  }

  deviation "/oc-vlan:vlans/oc-vlan:vlan/oc-vlan:config/oc-vlan:tpid" {
    deviate not-supported;
  }

  deviation "/oc-vlan:vlans/oc-vlan:vlan/oc-vlan:state/oc-vlan:tpid" {
    deviate not-supported;
  }

  deviation "/oc-if:interfaces/oc-if:interface" +
            "/oc-if:subinterfaces/oc-if:subinterface/oc-vlan:vlan" {
    deviate not-supported;
  }
}
