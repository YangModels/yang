module Cisco-IOS-XE-lldp {
  namespace "http://cisco.com/ns/yang/Cisco-IOS-XE-lldp";
  prefix ios-lldp;


  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Link Layer Discovery Protocol (LLDP) Yang model.
     Copyright (c) 2016-2017 by Cisco Systems, Inc.
     All rights reserved.";

  // =========================================================================
  // REVISION
  // =========================================================================
  revision 2019-01-22 {
     description
      "Added leaf for App-hosting Gigabit Ethernet interface";
  }

  revision 2018-11-07 {
      description
      "Cleanup spelling errors in description statements";
  }
 revision 2018-07-25 {
     description
       "Changed the type of tlv-select leafs to boolean to better represent CLI state";
  }

 revision 2018-07-17 {
     description
       "Changed the range of the timer leaf to match CLI";
  }

  revision 2017-11-27 {
     description
       "Added Change 25GE name";
  }

  revision 2017-11-14 {
    description
      "This revision has changes for new 100GE interface addition";
  }

  revision 2017-09-15 {
    description
      "This revision has changes for new 2gig interface addition";
  }
  revision 2017-08-16 {
    description
      "This revision has changes for new 5gig and 25gig interfaces addition";
  }
  revision 2017-03-31 {
    description
      "Move interface LLDP configuration from switch to common";
  }
  revision 2017-02-07 {
    description
      "Initial revision";
  }

  // Global configs
  grouping config-lldp-grouping {
    container lldp {
      description "Enables LLDP globally.";
      leaf holdtime {
        description "Specify the holdtime (in sec) to be sent in packets";
        type uint32 {
          range "0..65535";
        }
      }
      leaf reinit {
        description "Specify the delay (in secs) for LLDP to initialize";
        type uint8 {
          range "2..5";
        }
      }
      leaf run {
        description "Enable LLDP";
        type empty;
      }
      leaf timer {
        description "Rate at which LLDP packets are sent (in sec)";
        type uint16 {
          range "5..65534";
        }
      }
      container tlv-select {
        description "Selection of LLDP TLVs to send";
        leaf four-wire-power-management {
          description "Cisco 4-wire Power via MDI TLV";
          type enumeration {
            enum "4-wire-power-management";
          }
        }
        leaf mac-phy-cfg {
          description "IEEE 802.3 MAC/Phy Configuration/status TLV";
          type boolean;
        }
        leaf management-address {
          description "Management Address TLV";
          type boolean;
        }
        leaf port-description {
          description "Port Description TLV";
          type boolean;
        }
        leaf port-vlan {
          description "Port VLAN ID TLV";
          type boolean; 
        }
        leaf power-management {
          description "IEEE 802.3 DTE Power via MDI TLV";
          type boolean;
        }
        leaf system-capabilities {
          description "System Capabilities TLV";
          type boolean;
        }  
        leaf system-description {
          description "System Description TLV";
          type boolean;
        }  
        leaf system-name {
          description "System Name TLV";
          type boolean;
        }  
      }
    }
  }

  // Interface configs
  grouping config-interface-lldp-grouping {
    // interface * / lldp
    container lldp {
      description
        "LLDP interface subcommands";
      leaf receive {
        description
          "Enable LLDP reception on interface";
        type boolean;
      }
      container tlv-select {
        description "Selection of LLDP TLVs to send"; 
        leaf four-wire-power-management {
          description "Cisco 4-wire Power via MDI TLV"; 
          type enumeration {
            enum "4-wire-power-management";
          }

        }
        leaf power-management {
          description "IEEE 802.3 DTE Power via MDI TLV"; 
          type empty;
        }
      }
      leaf transmit {
        description
          "Enable LLDP transmission on interface";
        type boolean;
      }
    }
}


  /////////////////////////////////////////////////////////
  // native / lldp 
  /////////////////////////////////////////////////////////
  augment "/ios:native" {
    uses config-lldp-grouping;
  }

  /////////////////////////////////////////////////////////
  // native / interface * / lldp
  //
  //   The config is only allowed on generic "Ethernet" type of interfaces. 
  //   See config check in sys/lldp/cfg_int_lldp.h :
  //      LLDP_DEFAULT_ENABLE_INT(csb->interface)
  /////////////////////////////////////////////////////////
  augment "/ios:native/ios:interface/ios:FastEthernet" {
    uses config-interface-lldp-grouping;
  }

  augment "/ios:native/ios:interface/ios:GigabitEthernet" {
    uses config-interface-lldp-grouping;
  }

  augment "/ios:native/ios:interface/ios:TwoGigabitEthernet" {
    uses config-interface-lldp-grouping;
  }

  augment "/ios:native/ios:interface/ios:FiveGigabitEthernet" {
    uses config-interface-lldp-grouping;
  }

  augment "/ios:native/ios:interface/ios:AppGigabitEthernet" {
    uses config-interface-lldp-grouping;
  }

  augment "/ios:native/ios:interface/ios:TenGigabitEthernet" {
    uses config-interface-lldp-grouping;
  }

  augment "/ios:native/ios:interface/ios:TwentyFiveGigE" {
    uses config-interface-lldp-grouping;
  }

  augment "/ios:native/ios:interface/ios:FortyGigabitEthernet" {
    uses config-interface-lldp-grouping;
  }

  augment "/ios:native/ios:interface/ios:HundredGigE" {
    uses config-interface-lldp-grouping;
  }
}
