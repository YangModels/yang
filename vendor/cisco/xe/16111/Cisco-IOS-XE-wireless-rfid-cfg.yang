module Cisco-IOS-XE-wireless-rfid-cfg {
  yang-version 1;
  namespace "http://cisco.com/ns/yang/Cisco-IOS-XE-wireless-rfid-cfg";
  prefix wireless-rfid-cfg;

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG 
     definitions for configuration of rfid.
     Copyright (c) 2017-2018 by Cisco Systems, Inc.
     All rights reserved.";

  revision 2018-10-29 {
    description
      "Cleaned up spelling errors in descriptions.";
    reference "4.1.0";
  }
  revision 2018-03-31 {
    description
      "add a must clause in the rfid config variable";
    reference "4.0.0";
  }
  revision 2018-03-22 {
    description
      "Change in defaults";
    reference "3.0.0";
  }
  revision 2018-01-24 {
    description
      "The first generally available version";
    reference "2.0.0";
  }
  revision 2017-10-11 {
    description
      "Initial revision";
    reference "1.0.0";
  }

  grouping st-rfid-config {
    description
      "This typedef has all the RFID 
       config related attributes.";
    leaf rfid-enable-bluesoft {
      type boolean;
      default "true";
      description
        "Rfid enable bluesoft represents whether bluesoft tag supported or not. 
         If enable state then bluesoft tag is supported and if disable state then bluesoft
         tag not supported";
    }
    leaf rfid-timeout {
      type uint16 {
        range "60 .. 7200";
      }
      default "1200";
      description
        "Rfid timeout represents the timeout value to cleanup stale rfid entries.";
    }
    leaf rfid-enable-cisco {
      type boolean;
      default "true";
      description
        "Rfid enable Cisco represents whether Cisco tag rfid supported or not.
         If enable state then Cisco tag is supported and if disable state then Cisco
         tag not supported";
    }
    leaf rfid-rssi-expiry {
      type uint16 {
        range "5 .. 300";
      }
      default "5";
      description
        "Rfid rssi expiry time represents to cleanup rfid rssi when rssi value expires.";
    }
    leaf rfid-rssi-halflife {
      type uint32 {
        range "0 .. 300";
      }
      must "(../rfid-rssi-halflife = 0) or (../rfid-rssi-halflife = 1) or (../rfid-rssi-halflife = 2) or (../rfid-rssi-halflife = 5) or (../rfid-rssi-halflife = 10) or (../rfid-rssi-halflife = 20) or (../rfid-rssi-halflife = 30) or (../rfid-rssi-halflife = 60) or (../rfid-rssi-halflife = 90) or (../rfid-rssi-halflife = 120) or (../rfid-rssi-halflife = 180) or (../rfid-rssi-halflife = 300) " {
        error-message "Invalid input value";
        error-app-tag "must-violation";
      }
      default "0";
      description
        "Rfid rssi halflife represents half life when averaging
         two RSSI readings for RFID tags,
         timeout value zero indicates that timeout is disabled.";
    }
    leaf rfid-notify-threshold {
      type uint32 {
        range "1 .. 10";
      }
      default "5";
      description
        "Rfid notify threshold indicates LOCP notification 
         threshold for RSSI measurements.";
    }
  }

  container rfid-cfg-data {
    description
      "This subtype is used for setting  
       notify threshold timer";
    container rfid {
      presence "rfid";
      description
        "This is the typedef which holds all the 
         rfid config attributes.";
      uses wireless-rfid-cfg:st-rfid-config;
    }
  }
}
