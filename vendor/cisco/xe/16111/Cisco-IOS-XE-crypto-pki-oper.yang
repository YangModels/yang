module Cisco-IOS-XE-crypto-pki-oper {
  yang-version 1;
  namespace "http://cisco.com/ns/yang/Cisco-IOS-XE-crypto-pki-oper";
  prefix crypto-pki-ios-xe-oper;

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of yang definitions
     for PKI operational data.
     Copyright (c) 2018 by Cisco Systems, Inc.
     All rights reserved.";

  revision 2018-12-03 {
    description
      "Initial revision";
    reference "1.0.0";
  }

  typedef crypto-pki-tp-mode {
    type enumeration {
      enum "crypto-pki-mode-none" {
        value 0;
        description
          "Normal Trustpoint";
      }
      enum "crypto-pki-mode-ra" {
        value 1;
        description
          "Registration Authority mode Trustpoint";
      }
      enum "crypto-pki-mode-subcs" {
        value 2;
        description
          "Subordinate Certificate Server mode Trustpoint";
      }
    }
    description
      "Trustpoint mode whether it is RA or SUBCS or neither.";
  }

  grouping crypto-pki-data {
    description
      "crypto pki data";
    leaf label {
      type string;
      description
        "Trustpoint label or name";
    }
    leaf mode {
      type crypto-pki-ios-xe-oper:crypto-pki-tp-mode;
      description
        "Trustpoint mode";
    }
  }

  container crypto-pki-oper-data {
    config false;
    description
      "Crypto PKI operational data";
    list crypto-pki-bundle {
      key "label";
      description
        "PKI data list";
      uses crypto-pki-ios-xe-oper:crypto-pki-data;
    }
  }
}
