module Cisco-IOS-XE-diagnostics {
  namespace "http://cisco.com/ns/yang/Cisco-IOS-XE-diagnostics";
  prefix ios-diag;


  import Cisco-IOS-XE-native {
    prefix ios;
  }

  import Cisco-IOS-XE-types {
    prefix ios-types;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Diagnostic Yang Model.
     Copyright (c) 2016 by Cisco Systems, Inc.
     All rights reserved.";

  // =========================================================================
  // REVISION
  // =========================================================================
  revision 2018-11-07 {
      description
      "Cleanup spelling errors in description statements";
  }
  revision 2017-02-07 {
    description
      "Initial revision";
  }

  grouping diagnostic-daily-on-weekly-grouping {
    container daily {
      description
        " Daily Schedule ";
      leaf hh-mm {
        description
          "Begin Time hh:mm";
        type ios-types:hhmm-type;
      }
    }
    container on {
      description
        " Absolute Schedule ";
      leaf month {
        description
          "Enter month ->
     Jan|Feb|Mar|Apr|May|Jun|Jul|Aug|Sep|Oct|Nov|Dec";
        type ios-types:month-type;
      }
      leaf day-of-month {
        description
          " <1-31>  Day of month ";
        type uint16 {
          range "1..31";
        }
      }
      leaf Year {
        description
          "Enter Year <1993-2035>";
        type uint16 {
          range "1993..2035";
        }
      }
      leaf hh-mm {
        description
          "Begin Time hh:mm";
        type ios-types:hhmm-type;
      }
    } // container on
    container weekly {
      description
      "Weekly schedule";
      leaf day {
        description
        "Enter Day of the week
           Mon|Tue|Wed|Thu|Fri|Sat|Sun";
        type ios-types:weekday-type;
      }
      leaf hh-mm {
      description
          "Begin Time hh:mm";
        type ios-types:hhmm-type;
      }
    } // container weekly
  }

  grouping diagnostic-schedule-port-grouping {
    container port {
      description
      "Interface port selection";
      list interface-port-number {
        description
        "Interface port number";
      key "number";
      leaf number {
          type uint8 {
            range "1..32";
          }
        }
        uses diagnostic-daily-on-weekly-grouping;
      } // list port-number
      list port-number-list {
        description
        "Port number list (e.g. 2,4-7)";
      key "number-list";
        leaf number-list {
          description
            "Port number list (e.g. 2,4-7)";
          type string;
        }
      uses diagnostic-daily-on-weekly-grouping;
      } // port-number-list
      container all {
      description
        "Select all ports";
      uses diagnostic-daily-on-weekly-grouping;
      }
    }
  }

  grouping config-diagnostic-grouping {
    container diagnostic { //50268
      description
        "Configure diagnostic information";
      container bootup {
        description
          "Configure diagnostic for bootup";
        leaf level {
          description
            "Select diagnostic level";
          type enumeration {
          enum "complete";
          enum "minimal";
        }
        }
      }
      container event-log {
        description
          "Configure diagnostic event log";
        leaf size {
          description
            "Configure event log size
            Number of entries <1-10000>";
          type uint16 {
            range "1..10000";
          }
        }
      }
      container monitor {
        description
          "Configure diagnostic monitoring tests";
        container interval {
          description
            "Configure diagnostic monitoring tests interval";
          container switch {
            description
              "Configure diagnostic monitoring tests interval on selected switch";
            list switch {
              description
                "Configure diagnostic monitoring tests on selected switch";
              key "number";
              leaf number {
                    description
                      "switch number";
                type uint8 {
                  range "1..9";
                }
              }
              container test {
                description
                  "Diagnostic test selection
                   Diagnostics test suite attributes:
                   M/C/* - Minimal bootup level test / Complete bootup level test / NA
                   B/* - Basic ondemand test / NA
                   P/V/* - Per port test / Per device test / NA
                   D/N/* - Disruptive test / Non-disruptive test / NA
                   S/* - Only applicable to standby unit / NA
                   X/* - Not a health monitoring test / NA
                   F/* - Fixed monitoring interval test / NA
                   E/* - Always enabled monitoring test / NA
                   A/I - Monitoring is active / Monitoring is inactive

                                                                  Test Interval
           ID   Test Name                          Attributes     day hh:mm:ss.ms Threshold
           ==== ================================  ============   =============== =====
           1) DiagGoldPktTest ----------------->  *BPN*X**I       not configured    n/a
           2) DiagThermalTest ----------------->  *B*N****A       000 00:01:30.00   5
           3) DiagFanTest --------------------->  *B*N****A       000 00:01:30.00   5
           4) DiagPhyLoopbackTest ------------->  *BPD*X**I       not configured    n/a
           5) DiagScratchRegisterTest --------->  *B*N****A       000 00:01:30.00   5
           6) DiagPoETest --------------------->  ***D*X**I       not configured    n/a
           7) DiagStackCableTest -------------->  ***D*X**I       not configured    n/a
           8) DiagMemoryTest ------------------>  *B*D*X**I       not configured    n/a ";

                list test-ids {
                  key "id";
                    leaf id {
                      description
                        "Test ID list (e.g. 1,3-6) or Test Name";
                      type string;
                  }
                  leaf hh-mm-ss {
                    description
                      "Monitoring interval in hh:mm:ss format";
                    type ios-types:hhmmss-type;
                  }
                  leaf milli-seconds {
                    description
                      "Number of milli-seconds [0-999]";
                    type uint16 {
                      range "0..999";
                    }
                  }
                  leaf number-of-days {
                    description
                      "Number of days [0-20]";
                    type uint16 {
                      range "0..20";
                    }
                  }
                }
                container all {
                  description
                    "Select all test ID ";
                  leaf hh-mm-ss {
                    description
                      "Monitoring interval in hh:mm:ss format";
                    type ios-types:hhmmss-type;
                  }
                  leaf milli-seconds {
                    description
                      "Number of milli-seconds [0-999]";
                    type uint16 {
                      range "0..999";
                    }
                  }
                  leaf number-of-days {
                    description
                      "Number of days [0-20]";
                    type uint16 {
                      range "0..20";
                    }
                  }
                }// container all
              } /// container test
            } ///  number 1
          } //switch
        } //interval
        list switch {
          description
            "Configure diagnostic monitoring tests on selected switch";
        key "number";
        leaf number{
            description
              "switch number";
            type uint8 {
              range "1..9";
          }
        }
          container test {
            description
              "Diagnostic test selection
               Diagnostics test suite attributes:
               M/C/* - Minimal bootup level test / Complete bootup level test / NA
               B/* - Basic ondemand test / NA
               P/V/* - Per port test / Per device test / NA
               D/N/* - Disruptive test / Non-disruptive test / NA
               S/* - Only applicable to standby unit / NA
               X/* - Not a health monitoring test / NA
               F/* - Fixed monitoring interval test / NA
               E/* - Always enabled monitoring test / NA
               A/I - Monitoring is active / Monitoring is inactive

               Test                                                  Test Interval
            ID   Test Name                          Attributes      day hh:mm:ss.ms Threshold
         ==== ================================== ============    =============== =====
          1) DiagGoldPktTest -----------------> *BPN*X**I       not configured    n/a
            2) DiagThermalTest -----------------> *B*N****A       000 00:01:30.00   5
          3) DiagFanTest ---------------------> *B*N****A       000 00:01:30.00   5
            4) DiagPhyLoopbackTest -------------> *BPD*X**I       not configured    n/a
          5) DiagScratchRegisterTest ---------> *B*N****A       000 00:01:30.00   5
          6) DiagPoETest ---------------------> ***D*X**I       not configured    n/a
          7) DiagStackCableTest --------------> ***D*X**I       not configured    n/a
            8) DiagMemoryTest ------------------> *B*D*X**I       not configured    n/a ";

          choice test-id {
            leaf id {
                description
                  "Test ID list (e.g. 1,3-6) or Test Name";
                type string;
            }
              leaf all {
                description
                  "Select all test ID ";
                type empty;
              }
          }
          }  /// container test
        } ///switch
        leaf syslog {
          description
            "Configure diagnostic monitoring syslog";
        type empty;
        }
        container threshold {
          description
          "Configure diagnostic monitoring failure threshold";
          list switch {
            description
            "Configure diagnostic monitoring tests threshold on selected switch";
          key "number";
          leaf number {
              description
                "switch number";
            type uint8 {
              range "1..9";
            }
          }
            container test {
              description
                "Diagnostic test selection
                 Diagnostics test suite attributes:
                 M/C/* - Minimal bootup level test / Complete bootup level test / NA
                 B/* - Basic ondemand test / NA
                 P/V/* - Per port test / Per device test / NA
                 D/N/* - Disruptive test / Non-disruptive test / NA
                 S/* - Only applicable to standby unit / NA
                 X/* - Not a health monitoring test / NA
                 F/* - Fixed monitoring interval test / NA
                 E/* - Always enabled monitoring test / NA
                 A/I - Monitoring is active / Monitoring is inactive

                                                                    Test
                                                                    Interval
         ID   Test Name                          Attributes        day hh:mm:ss.ms Threshold
            ==== ================================== ============   =============== =====
         1) DiagGoldPktTest ----------------->  *BPN*X**I          not configured  n/a
         2) DiagThermalTest ----------------->  *B*N****A          000 00:01:30.00 5
         3) DiagFanTest --------------------->  *B*N****A          000 00:01:30.00 5
         4) DiagPhyLoopbackTest ------------->  *BPD*X**I          not configured  n/a
         5) DiagScratchRegisterTest --------->  *B*N****A          000 00:01:30.00 5
         6) DiagPoETest --------------------->  ***D*X**I          not configured  n/a
         7) DiagStackCableTest -------------->  ***D*X**I          not configured  n/a
         8) DiagMemoryTest ------------------>  *B*D*X**I          not configured  n/a ";

          list test-ids {
          key "id";
          leaf id {
                description
                  "Test ID list (e.g. 1,3-6) or Test Name";
                type string;
          }
          container failure {
                description
              "Setting failure threshold";
                list count {
                  description
                "Setting failure threshold count";
              key "range";
                  leaf range {
                  description
                "Number of allowable failures [1-1000]";
                    type uint16 {
                      range "1..1000";
                    }
                  }
                  leaf days {
                    description
                "Set failure history window in days <1-1000000>";
                    type uint32 {
                      range "1..1000000";
                    }
                  }
                  leaf hours {
                    description
                "Set failure history window in hours <1-1000000>";
                type uint32 {
                      range "1..1000000";
                    }
              }
                  leaf milli-seconds {
                    description
                "Set failure history window in milli-seconds <15-1000000>";
                type uint32 {
                      range "15..1000000";
                    }
                  }
                  leaf minutes {
                    description
                  "Set failure history window in minutes";
                    type uint32 {
                      range "1..1000000";
                    }
              }
                  leaf runs {
                    description
                "Set failure history window in test-run count";
                      type uint16 {
                        range "1..5000";
                      }
              }
                  leaf seconds {
                    description
                "Set failure history window in seconds";
                    type uint32 {
                      range "1..1000000";
                    } // type
              } //leaf seconds
            }// count
          } // failure
          } /// test ids
          container all {
              description
                "Select all test ID ";
          container failure {
                description
              "Setting failure threshold";
                list count {
                  description
                "Setting failure threshold count";
              key "range";
                    leaf range {
                    description
                  "Number of allowable failures [1-1000]";
                      type uint16 {
                        range "1..1000";
                      }
                    }
                    leaf days {
                      description
                  "Set failure history window in days";
                      type uint32 {
                        range "1..1000000";
                      }
                }
                    leaf hours {
                      description
                  "Set failure history window in hours";
                  type uint32 {
                        range "1..1000000";
                      }
                    }
                    leaf milli-seconds {
                      description
                  "Set failure history window in milli-seconds";
                  type uint32 {
                        range "15..1000000";
                      }
                }
                    leaf minutes {
                      description
                  "Set failure history window in minutes";
                      type uint32 {
                        range "1..1000000";
                      }
                    }
                    leaf runs {
                      description
                  "Set failure history window in test-run count";
                  type uint16 {
                        range "1..5000";
                      }
                }
                leaf seconds {
                      description
                  "Set failure history window in seconds";
                      type uint32 {
                        range "1..1000000";
                      }
                }
              } // list count
            } // failure
            }// container all
          }// test
          } // list switch
      } /// threshold
      } /// monitor
      //// diagnostic schedule
      container schedule {
        description
          "Configure diagnostic schedule for a card";
        list switch {
          description
            "Configure diagnostic monitoring tests interval on selected switch";
          key "switch-number";
          leaf switch-number {
            description
              "switch number";
          type uint8 {
            range "1..9";
          }
        }
          container test {
            description
              "Diagnostic test selection
               Diagnostics test suite attributes:
               M/C/* - Minimal bootup level test / Complete bootup level test / NA
               B/* - Basic ondemand test / NA
               P/V/* - Per port test / Per device test / NA
               D/N/* - Disruptive test / Non-disruptive test / NA
               S/* - Only applicable to standby unit / NA
               X/* - Not a health monitoring test / NA
               F/* - Fixed monitoring interval test / NA
               E/* - Always enabled monitoring test / NA
               A/I - Monitoring is active / Monitoring is inactive
                                                                   Test Interval
           ID   Test Name                          Attributes      day hh:mm:ss.ms Threshold
        ==== ================================== ============    ===============  =====
         1)   DiagGoldPktTest -----------------> *BPN*X**I       not configured   n/a
         2)   DiagThermalTest -----------------> *B*N****A       000 00:01:30.0   5
         3)   DiagFanTest ---------------------> *B*N****A       000 00:01:30.00  5
         4)   DiagPhyLoopbackTest -------------> *BPD*X**I       not configured   n/a
           5)   DiagScratchRegisterTest ---------> *B*N****A       000 00:01:30.00  5
           6)   DiagPoETest ---------------------> ***D*X**I       not configured   n/a
           7)   DiagStackCableTest --------------> ***D*X**I       not configured   n/a
           8)   DiagMemoryTest ------------------> *B*D*X**I       not configured   n/a " ;

            list test-ids {
              key "id";
              leaf id {
                description
                  "Test ID list (e.g. 1,3-6) or Test Name";
                type string;
            }
            uses diagnostic-daily-on-weekly-grouping;
            uses diagnostic-schedule-port-grouping;
          } // list test id over
            container all {
              description
                    "Select all test ID ";
              uses diagnostic-daily-on-weekly-grouping;
              uses diagnostic-schedule-port-grouping;
            }  // container all
            container basic {
              description
                "Select the Basic ondemand test suite [Attribute = B]";
              uses diagnostic-daily-on-weekly-grouping;
              uses diagnostic-schedule-port-grouping;
            }  // container basic
            container complete {
              description
                "Select the Complete bootup test suite [Attribute = C]";
              uses diagnostic-daily-on-weekly-grouping;
            }  // complete
            container minimal {
              description
                "Select the Minimal bootup test suite [Attribute = M]";
              uses diagnostic-daily-on-weekly-grouping;
            }  // minimal
            container non-disruptive {
              description
                "Select the Non-Disruptive test suite [Attribute = N]";
              uses diagnostic-daily-on-weekly-grouping;
              uses diagnostic-schedule-port-grouping;
            }  // non-disruptive
            container per-port {
              description
                "Select the Per-Port test suite [Attribute = P]";
              uses diagnostic-daily-on-weekly-grouping;
              uses diagnostic-schedule-port-grouping;
            } // per-port
          } // test
        }  // list switch
      } // container schedule
    } // diagnostic
  }

  /////////////////////////////////////////////////////////
  // native / diagnostic
  /////////////////////////////////////////////////////////
  augment "/ios:native" {
    uses config-diagnostic-grouping;
  }
}
