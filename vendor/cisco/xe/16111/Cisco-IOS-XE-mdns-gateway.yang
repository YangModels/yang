module Cisco-IOS-XE-mdns-gateway {
  namespace "http://cisco.com/ns/yang/Cisco-IOS-XE-mdns-gateway";
  prefix ios-mdns;

  import Cisco-IOS-XE-native {
    prefix ios;
  }
  import ietf-yang-types {
      prefix yang;
  }
  import ietf-inet-types {
      prefix inet;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native MDNS Gateway Yang Model.
     Copyright (c) 2018 by Cisco Systems, Inc.
     All rights reserved.";

  // =========================================================================
  // REVISION
  // =========================================================================
  revision 2018-11-29 {
    description
      "Corrected service-definition description 
       and added additional checks in service-list";
  }
  revision 2018-11-07 {
      description
      "Cleanup spelling errors in description statements";
  }
  revision 2018-07-07 {
    description
      "Initial revision";
  }
  grouping config-mdns-sd-grouping {
    container mdns-sd {
      description "Configure mDNS Service Discovery";
      container gateway {
        description "mDNS Gateway Configuration";
        presence true;
        container active-query {
          description "mDNS Global Active Query";
          leaf timer {
              description "Active Query Periodicity in Minutes";
              type uint16 {
                  range "15..120";
              }
              default "30";
          }
        }
        leaf transport {
          description "mDNS message processing on a specific transport";
          type enumeration {
            enum "both";
            enum "ipv4";
            enum "ipv6";
          }
          default "ipv4";
        }
      }
      list service-policy {
        description "mDNS Service Policy";
        key "service-policy-name";
        leaf service-policy-name {
            description "mDNS Service Policy Name";
            type string;
        }
        leaf location {
            description "mDNS Location Based Filtering";
            type enumeration {
               enum "lss";
               enum "site-tag";
            }
        }
        list service-list {
          key "name";
          leaf name {
            description "mDNS Service List Name";
            type leafref {
              path "/ios:native/ios-mdns:mdns-sd/service-list/service-list-name";
            }
          }
          leaf direction {
              description "Select Service List Direction IN/OUT";
              type enumeration {
                 enum "IN";
                 enum "OUT";
              }
          }
        }
      }
      list service-list {
        description "mDNS Service List";
        key "service-list-name";
        leaf service-list-name {
          description "mDNS Service List Name";
          type string;
        }
        list direction {
            description "Direction IN/OUT for mDNS service-list";
            max-elements "1";
            key "dir";
            leaf dir {
              description "Select direction IN/OUT";
              type enumeration {
                 enum "IN";
                 enum "OUT";
              }
            }
            container IN {
              must "../dir = 'IN'" {
                  error-message "Configuration allowed for IN direction";
              }
              description "IN Bound Filtering";
              presence true;
              list match {
                description "Specify service to match";
                key "name";
                leaf name {
                  description "mDNS Service Definition Name";
                  type string;
                  
                }
                leaf message-type {
                  description "To set the message type";
                  type enumeration {
                    enum "any";
                    enum "announcement";
                    enum "query";
                  }
                  default "any";
                }
              }
            }
            container OUT {
              must "../dir = 'OUT'" {
                  error-message "Configuration allowed for OUT direction";
              }
              description "Out Bound Filtering";
              presence true;
              list match {
                description "Specify service to match";
                key "name";
                leaf name {
                  type string;
                  
                }
              }
            }
        }
      }
      list service-definition {
        description "mDNS Service Definition";
        key "name";
        leaf name {
          description "mDNS Service Definition Name";
          type string;
        }
        leaf description {
          description "Description of the Custom Service";
          type string;
        }
        list service-type {
          key "service-type-name";
          leaf service-type-name {
            description "Specify Service-Type String";
            type string;
          }
        }
      }
    }
  }
  /////////////////////////////////////////////////////////
  // native / mdns-sd
  /////////////////////////////////////////////////////////
  augment "/ios:native" {
    uses config-mdns-sd-grouping;
  }
}
