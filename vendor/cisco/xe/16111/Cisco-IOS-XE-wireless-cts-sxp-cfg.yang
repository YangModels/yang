module Cisco-IOS-XE-wireless-cts-sxp-cfg {
  yang-version 1;
  namespace "http://cisco.com/ns/yang/Cisco-IOS-XE-wireless-cts-sxp-cfg";
  prefix wireless-cts-sxp-cfg;

  import Cisco-IOS-XE-wireless-types {
    prefix wireless-types;
  }
  import ietf-inet-types {
    prefix inet;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Model for managing CTS SXP configuration
     Copyright (c) 2017-2018 by Cisco Systems, Inc.
     All rights reserved.";

  revision 2018-10-29 {
    description
      "Cleaned up spelling errors in descriptions.";
    reference "1.1.0";
  }
  revision 2018-04-09 {
    description
      "Initial revision";
    reference "1.0.0";
  }

  grouping cts-sxp-profile-conn {
    description
      "This contains SXP connection information";
    leaf peer-ip-address {
      type inet:ip-address;
      description
        "Peer ip address for SXP connection";
    }
    leaf connection-mode {
      type wireless-types:enm-cts-sxp-conn-mode;
      description
        "SXP connection mode ";
    }
    leaf password-type {
      type wireless-types:enm-cts-sxp-password-type;
      description
        "Describes SXP connection password type";
    }
  }

  grouping cts-sxp-config-profile {
    description
      "This contains all attributes for CTS SXP configuration";
    leaf sxp-profile-name {
      type string {
        length "0..31";
      }
      description
        "CTS SXP profile name";
    }
    leaf enable {
      type boolean;
      default "false";
      description
        "Enable CTS SXP configuration";
    }
    leaf default-password {
      type string {
        length "0..80";
      }
      default "";
      description
        "Describes CTS SXP default password";
    }
    leaf listener-minimum-holdtime {
      type uint32 {
        range "1 .. 65534";
      }
      default "90";
      description
        "Describes CTS SXP listener hold time min";
    }
    leaf listener-maximum-holdtime {
      type uint32 {
        range "1 .. 65534";
      }
      default "120";
      description
        "Describes CTS SXP listener hold time max";
    }
    leaf speaker-holdtime {
      type uint32 {
        range "1 .. 65534";
      }
      default "120";
      description
        "Describes CTS SXP speaker hold time";
    }
    leaf reconcile-period {
      type uint32 {
        range "0 .. 64000";
      }
      default "120";
      description
        "This contains CTS SXP reconcile period";
    }
    leaf retry-period {
      type uint32 {
        range "0 .. 64000";
      }
      default "120";
      description
        "Describes CTS SXP retry period";
    }
    container sxp-connections {
      description
        "This contains SXP connection information";
      list sxp-connection-config {
        key "peer-ip-address";
        max-elements "5";
        description
          "This contains SXP connections information";
        uses wireless-cts-sxp-cfg:cts-sxp-profile-conn;
      }
    }
  }

  container cts-sxp-cfg-data {
    description
      "This contains CTS SXP configuration";
    container cts-sxp-configuration {
      description
        "This contains CTS SXP configuration";
      list cts-sxp-config {
        key "sxp-profile-name";
        description
          "This contains CTS SXP configuration";
        uses wireless-cts-sxp-cfg:cts-sxp-config-profile;
      }
    }
  }
}
