module Cisco-IOS-XE-site-manager {

  namespace "http://cisco.com/ns/yang/Cisco-IOS-XE-site-manager";
  prefix ios-site-manager;

  import ietf-inet-types {
    prefix inet;
  }

  import ietf-yang-types {
    prefix yang;
  }

  import Cisco-IOS-XE-types {
    prefix ios-types;
  }

  import Cisco-IOS-XE-features {
    prefix ios-features;
  }

  import Cisco-IOS-XE-native {
    prefix ios;
  }

  import Cisco-IOS-XE-atm {
    prefix ios-atm;
  }


  organization
    "Cisco Systems, Inc.";

  contact
    "Cisco Systems, Inc.
     Customer Service

     Postal: 170 W Tasman Drive
     San Jose, CA 95134

     Tel: +1 1800 553-NETS

     E-mail: cs-yang@cisco.com";


  description
    "Cisco XE Native Policy Map Yang Model.
     Copyright (c) 2018 by Cisco Systems, Inc.
     All rights reserved.";

  // =========================================================================
  // REVISION
  // =========================================================================
  revision 2019-01-22 {
     description
      "Added leaf for App-hosting Gigabit Ethernet interface";
  }
  revision 2018-12-13 {
    description
      "Deleting site-manager's name as IOS CLI deleting it";
  }

  revision 2018-11-21 {
    description
      "Adding site-manager";
  }


  typedef site-manager-site-type {
    type enumeration {
      enum "hub";
      enum "branch";
    }
  }

  grouping config-password {
    container password {
      description
        "MD5 password to be used with MC or BRs";
      
      leaf enryption-type {
        description 
          "Encryption type (0=not yet encrypted) (7=encrypted) password";
        type enumeration {
          enum "0";
          enum "7";
        }
      }
      leaf auth-password {
        description 
          "authentication password";
        type string;
      }
    }
  }

  // ** source-interface loopback *
  grouping config-source-interface {
    container source-interface {
      description
        "Source Interface for master controller";
      leaf Loopback {
        description
          "Loopback interface";
        
        type leafref {
          path "/ios:native/ios:interface/ios:Loopback/ios:name";
        }
      }
    }
  }

  grouping config-class-app-policy-type {
    leaf policy {
      description
        "Specify the policy (user defined/predefined)";
      type enumeration {
        enum "best-effort";
        enum "custom";
        enum "saas-dca";
      }
    }
  }
  grouping class-app-group {
    list app-group {
      description
        "Specify the application names";
      
      key "name";
      leaf name {
        description
          "user-defined application name";
        type string;
      }
      uses config-class-app-policy-type;
    }
  }
  grouping class-application {
    list application {
      description
        "Specify the application names";
      
      key "name";
      leaf name {
        description
          "user-defined application name";
        type string;
      }
      uses config-class-app-policy-type;
    }
  }
  grouping config-policy-class {
    list class {
      description
        "Create site-manager class and enter site-manager class command mode";
      key "name sequence";
      leaf name {
        description
          "site-manager class name";
        type string;
      }
      leaf sequence {
        description
          "Set the Sequence for the class";
        type uint16 {
          range "1..65535";
        }
      }
      container match {
        description
          "Specify the applications the policy applies to";
        uses class-app-group;
        uses class-application;
      }
      container path-preference {
        description
          "Specify the preferred provider";
        
        leaf primary {
          description
            "Primary service provider";
          type string;
        }
        leaf primary2 {
          description
            "Primary service provider";
          type string;
        }
        leaf primary3 {
          description
            "Primary service provider";
          type string;
        }
        leaf fallback {
          description
            "Specify the fallback provider";
          type union {
            type enumeration {
              enum "routing";
            }
            type string;
          }
        }
        leaf fallback2 {
          description
            "Fallback service provider";
          type string;
        }
        leaf fallback3 {
          description
            "Fallback service provider";
          type string;
        }
        leaf next-fallback {
          description
            "Specify the next-fallback provider";
          type union {
            type enumeration {
              enum "routing";
            }
            type string;
          }
        }
        leaf next-fallback2 {
          description
            "Next-fallback service provider";
          type string;
        }
        leaf next-fallback3 {
          description
            "Next-fallback service provider";
           type string;
        }
      }
    }
  }
  grouping config-policy {
    container policy {
      description
        "Create policy with policy group or policy type and service type";
      list local {
        description
          "Create local policy";
        when "../../name = 'branch'";
        key "type";
        leaf type {
          description
            "Select policy service type";
           type enumeration {
             enum "dia";
             enum "dca";
           }
        }
        uses config-policy-class;
      }
      list group {
        description
          "Create group policy";
        when "../../name = 'hub'";
        key "group-name type";
        leaf group-name {
          description
            "Create group policy";
          type union {
            type enumeration {
              enum "default";
            }
          }
        }
        leaf type {
          description
            "Select policy service type";
          type enumeration {
            enum "dia";
            enum "dca";
          }
        }
        uses config-policy-class;
      }
    }
  }

  // interface * / site-manager inside/path
  grouping config-interface-site-manager-grouping {
    container site-manager {
      description
        "Specify a site-manager";
      
      choice sitemgr-path-type {
        case sitemgr-path {
          leaf path {
            description
              "Specify a service provider for this interface";
            type string;
          }
          leaf direct-internet-access {
            description
              "Specify Direct-Internet-Access interface";
            type empty;
          }
        }
        case sitemgr-inside {
          leaf inside {
            description
              "Designate this interface as LAN interface on Branch border";
            type empty;
          }
        }
      }
    }
  }
  grouping config-allvrfs-hub-br-common {
    leaf dca-probe-http-interval {
      description
        "DCA sla http probe interval";
      type union {
        type int8 {
          range "20..60";
        }
        type enumeration {
          enum "infinite";
        }
      }
    }
    leaf dia-probe-icmp-interval {
      description 
        "DIA sla icmp probe interval";
      type union {
        type int8 {
          range "20..60";
        }
        type enumeration {
          enum "infinite";
        }
      }
    }
    leaf dns-redirect {
      description
        "Specify new dns resolver address for DCA";
      type inet:ipv4-address {
      }
    }
  }

  // site-manager * 
  grouping config-sitemgr-grouping {
    container site-manager {
      description
        "Configure Site Manager";
      presence true;

      // site-manager * / master *
      list master {
        description
          "Enter master controller configuration submode";
        key "name";
        leaf name {
          type site-manager-site-type;
        }
        // site-manager * / master * / advancd
        container advanced {
          description
            "Advanced configuration submode";
          when "../name = 'hub'";
          uses config-allvrfs-hub-br-common;
        }
        uses config-allvrfs-hub-br-common;
        container domain-map {
          description
            "Enter domain mapping configuration submode";
          when "../name = 'branch'";
          list application {
            description
              "Application name";
            
            key "name";
            leaf name {
              description
                "Specify the application name of the mapping";
              type string;
            }
            leaf domain {
              description
                "Domain url";
              type string;
            }
            leaf dscp {
              description
                "DSCP value";
              type ios-types:dscp-type;
            }
          }
        }
      }

      // site-manager * / vrf *
      list vrf {
        description
          "Configure Site Manager VRF";
        key "name";
        leaf name {
          description
            "Configure VRF";
          type string;
        }

        // site-manager * / vrf * / border
        container border {
          description
            "Configure Site Manager's Border in VRF";

          // site-manager * / vrf * / border / master x
          leaf master {
            description
              "Specify IP address of Site-manager master controller";
            type union {
              type enumeration {
                enum "local";
              }
              type inet:ipv4-address {
              }
            }
          }

          leaf shutdown {
            description
              "Disable Site-manager border router functionality";
            type empty;
          }
          uses config-source-interface;
          uses config-password;

        }

        // site-manager * / vrf * / master *
        list master {
          description
            "Configure Site Manager VRF";
          key "name";
          leaf name {
            description
              "Configure Master type";
            type site-manager-site-type;
          }
          uses config-source-interface;
          // site-manager * / vrf * / master * / shutdown
          leaf shutdown {
            description
              "Disable site-manager master controller functionality";
            type empty;
          }
          // site-manager * / vrf * / master * / advanced
          container advanced {
            description
              "Advanced configuration submode";
            when "../name = 'hub'";

            // site-manager * / vrf * / master * / advanced / tcp *
            container tcp {
              description
                "Specify tcp port numbers for mc-br communication";
              leaf mc-port {
                description
                  "Specify tcp MC self port for mc-br communication";
                type uint16 {
                  range "1..65535";
                }
              }
            }
            // site-manager * / vrf * / master * / advanced / connection-keepalives-interval *
            leaf connection-keepalive-interval {
              description
                "Specify timer to send keepalives to peer";
              type int8 {
                range "1..60";
              }
            }
          }
          // site-manager * / vrf * / master * / password
          uses config-password;
          // site-manager * / vrf * / master * / policy
          uses config-policy;
        }
      }
    } 
  }


  /////////////////////////////////////////////////////////
  // native / site-manager
  /////////////////////////////////////////////////////////
  augment "/ios:native" {
    uses config-sitemgr-grouping;
  }

  /////////////////////////////////////////////////////////
  // native / interface * / site-manager
  /////////////////////////////////////////////////////////
  augment "/ios:native/ios:interface/ios:Ethernet" {
    uses config-interface-site-manager-grouping;
  }

  augment "/ios:native/ios:interface/ios:FastEthernet" {
    uses config-interface-site-manager-grouping;
  }

  augment "/ios:native/ios:interface/ios:ATM" {
    uses config-interface-site-manager-grouping;
  }

  augment "/ios:native/ios:interface/ios:ATM-subinterface/ios:ATM" {
    uses config-interface-site-manager-grouping;
  }

  augment "/ios:native/ios:interface/ios:ATM/ios-atm:pvc" {
    uses config-interface-site-manager-grouping;
  }

  augment "/ios:native/ios:interface/ios:ATM-subinterface/ios:ATM/ios-atm:pvc" {
    uses config-interface-site-manager-grouping;
  }

  augment "/ios:native/ios:interface/ios:GigabitEthernet" {
    uses config-interface-site-manager-grouping;
  }

  augment "/ios:native/ios:interface/ios:TenGigabitEthernet" {
    uses config-interface-site-manager-grouping;
  }

  augment "/ios:native/ios:interface/ios:FiveGigabitEthernet" {
    uses config-interface-site-manager-grouping;
  }

  augment "/ios:native/ios:interface/ios:AppGigabitEthernet" {
    uses config-interface-site-manager-grouping;
  }

  augment "/ios:native/ios:interface/ios:TwentyFiveGigE" {
    uses config-interface-site-manager-grouping;
  }

  augment "/ios:native/ios:interface/ios:FortyGigabitEthernet" {
    uses config-interface-site-manager-grouping;
  }

  augment "/ios:native/ios:interface/ios:TwoGigabitEthernet" {
    uses config-interface-site-manager-grouping;
  }

  augment "/ios:native/ios:interface/ios:HundredGigE" {
    uses config-interface-site-manager-grouping;
  }

  augment "/ios:native/ios:interface/ios:Multilink" {
    uses config-interface-site-manager-grouping;
  }

  augment "/ios:native/ios:interface/ios:Port-channel" {
    uses config-interface-site-manager-grouping;
  }

  augment "/ios:native/ios:interface/ios:Tunnel" {
    uses config-interface-site-manager-grouping;
  }

  augment "/ios:native/ios:interface/ios:LISP" {
    uses config-interface-site-manager-grouping;
  }

  augment "/ios:native/ios:interface/ios:Virtual-Template" {
    uses config-interface-site-manager-grouping;
  }

  augment "/ios:native/ios:interface/ios:vasileft" {
    uses config-interface-site-manager-grouping;
  }

  augment "/ios:native/ios:interface/ios:vasiright" {
    uses config-interface-site-manager-grouping;
  }

  augment "/ios:native/ios:interface/ios:Vlan" {
    uses config-interface-site-manager-grouping;
  }

  augment "/ios:native/ios:interface/ios:BDI" {
    uses config-interface-site-manager-grouping;
  }

  augment "/ios:native/ios:interface/ios:Cellular" {
    uses config-interface-site-manager-grouping;
  }

  augment "/ios:native/ios:interface/ios:Dialer" {
    uses config-interface-site-manager-grouping;
  }

  augment "/ios:native/ios:interface/ios:Serial" {
    uses config-interface-site-manager-grouping;
  }
}//module
