module Cisco-IOS-XE-template {
  namespace "http://cisco.com/ns/yang/ios-xe/template";
  prefix ios-template;

  import ietf-inet-types {
    prefix inet;
  }


  import Cisco-IOS-XE-native {
    prefix ios;
  }

  import Cisco-IOS-XE-features {
    prefix ios-features;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Template Yang Model.
     Copyright (c) 2016-2019 by Cisco Systems, Inc.
     All rights reserved.";

  // =========================================================================
  // REVISION
  // =========================================================================
  revision 2019-01-29 {
      description
      "Added timer mode for template authentication";
  }
  revision 2018-11-07 {
      description
      "Cleanup spelling errors in description statements";
  }
  revision 2018-08-20 {
    description
      "Added some model for template";
  }
  revision 2017-11-06 {
    description
      "Make some option switch platform dependent";
  }
  revision 2017-02-13 {
    description
      "Initial Revision";
  }

  grouping template-grouping {
      container dot1x {
        description "Interface Config Commands for IEEE 802.1X";
        leaf  pae {
          description "Set 802.1x interface pae type";
          type enumeration {
            enum "authenticator";
            enum "both";
            enum "supplicant";
          }
        }
      }
      container service-policy {
        description "Configure CPL Service Policy";
        container input {
          description "Assign policy-map to the input of an interface";
          leaf policy-map-name {
            description "policy-map name";
            type string;
          }
        }
        container output {
          description "Assign policy-map to the output of an interface";
          leaf policy-map-name {
            description "policy-map name";
            type string;
          }
        }
        container type {
          description "Configure CPL Service Policy";
          container control {
            description "Apply a control policy to the interface";
            leaf subscriber {
              description "Apply a subscriber control policy to the interface";
              type string;
            }
          }
        }
      }
      container switchport {
        description "Set switching mode characteristics";
        if-feature ios-features:switching-platform;
        container mode {
          description "Set trunking mode of the interface";
          leaf trunk {
            description "Set trunking mode to TRUNK unconditionally";
            type empty;
          }
          leaf access {
            description "Set trunking mode to ACCESS unconditionally";
            type empty;
          }
        }
        leaf nonegotiate {
          description "Device will not engage in negotiation protocol on this interface";
          type empty;
        }
        container block {
          description "Disable forwarding of unknown uni/multi cast addresses";
          leaf unicast {
            description "Block unknown unicast addresses";
            type empty;
          }
        }
        container port-security {
          description "Security related command";
          presence true;
          container aging {
            description "Port-security aging commands";
            leaf static {
              description "Enable aging for configured secure addresses";
                type empty;
            }
            leaf time {
              description "Port-security aging time";              
              type uint16 {
                range "1..1440";
              }              
            }
            container type {
              description "Port-security aging type";
              presence true;
              leaf inactivity {
                description "Aging based on inactivity time period";
                type empty;
              }
            }
          }
          container maximum {
            description "Max secure addresses";
            list range {
              key "range";
              leaf range {
                description "Maximum addresses";
                type uint16 {
                  range "1..3072";
                }
              }
              container vlan {
                description "Max secure addresses per vlan";
                presence true;
                leaf access {
                  description "access vlan";
                  type empty;
                }
              }
            }
          }
          container violation {
            description "Security violation mode";
            leaf protect {
              description "Security violation protect mode";
              type empty;
            }
            leaf restrict {
              description "Security violation restrict mode";
              type empty;
            }
            leaf shutdown {
              description "Security violation shutdown mode";
              type empty;
            }
          }
        }
        container access {
          description "Set access mode characteristics of the interface";
          leaf vlan {
            description "VLAN ID of the VLAN when this port is in access mode";
            type uint16 {
              range "1..4094";
            }
          }
        }
        container voice {
          description "Voice appliance attributes";
          leaf vlan {
            description "Vlan for voice traffic";
            type uint16 {
              range "1..4094";
            }
          }
        }
      }
      container mab {
        description "MAC Authentication Bypass Interface Config Commands";
        presence true;
      }
      container access-session {
        description "Access Session specific Interface Configuration Commands";
        leaf closed {
          description 
            "Enable closed access on port (disabled by default, i.e. open access)";
          type empty;
        }
        leaf port-control {
          description "Set the port-control value";
          type enumeration {
            enum "auto";
            enum "force-authorized";
            enum "force-unauthorized";
          }
          default "force-authorized";
        }
      }
      container authentication {
        description "Auth Manager Interface Configuration Commands";
        leaf periodic {
          description "Enable or Disable Reauthentication for this port";
          type empty;
        }
        container timer {
          description
            "Set authentication timer values";
          container reauthenticate {
            description
              "Time in seconds after which an automatic re-authentication"+
                              " should be initiated (default 1 hour)";
            choice value {
              leaf server {
                description
                  "Obtain re-authentication timeout value from the server";
                type empty;
                }
              leaf range {
                description
                  "Enter a value between 1 and 65535";
                type uint16 {
                  range "1..65535";
                }
              }
            }
          }
        }
      }
      container spanning-tree {
        description "Spanning Tree Subsystem";
        presence true;
        container bpduguard {
          description "Don't accept BPDUs on this interface";
          leaf enable {
            description "Enable BPDU guard for this interface";
              type empty;
          }
        }
        leaf service-policy {
          description "help";
          type empty;
        }
        container portfast {
          description "Portfast options for the interface";
          presence true;
          leaf disable {
            description
              "Disable portfast for this interface";
            type empty;
          }
          leaf edge {
            description
              "Enable portfast edge on the interface";
            type empty;
          }
          leaf network {
            description
              "Enable portfast network on the interface";
            type empty;
          }
        }
      }
      container storm-control {
        description "storm configuration";
        if-feature ios-features:switching-platform;
        container broadcast {
          description "Broadcast address storm control";
          container level {
            description "Set storm suppression level on this interface";
            container pps {
              description "Enter suppression level in packets per second";
              leaf threshold {              
                description "Enter threshold";
                type string;
              }           
            }
            container bps {
              description "Enter suppression level in bits per second";
              leaf threshold {              
                description "Enter threshold";
                type decimal64 {
                  fraction-digits 1;
                  range "0.0..10000000000.0";
                }
              }
              leaf b-unit{
                type string;
              }
            }          
            leaf threshold {            
              description "Enter threshold";
              type decimal64 {
                fraction-digits 2;
                range "0.00..100.00";
              }            
            }
          }
        }
        container multicast {
          description "Multicast address storm control";
          container level {
            description "Set storm suppression level on this interface";
            container pps {
              description "Enter suppression level in packets per second";
              leaf threshold {              
                description "Enter threshold";
                type string;
              }           
            }
            container bps {
              description "Enter suppression level in bits per second";
              leaf threshold {              
                description "Enter threshold";
                type decimal64 {
                  fraction-digits 1;
                  range "0.0..10000000000.0";
                }
              }
              leaf b-unit{
                type string;
              }
            }          
            leaf threshold {            
              description "Enter threshold";
              type decimal64 {
                fraction-digits 2;
                range "0.00..100.00";
              }            
            }
          }
        }
        container action {
          description
            "Action to take for storm-control";
          leaf shutdown {
            description
              "Shutdown this interface if a storm occurs";
            type empty;
          }
          leaf trap {
            description
              "Send SNMP trap if a storm occurs";
            type empty;
          }
        }
      }
      leaf load-interval {
        description "Load interval delay in seconds";
        type uint16 {
          range "30..600";
        }
      }
      container ip {
        description "IP template config";
        container dhcp {
          description "DHCP template config";
          if-feature ios-features:switching-platform;
          container snooping {
            description "DHCP Snooping";
            container limit {
              description "DHCP Snooping limit";
              leaf rate {
                description "DHCP snooping rate limit";
                type uint16 {
                  range "1..2048";
                }
              }
            }
            leaf trust {
              description "DHCP Snooping trust config";
              type empty;
            }
          }
        }
      }
  }

  grouping config-template-sw-grouping {
        container IP_CAMERA_INTERFACE_TEMPLATE {
          description "built-in modified";
          uses template-grouping;       
        }
        container LAP_INTERFACE_TEMPLATE {
          description "built-in modified";
          uses template-grouping;
        }
        container AP_INTERFACE_TEMPLATE {
          description "built-in modified";
          uses template-grouping;
        }
        container DMP_INTERFACE_TEMPLATE {
          description "built-in modified";
          presence true;
          uses template-grouping;
        }
        container IP_PHONE_INTERFACE_TEMPLATE {
          description "built-in modified";
          presence true;
          uses template-grouping;          
        }
        container MSP_CAMERA_INTERFACE_TEMPLATE {
          description "built-in modified";
          uses template-grouping;
        }
        container MSP_VC_INTERFACE_TEMPLATE {
          description "built-in modified";
          uses template-grouping;
        }
        container PRINTER_INTERFACE_TEMPLATE {
          description "built-in modified";
          uses template-grouping;
        }
        container ROUTER_INTERFACE_TEMPLATE {
          description "built-in modified";
          uses template-grouping;
        }
        container SWITCH_INTERFACE_TEMPLATE {
          description "built-in modified";
          uses template-grouping;
        }
        container TP_INTERFACE_TEMPLATE {
          description "built-in modified";
          uses template-grouping;
        }
  }

  grouping template-error-disable-grouping {
    leaf error-disable-interface {
      type empty;
    }
  }
  grouping template-threshold-grouping-64k {
    container threshold {
      description "threshold";
      container high {
        description "High Threshold";
        leaf high-range {
          description "Set the high threshold";
          type uint16 {
            range "1..65535";
          }
        }
        leaf none {
          description "Disable high threshold";
          type empty;
        }
      }
      leaf low {
        description "Set the low threshold";
        type uint16 {
          range "0..65535";
        }
      }
    }
  }

  grouping template-window-grouping-64k {
    leaf window {
      description "Set window size in number of 10000 frames";
      type uint16 {
        range "1..65535";
      }
    }
  }
    
  grouping template-window-grouping-1800 {
    leaf window {
      description "Set window size in number of 10000 frames";
      type uint16 {
        range "10..1800";
      }
    }
  }
  grouping  config-template-grouping {
    list template_details {
      key "template_name";
      leaf template_name {
        description "Template name";
        type string;
      }
      container ethernet {
        description "Ethernet service";
        container oam {
          description "Operations, Administration and Maintenance";
          container link-monitor {
            description "Ethernet OAM Link Monitor";
            container frame {
              description "Errored frames in a period measured by time";
              uses template-threshold-grouping-64k;
            }
            leaf window {
              description "Set window size in multiple of 100 milliseconds (will be rounded off to second)";
              type uint16 {
                range "10..600";
              }
            }
            container frame-period {
              description "Errored frames in a period measured by number of frames";
              uses template-threshold-grouping-64k;
              uses template-window-grouping-64k;
            }
            container frame-seconds {
              description "Errored frame seconds in a period";
              container threshold {
                description "Errored frame-seconds threshold";
                container high {
                  description "High Threshold";
                  leaf high-range {
                    description "Set the high errored frame-seconds threshold in number of seconds";
                    type uint16 {
                      range "1..900";
                    }
                  }
                  leaf none {
                    description "Disable high threshold";
                    type empty;
                  }
                }
                leaf low {
                  description "Set the low errored frame-seconds threshold in number of seconds";
                  type uint16 {
                    range "1..900";
                  }
                }
              }
              leaf window {
                description "Set window size in multiple of 100 milliseconds (will be rounded off to second)";
                type uint16 {
                  range "100..9000";
                }
              }
            }
            container high-threshold {
              description "Additional high threshold configuration";
              container action {
                description "Specify an action when the high threshold is crossed";
                uses template-error-disable-grouping;
              }
            }
            container receive-crc {
              description "Received frames with CRC errors in a period";
              uses template-threshold-grouping-64k;
              uses template-window-grouping-1800;
            }
            container symbol-period {
              description "Errored symbols in a period";
              uses template-threshold-grouping-64k;
              uses template-window-grouping-64k;
            }
            container transmit-crc {
              description "Transmitted frames with CRC errors in a period";
              uses template-threshold-grouping-64k;
              uses template-window-grouping-1800;
            }
          }
          container remote-failure {
            description "Ethernet OAM remote failure indication";
            container critical-event {
              description "Critical event";
              container action {
                description "Specify an action when a remote failure is detected";
                uses template-error-disable-grouping;
              }
            }
            container dying-gasp {
              description "Dying gasp";
              container action {
                description "Specify an action when a remote failure is detected";
                presence true;
                uses template-error-disable-grouping;
              }
            }
            container link-fault {
              description "Link fault";
              container action {
                description "Specify an action when a remote failure is detected";
                presence true;
                uses template-error-disable-grouping;
              }
            }
          }
        }
      }
      uses template-grouping;
    }
    uses config-template-sw-grouping {
      if-feature ios-features:switching-platform;
    }
  }

  /////////////////////////////////////////////////////////
  // native / template
  /////////////////////////////////////////////////////////
  augment "/ios:native/ios:template" {
    uses config-template-grouping;
  }
}
