module Cisco-IOS-XE-icmp {
  namespace "http://cisco.com/ns/yang/Cisco-IOS-XE-icmp";
  prefix ios-icmp;


  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Internet Control Message Protocol (ICMP) Yang model.
     Copyright (c) 2016-2017 by Cisco Systems, Inc.
     All rights reserved.";

  // =========================================================================
  // REVISION
  // =========================================================================
  revision 2019-01-22 {
     description
      "Added leaf for App-hosting Gigabit Ethernet interface";
  }

  revision 2018-08-29 {
    description
      "add config-interface-ip-icmp-grouping use for interface Multilink and Cellular";
  }

  revision 2017-11-27 {
     description
       "Added Change 25GE name";
  }

  revision 2017-11-14 {
    description
      "This revision has changes for new 40 and 100 GE interface addition";
  }
 
  revision 2017-09-14 {
    description
      "This revision has changes for new 2gig interface addition";
  }
  revision 2017-08-16 {
    description
      "This revision has changes for new 5gig and 25gig interfaces addition";
  }
  revision 2017-06-12 {
    description
      "add config-interface-ip-icmp-grouping use for interface Vlan";
  }

  revision 2017-02-07 {
    description
      "Initial revision";
  }

  grouping config-icmp-grouping {
    container icmp { //42011
        description
          "ICMP options";
      container rate-limit {
        description
          "rate limit ICMP messages generated";
        container unreachable {
          description
            "ICMP type 3, Destination Unreachable";
          leaf time {
            description
              "Once per milliseconds";
            type uint32;
          }
          container DF {
            description
              "code 4, fragmentation needed and DF set";
            leaf time {			
              description
                "Once per milliseconds";
              type uint32;
            }			  
          }
          container log {
            description
              "log message if rate limiting is excessive";
            presence "true";
            leaf number-unreachables {
              description
                "number of unreachables within interval to trigger a message";
              type uint32;
            }
            leaf log-message {
              description
                "log message once per milliseconds";
              type uint32 {
                range "10000..4294967295";
              }
            }
          }
        }
        leaf redirect {
          description
            "description";
          type enumeration {
            enum "host";
            enum "subnet";
          }
        }
      }
    }
  }

  grouping config-interface-ip-icmp-grouping {
    leaf unreachables {
      description
        "Enable sending ICMP Unreachable messages";
      type boolean;
    }
  }

  /////////////////////////////////////////////////////////
  // native / ip / icmp
  /////////////////////////////////////////////////////////
  augment "/ios:native/ios:ip" {
    uses config-icmp-grouping;
  }

  /////////////////////////////////////////////////////////
  // native / interface * / ip unreachables  
  /////////////////////////////////////////////////////////
  augment "/ios:native/ios:interface/ios:FastEthernet/ios:ip" {
    uses config-interface-ip-icmp-grouping;
  }

  augment "/ios:native/ios:interface/ios:GigabitEthernet/ios:ip" {
    uses config-interface-ip-icmp-grouping;
  }

  augment "/ios:native/ios:interface/ios:TenGigabitEthernet/ios:ip" {
    uses config-interface-ip-icmp-grouping;
  }

  augment "/ios:native/ios:interface/ios:FiveGigabitEthernet/ios:ip" {
    uses config-interface-ip-icmp-grouping;
  }

  augment "/ios:native/ios:interface/ios:AppGigabitEthernet/ios:ip" {
    uses config-interface-ip-icmp-grouping;
  }

  augment "/ios:native/ios:interface/ios:TwentyFiveGigE/ios:ip" {
    uses config-interface-ip-icmp-grouping;
  }

  augment "/ios:native/ios:interface/ios:TwoGigabitEthernet/ios:ip" {
    uses config-interface-ip-icmp-grouping;
  }

  augment "/ios:native/ios:interface/ios:FortyGigabitEthernet/ios:ip" {
    uses config-interface-ip-icmp-grouping;
  }

  augment "/ios:native/ios:interface/ios:HundredGigE/ios:ip" {
    uses config-interface-ip-icmp-grouping;
  }

  augment "/ios:native/ios:interface/ios:Multilink/ios:ip" {
    uses config-interface-ip-icmp-grouping;
  }

  augment "/ios:native/ios:interface/ios:Cellular/ios:ip" {
    uses config-interface-ip-icmp-grouping;
  }

  augment "/ios:native/ios:interface/ios:Tunnel/ios:ip" {
    uses config-interface-ip-icmp-grouping;
  }   
 
  augment "/ios:native/ios:interface/ios:Vlan/ios:ip" {
    uses config-interface-ip-icmp-grouping;
  }

  /////////////////////////////////////////////////////////
  // native / interface * / ipv6 unreachables  
  /////////////////////////////////////////////////////////
  augment "/ios:native/ios:interface/ios:FastEthernet/ios:ipv6" {
    uses config-interface-ip-icmp-grouping;
  }

  augment "/ios:native/ios:interface/ios:GigabitEthernet/ios:ipv6" {
    uses config-interface-ip-icmp-grouping;
  }

  augment "/ios:native/ios:interface/ios:TenGigabitEthernet/ios:ipv6" {
    uses config-interface-ip-icmp-grouping;
  }

  augment "/ios:native/ios:interface/ios:FiveGigabitEthernet/ios:ipv6" {
    uses config-interface-ip-icmp-grouping;
  }

  augment "/ios:native/ios:interface/ios:AppGigabitEthernet/ios:ipv6" {
    uses config-interface-ip-icmp-grouping;
  }

  augment "/ios:native/ios:interface/ios:TwentyFiveGigE/ios:ipv6" {
    uses config-interface-ip-icmp-grouping;
  }

  augment "/ios:native/ios:interface/ios:TwoGigabitEthernet/ios:ipv6" {
    uses config-interface-ip-icmp-grouping;
  }

  augment "/ios:native/ios:interface/ios:FortyGigabitEthernet/ios:ipv6" {
    uses config-interface-ip-icmp-grouping;
  }

  augment "/ios:native/ios:interface/ios:HundredGigE/ios:ipv6" {
    uses config-interface-ip-icmp-grouping;
  }

  augment "/ios:native/ios:interface/ios:Tunnel/ios:ipv6" {
    uses config-interface-ip-icmp-grouping;
  }  
}
