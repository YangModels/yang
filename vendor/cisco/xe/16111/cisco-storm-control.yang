module cisco-storm-control {
  namespace "urn:cisco:params:xml:ns:yang:cisco-storm-control";
  prefix cisco-stormctrl;

  import ietf-yang-types {
    prefix yang;
  }

  import cisco-bridge-common {
    prefix cbridge;
  }


  organization "Cisco Systems, Inc.";
  contact
    "Cisco Systems, Inc.
     Customer Service

     Postal: 170 W Tasman Drive
     San Jose, CA 95134

     Tel: +1 1800 553-NETS

     E-mail: cs-yang@cisco.com";
  description
    "This module defines data model for strom control feature.

     Traffic storm occurs when packets flood a bridge, creating
     excessive traffic and degrading network performance. Traffic
     storm control prevents bridge disruption by suppressing traffic
     when the number of packets reaches configured threshold
     levels.";

  revision 2016-12-14 {
    description
      "Removed cisco govern extension";
  }

  revision 2014-09-25 {
    description
      "Proposed";
    reference
      "TODO";
  }

  feature configurable-storm-control-actions {
    description
     "This feature represents the ability to configure storm
      control.";
  }

  identity storm-control-action {
    description
      "Actions to be taken once storm control limit threshold is
       exceeded for a traffic class.";
  }

  identity action-drop {
    base storm-control-action;
    description
      "Drop packets.";
  }

  identity action-snmp-trap {
    base storm-control-action;
    description
      "Generate SNMP traps.";
  }

  identity action-shutdown {
    base storm-control-action;
    description
      "Shutdown service.";
  }

  grouping traffic-threshold-config {
    description
      "This grouping defines a threshold value for traffic rate.";
    leaf value {
      type uint32;
      mandatory true;
      description
        "Traffic threshold value. Unit of the value is indicated by
         leaf 'unit'.";
    }

    leaf unit {
      type enumeration {
        enum bps {
          description
            "Bits per second.";
        }
        enum kbps {
          description
            "Kilobits per second.";
        }
        enum pps {
          description
            "Packets per seconds.";
        }
      }
      mandatory true;
      description
        "This enumeration define unit of the traffic threshold
         value.";
    }
  }

  grouping storm-control-config {
    description
      "Storm control feature for an ethernet bridge.

       A traffic storm occurs when packets flood the LAN, creating
       excessive traffic and degrading network performance. The
       traffic storm control feature prevents LAN ports from being
       disrupted by a broadcast, multicast, or unicast traffic storm
       on physical or logical interfaces.";

    container storm-control {
      description
        "A collection of storm control threshold and action
         configurations.";

      list thresholds {
        key "traffic-class";
        description
          "A collection of storm control threshold configuration
           entries.";

        leaf traffic-class {
          type cbridge:eth-traffic-class;
          description
            "This leaf identifies a ethernet traffic type for
             which an administrator desires to configure storm
             control.";
        }

        uses traffic-threshold-config {
          description
            "This grouping represents traffic rate threshold for
             the traffic class.";
        }
      }

      leaf action {
        if-feature configurable-storm-control-actions;
        type identityref {
          base storm-control-action;
        }
        description
          "This leaf represents the storm control action taken when
           the traffic of a particular type exceeds the configured
           threshold values.";
      }
    }
  } // end storm control grouping
  
  grouping storm-control-stats {
    description
      "This groping defines storm control statistics.";
    container storm-control {
      description
        "Storm control statistics.";
      list drop-counter {
        key "traffic-class";
        description
          "Collection of packet drop statistics for ethernet traffic
           clasess.";
        leaf traffic-class {
          type cbridge:eth-traffic-class;
          description
            "Ethernet traffic class i.e. broadcast, multicast or
             unknown unicast.";
        }
        
        leaf packet-drops {
          type yang:counter64;
           description
             "The total number of dropped packets due to storm
              control violations.";
        }

        leaf octate-drops {
          type yang:counter64;
           description
             "The total number of bytes of traffic dropped due to
              storm control violations.";
        }
      } 
    }
  }
} // end module
