module Cisco-IOS-XE-lisp-oper {
  yang-version 1;
  namespace "http://cisco.com/ns/yang/Cisco-IOS-XE-lisp-oper";
  prefix lisp-ios-xe-oper;

  import ietf-inet-types {
    prefix inet;
  }
  import ietf-yang-types {
    prefix yang;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions for
     LISP operational data.
     Copyright (c) 2017-2018 by Cisco Systems, Inc.
     All rights reserved.";

  revision 2018-12-07 {
    description
      "- Added lisp publish/subscribe data
       - Cleaned up spelling errors in descriptions
       - New IAF leaves for first packet loss
       - New Map cache leaves for first packet loss
       - Add last-stats-clear-time and ddt-requests-failed leaves under
         instances/af";
    reference "2.3.0";
  }
  revision 2018-08-01 {
    description
      "- New stats leafs for LISP assurance
       - New lists:
          - Extranets
          - Extranet member instances
          - Extranet per-address-family EIDs
       - Added map-cache best information source
       - Added lisp prefix-list";
    reference "2.2.0";
  }
  revision 2018-02-01 {
    description
      "New leaf in the Local Database Grouping.
       Added lisp prefix-list";
    reference "2.1.0";
  }
  revision 2017-10-25 {
    description
      "New leaves in lists:
        - LISP instance
        - Instance-AF
        - ITR's map-cache
        - ITR's map-cache RLOCs (and the list is renamed)
       New lists:
        - Reliable Registration sessions
        - Map-Server registration database
        - ETR's local mappings
        - Local RLOCs
        - ETR's list of map-servers
        - ITR's list of map-resolvers
        - ITR's list of Proxy ETRs
        - Map-Server EID membership
        - ETR EID membership";
    reference "2.0.0";
  }
  revision 2017-07-04 {
    description
      "Initial revision";
    reference "1.0.0";
  }

  typedef lisp-address-family-type {
    type enumeration {
      enum "ipv4-afi" {
        value 0;
        description
          "IANA IPv4 address family";
      }
      enum "ipv6-afi" {
        value 1;
        description
          "IANA IPv6 address family";
      }
      enum "mac-afi" {
        value 2;
        description
          "IANA MAC address family";
      }
    }
    description
      "Address-family of a LISP address or prefix";
  }

  typedef lisp-iaftype-type {
    type enumeration {
      enum "iaf-ipv4" {
        value 0;
        description
          "IPv4 instance service";
      }
      enum "iaf-ipv6" {
        value 1;
        description
          "IPv6 instance service";
      }
      enum "iaf-mac" {
        value 2;
        description
          "MAC (L2) instance service";
      }
      enum "iaf-ar" {
        value 3;
        description
          "Address Resolution (L3 address-to-MAC) instance
           service";
      }
      enum "iaf-rar" {
        value 4;
        description
          "Reverse Address Resolution (MAC-to-L3 address)
           instance service";
      }
    }
    description
      "Type of service for an Address-Family within a single
       LISP instance";
  }

  typedef lisp-map-reply-action-type {
    type enumeration {
      enum "no-action" {
        value 0;
        description
          "Mapping is kept alive and no encapsulation occurs";
      }
      enum "natively-forward" {
        value 1;
        description
          "Matching packets are forwarded without
           LISP encapsulation";
      }
      enum "send-map-request" {
        value 2;
        description
          "Matching packets trigger sending Map-Requests";
      }
      enum "drop" {
        value 3;
        description
          "Matching packets are dropped";
      }
      enum "unknown-eid-forward" {
        value 4;
        description
          "Unknown EIDs are replied by MR with address of PETR";
      }
    }
    description
      "Defines the LISP map-cache ACT type as described
       in the section 6.1.4 of RFC 6830. Valid only
       for negative map-cache entries";
  }

  typedef lisp-rloc-state-type {
    type enumeration {
      enum "lisp-rloc-state-down" {
        value 0;
        description
          "Locator is down or unreachable";
      }
      enum "lisp-rloc-state-up" {
        value 1;
        description
          "Locator is up and reachable";
      }
    }
    description
      "Reachability state of a RLOC";
  }

  typedef lisp-session-state-type {
    type enumeration {
      enum "lisp-session-state-incomplete" {
        value 0;
        description
          "Session parameters are incomplete";
      }
      enum "lisp-session-state-listening" {
        value 1;
        description
          "Session represents the passively listening socket";
      }
      enum "lisp-session-state-down" {
        value 2;
        description
          "Session is down";
      }
      enum "lisp-session-state-up" {
        value 3;
        description
          "Session is up";
      }
    }
    description
      "State of a TCP session";
  }

  typedef lisp-map-cache-information-best-source-type {
    type enumeration {
      enum "lisp-map-cache-info-best-source-invalid" {
        value 0;
        description
          "Map-cache best source invalid";
      }
      enum "lisp-map-cache-info-best-source-static" {
        value 1;
        description
          "Map-cache best source is static";
      }
      enum "lisp-map-cache-info-best-source-use-nat-rtr" {
        value 2;
        description
          "Map-cache installed for encapsulation via NAT-RTR";
      }
      enum "lisp-map-cache-info-best-source-nat-rtr" {
        value 3;
        description
          "Map-cache installed by RTR";
      }
      enum "lisp-map-cache-info-best-source-transient" {
        value 4;
        description
          "Map-cache installed from a set";
      }
      enum "lisp-map-cache-info-best-source-static-configured" {
        value 5;
        description
          "Map-cache statically configured";
      }
      enum "lisp-map-cache-info-best-source-via-site-reg" {
        value 6;
        description
          "Map-cache installed via site registration";
      }
      enum "lisp-map-cache-info-best-source-rtimp" {
        value 7;
        description
          "Map-cache installed via route import";
      }
      enum "lisp-map-cache-info-best-source-dyn-eid-group" {
        value 8;
        description
          "Map-cache source via dynamic eid group";
      }
      enum "lisp-map-cache-info-best-source-away" {
        value 9;
        description
          "Map-cache is known to be away";
      }
      enum "lisp-map-cache-info-best-source-extranet-policy" {
        value 10;
        description
          "Map-cache best source due to extranet policy";
      }
      enum "lisp-map-cache-info-best-source-pub-sub" {
        value 11;
        description
          "Map-cache installed via publication";
      }
    }
    description
      "Source of the best map cache information";
  }

  typedef lisp-map-cache-information-best-source-trans-type {
    type enumeration {
      enum "lisp-map-cache-info-best-source-trans-invalid" {
        value 0;
        description
          "Map-cache best source transient invalid";
      }
      enum "lisp-map-cache-info-best-source-trans-map-request" {
        value 1;
        description
          "Map-cache best source is transient via map request";
      }
      enum "lisp-map-cache-info-best-source-trans-map-reply" {
        value 2;
        description
          "Map-cache best source is transient via map reply";
      }
      enum "lisp-map-cache-info-best-source-trans-nsf-replay" {
        value 3;
        description
          "Map-cache best source transient through NSF replay";
      }
      enum "lisp-map-cache-info-best-source-trans-persistent-replay" {
        value 4;
        description
          "Map-cache best source transient via persistent replay";
      }
      enum "lisp-map-cache-info-best-source-trans-data-signal" {
        value 5;
        description
          "Map-cache best source is transient due to data signal";
      }
      enum "lisp-map-cache-info-best-source-trans-lig" {
        value 6;
        description
          "Map-cache best source is transient via LIG";
      }
      enum "lisp-map-cache-info-best-source-trans-eid-probe" {
        value 7;
        description
          "Map-cache best source is transient via EID probe";
      }
      enum "lisp-map-cache-info-best-source-trans-eid-watch" {
        value 8;
        description
          "Map-cache best source is transient via EID watch";
      }
      enum "lisp-map-cache-info-best-source-trans-away" {
        value 9;
        description
          "Map-cache best source is transient via away entry";
      }
      enum "lisp-map-cache-info-best-source-trans-wlc-mnotify" {
        value 10;
        description
          "Map-cache best source transient via WLC map notify";
      }
    }
    description
      "Source of the best map_cache transient information";
  }

  typedef lisp-capabilities-type {
    type bits {
      bit publish-subscribe-instance-id {
        position 0;
        description
          "Capability to support mapping publication and subscription by
           instance-id";
      }
    }
    description
      "Capabilities enabled for a LISP router";
  }

  grouping lisp-address-type {
    description
      "Generalized LISP address (EID or RLOC)";
    leaf afi {
      type lisp-ios-xe-oper:lisp-address-family-type;
      description
        "LISP Address-Family of the address";
    }
    leaf address {
      type string;
      description
        "LISP address. Format is defined by the AF";
    }
  }

  grouping lisp-prefix-type {
    description
      "Generalized LISP EID prefix";
    leaf afi {
      type lisp-ios-xe-oper:lisp-address-family-type;
      description
        "LISP Address-Family of the prefix";
    }
    leaf prefix {
      type string;
      description
        "LISP prefix. Format is defined by the AF";
    }
  }

  grouping lisp-rloc-parameters-type {
    description
      "Packet forwarding properties of a RLOC";
    leaf priority {
      type uint8;
      description
        "Locator priority";
    }
    leaf weight {
      type uint8;
      description
        "Locator weight";
    }
    leaf mcast-priority {
      type uint8;
      description
        "Locator's multicast priority";
    }
    leaf mcast-weight {
      type uint8;
      description
        "Locator's multicast weight";
    }
  }

  grouping lisp-local-dbase-rloc-type {
    description
      "Description of a RLOC (locator address and its properties)";
    container params {
      description
        "Properties of the locator";
      uses lisp-ios-xe-oper:lisp-rloc-parameters-type;
    }
    leaf state {
      type lisp-ios-xe-oper:lisp-rloc-state-type;
      description
        "Up/down state of the locator";
    }
    leaf is-local {
      type boolean;
      description
        "Indicates if RLOC local to the device or to another xTR
         in the site; TRUE means RLOC is local to the device";
    }
  }

  grouping lisp-local-dbase-mapping-type {
    description
      "EID prefix local to an ETR";
    leaf lsb {
      type uint32;
      description
        "The Locator Status Bits for this EID-Prefix";
    }
    leaf is-reachable {
      type boolean;
      description
        "If the prefix is currently reachable from this device
         via EID interfaces";
    }
    list local-dbase-rloc {
      key "afi address";
      description
        "List of locators";
      uses lisp-ios-xe-oper:lisp-local-dbase-rloc-type;
      uses lisp-ios-xe-oper:lisp-address-type;
    }
    leaf is-proxy {
      type boolean;
      description
        "If local database mapping is proxy";
    }
  }

  grouping lisp-ms-registration-rloc-type {
    description
      "Description of a Map-Server registration RLOC (locator
       address and its properties)";
    container params {
      description
        "Properties of the locator";
      uses lisp-ios-xe-oper:lisp-rloc-parameters-type;
    }
    leaf state {
      type lisp-ios-xe-oper:lisp-rloc-state-type;
      description
        "Up/down state of the locator";
    }
    leaf is-local {
      type boolean;
      description
        "Indicates if RLOC is local to device which sent
         registration or to another xTR in the site; TRUE means
         RLOC is local to the registering device";
    }
  }

  grouping lisp-ms-registration-type {
    description
      "Registration received by MS from an ETR";
    leaf last-registration-time {
      type yang:date-and-time;
      description
        "Time when valid registration from the source was last
         received";
    }
    leaf ttl {
      type uint32;
      units "minutes";
      description
        "Registration validity period";
    }
    leaf proxy-reply {
      type boolean;
      description
        "Indicates if the registering ETR requested proxy-replying
         on Map-Requests by the Map-Server";
    }
    leaf wants-map-notify {
      type boolean;
      description
        "Indicates if the registering ETR wants to be informed about
         matching registrations with Map-Notifies";
    }
    list ms-registration-rloc {
      key "afi address";
      description
        "List of locators";
      uses lisp-ios-xe-oper:lisp-ms-registration-rloc-type;
      uses lisp-ios-xe-oper:lisp-address-type;
    }
  }

  grouping lisp-ms-registration-source-type {
    description
      "Source address and port for a registration in MS database";
    leaf source-address {
      type inet:ip-address;
      description
        "RLOC address of the registration source";
    }
    leaf source-port {
      type uint16;
      description
        "Port of the registration source";
    }
  }

  grouping lisp-ms-mapping-type {
    description
      "EID prefix registered on the Mapping-Server";
    container last-registration-source {
      description
        "Source address of the last valid registration received
         for this EID prefix";
      uses lisp-ios-xe-oper:lisp-address-type;
    }
    leaf last-registration-source-port {
      type uint16;
      description
        "Source port of the last valid registration received for
         this EID prefix";
    }
    leaf creation-time {
      type yang:date-and-time;
      description
        "Time when a valid registration was first received for
         this EID prefix";
    }
    leaf last-registration-time {
      type yang:date-and-time;
      description
        "Time when most recent valid registration was received
         for this EID prefix";
    }
    leaf site-name {
      type string;
      description
        "Name of site matching this registration";
    }
    leaf site-description {
      type string;
      description
        "Description given for the site matching this registration";
    }
    leaf is-registered {
      type boolean;
      description
        "Indicates the registration status of the given EID-Prefix.
         If this object is true, then it means the EID-Prefix
         is registered";
    }
    leaf authentication-error {
      type uint64;
      description
        "Count of registrations received for the EID prefix with
         authentication error";
    }
    leaf rloc-mismatch-error {
      type uint64;
      description
        "Count of received registrations for the prefix that had
         at least one RLOC that was not in the allowed list of
         RLOCs";
    }
    list etr-registrations {
      key "source-address source-port";
      description
        "List of registrations for this EID prefix received
         from different ETRs";
      uses lisp-ios-xe-oper:lisp-ms-registration-type;
      uses lisp-ios-xe-oper:lisp-ms-registration-source-type;
    }
  }

  grouping lisp-etr-map-server-type {
    description
      "Properties of a Map-Server where the ETR should send its
       registrations";
    leaf state {
      type lisp-ios-xe-oper:lisp-rloc-state-type;
      description
        "Up/down state of the locator";
    }
    leaf avg-rtt-5sec {
      type uint32;
      description
        "Average RTT of map-register in milliseconds during last 5 sec";
    }
    leaf avg-rtt-1min {
      type uint32;
      description
        "Average RTT of map-register in milliseconds during last 1 min";
    }
    leaf avg-rtt-5min {
      type uint32;
      description
        "Average RTT of map-register in milliseconds during last 5 min";
    }
  }

  grouping lisp-itr-map-resolver-type {
    description
      "Properties of a Map-Resolver where the [P]ITR should send
       Map-Requests";
    leaf state {
      type lisp-ios-xe-oper:lisp-rloc-state-type;
      description
        "Up/down state of the locator";
    }
    leaf avg-rtt-5sec {
      type uint32;
      description
        "Average RTT of map-request in milliseconds during last 5 sec";
    }
    leaf avg-rtt-1min {
      type uint32;
      description
        "Average RTT of map-request in milliseconds during last 1 min";
    }
    leaf avg-rtt-5min {
      type uint32;
      description
        "Average RTT of map-request in milliseconds during last 5 min";
    }
  }

  grouping lisp-proxy-etr-type {
    description
      "Properties of a Proxy ETR where this device will send traffic
       in case of the negative mapping";
    container params {
      description
        "Properties of the locator";
      uses lisp-ios-xe-oper:lisp-rloc-parameters-type;
    }
    leaf state {
      type lisp-ios-xe-oper:lisp-rloc-state-type;
      description
        "Up/down state of the locator";
    }
    leaf iid {
      type uint32 {
        range "0 .. 16777215";
      }
      description
        "Instance-ID to use when sending packets to PETR";
    }
    leaf is-iid-present {
      type boolean;
      description
        "Whether specific IID should be used sending packets to PETR";
    }
    leaf is-proxy-etr-learned-from-msmr {
      type boolean;
      description
        "Indicates whether the proxy-etr is configured or learned from MSMR";
    }
  }

  grouping lisp-session-peer-type {
    description
      "Source address and port for a LISP session peer";
    leaf peer-address {
      type inet:ip-address;
      description
        "Address of the peer";
    }
    leaf peer-port {
      type uint16;
      description
        "Remote port used by the peer";
    }
  }

  grouping lisp-pubsub-publisher-type {
    description
      "Attributes of a publisher from which this device is sourcing
       registrations";
    leaf is-established {
      type boolean;
      description
        "If the connection to the publisher is established";
    }
    leaf publication-count {
      type uint64;
      description
        "Count of publications received from this
         publisher";
    }
  }

  grouping lisp-pubsub-subscriber-type {
    description
      "Attributes of a subscriber to publish-subscribe
       notifications";
    leaf is-established {
      type boolean;
      description
        "If the connection to the subscriber is
         established";
    }
  }

  grouping lisp-pubsub-mapping-rloc-type {
    description
      "Attributes of a locator received in a mapping from a
       publisher";
    leaf state {
      type lisp-ios-xe-oper:lisp-rloc-state-type;
      description
        "Up/down state of the locator";
    }
    container params {
      description
        "Properties of the locator";
      uses lisp-ios-xe-oper:lisp-rloc-parameters-type;
    }
  }

  grouping lisp-pubsub-mapping-type {
    description
      "Attributes of a mapping received from a publisher";
    leaf last-publication-time {
      type yang:date-and-time;
      description
        "Last time a mapping record was received from this
         publisher";
    }
    leaf site-id {
      type uint64;
      description
        "Site-ID common to all devices attached to the site of the
         registering device";
    }
    leaf-list xtr-id {
      type uint8;
      max-elements "16";
      ordered-by user;
      description
        "xTR-ID of the registering device";
    }
    list lisp-publication-rloc {
      key "afi address";
      description
        "Locator associated with this mapping";
      uses lisp-ios-xe-oper:lisp-pubsub-mapping-rloc-type;
      uses lisp-ios-xe-oper:lisp-address-type;
    }
  }

  grouping lisp-pubsub-mapping-publisher-type {
    description
      "The address and port of the publisher of this
       mapping";
    leaf publisher-address {
      type inet:ip-address;
      description
        "Address of the publisher";
    }
    leaf publisher-port {
      type uint16;
      description
        "Port of the publisher";
    }
  }

  grouping lisp-pubsub-publication-type {
    description
      "Attributes of a received publication";
    leaf first-publication-time {
      type yang:date-and-time;
      description
        "First time a mapping record was received for this
         EID";
    }
    leaf last-publication-time {
      type yang:date-and-time;
      description
        "Last time a mapping record was received for this
         EID";
    }
    list lisp-publication-mapping {
      key "publisher-address publisher-port";
      description
        "A mapping received for this EID";
      uses lisp-ios-xe-oper:lisp-pubsub-mapping-type;
      uses lisp-ios-xe-oper:lisp-pubsub-mapping-publisher-type;
    }
  }

  grouping lisp-extranet-eid-type {
    description
      "Properties of extranet EID prefix";
    leaf is-configured {
      type boolean;
      description
        "Is the EID configured or learned from registrations";
    }
  }

  grouping lisp-map-cache-rloc-type {
    description
      "Description of a RLOC (locator address and its properties)";
    leaf state {
      type lisp-ios-xe-oper:lisp-rloc-state-type;
      description
        "Up/down state of the locator";
    }
    leaf creation-time {
      type yang:date-and-time;
      description
        "Time when this RLOC entry was created";
    }
    leaf last-state-change-time {
      type yang:date-and-time;
      description
        "Time when up/down state of the RLOC for this map-cache
         entry last changed";
    }
    leaf rloc-probe-rtt {
      type uint32;
      units "milliseconds";
      description
        "Round-trip time of RLOC probe and corresponding reply";
    }
    container params {
      description
        "Properties of the locator";
      uses lisp-ios-xe-oper:lisp-rloc-parameters-type;
    }
    leaf encap-iid {
      type uint32 {
        range "0 .. 16777215";
      }
      description
        "Instance-ID to use when sending map requests";
    }
    leaf is-encap-iid-present {
      type boolean;
      description
        "Whether encapsulation Instance-ID should be used when sending map requests";
    }
  }

  grouping lisp-map-cache-mapping-type {
    description
      "[P]ITR's map-cache forwarding entry";
    leaf up-time {
      type yang:date-and-time;
      description
        "Time that this entry was created";
    }
    leaf last-modified-time {
      type yang:date-and-time;
      description
        "Last time that the RLOC information or the entry state
         were modified";
    }
    leaf last-update-time {
      type yang:date-and-time;
      description
        "Last time a mapping record for this entry was received,
         not valid if the entry is static";
    }
    leaf ttl {
      type uint32;
      units "milliseconds";
      description
        "Mapping validity period";
    }
    leaf is-authoritative {
      type boolean;
      description
        "Indication if the mapping came from an authoritative source";
    }
    leaf is-static {
      type boolean;
      description
        "Indication if the mapping is static (i.e. configured)";
    }
    leaf is-negative {
      type boolean;
      description
        "Indication if the mapping is negative (i.e. provides no
         locators for LISP encapsulation)";
    }
    leaf nmr-action {
      type lisp-ios-xe-oper:lisp-map-reply-action-type;
      description
        "Forwarding action in case of negative entry";
    }
    leaf expiry-time {
      type yang:date-and-time;
      description
        "Time when this entry will expire if not refreshed;
         for entries which do not have an expiration time this
         time will be less than the entry creation time";
    }
    leaf encapsulated-packets {
      type uint64;
      description
        "Number of packets of the transit traffic which were
         encapsulated because they matched this map-cache entry";
    }
    leaf encapsulated-octets {
      type uint64;
      description
        "Number of bytes of the transit traffic which were
         encapsulated because they matched this map-cache entry";
    }
    leaf is-active {
      type boolean;
      description
        "Indication if the mapping is active, that is there was
         transit traffic matching this map-cache entry seen in
         approximately the last minute";
    }
    list map-cache-rloc {
      key "afi address";
      description
        "List of locators for positive mapping";
      uses lisp-ios-xe-oper:lisp-map-cache-rloc-type;
      uses lisp-ios-xe-oper:lisp-address-type;
    }
    leaf info-best-source {
      type lisp-ios-xe-oper:lisp-map-cache-information-best-source-type;
      description
        "Source of best map cache information";
    }
    leaf info-best-trans-source {
      type lisp-ios-xe-oper:lisp-map-cache-information-best-source-trans-type;
      description
        "Source of best map cache transient information";
    }
    leaf is-encapsulating-to-petr {
      type boolean;
      description
        "Encapsulating packets to Proxy ETR";
    }
  }

  grouping lisp-role-type {
    description
      "LISP role of the device";
    leaf is-ms {
      type boolean;
      description
        "LISP Map-Server";
    }
    leaf is-mr {
      type boolean;
      description
        "LISP Map-Resolver";
    }
    leaf is-itr {
      type boolean;
      description
        "LISP ITR";
    }
    leaf is-etr {
      type boolean;
      description
        "LISP ETR";
    }
    leaf is-pitr {
      type boolean;
      description
        "LISP Proxy-ITR";
    }
    leaf is-petr {
      type boolean;
      description
        "LISP Proxy-ETR";
    }
  }

  grouping lisp-instance-af-type {
    description
      "Operational data specific to behavior of an Address-Family
       service within a single LISP instance";
    leaf iaftype {
      type lisp-ios-xe-oper:lisp-iaftype-type;
      description
        "Instance-specific service type";
    }
    container role {
      description
        "LISP device role for this service";
      uses lisp-ios-xe-oper:lisp-role-type;
    }
    list map-cache {
      key "afi prefix";
      description
        "Map-cache for this service instance";
      uses lisp-ios-xe-oper:lisp-map-cache-mapping-type;
      uses lisp-ios-xe-oper:lisp-prefix-type;
    }
    leaf l2-domain-id {
      type uint32;
      description
        "ID of Vlan or Bridge-Domain that is mapped to the given
         L2 LISP Instance ID";
    }
    leaf map-cache-size {
      type uint32;
      description
        "Current size of EID-to-RLOC map-cache on this device";
    }
    leaf map-cache-limit {
      type uint32;
      description
        "Maximum permissible number of entries in EID-to-RLOC
         map-cache on this device";
    }
    leaf etr-map-cache-ttl {
      type uint32;
      units "minutes";
      description
        "TTL of the EID-to-RLOC map record provided by the local
         device in mapping records";
    }
    leaf registration-more-specific {
      type uint32;
      description
        "Number of EID prefix registrations that were accepted as
         a result of the 'accept-more-specific' configuration";
    }
    leaf registration-more-specific-warning-threshold {
      type uint32;
      description
        "The warning threshold for the 'accept-more-specific'
         registration count on the Map-Server";
    }
    leaf registration-more-specific-limit {
      type uint32;
      description
        "Maximum number of registrations on the Map-Server which
         could be accepted due to configuration of
         'accept-more-specific'";
    }
    leaf map-cache-threshold {
      type uint32;
      description
        "The map-cache utilization warning threshold on the xTR";
    }
    leaf map-requests-in {
      type uint64;
      description
        "Total number of map requests received by this device for
         any EID-Prefix of the given address family and Instance ID";
    }
    leaf map-requests-out {
      type uint64;
      description
        "Total number of map requests sent by this device for any
         EID-Prefix of the given address family and Instance ID";
    }
    leaf encapsulated-map-requests-in {
      type uint64;
      description
        "Total number of encapsulated Map-Requests received by this
         device for any EID-Prefix of the given address family
         and Instance ID";
    }
    leaf encapsulated-map-requests-out {
      type uint64;
      description
        "Total number of encapsulated Map-Requests sent by this
         device for any EID-Prefix of the given address family
         and Instance ID";
    }
    leaf rloc-probe-map-requests-in {
      type uint64;
      description
        "Total number of RLOC probe Map-Requests received by
         this device for any EID-Prefix of the given address
         family and Instance ID";
    }
    leaf rloc-probe-map-requests-out {
      type uint64;
      description
        "Total number of RLOC probe Map-Requests sent by this
         device for any EID-Prefix of the given address family
         and Instance ID";
    }
    leaf map-requests-expired-on-queue {
      type uint64;
      description
        "Total number of Map-Requests for any EID-Prefix of the
         given address family and Instance ID which were not sent
         out by this device because they timed out while on the
         transmit queue";
    }
    leaf map-requests-no-reply {
      type uint64;
      description
        "Total number of Map-Requests attempted by this device
         for any EID-Prefix of the given address family and
         Instance ID without receiving a Map-Reply";
    }
    leaf map-requests-from-disallowed-locators {
      type uint64;
      description
        "Total number of Map-Request messages for any EID-Prefix
         of the given address family and Instance ID dropped by
         this device due to configuration
         'map-resolver allowed-locator'";
    }
    leaf smr-map-requests-in {
      type uint64;
      description
        "Total number of SMR Map-Requests received by this device
         for any EID-Prefix of the given address family and
         Instance ID";
    }
    leaf smr-map-requests-out {
      type uint64;
      description
        "Total number of SMR Map-Requests sent by this device for
         any EID-Prefix of the given address family and Instance ID";
    }
    leaf ddt-itr-map-requests-dropped {
      type uint64;
      description
        "Total number of ITR's Map-Request messages for any
         EID-Prefix of the given address family and Instance ID
         dropped by the DDT Map-Resolver";
    }
    leaf ddt-itr-map-requests-nonce-collision {
      type uint64;
      description
        "Total number of ITR's Map-Request messages for any
         EID-Prefix of the given address family and Instance ID
         dropped by the DDT Map-Resolver due to nonce conflict";
    }
    leaf ddt-itr-map-requests-bad-xtr-nonce {
      type uint64;
      description
        "Total number of ITR's Map-Request messages for any
         EID-Prefix of the given address family and Instance ID
         dropped by the DDT Map-Resolver due bad nonce";
    }
    leaf mr-map-requests-forwarded {
      type uint64;
      description
        "Total number of Map-Requests for any EID-Prefix of the
         given address family and Instance ID forwarded by this
         device to Map-Resolver on ALT";
    }
    leaf ms-map-requests-forwarded {
      type uint64;
      description
        "Total number of Map-Requests for any EID-Prefix of the
         given address family and Instance ID forwarded by this
         device to ETR";
    }
    leaf to-alt-map-requests-out {
      type uint64;
      description
        "Total number of Map-Requests for any EID-Prefix of the
         given address family and Instance ID forwarded by this
         device to ALT";
    }
    leaf map-reply-records-in {
      type uint64;
      description
        "Total number of Map-Reply records received by this device
         for any EID-Prefix of the given address family and
         Instance ID";
    }
    leaf map-reply-records-out {
      type uint64;
      description
        "Total number of Map-Reply records sent by this device for
         any EID-Prefix of the given address family and Instance ID";
    }
    leaf authoritative-records-in {
      type uint64;
      description
        "Total number of authoritative Map-Reply records received
         by this device for any EID-Prefix of the given address
         family and Instance ID";
    }
    leaf authoritative-records-out {
      type uint64;
      description
        "Total number of authoritative Map-Reply records sent by
         this device for any EID-Prefix of the given address family
         and Instance ID";
    }
    leaf non-authoritative-records-in {
      type uint64;
      description
        "Total number of non authoritative Map-Reply records
         received by this device for any EID-Prefix of the given
         address family and Instance ID";
    }
    leaf non-authoritative-records-out {
      type uint64;
      description
        "Total number of non authoritative Map-Reply records sent
         by this device for any EID-Prefix of the given address
         family and Instance ID";
    }
    leaf negative-records-in {
      type uint64;
      description
        "Total number of negative Map-Reply records received by
         this device for any EID-Prefix of the given address
         family and Instance ID";
    }
    leaf negative-records-out {
      type uint64;
      description
        "Total number of negative Map-Reply records sent by this
         device for any EID-Prefix of the given address family and
         Instance ID";
    }
    leaf rloc-probe-records-in {
      type uint64;
      description
        "Total number of RLOC probe Map-Replies for any EID-Prefix
         of the given address family and Instance ID received by
         this device";
    }
    leaf rloc-probe-records-out {
      type uint64;
      description
        "Total number of RLOC probe Map-Replies for any EID-Prefix
         of the given address family and Instance ID sent by this
         device";
    }
    leaf ms-proxy-reply-records-out {
      type uint64;
      description
        "Total number of MS proxy Map-Replies for any EID-Prefix
         of the given address family and Instance ID sent by this
         device";
    }
    leaf wlc-subscribe-in {
      type uint64;
      description
        "Total number of WLC Subscribe messages received by this
         device for the given address family and Instance ID";
    }
    leaf wlc-subscribe-out {
      type uint64;
      description
        "Total number of WLC Subscribe messages sent by this
         device for the given address family and Instance ID";
    }
    leaf wlc-subscribe-in-failure {
      type uint64;
      description
        "Total number of received WLC Subscribe messages for the
         given address family and Instance ID with incorrect
         formatting";
    }
    leaf wlc-subscribe-out-failure {
      type uint64;
      description
        "Total number of WLC Subscribe messages for the given
         address family and Instance ID which were not sent due to
         internal errors";
    }
    leaf wlc-unsubscribe-in {
      type uint64;
      description
        "Total number of WLC Unsubscribe messages received by this
         device for the given address family and Instance ID";
    }
    leaf wlc-unsubscribe-out {
      type uint64;
      description
        "Total number of WLC Unsubscribe messages sent by this
         device for the given address family and Instance ID";
    }
    leaf wlc-unsubscribe-in-failure {
      type uint64;
      description
        "Total number of received WLC Unsubscribe messages for the
         given address family and Instance ID with incorrect
         formatting";
    }
    leaf wlc-unsubscribe-out-failure {
      type uint64;
      description
        "Total number of WLC Unsubscribe messages for the given
         address family and Instance ID which were not sent due to
         internal errors";
    }
    leaf map-register-records-in {
      type uint64;
      description
        "Total number of Map-Register records for any EID-Prefix
         of the given address family and Instance ID received by
         this device";
    }
    leaf map-register-records-out {
      type uint64;
      description
        "Total number of Map-Registers records sent by this device
         for any EID-Prefix of the given address family and
         Instance ID";
    }
    leaf map-registers-ms-disabled {
      type uint64;
      description
        "Total number of Map-Register messages dropped due to
         Map-Server functionality not enabled for the given
         address family and Instance ID";
    }
    leaf map-registers-auth-failed {
      type uint64;
      description
        "Total number of Map-Register messages for any EID-Prefix
         of the given address family and Instance ID dropped due
         to authentication failure";
    }
    leaf map-registers-from-disallowed-locators {
      type uint64;
      description
        "Total number of Map-Register messages received from
         disallowed locators";
    }
    leaf wlc-map-register-records-in {
      type uint64;
      description
        "Total number of WLC Map-Register messages received by
         this device for any EID-Prefix of the given address
         family and Instance ID";
    }
    leaf wlc-map-register-records-out {
      type uint64;
      description
        "Total number of WLC Map-Register messages sent by this
         device for any EID-Prefix of the given address family
         and Instance ID";
    }
    leaf wlc-map-register-records-in-ap {
      type uint64;
      description
        "Total number of WLC Map-Register messages received by
         this device for AP join in the given address family
         and Instance ID";
    }
    leaf wlc-map-register-records-out-ap {
      type uint64;
      description
        "Total number of WLC Map-Register messages sent by
         this device for AP join in the given address family
         and Instance ID";
    }
    leaf wlc-map-register-records-in-client {
      type uint64;
      description
        "Total number of WLC Map-Register messages received by
         this device for wireless client join in the given
         address family and Instance ID";
    }
    leaf wlc-map-register-records-out-client {
      type uint64;
      description
        "Total number of WLC Map-Register messages sent by
         this device for wireless client join in the given
         address family and Instance ID";
    }
    leaf wlc-map-register-records-in-failure {
      type uint64;
      description
        "Total number of WLC Map-Register messages received in the
         given address family and Instance ID and discarded due to
         parsing error";
    }
    leaf wlc-map-register-records-out-failure {
      type uint64;
      description
        "Total number of WLC Map-Register messages for any
         EID-Prefix of the given address family and Instance ID
         which were not sent because of internal error";
    }
    leaf map-notify-records-in {
      type uint64;
      description
        "Total number of Map-Notify records for any EID-Prefix of
         the given address family and Instance ID received by
         this device";
    }
    leaf map-notify-records-out {
      type uint64;
      description
        "Total number of Map-Notify records for any EID-Prefix of
         the given address family and Instance ID sent by this
         device";
    }
    leaf map-notify-auth-failed {
      type uint64;
      description
        "Total number of Map-Notify messages for any EID-Prefix of
         the given address family and Instance ID dropped due to
         authentication failure";
    }
    leaf wlc-map-notify-records-in {
      type uint64;
      description
        "Total number of WLC Map-Notify records for any EID-Prefix
         of the given address family and Instance ID received by
         this device";
    }
    leaf wlc-map-notify-records-out {
      type uint64;
      description
        "Total number of WLC Map-Notify records for any EID-Prefix
         of the given address family and Instance ID sent by
         this device";
    }
    leaf wlc-map-notify-records-in-ap {
      type uint64;
      description
        "Total number of WLC Map-Notify records for any EID-Prefix
         of the given address family and Instance ID received by
         this device for AP join";
    }
    leaf wlc-map-notify-records-out-ap {
      type uint64;
      description
        "Total number of WLC Map-Notify records for any EID-Prefix
         of the given address family and Instance ID sent by
         this device for AP join";
    }
    leaf wlc-map-notify-records-in-client {
      type uint64;
      description
        "Total number of WLC Map-Notify records for any EID-Prefix
         of the given address family and Instance ID received by
         this device for wireless client join";
    }
    leaf wlc-map-notify-records-out-client {
      type uint64;
      description
        "Total number of WLC Map-Notify records for any EID-Prefix
         of the given address family and Instance ID sent by
         this device for wireless client join";
    }
    leaf wlc-map-notify-records-in-failure {
      type uint64;
      description
        "Total number of WLC Map-Notify messages received in the
         given address family and Instance ID and discarded due to
         parsing error";
    }
    leaf wlc-map-notify-records-out-failure {
      type uint64;
      description
        "Total number of WLC Map-Notify messages for any
         EID-Prefix of the given address family and Instance ID
         which were not sent because of internal error";
    }
    leaf mapping-record-ttl-alerts {
      type uint64;
      description
        "Total number of mapping records received by this device
         for any EID-Prefix of the given address family and
         Instance ID with TTL exceeding 7 days";
    }
    leaf remote-eid-entries-created {
      type uint64;
      description
        "Total number of remote EID map-cache entries created by
         this device for any EID-Prefix of the given address family
         and Instance ID";
    }
    leaf remote-eid-entries-deleted {
      type uint64;
      description
        "Total number of remote EID map-cache entries deleted by
         this device for any EID-Prefix of the given address family
         and Instance ID";
    }
    leaf remote-eid-nsf-replay-entries-created {
      type uint64;
      description
        "Total number of remote EID map-cache entries for any
         EID-Prefix of the given address family and Instance ID
         recreated by this device after NSF switchover";
    }
    leaf forwarding-data-signals-processed {
      type uint64;
      description
        "Total number of forwarding plane data signals processed
         by this device for any EID-Prefix of the given address
         family and Instance ID";
    }
    leaf forwarding-data-signals-dropped {
      type uint64;
      description
        "Total number of forwarding plane data signals for any
         EID-Prefix of the given address family and Instance ID
         dropped by this device";
    }
    leaf forwarding-reachability-reports-processed {
      type uint64;
      description
        "Total number of forwarding plane reachability reports for
         any EID-Prefix of the given address family and Instance ID
         processed by this device";
    }
    leaf forwarding-reachability-reports-dropped {
      type uint64;
      description
        "Total number of forwarding plane reachability reports for
         any EID-Prefix of the given address family and Instance ID
         dropped by this device";
    }
    leaf is-etr-accept-mapping {
      type boolean;
      description
        "Indicates whether the ETR accepts piggybacked mapping
         records received in a Map-Request";
    }
    leaf is-etr-accept-mapping-verify {
      type boolean;
      description
        "Indicates if ETR will try to verify accepted piggybacked
         mapping records received in a Map-Request";
    }
    list local-dbase {
      key "afi prefix";
      description
        "ETR's database of local EID prefixes";
      uses lisp-ios-xe-oper:lisp-local-dbase-mapping-type;
      uses lisp-ios-xe-oper:lisp-prefix-type;
    }
    list ms-registrations {
      key "afi prefix";
      description
        "Map-Server database of registered EID Prefixes";
      uses lisp-ios-xe-oper:lisp-ms-mapping-type;
      uses lisp-ios-xe-oper:lisp-prefix-type;
    }
    list map-servers {
      key "afi address";
      description
        "List of Map-Servers to which the ETR should register";
      uses lisp-ios-xe-oper:lisp-etr-map-server-type;
      uses lisp-ios-xe-oper:lisp-address-type;
    }
    list map-resolvers {
      key "afi address";
      description
        "List of Map-Resolvers where [P]ITR should send its
         Map-Requests";
      uses lisp-ios-xe-oper:lisp-itr-map-resolver-type;
      uses lisp-ios-xe-oper:lisp-address-type;
    }
    list proxy-etrs {
      key "afi address";
      description
        "List of all Proxy ETRs that this device is configured
         to use";
      uses lisp-ios-xe-oper:lisp-proxy-etr-type;
      uses lisp-ios-xe-oper:lisp-address-type;
    }
    list extranet-eids {
      key "afi prefix";
      description
        "Extranet EIDs for this service instance";
      uses lisp-ios-xe-oper:lisp-extranet-eid-type;
      uses lisp-ios-xe-oper:lisp-prefix-type;
    }
    leaf map-resolver-receive-count-last-5sec {
      type uint64;
      description
        "Total number of map requests received by map resolver during
         last 5 seconds";
    }
    leaf map-resolver-receive-count-last-1min {
      type uint64;
      description
        "Total number of map requests received by map resolver during
         last 1 minute";
    }
    leaf map-resolver-receive-count-last-5min {
      type uint64;
      description
        "Total number of map requests received by map resolver during
         last 5 minutes";
    }
    leaf map-server-receive-count-last-5sec {
      type uint64;
      description
        "Total number of Map-Register messages received by map server during
         last 5 seconds";
    }
    leaf map-server-receive-count-last-1min {
      type uint64;
      description
        "Total number of Map-Register messages received by map server during
         last 1 minute";
    }
    leaf map-server-receive-count-last-5min {
      type uint64;
      description
        "Total number of Map-Register messages received by map server during
         last 5 minutes";
    }
    leaf is-mr-use-petr-enabled {
      type boolean;
      description
        "LISP MR use Proxy-ETR";
    }
    leaf mr-use-petr-locator-set-name {
      type string;
      description
        "LISP MR-use-Proxy-ETR locator set name";
    }
    leaf remote-eid-entries-rejected {
      type uint64;
      description
        "Total number of remote EID map-cache entries rejected
         by this device due to the limit being exceeded for
         any EID-Prefix of the given address family and Instance ID";
    }
    leaf is-publication-subscription-enabled {
      type boolean;
      description
        "Indicates that the capability to send and receive registrations
         using the publish/subscribe mechanism is enabled for this instance
         and address family.";
    }
    leaf pubsub-sub-requests-in {
      type uint64;
      description
        "Total number of Subscription Request messages received by this
         device for this Instance ID and address family";
    }
    leaf pubsub-sub-requests-out {
      type uint64;
      description
        "Total number of Subscription Request messages sent by this
         device for this Instance ID and address family";
    }
    leaf pubsub-sub-requests-in-failure {
      type uint64;
      description
        "Total number of Subscription Request messages for this Instance ID
         and address family discarded due to parsing error";
    }
    leaf pubsub-sub-requests-out-failure {
      type uint64;
      description
        "Total number of Subscription Request messages for this Instance ID
         and address family which were not sent due to internal errors";
    }
    leaf pubsub-sub-status-in {
      type uint64;
      description
        "Total number of Subscription Status messages received by this
         device for this Instance ID and address family";
    }
    leaf pubsub-sub-status-out {
      type uint64;
      description
        "Total number of Subscription Status messages sent by this
         device for this Instance ID and address family";
    }
    leaf pubsub-sub-status-in-failure {
      type uint64;
      description
        "Total number of Subscription Status messages for this Instance ID
         and address family discarded due to parsing error";
    }
    leaf pubsub-sub-status-out-failure {
      type uint64;
      description
        "Total number of Subscription Status messages for this Instance ID
         and address family which were not sent due to internal errors";
    }
    leaf pubsub-sub-status-end-pub-in {
      type uint64;
      description
        "Total number of End-of-Publication Subscription Status messages
         received by this device for this Instance ID and address family";
    }
    leaf pubsub-sub-status-end-pub-out {
      type uint64;
      description
        "Total number of End-of-Publication Subscription Status messages
         sent by this device for this Instance ID and address family";
    }
    leaf pubsub-sub-status-removal-in {
      type uint64;
      description
        "Total number of Subscription-Removal Subscription Status messages
         received by this device for this Instance ID and address family";
    }
    leaf pubsub-sub-status-removal-out {
      type uint64;
      description
        "Total number of Subscription-Removal Subscription Status messages
         sent by this device for this Instance ID and address family";
    }
    leaf pubsub-sub-status-rejection-in {
      type uint64;
      description
        "Total number of Subscription-Rejection Subscription Status messages
         received by this device for this Instance ID and address family";
    }
    leaf pubsub-sub-status-rejection-out {
      type uint64;
      description
        "Total number of Subscription-Rejection Subscription Status messages
         sent by this device for this Instance ID and address family";
    }
    leaf pubsub-solicit-subs-in {
      type uint64;
      description
        "Total number of Solicit Subscription messages received by this
         device for this Instance ID and address family";
    }
    leaf pubsub-solicit-subs-out {
      type uint64;
      description
        "Total number of Solicit Subscription messages sent by this
         device for this Instance ID and address family";
    }
    leaf pubsub-solicit-subs-in-failure {
      type uint64;
      description
        "Total number of Solicit Subscription messages for this Instance ID
         and address family discarded due to parsing error";
    }
    leaf pubsub-solicit-subs-out-failure {
      type uint64;
      description
        "Total number of Solicit Subscription messages for this Instance ID
         and address family which were not sent due to internal errors";
    }
    leaf pubsub-pubs-in {
      type uint64;
      description
        "Total number of Publication messages received by this device for
         this Instance ID and address family";
    }
    leaf pubsub-pubs-out {
      type uint64;
      description
        "Total number of Publication messages sent by this device for this
         Instance ID and address family";
    }
    leaf pubsub-pubs-in-failure {
      type uint64;
      description
        "Total number of Publication messages for this Instance ID and
         address family discarded due to parsing error";
    }
    leaf pubsub-pubs-out-failure {
      type uint64;
      description
        "Total number of Publication messages for this Instance ID and
         address family which were not sent due to internal errors";
    }
    list lisp-publisher {
      key "peer-address peer-port";
      description
        "Publishers transmitting publication/subscription registrations for this
         service instance";
      uses lisp-ios-xe-oper:lisp-pubsub-publisher-type;
      uses lisp-ios-xe-oper:lisp-session-peer-type;
    }
    list lisp-subscriber {
      key "peer-address peer-port";
      description
        "Subscribers interested in publication/subscription registrations in this
         service instance";
      uses lisp-ios-xe-oper:lisp-pubsub-subscriber-type;
      uses lisp-ios-xe-oper:lisp-session-peer-type;
    }
    leaf received-publication-count {
      type uint64;
      description
        "Count of the active publications received in this
         service instance";
    }
    list lisp-received-publication {
      key "afi prefix";
      description
        "List of publications received from one or more publishers.
         Publications can be imported into the map-cache or export to the
         RIB. When imported to the map-cache, they remain valid as long as
         the received publication persists.";
      uses lisp-ios-xe-oper:lisp-pubsub-publication-type;
      uses lisp-ios-xe-oper:lisp-prefix-type;
    }
    leaf is-signal-suppression-enabled {
      type boolean;
      description
        "Is signal suppression enabled";
    }
    leaf signal-suppression-enabled-count {
      type uint64;
      description
        "Signal suppression enabled count";
    }
    leaf last-signal-suppression-time {
      type yang:date-and-time;
      description
        "Last time signal suppression state changed";
    }
    leaf ddt-requests-failed {
      type uint64;
      description
        "Total number of DDT requests for the given address family and
         Instance ID which failed";
    }
    leaf last-stats-clear-time {
      type yang:date-and-time;
      description
        "Timestamp when statistics for this instance-id and address-family
         were last cleared";
    }
  }

  grouping lisp-extranet-member-inst-type {
    description
      "The type of an instance(provider/subscriber) within an extranet";
    leaf iid {
      type uint32 {
        range "0 .. 16777215";
      }
      description
        "LISP Instance ID";
    }
    leaf is-provider {
      type boolean;
      description
        "This indicates whether this instance is a provider or subscriber";
    }
  }

  grouping lisp-extranet-instance-type {
    description
      "The member instances of a named extranet";
    leaf extranet-name {
      type string;
      description
        "Name of the extranet";
    }
    leaf extranet-inst-count {
      type uint32;
      description
        "Number of instances in this extranet";
    }
    list extranet-member-instances {
      key "iid";
      description
        "List of all the instances under this extranet";
      uses lisp-ios-xe-oper:lisp-extranet-member-inst-type;
    }
  }

  grouping lisp-ms-eid-membership-rloc-type {
    description
      "Description of RLOC in MS registration EID membership list";
    leaf rloc {
      type inet:ip-address;
      description
        "RLOC which is the allowed member";
    }
    leaf member-since {
      type yang:date-and-time;
      description
        "Time when this RLOC was added to the list of allowed
         locators";
    }
    leaf is-gleaned {
      type boolean;
      description
        "Indicates if MS gleaned this RLOC from received EID
         prefix registration";
    }
    leaf is-configured {
      type boolean;
      description
        "Indicates if this RLOC membership was provided via
         configuration";
    }
  }

  grouping lisp-etr-eid-membership-rloc-type {
    description
      "Description of RLOC in ETR EID membership list";
    leaf rloc {
      type inet:ip-address;
      description
        "RLOC which is the allowed member";
    }
    leaf member-since {
      type yang:date-and-time;
      description
        "Time when this RLOC was added to the list of allowed
         locators";
    }
    leaf is-learned-from-ms {
      type boolean;
      description
        "Indicates if ETR learned about this RLOC membership via
         message received from a Map-Server";
    }
    leaf is-configured {
      type boolean;
      description
        "Indicates if this RLOC membership was provided via
         configuration";
    }
  }

  grouping lisp-instance-type {
    description
      "Operational data of a single LISP Instance";
    leaf iid {
      type uint32 {
        range "0 .. 16777215";
      }
      description
        "LISP Instance ID";
    }
    list af {
      key "iaftype";
      description
        "List of Address-Families enabled in this LISP instance";
      uses lisp-ios-xe-oper:lisp-instance-af-type;
    }
    leaf vrf-name {
      type string;
      description
        "Name of VRF that is mapped to the given LISP Instance ID";
    }
    leaf is-rloc-probing {
      type boolean;
      description
        "Status of RLOC Probing";
    }
    list ms-eid-membership {
      key "rloc";
      description
        "MS registration EID membership list (list of locators
         known to the MS as allowed to send traffic in the
         instance)";
      uses lisp-ios-xe-oper:lisp-ms-eid-membership-rloc-type;
    }
    list etr-eid-membership {
      key "rloc";
      description
        "ETR EID membership list (list of locators known to the ETR
         as allowed to send traffic in the instance)";
      uses lisp-ios-xe-oper:lisp-etr-eid-membership-rloc-type;
    }
    list extranets {
      key "extranet-name";
      description
        "List of extranets configured under this instance";
      uses lisp-ios-xe-oper:lisp-extranet-instance-type;
    }
  }

  grouping lisp-session-source-destination-type {
    description
      "Addresses and ports of the session's endpoints";
    leaf local-address {
      type inet:ip-address;
      description
        "Address of the local socket";
    }
    leaf peer-address {
      type inet:ip-address;
      description
        "Address of the peer";
    }
    leaf local-port {
      type uint16;
      description
        "Port of the local socket";
    }
    leaf peer-port {
      type uint16;
      description
        "Port used by the peer";
    }
  }

  grouping lisp-session-type {
    description
      "Parameters of a Reliable Registration session";
    leaf state {
      type lisp-ios-xe-oper:lisp-session-state-type;
      description
        "Up/down state of the session";
    }
    leaf last-state-change-time {
      type yang:date-and-time;
      description
        "Timestamp when the session's state last changed";
    }
    leaf is-role-active {
      type boolean;
      description
        "Is session opening role Active or Passive; TRUE means
         session role is Active";
    }
    leaf is-routable {
      type boolean;
      description
        "Is route to peer's address known";
    }
    leaf messages-in {
      type uint64;
      description
        "Number of messages received over this session";
    }
    leaf messages-out {
      type uint64;
      description
        "Number of messages sent over this session";
    }
    leaf bytes-in {
      type uint64;
      description
        "Number of bytes received over this session";
    }
    leaf bytes-out {
      type uint64;
      description
        "Number of bytes sent over this session";
    }
    leaf capability-bits-in {
      type uint32;
      description
        "Raw capability bits advertised by the peer";
    }
    leaf known-capabilities-in {
      type lisp-ios-xe-oper:lisp-capabilities-type;
      description
        "Known capabilities advertised by the peer";
    }
    leaf capabilities-out {
      type lisp-ios-xe-oper:lisp-capabilities-type;
      description
        "Capabilities advertised over this session";
    }
    leaf capability-messages-in {
      type uint64;
      description
        "Capability advertisements received over this
         session";
    }
    leaf capability-error-messages-in {
      type uint64;
      description
        "Capability error messages received over this
         session";
    }
  }

  grouping lisp-local-rloc-type {
    description
      "Description of a RLOC local to the router or to the EID site
       served by the router";
    leaf state {
      type lisp-ios-xe-oper:lisp-rloc-state-type;
      description
        "Up/down state of the locator";
    }
    leaf is-local {
      type boolean;
      description
        "Indicates if RLOC is local to the device or to another xTR
         in the site; TRUE means RLOC is local to the device";
    }
  }

  grouping lisp-prefix-list-entry-type {
    description
      "Description of prefix list entry";
    leaf source-has-static {
      type boolean;
      description
        "Is the entry sourced statically";
    }
    leaf source-has-rib {
      type boolean;
      description
        "Is the entry sourced from RIB";
    }
    leaf source-has-site-reg {
      type boolean;
      description
        "Is the entry sourced from site registration";
    }
  }

  grouping lisp-prefix-list-type {
    description
      "Description of a prefix-list";
    leaf name {
      type string;
      description
        "Name of the prefix-list";
    }
    leaf count {
      type uint64;
      description
        "Number of entries in the list";
    }
    list prefix-list-entry {
      key "afi prefix";
      description
        "List of prefix list entries";
      uses lisp-ios-xe-oper:lisp-prefix-list-entry-type;
      uses lisp-ios-xe-oper:lisp-prefix-type;
    }
  }

  grouping lisp-router-type {
    description
      "Each entry contains operational data of a single LISP router";
    leaf top-id {
      type uint32;
      description
        "ID number of the LISP router";
    }
    leaf site-id {
      type uint64;
      description
        "Site-ID common to all devices attached to the same site";
    }
    leaf-list xtr-id {
      type uint8;
      max-elements "16";
      ordered-by user;
      description
        "xTR-ID of the device";
    }
    list instances {
      key "iid";
      description
        "List of LISP instances";
      uses lisp-ios-xe-oper:lisp-instance-type;
    }
    list sessions {
      key "local-address peer-address local-port peer-port";
      description
        "List of Reliable Registration sessions";
      uses lisp-ios-xe-oper:lisp-session-type;
      uses lisp-ios-xe-oper:lisp-session-source-destination-type;
    }
    list local-rlocs {
      key "afi address";
      description
        "This list represents the set of routing locators
         configured on this device";
      uses lisp-ios-xe-oper:lisp-local-rloc-type;
      uses lisp-ios-xe-oper:lisp-address-type;
    }
    list prefix-lists {
      key "name";
      description
        "This list represents list of prefix-lists configured on this device";
      uses lisp-ios-xe-oper:lisp-prefix-list-type;
    }
    leaf capabilities {
      type lisp-ios-xe-oper:lisp-capabilities-type;
      description
        "Capabilities enabled for the LISP router";
    }
  }

  container lisp-state {
    config false;
    description
      "Operational state of the LISP subsystem";
    list lisp-routers {
      key "top-id";
      description
        "List of LISP routers";
      uses lisp-ios-xe-oper:lisp-router-type;
    }
  }
}
