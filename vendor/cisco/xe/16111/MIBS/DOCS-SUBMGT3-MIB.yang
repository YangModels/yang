/*
 * Generated by confdc --mib2yang-std
 * Source: mgmt/dmi/model/mib/src/DOCS-SUBMGT3-MIB.mib
 */
/*
 * This YANG module has been generated by smidump 0.5.0:
 *
 *      smidump -f yang DOCS-SUBMGT3-MIB
 *
 * Do not edit. Edit the source file instead!
 */

module DOCS-SUBMGT3-MIB {

  namespace "urn:ietf:params:xml:ns:yang:smiv2:DOCS-SUBMGT3-MIB";
  prefix DOCS-SUBMGT3-MIB;

  import DOCS-IF3-MIB {
    prefix "docs-if3";
  }

  import DOCS-L2VPN-MIB {
    prefix "docs-l2vpn";
  }

  import INET-ADDRESS-MIB {
    prefix "inet-address";
  }

  import SNMP-TARGET-MIB {
    prefix "snmp-target";
  }

  import SNMPv2-TC {
    prefix "snmpv2-tc";
  }

  import ietf-inet-types {
    prefix "inet";
  }

  import ietf-yang-smiv2 {
    prefix "smiv2";
  }

  import ietf-yang-types {
    prefix "yang";
  }

  organization
   "Cable Television Laboratories, Inc.";

  contact
   " 
    Postal: Cable Television Laboratories, Inc. 
    858 Coal Creek Circle 
    Louisville, Colorado 80027-9750 
    U.S.A. 
    Phone: +1 303-661-9100 
    Fax:   +1 303-661-9199 
    E-mail: mibs@cablelabs.com";

  description
   "This MIB module contains the management objects for the 
    CMTS control of the IP4 and IPv6 traffic with origin and 
    destination to CMs and/or CPEs behind the CM.";

  revision 2007-05-18 {
    description
     "Revised Version includes ECNs 
      OSSIv3.0-N-07.0445-3 
      OSSIv3.0-N-07.0444-3 
      OSSIv3.0-N-07.0441-4 
      and published as I03";
  }

  revision 2006-12-07 {
    description
     "Initial version, published as part of the CableLabs 
      OSSIv3.0 specification CM-SP-OSSIv3.0-I01-061207 
      Copyright 1999-2006 Cable Television Laboratories, Inc. 
      All rights reserved.";
  }


  container DOCS-SUBMGT3-MIB {
    config false;

    container docsSubmgt3Base {
      smiv2:oid "1.3.6.1.4.1.4491.2.1.10.1.1";

      leaf docsSubmgt3BaseCpeMaxIpv4Def {
        type uint32 {
          range "0..1023";
        }
        description
         "This attribute represents the maximum number of IPv4  
          Addresses allowed for the CM's CPEs if not signaled in the  
          registration process.";
        smiv2:defval "16";
        smiv2:max-access "read-write";
        smiv2:oid "1.3.6.1.4.1.4491.2.1.10.1.1.1";
      }

      leaf docsSubmgt3BaseCpeMaxIpv6PrefixDef {
        type uint32 {
          range "0..1023";
        }
        description
         "This attribute represents the maximum number of IPv6  
          prefixes allowed for the CM's CPEs if not signaled in 
          the registration process.";
        smiv2:defval "16";
        smiv2:max-access "read-write";
        smiv2:oid "1.3.6.1.4.1.4491.2.1.10.1.1.2";
      }

      leaf docsSubmgt3BaseCpeActiveDef {
        type boolean;
        description
         "This attribute represents the default value for enabling 
          Subscriber Management filters and controls 
          in the CM if the parameter is not signaled in the DOCSIS 
          Registration process.";
        smiv2:defval "false";
        smiv2:max-access "read-write";
        smiv2:oid "1.3.6.1.4.1.4491.2.1.10.1.1.3";
      }

      leaf docsSubmgt3BaseCpeLearnableDef {
        type boolean;
        description
         "This attribute represents the default value for enabling 
          the CPE learning process for the CM if the parameter 
          is not signaled in the DOCSIS Registration process.";
        smiv2:defval "true";
        smiv2:max-access "read-write";
        smiv2:oid "1.3.6.1.4.1.4491.2.1.10.1.1.4";
      }

      leaf docsSubmgt3BaseSubFilterDownDef {
        type uint32 {
          range "0..1024";
        }
        description
         "This attribute represents the default value for the 
          subscriber (CPE) downstream filter group for the 
          CM if the parameter is not signaled in the DOCSIS Registration 
          process.";
        smiv2:defval "0";
        smiv2:max-access "read-write";
        smiv2:oid "1.3.6.1.4.1.4491.2.1.10.1.1.5";
      }

      leaf docsSubmgt3BaseSubFilterUpDef {
        type uint32 {
          range "0..1024";
        }
        description
         "This attribute represents the default value for the 
          subscriber (CPE) upstream filter group for the CM 
          if the parameter is not signaled in the DOCSIS Registration 
          process.";
        smiv2:defval "0";
        smiv2:max-access "read-write";
        smiv2:oid "1.3.6.1.4.1.4491.2.1.10.1.1.6";
      }

      leaf docsSubmgt3BaseCmFilterDownDef {
        type uint32 {
          range "0..1024";
        }
        description
         "This attribute represents the default value for the 
          CM stack downstream filter group applying to the CM 
          if the parameter is not signaled in the DOCSIS Registration 
          process.";
        smiv2:defval "0";
        smiv2:max-access "read-write";
        smiv2:oid "1.3.6.1.4.1.4491.2.1.10.1.1.7";
      }

      leaf docsSubmgt3BaseCmFilterUpDef {
        type uint32 {
          range "0..1024";
        }
        description
         "This attribute represents the default value for the 
          CM stack upstream filter group applying to the CM if 
          the parameter is not signaled in the DOCSIS Registration 
          process.";
        smiv2:defval "0";
        smiv2:max-access "read-write";
        smiv2:oid "1.3.6.1.4.1.4491.2.1.10.1.1.8";
      }

      leaf docsSubmgt3BasePsFilterDownDef {
        type uint32 {
          range "0..1024";
        }
        description
         "This attribute represents the default value for the 
          PS or eRouter downstream filter group for the CM if 
          the parameter is not signaled in the DOCSIS Registration 
          process.";
        smiv2:defval "0";
        smiv2:max-access "read-write";
        smiv2:oid "1.3.6.1.4.1.4491.2.1.10.1.1.9";
      }

      leaf docsSubmgt3BasePsFilterUpDef {
        type uint32 {
          range "0..1024";
        }
        description
         "This attribute represents the default value for the 
          PS or eRouter upstream filter group for the CM if the 
          parameter is not signaled in the DOCSIS Registration 
          process.";
        smiv2:defval "0";
        smiv2:max-access "read-write";
        smiv2:oid "1.3.6.1.4.1.4491.2.1.10.1.1.10";
      }

      leaf docsSubmgt3BaseMtaFilterDownDef {
        type uint32 {
          range "0..1024";
        }
        description
         "This attribute represents the default value for the 
          MTA downstream filter group for the CM if the parameter 
          is not signaled in the DOCSIS Registration process.";
        smiv2:defval "0";
        smiv2:max-access "read-write";
        smiv2:oid "1.3.6.1.4.1.4491.2.1.10.1.1.11";
      }

      leaf docsSubmgt3BaseMtaFilterUpDef {
        type uint32 {
          range "0..1024";
        }
        description
         "This attribute represents the default value for the 
          MTA upstream filter group for the CM if the parameter 
          is not signaled in the DOCSIS Registration process.";
        smiv2:defval "0";
        smiv2:max-access "read-write";
        smiv2:oid "1.3.6.1.4.1.4491.2.1.10.1.1.12";
      }

      leaf docsSubmgt3BaseStbFilterDownDef {
        type uint32 {
          range "0..1024";
        }
        description
         "This attribute represents the default value for the 
          STB downstream filter group for the CM if the parameter 
          is not signaled in the DOCSIS Registration process.";
        smiv2:defval "0";
        smiv2:max-access "read-write";
        smiv2:oid "1.3.6.1.4.1.4491.2.1.10.1.1.13";
      }

      leaf docsSubmgt3BaseStbFilterUpDef {
        type uint32 {
          range "0..1024";
        }
        description
         "This attribute represents the default value for the 
          STB upstream filter group for the CM if the parameter 
          is not signaled in the DOCSIS Registration process.";
        smiv2:defval "0";
        smiv2:max-access "read-write";
        smiv2:oid "1.3.6.1.4.1.4491.2.1.10.1.1.14";
      }
    }

    container docsSubmgt3CpeCtrlTable {
      description
       "This object maintains per-CM traffic policies enforced 
        by the CMTS. The CMTS acquires the CM traffic policies 
        through the CM registration process, or in the 
        absence of some or all of those parameters, from the 
        Base object. The CM information and controls are meaningful 
        and used by the CMTS, but only after the CM is 
        operational.";
      smiv2:oid "1.3.6.1.4.1.4491.2.1.10.1.2";

      list docsSubmgt3CpeCtrlEntry {
        key "docsIf3CmtsCmRegStatusId";
        description
         "The conceptual row of docsSubmgt3CpeCtrlTable. 
          The CMTS does not persist the instances of the CpeCtrl 
          object across reinitializations.";
        smiv2:oid "1.3.6.1.4.1.4491.2.1.10.1.2.1";

        leaf docsIf3CmtsCmRegStatusId {
          type leafref {
            path "/docs-if3:DOCS-IF3-MIB/docs-if3:docsIf3CmtsCmRegStatusTable/docs-if3:docsIf3CmtsCmRegStatusEntry/docs-if3:docsIf3CmtsCmRegStatusId";
          }
        }

        leaf docsSubmgt3CpeCtrlMaxCpeIpv4 {
          type uint32 {
            range "0..1023";
          }
          description
           "This attribute represents the number of simultaneous 
            IP v4 addresses permitted for CPE connected to the CM. 
            When the MaxCpeIpv4 attribute is set to zero (0), all Ipv4 CPE 
            traffic from the CM is dropped. The CMTS configures this 
            attribute with whichever of the 'Subscriber Management CPE IPv4 
            List' or 'Subscriber Management Control-Max_CpeIPv4' signaled 
            encodings is greater, or in the absence of all of those 
            provisioning parameters, with the CpeMaxIp v4Def 
            from the Base object. This limit applies to learned 
            and DOCSIS-provisioned entries but not to entries added 
            through some administrative process at the CMTS. 
            Note that this attribute is only meaningful when the 
            Active attribute of the CM is set to 'true'.";
          reference
           "DOCSIS 3.0 MAC and Upper Layer Protocols Interface 
            Specification CM-SP-MULPIv3.0-I04-070518, Subscriber Management 
            TLVs section in the Common Radio Frequency Interface Encodings 
            Annex.";
          smiv2:max-access "read-write";
          smiv2:oid "1.3.6.1.4.1.4491.2.1.10.1.2.1.1";
        }

        leaf docsSubmgt3CpeCtrlMaxCpeIpv6Prefix {
          type uint32 {
            range "0..1023";
          }
          description
           "This attribute represents the number of simultaneous 
            IPv6 prefixes permitted for CPE connected to the 
            CM.  
            When the MaxCpeIpv6Prefix is set to zero (0), all IPv6 CPE  
            traffic from the CM is dropped. The CMTS configures this  
            attribute with whichever of the 'Subscriber Management CPE IPv6 List'  
            or'Subscriber Management Control Max Cpe IPv6 Prefix'  
            signaled encodings is greater, or in the absence of all of those 
            provisioning parameters, with the CpeMaxIpv6PrefixDef 
            from the Base object. This limit applies to learned 
            and DOCSIS-provisioned entries but not to entries added 
            through some administrative process at the CMTS. 
            Note that this attribute is only meaningful when the 
            Active attribute of the CM is set to 'true'.";
          reference
           "DOCSIS 3.0 MAC and Upper Layer Protocols Interface 
            Specification CM-SP-MULPIv3.0-I04-070518, Subscriber Management 
            TLVs section in the Common Radio Frequency Interface Encodings 
            Annex.";
          smiv2:max-access "read-write";
          smiv2:oid "1.3.6.1.4.1.4491.2.1.10.1.2.1.2";
        }

        leaf docsSubmgt3CpeCtrlActive {
          type boolean;
          description
           "This attribute controls the application of subscriber 
            management to this CM. If this is set to 'true', 
            CMTS-based CPE control is active, and all the actions 
            required by the various filter policies and controls 
            apply at the CMTS. If this is set to false, no subscriber 
            management filtering is done at the CMTS (but other 
            filters may apply). If not set through DOCSIS provisioning, 
            this object defaults to the value of the Active 
            attribute of the Base object.";
          reference
           "DOCSIS 3.0 MAC and Upper Layer Protocols Interface 
            Specification CM-SP-MULPIv3.0-I04-070518, Subscriber Management 
            Control section in the Common Radio Frequency Interface 
            Encodings Annex.";
          smiv2:max-access "read-write";
          smiv2:oid "1.3.6.1.4.1.4491.2.1.10.1.2.1.3";
        }

        leaf docsSubmgt3CpeCtrlLearnable {
          type boolean;
          description
           "This attribute controls whether the CMTS may learn 
            (and pass traffic for) CPE IP addresses associated 
            with a CM. If this is set to 'true', the CMTS may learn up 
            to the CM MaxCpeIp value less any DOCSIS-provisioned 
            entries related to this CM. The nature of the learning 
            mechanism is not specified here. If not set through 
            DOCSIS provisioning, this object defaults to the 
            value of the CpeLearnableDef attribute from the Base 
            object. Note that this attribute is only meaningful 
            if docsSubMgtCpeControlActive is 'true' to enforce 
            a limit in the number of CPEs learned. CPE learning 
            is always performed for the CMTS for security reasons.";
          reference
           "DOCSIS 3.0 MAC and Upper Layer Protocols Interface 
            Specification CM-SP-MULPIv3.0-I04-070518, Subscriber Management 
            Control section in the Common Radio Frequency Interface 
            Encodings Annex.";
          smiv2:max-access "read-write";
          smiv2:oid "1.3.6.1.4.1.4491.2.1.10.1.2.1.4";
        }

        leaf docsSubmgt3CpeCtrlReset {
          type boolean;
          description
           "If set to 'true', this attribute commands the CMTS 
            to delete the instances denoted as 'learned' addresses 
            in the CpeIp object. This attribute always returns 
            false on read.";
          smiv2:max-access "read-write";
          smiv2:oid "1.3.6.1.4.1.4491.2.1.10.1.2.1.5";
        }

        leaf docsSubmgt3CpeCtrlLastReset {
          type yang:timestamp;
          description
           "This attribute represents the system Up Time of the 
            last set to 'true' of the Reset attribute of this instance. 
            Zero if never reset.";
          smiv2:max-access "read-write";
          smiv2:oid "1.3.6.1.4.1.4491.2.1.10.1.2.1.6";
        }
      }
    }

    container docsSubmgt3CpeIpTable {
      description
       "This object defines the list of IP Addresses behind 
        the CM known by the CMTS. 
        
        If the Active attribute of the CpeCtrl object associated 
        with a CM is set to 'true' and the CMTS receives an 
        IP packet from a CM that contains a source IP address that 
        does not match one of the CPE IP addresses associated 
        with this CM, one of two things occurs. If the number 
        of CPE IPs is less than the MaxCpeIp of the CpeCtrl object 
        for that CM, the source IP address is added to this 
        object and the packet is forwarded; otherwise, the 
        packet is dropped.";
      smiv2:oid "1.3.6.1.4.1.4491.2.1.10.1.3";

      list docsSubmgt3CpeIpEntry {
        key "docsIf3CmtsCmRegStatusId docsSubmgt3CpeIpId";
        description
         "The conceptual row of docsSubmgt3CpeIpTable.";
        smiv2:oid "1.3.6.1.4.1.4491.2.1.10.1.3.1";

        leaf docsIf3CmtsCmRegStatusId {
          type leafref {
            path "/docs-if3:DOCS-IF3-MIB/docs-if3:docsIf3CmtsCmRegStatusTable/docs-if3:docsIf3CmtsCmRegStatusEntry/docs-if3:docsIf3CmtsCmRegStatusId";
          }
        }

        leaf docsSubmgt3CpeIpId {
          type uint32 {
            range "1..1023";
          }
          description
           "This attribute represents a unique identifier for 
            a CPE IP of the CM. An instance of this attribute exists 
            for each CPE provisioned in the 'Subscriber Management 
            CPE IPv4 Table' or 'Subscriber Management CPE 
            IPv6 Table' encodings. An entry is created either through 
            the included CPE IP addresses in the provisioning 
            object, or CPEs learned from traffic sourced from the 
            CM.";
          smiv2:max-access "not-accessible";
          smiv2:oid "1.3.6.1.4.1.4491.2.1.10.1.3.1.1";
        }

        leaf docsSubmgt3CpeIpAddrType {
          type inet-address:InetAddressType;
          description
           "The type of Internet address of the Addr attribute.";
          smiv2:max-access "read-only";
          smiv2:oid "1.3.6.1.4.1.4491.2.1.10.1.3.1.2";
        }

        leaf docsSubmgt3CpeIpAddr {
          type inet-address:InetAddress;
          description
           "This attribute represents the IP address either set 
            from provisioning or learned via address gleaning 
            or other forwarding means.";
          smiv2:max-access "read-only";
          smiv2:oid "1.3.6.1.4.1.4491.2.1.10.1.3.1.3";
        }

        leaf docsSubmgt3CpeIpAddrPrefixLen {
          type inet-address:InetAddressPrefixLength;
          description
           "This attribute represents the prefix length associated with 
            the IP subnet prefix either set from provisioning or learned 
            via address gleaning or other forwarding means. For IPv4 CPE 
            addresses this attribute generally reports the value 32  
            (32 bits) to indicate a unicast IPv4 address. For IPv6, this 
            attribute represents either an IPv6 unicast address 
            (128 bits, equal to /128 prefix length) or a subnet prefix  
            length (for example 56 bits, equal to /56 prefix length).";
          smiv2:max-access "read-only";
          smiv2:oid "1.3.6.1.4.1.4491.2.1.10.1.3.1.4";
        }

        leaf docsSubmgt3CpeIpLearned {
          type boolean;
          description
           "This attribute is set to 'true' when the IP address 
            was learned from IP packets sent upstream rather than 
            via the CM provisioning process.";
          smiv2:max-access "read-only";
          smiv2:oid "1.3.6.1.4.1.4491.2.1.10.1.3.1.5";
        }

        leaf docsSubmgt3CpeIpType {
          type enumeration {
            enum "cpe" {
              value "1";
            }
            enum "ps" {
              value "2";
            }
            enum "mta" {
              value "3";
            }
            enum "stb" {
              value "4";
            }
            enum "tea" {
              value "5";
            }
            enum "erouter" {
              value "6";
            }
          }
          description
           "This attribute represents the type of CPE based on 
            the following classification below: 
                         'cpe' Regular CPE clients. 
                         'ps'  CableHome Portal Server (PS) 
                         'mta' PacketCable Multimedia Terminal Adapter (MTA) 
                         'stb' Digital Set-top Box (STB). 
                         'tea' T1 Emulation adapter (TEA) 
                         'erouter' Embedded Router (eRouter)";
          smiv2:max-access "read-only";
          smiv2:oid "1.3.6.1.4.1.4491.2.1.10.1.3.1.6";
        }
      }
    }

    container docsSubmgt3GrpTable {
      description
       "This object defines the set of downstream and upstream 
        filter groups that the CMTS applies to traffic associated 
        with that CM.";
      reference
       "DOCSIS 3.0 MAC and Upper Layer Protocols Interface 
        Specification CM-SP-MULPIv3.0-I01-060804, Subscriber 
        Management TLVs section in the Common Radio Frequency 
        Interface Encodings Annex.";
      smiv2:oid "1.3.6.1.4.1.4491.2.1.10.1.4";

      list docsSubmgt3GrpEntry {
        key "docsIf3CmtsCmRegStatusId";
        description
         "The conceptual row of docsSubmgt3GrpTable. 
          The CMTS does not persist the instances of the Grp 
          object across reinitializations.";
        smiv2:oid "1.3.6.1.4.1.4491.2.1.10.1.4.1";

        leaf docsIf3CmtsCmRegStatusId {
          type leafref {
            path "/docs-if3:DOCS-IF3-MIB/docs-if3:docsIf3CmtsCmRegStatusTable/docs-if3:docsIf3CmtsCmRegStatusEntry/docs-if3:docsIf3CmtsCmRegStatusId";
          }
        }

        leaf docsSubMgt3GrpUdcGroupIds {
          type snmp-target:SnmpTagList;
          description
           "This attribute represents the filter group(s) associated 
            with the CM signaled 'Upstream Drop Classifier Group ID'  
            encodings during the registration process. UDC Group IDs are 
            integer values and this attribute reports them as decimal  
            numbers that are space-separated. The zero-length string indicates  
            that the CM didn't signal UDC Group IDs.  
            This attribute provides two functions:  
            - Communicate the CM the configured UDC Group ID(s), irrespective  
            of the CM being provisioned to filter upstream traffic based  
            on IP Filters or UDCs.  
            - Optionally, and with regards to the CMTS, if the value of the 
            attribute UdcSentInReqRsp is 'true', indicates that the filtering  
            rules associated with the Subscriber Management Group ID(s) will 
            be sent during registration to the CM. It is vendor specific  
            whether the CMTS updates individual CM UDCs after registration 
            when rules are changed in the Grp object.";
          smiv2:defval "";
          smiv2:max-access "read-write";
          smiv2:oid "1.3.6.1.4.1.4491.2.1.10.1.4.1.1";
        }

        leaf docsSubMgt3GrpUdcSentInRegRsp {
          type boolean;
          description
           "This attribute represents the CMTS upstream filtering  
            status for this CM. The value 'true' indicates that the  
            CMTS has sent UDCs to the CM during registration process.  
             
            In order for a CMTS to send UDCs to a CM, the CMTS MAC Domain 
            needed to be enabled via the MAC Domain attribute  
            SendUdcRulesEnabled and the CM had indicated the UDC capability  
            support during the registration process. The value 'false'  
            indicates that the CMTS was not enabled to sent UDCs to the  
            CMs in the MAC Domain, or the CM does not advertised UDC  
            support in its capabilities encodings, or both. Since the  
            CMTS capability to sent UDCs to CMs during the registration 
            process is optional, the CMTS is not required to implement  
            the value 'true'.";
          smiv2:defval "false";
          smiv2:max-access "read-write";
          smiv2:oid "1.3.6.1.4.1.4491.2.1.10.1.4.1.2";
        }

        leaf docsSubmgt3GrpSubFilterDs {
          type uint32 {
            range "0..1024";
          }
          description
           "This attribute represents the filter group applied 
            to traffic destined for subscriber's CPE attached to the 
            referenced CM (attached to CM CPE interfaces). This 
            value corresponds to the 'Subscriber Downstream 
            Group' value of the 'Subscriber Management Filter Groups' 
            encoding signaled during the CM registration 
            or in its absence, to the SubFilterDownDef attribute 
            of the Base object. The value zero or a filter group 
            ID not configured in the CMTS means no filtering is applied 
            to traffic destined to hosts attached to this CM.";
          smiv2:max-access "read-write";
          smiv2:oid "1.3.6.1.4.1.4491.2.1.10.1.4.1.3";
        }

        leaf docsSubmgt3GrpSubFilterUs {
          type uint32 {
            range "0..1024";
          }
          description
           "This attribute represents the filter group applied 
            to traffic originating from subscriber's CPE attached 
            to the referenced CM (attached to CM CPE interfaces). 
            This value corresponds to the 'Subscriber Upstream 
            Group' value of the 'Subscriber Management Filter 
            Groups' encoding signaled during the CM registration 
            or in its absence, to the SubFilterUpDef attribute 
            of the Base object. The value zero or a filter group 
            ID not configured in the CMTS means no filtering 
            is applied to traffic originating from hosts attached 
            to this CM.";
          smiv2:max-access "read-write";
          smiv2:oid "1.3.6.1.4.1.4491.2.1.10.1.4.1.4";
        }

        leaf docsSubmgt3GrpCmFilterDs {
          type uint32 {
            range "0..1024";
          }
          description
           "This attribute represents the filter group applied 
            to traffic destined for the CM itself. This value corresponds 
            to the 'CM Downstream Group' value of the 
            'Subscriber Management Filter Groups' encoding signaled 
            during the CM registration or in its absence, 
            to the CmFilterDownDef attribute of the Base object. 
            The value zero or a filter group ID not configured in 
            the CMTS means no filtering is applied to traffic destined 
            to the CM.";
          smiv2:max-access "read-write";
          smiv2:oid "1.3.6.1.4.1.4491.2.1.10.1.4.1.5";
        }

        leaf docsSubmgt3GrpCmFilterUs {
          type uint32 {
            range "0..1024";
          }
          description
           "This attribute represents the filter group applied 
            to traffic originating from the CM itself. This value 
            corresponds to the 'Subscriber Upstream Group' 
            value of the 'Subscriber Management Filter Groups' 
            encoding signaled during the CM registration or in its 
            absence, to the SubFilterUpDef attribute of the Base 
            object. The value zero or a filter group ID not configured 
            in the CMTS means no filtering is applied to traffic 
            originating from this CM.";
          smiv2:max-access "read-write";
          smiv2:oid "1.3.6.1.4.1.4491.2.1.10.1.4.1.6";
        }

        leaf docsSubmgt3GrpPsFilterDs {
          type uint32 {
            range "0..1024";
          }
          description
           "This attribute represents the filter group applied 
            to traffic destined to the Embedded CableHome Portal 
            Services Element or the Embedded Router on the referenced 
            CM. This value corresponds to the 'PS Downstream 
            Group' value of the 'Subscriber Management Filter 
            Groups' encoding signaled during the CM registration 
            or in its absence, to the SubFilterDownDef attribute 
            of the Base object. The value zero or a filter 
            group ID not configured in the CMTS means no filtering 
            is applied to traffic destined to the Embedded CableHome 
            Portal Services Element or Embedded Router on 
            this CM.";
          smiv2:max-access "read-write";
          smiv2:oid "1.3.6.1.4.1.4491.2.1.10.1.4.1.7";
        }

        leaf docsSubmgt3GrpPsFilterUs {
          type uint32 {
            range "0..1024";
          }
          description
           "This attribute represents the filter group applied 
            to traffic originating from the Embedded CableHome 
            Portal Services Element or Embedded Router on the 
            referenced CM. This value corresponds to the 'PS Upstream 
            Group' value of the 'Subscriber Management Filter 
            Groups' encoding signaled during the CM registration 
            or in its absence, to the SubFilterUpDef attribute 
            of the Base object. The value zero or a filter group 
            ID not configured in the CMTS means no filtering is 
            applied to traffic originating from the Embedded CableHome 
            Portal Services Element or Embedded Router 
            on this CM.";
          smiv2:max-access "read-write";
          smiv2:oid "1.3.6.1.4.1.4491.2.1.10.1.4.1.8";
        }

        leaf docsSubmgt3GrpMtaFilterDs {
          type uint32 {
            range "0..1024";
          }
          description
           "This attribute represents the filter group applied 
            to traffic destined to the Embedded Multimedia Terminal 
            Adapter on the referenced CM. This value corresponds 
            to the 'MTA Downstream Group' value of the 'Subscriber 
            Management Filter Groups' encoding signaled 
            during the CM registration or in its absence, to 
            the SubFilterDownDef attribute of the Base object. 
            The value zero or a filter group ID not configured in the 
            CMTS means no filtering is applied to traffic destined 
            to the Embedded Multimedia Terminal Adapter on 
            this CM.";
          smiv2:max-access "read-write";
          smiv2:oid "1.3.6.1.4.1.4491.2.1.10.1.4.1.9";
        }

        leaf docsSubmgt3GrpMtaFilterUs {
          type uint32 {
            range "0..1024";
          }
          description
           "This attribute represents the filter group applied 
            to traffic originating from the Embedded Multimedia 
            Terminal Adapter on the referenced CM. This value 
            corresponds to the 'MTA Upstream Group' value of the 
            'Subscriber Management Filter Groups' encoding signaled 
            during the CM registration or in its absence, 
            to the SubFilterUpDef attribute of the Base object. 
            The value zero or a filter group ID not configured in 
            the CMTS means no filtering is applied to traffic originating 
            from the Embedded Multimedia Terminal Adapter 
            on this CM.";
          smiv2:max-access "read-write";
          smiv2:oid "1.3.6.1.4.1.4491.2.1.10.1.4.1.10";
        }

        leaf docsSubmgt3GrpStbFilterDs {
          type uint32 {
            range "0..1024";
          }
          description
           "This attribute represents the filter group applied 
            to traffic destined for the Embedded Set-Top Box on 
            the referenced CM. This value corresponds to the 'STB 
            Downstream Group' value of the 'Subscriber Management 
            Filter Groups' encoding signaled during the CM 
            registration or in its absence, to the SubFilterDownDef 
            attribute of the Base object. The value zero or 
            a filter group ID not configured in the CMTS means no filtering 
            is applied to traffic destined to the Embedded 
            Set-Top Box on this CM.";
          smiv2:max-access "read-write";
          smiv2:oid "1.3.6.1.4.1.4491.2.1.10.1.4.1.11";
        }

        leaf docsSubmgt3GrpStbFilterUs {
          type uint32 {
            range "0..1024";
          }
          description
           "This attribute represents the filter group applied 
            to traffic originating from the Embedded Set-Top 
            Box on the referenced CM. This value corresponds to the 
            'STB Upstream Group' value of the 'Subscriber Management 
            Filter Groups' encoding signaled during the 
            CM registration or in its absence, to the SubFilterUpDef 
            attribute of the Base object. The value zero or 
            a filter group ID not configured in the CMTS means no filtering 
            is applied to traffic originating from the 
            Embedded Set-Top Box on this CM.";
          smiv2:max-access "read-write";
          smiv2:oid "1.3.6.1.4.1.4491.2.1.10.1.4.1.12";
        }
      }
    }

    container docsSubmgt3FilterGrpTable {
      description
       "This object describes a set of filter or classifier 
        criteria. Classifiers are assigned by group to the 
        individual CMs. That assignment is made via the 'Subscriber 
        Management TLVs' encodings sent upstream from 
        the CM to the CMTS during registration or in their 
        absence, default values configured in the CMTS. 
        A Filter Group ID (GrpId) is a set of rules that correspond 
        to the expansion of a UDC Group ID into UDC individual  
        classification rules.  The Filter Group Ids are generated  
        whenever the CMTS is configured to send UDCs during the CM  
        registration process. Implementation of L2 classification  
        criteria is optional for the CMTS; LLC/MAC upstream and  
        downstream filter criteria can be ignored during the packet 
        matching process.";
      smiv2:oid "1.3.6.1.4.1.4491.2.1.10.1.5";

      list docsSubmgt3FilterGrpEntry {
        key "docsSubmgt3FilterGrpGrpId docsSubmgt3FilterGrpRuleId";
        description
         "The conceptual row of docsSubmgt3FilterGrpTable. 
          The CMTS persists all instances of the FilterGrp object 
          across reinitializations.";
        smiv2:oid "1.3.6.1.4.1.4491.2.1.10.1.5.1";

        leaf docsSubmgt3FilterGrpGrpId {
          type uint32 {
            range "1..65535";
          }
          description
           "This key is an identifier for a set of classifiers known 
            as a filter group. Each CM may be associated with 
            several filter groups for its upstream and downstream 
            traffic, one group per target end point on the CM as 
            defined in the Grp object. Typically, many CMs share 
            a common set of filter groups.";
          smiv2:max-access "not-accessible";
          smiv2:oid "1.3.6.1.4.1.4491.2.1.10.1.5.1.1";
        }

        leaf docsSubmgt3FilterGrpRuleId {
          type uint32 {
            range "1..65535";
          }
          description
           "This key represents an ordered classifier identifier 
            within the group.  Filters are applied in order if 
            the Priority attribute is not supported.";
          smiv2:max-access "not-accessible";
          smiv2:oid "1.3.6.1.4.1.4491.2.1.10.1.5.1.2";
        }

        leaf docsSubmgt3FilterGrpAction {
          type enumeration {
            enum "permit" {
              value "1";
            }
            enum "deny" {
              value "2";
            }
          }
          description
           "This attribute represents the action to take upon 
            this filter matching.  'permit' means to stop the classification 
            matching and accept the packet for further 
            processing.  'deny' means to drop the packet.";
          smiv2:defval "permit";
          smiv2:max-access "read-write";
          smiv2:oid "1.3.6.1.4.1.4491.2.1.10.1.5.1.3";
        }

        leaf docsSubmgt3FilterGrpPriority {
          type uint32 {
            range "0..65535";
          }
          description
           "This attribute defines the order in which classifiers 
            are compared against packets. The higher the value, 
            the higher the priority.";
          smiv2:defval "0";
          smiv2:max-access "read-write";
          smiv2:oid "1.3.6.1.4.1.4491.2.1.10.1.5.1.4";
        }

        leaf docsSubmgt3FilterGrpIpTosLow {
          type binary {
            length "1";
          }
          description
           "This attribute represents the low value of a range 
            of ToS (Type of Service) octet values. This object is 
            defined as an 8-bit octet as per the DOCSIS Specification 
            for packet classification. 
            The IP ToS octet, as originally defined in RFC 791, has 
            been superseded by the 6-bit Differentiated Services 
            Field (DSField, RFC 3260) and the 2-bit Explicit 
            Congestion Notification Field (ECN field, RFC 3168).";
          reference
           "DOCSIS 3.0 MAC and Upper Layer Protocols Interface 
            Specification CM-SP-MULPIv3.0-I01-060804. 
            RFC 791. 
            RFC 3260. 
            RFC 3168.";
          smiv2:defval "'00'H";
          smiv2:max-access "read-write";
          smiv2:oid "1.3.6.1.4.1.4491.2.1.10.1.5.1.5";
        }

        leaf docsSubmgt3FilterGrpIpTosHigh {
          type binary {
            length "1";
          }
          description
           "This attribute represents the high value of a range 
            of ToS octet values. This object is defined as an 8-bit 
            octet as per the DOCSIS Specification for packet classification. 
            The IP ToS octet, as originally defined in RFC 791, has 
            been superseded by the 6-bit Differentiated Services 
            Field (DSField, RFC 3260) and the 2-bit Explicit 
            Congestion Notification Field (ECN field, RFC 3168).";
          reference
           "DOCSIS 3.0 MAC and Upper Layer Protocols Interface 
            Specification CM-SP-MULPIv3.0-I01-060804. 
            RFC 791. 
            RFC 3260. 
            RFC 3168.";
          smiv2:defval "'00'H";
          smiv2:max-access "read-write";
          smiv2:oid "1.3.6.1.4.1.4491.2.1.10.1.5.1.6";
        }

        leaf docsSubmgt3FilterGrpIpTosMask {
          type binary {
            length "1";
          }
          description
           "This attribute represents the mask value that is bitwise 
            ANDed with ToS octet in an IP packet, and the resulting value 
            is used for range checking of IpTosLow and IpTosHigh.";
          smiv2:defval "'00'H";
          smiv2:max-access "read-write";
          smiv2:oid "1.3.6.1.4.1.4491.2.1.10.1.5.1.7";
        }

        leaf docsSubmgt3FilterGrpIpProtocol {
          type uint32 {
            range "0..257";
          }
          description
           "This attribute represents the value of the IP Protocol 
            field required for IP packets to match this rule. 
            The value 256 matches traffic with any IP Protocol value. 
            The value 257 by convention matches both TCP and 
            UDP.";
          smiv2:defval "256";
          smiv2:max-access "read-write";
          smiv2:oid "1.3.6.1.4.1.4491.2.1.10.1.5.1.8";
        }

        leaf docsSubmgt3FilterGrpInetAddrType {
          type inet-address:InetAddressType;
          description
           "The type of the Internet address for InetSrcAddr, 
            InetSrcMask, InetDestAddr, and InetDestMask.";
          smiv2:defval "unknown";
          smiv2:max-access "read-write";
          smiv2:oid "1.3.6.1.4.1.4491.2.1.10.1.5.1.9";
        }

        leaf docsSubmgt3FilterGrpInetSrcAddr {
          type inet-address:InetAddress;
          description
           "This attribute specifies the value of the IP Source Address 
            required for packets to match this rule. An IP packet 
            matches the rule when the packet's IP Source Address 
            bitwise ANDed with the InetSrcMask value equals 
            the InetSrcAddr value. The address type of this object 
            is specified by the InetAddressType attribute.";
          smiv2:defval "";
          smiv2:max-access "read-write";
          smiv2:oid "1.3.6.1.4.1.4491.2.1.10.1.5.1.10";
        }

        leaf docsSubmgt3FilterGrpInetSrcMask {
          type inet-address:InetAddress;
          description
           "This attribute represents which bits of a packet's 
            IP Source Address are compared to match this rule. An 
            IP packet matches the rule when the packet's IP Source 
            Address bitwise ANDed with the InetSrcMask value equals 
            the InetSrcAddr value. The address type of this 
            object is specified by InetAddrType.";
          smiv2:defval "";
          smiv2:max-access "read-write";
          smiv2:oid "1.3.6.1.4.1.4491.2.1.10.1.5.1.11";
        }

        leaf docsSubmgt3FilterGrpInetDestAddr {
          type inet-address:InetAddress;
          description
           "This attribute specifies the value of the IP Destination 
            Address required for packets to match this rule. 
            An IP packet matches the rule when the packet's IP Destination 
            Address bitwise ANDed with the InetSrcMask 
            value equals the InetDestAddr value. The address type 
            of this object is specified by the InetAddrType attribute.";
          smiv2:defval "";
          smiv2:max-access "read-write";
          smiv2:oid "1.3.6.1.4.1.4491.2.1.10.1.5.1.12";
        }

        leaf docsSubmgt3FilterGrpInetDestMask {
          type inet-address:InetAddress;
          description
           "This attribute represents which bits of a packet's 
            IP Destination Address are compared to match this rule. 
            An IP packet matches the rule when the packet's IP Destination 
            Address bitwise ANDed with the InetDestMask value 
            equals the InetDestAddr value. The address type 
            of this object is specified by InetAddrType.";
          smiv2:defval "";
          smiv2:max-access "read-write";
          smiv2:oid "1.3.6.1.4.1.4491.2.1.10.1.5.1.13";
        }

        leaf docsSubmgt3FilterGrpSrcPortStart {
          type inet:port-number;
          description
           "This attribute represents the low-end inclusive 
            range of TCP/UDP source port numbers to which a packet 
            is compared. This attribute is irrelevant for non-TCP/UDP 
            IP packets.";
          smiv2:defval "0";
          smiv2:max-access "read-write";
          smiv2:oid "1.3.6.1.4.1.4491.2.1.10.1.5.1.14";
        }

        leaf docsSubmgt3FilterGrpSrcPortEnd {
          type inet:port-number;
          description
           "This attribute represents the high-end inclusive 
            range of TCP/UDP source port numbers to which a packet 
            is compared. This attribute is irrelevant for non-TCP/UDP 
            IP packets.";
          smiv2:defval "65535";
          smiv2:max-access "read-write";
          smiv2:oid "1.3.6.1.4.1.4491.2.1.10.1.5.1.15";
        }

        leaf docsSubmgt3FilterGrpDestPortStart {
          type inet:port-number;
          description
           "This attribute represents the low-end inclusive 
            range of TCP/UDP destination port numbers to which a 
            packet is compared. This attribute is irrelevant for 
            non-TCP/UDP IP packets.";
          smiv2:defval "0";
          smiv2:max-access "read-write";
          smiv2:oid "1.3.6.1.4.1.4491.2.1.10.1.5.1.16";
        }

        leaf docsSubmgt3FilterGrpDestPortEnd {
          type inet:port-number;
          description
           "This attribute represents the high-end inclusive 
            range of TCP/UDP destination port numbers to which a packet 
            is compared. This attribute is irrelevant for non-TCP/UDP 
            IP packets.";
          smiv2:defval "65535";
          smiv2:max-access "read-write";
          smiv2:oid "1.3.6.1.4.1.4491.2.1.10.1.5.1.17";
        }

        leaf docsSubmgt3FilterGrpDestMacAddr {
          type yang:mac-address;
          description
           "This attribute represents the criteria to match against 
            an Ethernet packet MAC address bitwise ANDed 
            with DestMacMask.";
          smiv2:defval "'000000000000'H";
          smiv2:max-access "read-write";
          smiv2:oid "1.3.6.1.4.1.4491.2.1.10.1.5.1.18";
        }

        leaf docsSubmgt3FilterGrpDestMacMask {
          type yang:mac-address;
          description
           "An Ethernet packet matches an entry when its 
            destination MAC address bitwise ANDed with 
            the DestMacMask attribute equals the value of 
            the DestMacAddr attribute.";
          smiv2:defval "'000000000000'H";
          smiv2:max-access "read-write";
          smiv2:oid "1.3.6.1.4.1.4491.2.1.10.1.5.1.19";
        }

        leaf docsSubmgt3FilterGrpSrcMacAddr {
          type yang:mac-address;
          description
           "This attribute represents the value to match against 
            an Ethernet packet source MAC address.";
          smiv2:defval "'ffffffffffff'H";
          smiv2:max-access "read-write";
          smiv2:oid "1.3.6.1.4.1.4491.2.1.10.1.5.1.20";
        }

        leaf docsSubmgt3FilterGrpEnetProtocolType {
          type enumeration {
            enum "none" {
              value "0";
            }
            enum "ethertype" {
              value "1";
            }
            enum "dsap" {
              value "2";
            }
            enum "mac" {
              value "3";
            }
            enum "all" {
              value "4";
            }
          }
          description
           "This attribute indicates the format of the layer 3 
            protocol ID in the Ethernet packet. A value of 'none' 
            means that the rule does not use the layer 3 protocol 
            type as a matching criteria. A value of 'ethertype' 
            means that the rule applies only to frames that contain 
            an EtherType value. EtherType values are contained 
            in packets using the DEC-Intel-Xerox (DIX) encapsulation 
            or the RFC 1042 Sub-Network Access Protocol 
            (SNAP) encapsulation formats. A value of 'dsap' means 
            that the rule applies only to frames using the IEEE802.3 
            encapsulation format with a Destination Service 
            Access Point (DSAP) other than 0xAA (which is reserved 
            for SNAP). A value of 'mac' means that the rule 
            applies only to MAC management messages for MAC management 
            messages. A value of 'all' means that the rule 
            matches all Ethernet packets. If the Ethernet frame 
            contains an 802.1P/Q Tag header (i.e., EtherType 
            0x8100), this attribute applies to the embedded EtherType 
            field within the 802.1p/Q header. 
            The value 'mac' is only used for passing UDCs to CMs during  
            Registration. The CMTS ignores filter rules that include  
            the value of this attribute set to 'mac' for CMTS enforced  
            upstream and downstream subscriber management filter group 
            rules.";
          reference
           "RFC1042 Sub-Network Access Protocol (SNAP) encapsulation 
            formats.";
          smiv2:defval "none";
          smiv2:max-access "read-write";
          smiv2:oid "1.3.6.1.4.1.4491.2.1.10.1.5.1.21";
        }

        leaf docsSubmgt3FilterGrpEnetProtocol {
          type uint32 {
            range "0..65535";
          }
          description
           "This attribute represents the Ethernet protocol 
            type to be matched against the packets. For EnetProtocolType 
            set to 'none', this attribute is ignored when considering 
            whether a packet matches the current rule. 
            If the attribute EnetProtocolType is 'ethertype', 
            this attribute gives the 16-bit value of the EtherType 
            that the packet must match in order to match the rule. 
            If the attribute EnetProtocolType is 'dsap', the lower 
            8 bits of this attribute's value must match the DSAP 
            octet of the packet in order to match the rule. If the Ethernet 
            frame contains an 802.1p/Q Tag header (i.e., 
            EtherType 0x8100), this attribute applies to the embedded 
            EtherType field within the 802.1p/Q header.";
          smiv2:defval "0";
          smiv2:max-access "read-write";
          smiv2:oid "1.3.6.1.4.1.4491.2.1.10.1.5.1.22";
        }

        leaf docsSubmgt3FilterGrpUserPriLow {
          type uint32 {
            range "0..7";
          }
          description
           "This attribute applies only to Ethernet frames using 
            the 802.1p/Q tag header (indicated with EtherType 
            0x8100). Such frames include a 16-bit Tag that contains 
            a 3-bit Priority field and a 12-bit VLAN number. 
            Tagged Ethernet packets must have a 3-bit Priority 
            field within the range of PriLow to PriHigh in order to 
            match this rule.";
          smiv2:defval "0";
          smiv2:max-access "read-write";
          smiv2:oid "1.3.6.1.4.1.4491.2.1.10.1.5.1.23";
        }

        leaf docsSubmgt3FilterGrpUserPriHigh {
          type uint32 {
            range "0..7";
          }
          description
           "This attribute applies only to Ethernet frames using 
            the 802.1p/Q tag header (indicated with EtherType 
            0x8100). Such frames include a 16-bit Tag that contains 
            a 3-bit Priority field and a 12-bit VLAN number. 
            Tagged Ethernet packets must have a 3-bit Priority 
            field within the range of PriLow to PriHigh in order to 
            match this rule.";
          smiv2:defval "7";
          smiv2:max-access "read-write";
          smiv2:oid "1.3.6.1.4.1.4491.2.1.10.1.5.1.24";
        }

        leaf docsSubmgt3FilterGrpVlanId {
          type uint32 {
            range "0..4094";
          }
          description
           "This attribute applies only to Ethernet frames using 
            the 802.1p/Q tag header. Tagged packets must have 
            a VLAN Identifier that matches the value in order to 
            match the rule.";
          smiv2:max-access "read-write";
          smiv2:oid "1.3.6.1.4.1.4491.2.1.10.1.5.1.25";
        }

        leaf docsSubmgt3FilterGrpClassPkts {
          type yang:counter64;
          description
           "This attribute counts the number of packets 
            that have been classified (matched) using this rule 
            entry. This includes all packets delivered to a Service 
            Flow maximum rate policing function, whether 
            or not that function drops the packets. Discontinuities 
            in the value of this counter can occur at re-initialization 
            of the managed system, and at other times 
            as indicated by the value of ifCounterDiscontinuityTime 
            for the CM MAC Domain interface.";
          smiv2:max-access "read-only";
          smiv2:oid "1.3.6.1.4.1.4491.2.1.10.1.5.1.26";
        }

        leaf docsSubmgt3FilterGrpFlowLabel {
          type uint32 {
            range "0..1048575";
          }
          description
           "This attribute represents the Flow Label field in 
            the IPv6 header to be matched by the classifier. 
            The value zero indicates that the Flow Label is not specified 
            as part of the classifier and is not matched against packets.";
          reference
           "DOCSIS 3.0 MAC and Upper Layer Protocols Interface 
            Specification CM-SP-MULPIv3.0-I03-070223, IPv6 Flow  
            Label section in the Common Radio Frequency Interface 
            Encodings Annex.";
          smiv2:max-access "read-write";
          smiv2:oid "1.3.6.1.4.1.4491.2.1.10.1.5.1.27";
        }

        leaf docsSubmgt3FilterGrpCmInterfaceMask {
          type docs-l2vpn:DocsL2vpnIfList;
          description
           "This attribute represents a bit-mask of the CM in-bound 
            interfaces to which this classifier applies. 
            This attribute only applies to upstream Drop Classifiers  
            being sent to CMs during the registration process.";
          reference
           "DOCSIS 3.0 MAC and Upper Layer Protocols Interface 
            Specification CM-SP-MULPIv3.0-I03-070223, CM  
            Interface Mask (CMIM) Encoding section in the Common  
            Radio Frequency Interface Encodings Annex.";
          smiv2:max-access "read-write";
          smiv2:oid "1.3.6.1.4.1.4491.2.1.10.1.5.1.28";
        }

        leaf docsSubmgt3FilterGrpRowStatus {
          type snmpv2-tc:RowStatus;
          description
           "The conceptual row status of this object.";
          smiv2:max-access "read-write";
          smiv2:oid "1.3.6.1.4.1.4491.2.1.10.1.5.1.29";
        }
      }
    }
  }

  smiv2:alias "docsSubmgt3Mib" {
    smiv2:oid "1.3.6.1.4.1.4491.2.1.10";
  }

  smiv2:alias "docsSubmgt3MibObjects" {
    smiv2:oid "1.3.6.1.4.1.4491.2.1.10.1";
  }

  smiv2:alias "docsSubmgt3Base" {
    smiv2:oid "1.3.6.1.4.1.4491.2.1.10.1.1";
  }

  smiv2:alias "docsSubmgt3MibConformance" {
    smiv2:oid "1.3.6.1.4.1.4491.2.1.10.2";
  }

  smiv2:alias "docsSubmgt3MibCompliances" {
    smiv2:oid "1.3.6.1.4.1.4491.2.1.10.2.1";
  }

  smiv2:alias "docsSubmgt3MibGroups" {
    smiv2:oid "1.3.6.1.4.1.4491.2.1.10.2.2";
  }

}
