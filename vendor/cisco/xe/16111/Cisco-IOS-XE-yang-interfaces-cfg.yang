module Cisco-IOS-XE-yang-interfaces-cfg {
  yang-version 1;
  namespace "http://cisco.com/ns/yang/Cisco-IOS-XE-yang-interfaces-cfg";
  prefix yang-interfaces-cfg;

  organization
    "Cisco Systems, Inc.";
  contact
    "Cisco Systems, Inc.
     Customer Service
     
     Postal: 170 W Tasman Drive
     San Jose, CA 95134
     
     Tel: +1 1800 553-NETS
     
     E-mail: cs-yang@cisco.com";
  description
    "Service ACLs for YANG Interfaces";

  revision 2018-11-01 {
    description
      "Initial revision";
    reference "1.0.0";
  }

  grouping dmi-acl-nbi-type {
    description
      "Update access-list of the selected service";
    leaf ipv4-acl-name {
      type string {
        length "1..32";
        pattern "[0-9a-zA-Z_]+";
      }
      description
        "Validate access using an IPv4 access-list";
    }
    leaf ipv6-acl-name {
      type string {
        length "1..32";
        pattern "[0-9a-zA-Z_]+";
      }
      description
        "Validate access using an IPv6 access-list";
    }
  }

  grouping dmi-acl {
    description
      "Select the northbound service to configure Service ACLs";
    container netconf-yang-ssh {
      description
        "Netconf-Yang SSH service";
      uses yang-interfaces-cfg:dmi-acl-nbi-type;
    }
    container restconf {
      description
        "Restconf service";
      uses yang-interfaces-cfg:dmi-acl-nbi-type;
    }
  }

  container yang-interfaces-cfg-data {
    description
      "Service ACLs for YANG Interfaces";
    container acl {
      description
        "Optioanlly configure an access-list to validate access
         to the device";
      uses yang-interfaces-cfg:dmi-acl;
    }
  }
}
