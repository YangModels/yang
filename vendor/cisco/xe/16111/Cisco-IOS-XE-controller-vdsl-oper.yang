module Cisco-IOS-XE-controller-vdsl-oper {
  yang-version 1;
  namespace "http://cisco.com/ns/yang/Cisco-IOS-XE-controller-vdsl-oper";
  prefix vdsl-ios-xe-oper;

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for monitoring controller VDSL operational information.
     Copyright (c) 2018 by Cisco Systems, Inc.
     All rights reserved.";

  revision 2018-10-29 {
    description
      "Cleaned up spelling errors in descriptions.";
    reference "1.1.0";
  }
  revision 2018-01-31 {
    description
      "Initial revision";
    reference "1.0.0";
  }

  typedef idb-states {
    type enumeration {
      enum "down" {
        value 0;
        description
          "Interface down";
      }
      enum "going-down" {
        value 1;
        description
          "Interface going down";
      }
      enum "init" {
        value 2;
        description
          "Interface initialization";
      }
      enum "testing" {
        value 3;
        description
          "Interface testing";
      }
      enum "up" {
        value 4;
        description
          "Interface up";
      }
      enum "reset" {
        value 5;
        description
          "Interface reset";
      }
      enum "admindown" {
        value 6;
        description
          "Interface admindown";
      }
      enum "deleted" {
        value 7;
        description
          "Interface deleted";
      }
    }
    description
      "Interface state";
  }

  typedef mode-tc {
    type enumeration {
      enum "ptm" {
        value 0;
        description
          "MODE Ethernet";
      }
      enum "atm" {
        value 1;
        description
          "MODE Atm";
      }
    }
    description
      "Operation Mode";
  }

  grouping slot-info-key {
    description
      "Key information";
    leaf slot-num {
      type uint32;
      description
        "Slot number";
    }
    leaf subslot-num {
      type uint32;
      description
        "Sub Slot number";
    }
  }

  grouping vdsl-line-stats {
    description
      "Line specific information";
    leaf chip-vendor {
      type string;
      description
        "Chip vendor ID";
    }
    leaf line-attenuation {
      type string;
      description
        "Line attenuation in decibels";
    }
    leaf noise-margin {
      type string;
      description
        "Noise margin in decibels";
    }
    leaf attainable-rate {
      type uint32;
      description
        "Attainable rate in kilobits per sec";
    }
    leaf actual-power {
      type string;
      description
        "Actual power in decibel-milliwatts";
    }
    leaf speed {
      type uint32;
      description
        "Speed in kilobits per sec";
    }
    leaf modem-serial {
      type string;
      description
        "Modem serial number";
    }
  }

  grouping controller-info {
    description
      "VDSL Controller information";
    leaf state {
      type vdsl-ios-xe-oper:idb-states;
      description
        "Controller database state";
    }
    leaf mode {
      type vdsl-ios-xe-oper:mode-tc;
      description
        "Operational mode";
    }
    leaf modem-status {
      type string;
      description
        "Modem status";
    }
    leaf trained-mode {
      type string;
      description
        "Trained Mode";
    }
    leaf firmware-version {
      type string;
      description
        "Firmware version";
    }
    leaf phy-version {
      type string;
      description
        "PHY version";
    }
    container cpe-stats {
      description
        "XTU-R customer-premises equipment statistics";
      uses vdsl-ios-xe-oper:vdsl-line-stats;
    }
    container co-stats {
      description
        "XTU-C central office statistics";
      uses vdsl-ios-xe-oper:vdsl-line-stats;
    }
  }

  container vdsl-oper-data {
    config false;
    description
      "VDSL controller information";
    list vdsl-info {
      key "slot-num subslot-num";
      description
        "VDSL controller information";
      uses vdsl-ios-xe-oper:controller-info;
      uses vdsl-ios-xe-oper:slot-info-key;
    }
  }
}
