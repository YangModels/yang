module Cisco-IOS-XE-mka {
  namespace "http://cisco.com/ns/yang/Cisco-IOS-XE-mka";
  prefix ios-mka;

  import Cisco-IOS-XE-native {
    prefix ios;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE  Macsec Key Agreement protocol (MKA) Yang Model.
     Copyright (c) 2016-2017 by Cisco Systems, Inc.
     All rights reserved.";

  // =========================================================================
  // REVISION
  // =========================================================================
  revision 2019-01-22 {
     description
      "Added leaf for App-hosting Gigabit Ethernet interface";
  }

  revision 2017-11-27 {
     description
       "Added Change 25GE name";
  }

  revision 2017-11-14 {
    description
      "Add 100GE Support";
  }

  revision 2017-09-17 {
    description
      "add key-server priority for mka grouping";
  }
  revision 2017-08-16 {
    description
      "This revision has changes for new 5gig and 25gig interfaces addition";
  }
  revision 2017-07-26 {
    description
      "add confidentiality-offset for mka grouping";
  }  
  revision 2017-02-07 {
    description
      "Initial revision";
  }

  grouping config-mka-grouping {
      list policy {
        description "Configure MKA Policy";
        key "name";
        leaf name {
          description "MKA Policy NAME";
          type string;
        }
        container key-server {
          description "Configure MKA key-server options";
          leaf priority {
            description
              "Set MKA key-server priority";
            type uint8;
          }
        }
        container macsec-cipher-suite {
          description "Cipher Suite for SAK derivation";
          leaf gcm-aes-128 {
            description
              "GCM-AES-128 Cipher Suite";
            type empty;
          }
          leaf gcm-aes-256 {
            description
              "GCM-AES-256 Cipher Suite";
            type empty;
          }
        }
        leaf confidentiality-offset {
          description
            "Set the confidentiality offset for MACsec operation";
          type enumeration {
            enum "0";
            enum "30";
            enum "50";
          }
        }
      }
  }

  grouping config-interface-mka-grouping {
    container mka {
      description
        "MACsec Key Agreement (MKA) interface configuration";
      container policy {
        description
          "Apply MKA Policy";
        leaf name {
          description
            "MKA Policy NAME";
          type string;
        }
      }
      container pre-shared-key {
        description
          "Configure MKA Pre-Shared-Key";
        container key-chain {
          description
            "Configure the key-chain name";
          leaf name {
            description
              "Name of key-chain to be used to get keys";
            type string;
          }
        }
      }
    }
  }

  /////////////////////////////////////////////////////////
  // native / mka
  /////////////////////////////////////////////////////////
  augment "/ios:native/ios:mka" {
    uses config-mka-grouping;
  }

  /////////////////////////////////////////////////////////
  // interface * / mka 
  /////////////////////////////////////////////////////////
  augment "/ios:native/ios:interface/ios:FastEthernet" {
    uses config-interface-mka-grouping;
  }

  augment "/ios:native/ios:interface/ios:GigabitEthernet" {
    uses config-interface-mka-grouping;
  }

  augment "/ios:native/ios:interface/ios:TenGigabitEthernet" {
    uses config-interface-mka-grouping;
  }

  augment "/ios:native/ios:interface/ios:FiveGigabitEthernet" {
    uses config-interface-mka-grouping;
  }

  augment "/ios:native/ios:interface/ios:AppGigabitEthernet" {
    uses config-interface-mka-grouping;
  }

  augment "/ios:native/ios:interface/ios:TwentyFiveGigE" {
    uses config-interface-mka-grouping;
  }

  augment "/ios:native/ios:interface/ios:TwoGigabitEthernet" {
    uses config-interface-mka-grouping;
  }

  augment "/ios:native/ios:interface/ios:FortyGigabitEthernet" {
    uses config-interface-mka-grouping;
  }

  augment "/ios:native/ios:interface/ios:HundredGigE" {
    uses config-interface-mka-grouping;
  }
}
