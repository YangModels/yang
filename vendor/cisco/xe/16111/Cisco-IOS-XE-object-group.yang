module Cisco-IOS-XE-object-group {
  namespace "http://cisco.com/ns/yang/Cisco-IOS-XE-object-group";
  prefix ios-og;

  import Cisco-IOS-XE-types {
    prefix ios-types;
  }

  import Cisco-IOS-XE-native {
    prefix ios;
  }


  import ietf-inet-types {
      prefix inet;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Object Group Yang model.
     Copyright (c) 2016, 2018 by Cisco Systems, Inc.
     All rights reserved.";

  // =========================================================================
  // REVISION
  // =========================================================================
  revision 2018-11-07 {
      description
      "Cleanup spelling errors in description statements";
  }
  revision 2018-10-03 {
    description
      "Fix protocol icmp, tcp and udp able to standalone";
  }
  revision 2018-10-01 {
    description
      "Fix not being able to configure multiple protocol numbers and names";
  }
  revision 2018-06-24 {
    description
      "Refactor source port service object-group support";
  }
  revision 2018-06-20 {
    description
      "Add source port support to service object-group";
  }
  revision 2017-07-31 {
    description
      "Support multiple-host under object group network";
  }
  revision 2017-02-07 {
    description
      "Initial revision";
  }

  typedef object-group-port-operator {
    type enumeration {
      enum "eq";
      enum "gt";
      enum "lt";
    }
  }

  grouping object-group-service-grouping {
    leaf description {
      description
        "Service object group description";
      type string {
        length "1..200";
      }
    }
    leaf group-object {
      description
        "Nested object group";
      type string;
    }
    leaf-list protocal-number {
      description
        "An IP protocol number";
      type uint8;
    }
    leaf ahp {
      description
        "Authentication Header Protocol";
      type empty;
    }
    leaf eigrp {
      description
        "Cisco's EIGRP routing protocol";
      type empty;
    }
    leaf esp {
      description
        "Encapsulation Security Payload";
      type empty;
    }
    leaf gre {
      description
        "Cisco's GRE tunneling";
      type empty;
    }
    leaf icmp {
      description
        "Internet Control Message Protocol";
      type empty;
    }
    container icmp-conf {
      container icmp {
        description
          "Internet Control Message Protocol";
        leaf port-number {
          type uint8;
        }
        leaf alternate-address {
          description
            "Alternate address";
          type empty;
        }
        leaf conversion-error {
          description
            "Datagram conversion";
          type empty;
        }
        leaf echo {
          description
            "Echo (ping)";
          type empty;
        }
        leaf echo-reply {
          description
            "Echo reply";
          type empty;
        }
        leaf information-reply {
          description
            "Information replies";
          type empty;
        }
        leaf information-request {
          description
            "Information requests";
          type empty;
        }
        leaf mask-reply {
          description
            "Mask replies";
          type empty;
        }
        leaf mask-request {
          description
            "Mask requests";
          type empty;
        }
        leaf mobile-redirect {
          description
            "Mobile host redirect";
          type empty;
        }
        leaf parameter-problem {
          description
            "All parameter problems";
          type empty;
        }
        leaf redirect {
          description
            "All redirects";
          type empty;
        }
        leaf router-advertisement {
          description
            "Router discovery advertisements";
          type empty;
        }
        leaf router-solicitation {
          description
            "Router discovery solicitations";
          type empty;
        }
        leaf source-quench {
          description
            "Source quenches";
          type empty;
        }
        leaf time-exceeded {
          description
            "All time exceeded";
          type empty;
        }
        leaf timestamp-reply {
          description
            "Timestamp replies";
          type empty;
        }
        leaf timestamp-request {
          description
            "Timestamp requests";
          type empty;
        }
        leaf traceroute {
          description
            "Traceroute";
          type empty;
        }
        leaf unreachable {
          description
            "All unreachables";
          type empty;
        }
      }
    }
    leaf igmp {
      description
        "Internet Gateway Message Protocol";
      type empty;
    }
    leaf ip {
      description
        "Any Internet Protocol";
      type empty;
    }
    leaf ipinip {
      description
        "IP in IP tunneling";
      type empty;
    }
    leaf nos {
      description
        "KA9Q NOS compatible IP over IP tunneling";
      type empty;
    }
    leaf ospf {
      description
        "OSPF routing protocol";
      type empty;
    }
    leaf pcp {
      description
        "Payload Compression Protocol";
      type empty;
    }
    leaf pim {
      description
        "Protocol Independent Multicast";
      type empty;
    }
    leaf tcp {
      type empty;
    }
    container tcp-conf {
      container tcp {
        description
          "Transmission Control Protocol";
        list tcp-port-list {
          key "tcp-port";
          leaf tcp-port {
            type ios-types:acl-tcp-port-type;
          }
          leaf operator {
            type object-group-port-operator;
          }
        }
        container tcp-range-port-list {
          list range {
            description
              "Match only packets in the range of port numbers";
            key "tcp-min-port tcp-max-port";
            leaf tcp-min-port {
              type ios-types:acl-tcp-port-type;
            }
            leaf tcp-max-port {
              type ios-types:acl-tcp-port-type;
            }
          }
        }
        container tcp-src-port-list {
          list source {
            description
              "Source port number";
            key "tcp-port";
            leaf tcp-port {
              type ios-types:acl-tcp-port-type;
            }
            leaf operator {
              type object-group-port-operator;
            }
          }
        }
        container tcp-src-range-port-list {
          container source {
            description
              "Source port number";
            list range {
              description
                "Match only packets in the range of port numbers";
              key "tcp-min-port tcp-max-port";
              leaf tcp-min-port {
                type ios-types:acl-tcp-port-type;
              }
              leaf tcp-max-port {
                type ios-types:acl-tcp-port-type;
              }
            }
          }
        }
        container tcp-src-dst-port-list {
          list source {
            description
              "Source port number";
            key "tcp-src-port tcp-dst-port";
            leaf src-operator {
              
              type object-group-port-operator;
            }
            leaf tcp-src-port {
              type ios-types:acl-tcp-port-type;
            }
            leaf dst-operator {
              
              type object-group-port-operator;
            }
            leaf tcp-dst-port {
              type ios-types:acl-tcp-port-type;
            }
          }
        }
        container tcp-src-range-dst-port-list {
          list source {
            description
              "Source port number";
            key "tcp-src-min-port tcp-src-max-port tcp-dst-port";
            leaf tcp-src-min-port {
              type ios-types:acl-tcp-port-type;
            }
            leaf tcp-src-max-port {
              type ios-types:acl-tcp-port-type;
            }
            leaf operator {
              
              type object-group-port-operator;
            }
            leaf tcp-dst-port {
              type ios-types:acl-tcp-port-type;
            }
          }
        }
        container tcp-src-dst-range-port-list {
          list source {
            description
              "Source port number";
            key "tcp-src-port tcp-dst-min-port tcp-dst-max-port";
            leaf operator {
              
              type object-group-port-operator;
            }
            leaf tcp-src-port {
              type ios-types:acl-tcp-port-type;
            }
            leaf tcp-dst-min-port {
              type ios-types:acl-tcp-port-type;
            }
            leaf tcp-dst-max-port {
              type ios-types:acl-tcp-port-type;
            }
          }
        }
        container tcp-src-range-dst-range-port-list {
          list source {
            description
              "Source port number";
            key "tcp-src-min-port tcp-src-max-port tcp-dst-min-port tcp-dst-max-port";
            leaf tcp-src-min-port {
              type ios-types:acl-tcp-port-type;
            }
            leaf tcp-src-max-port {
              type ios-types:acl-tcp-port-type;
            }
            leaf tcp-dst-min-port {
              type ios-types:acl-tcp-port-type;
            }
            leaf tcp-dst-max-port {
              type ios-types:acl-tcp-port-type;
            }
          }
        }
      }
    }
    container tcp-udp {
      description
        "TCP or UDP protocol";
      list tcp-udp-port-list {
        key "tcp-udp-port";
        leaf tcp-udp-port {
          type ios-types:acl-tcp-udp-port-type;
        }
        leaf operator {
          type object-group-port-operator;
        }
      }
      container tcp-udp-range-port-list {
        list range {
          description
            "Match only packets in the range of port numbers";
          key "tcp-udp-min-port tcp-udp-max-port";
          leaf tcp-udp-min-port {
            type ios-types:acl-tcp-udp-port-type;
          }
          leaf tcp-udp-max-port {
            type ios-types:acl-tcp-udp-port-type;
          }
        }
      }
      container tcp-udp-src-port-list {
        list source {
          description
            "Source port number";
          key "tcp-udp-port";
          leaf tcp-udp-port {
            type ios-types:acl-tcp-udp-port-type;
          }
          leaf operator {
            type object-group-port-operator;
          }
        }
      }
      container tcp-udp-src-range-port-list {
        container source {
          description
            "Source port number";
          list range {
            description
              "Match only packets in the range of port numbers";
            key "tcp-udp-min-port tcp-udp-max-port";
            leaf tcp-udp-min-port {
              type ios-types:acl-tcp-udp-port-type;
            }
            leaf tcp-udp-max-port {
              type ios-types:acl-tcp-udp-port-type;
            }
          }
        }
      }
      container tcp-udp-src-dst-port-list {
          list source {
          description
            "Source port number";
          key "tcp-udp-src-port tcp-udp-dst-port";
          leaf src-operator {
            
            type object-group-port-operator;
          }
          leaf tcp-udp-src-port {
            type ios-types:acl-tcp-udp-port-type;
          }
          leaf dst-operator {
            
            type object-group-port-operator;
          }
          leaf tcp-udp-dst-port {
            type ios-types:acl-tcp-udp-port-type;
          }
        }
      }
      container tcp-udp-src-range-dst-port-list {
        list source {
          description
            "Source port number";
          key "tcp-udp-src-min-port tcp-udp-src-max-port tcp-udp-dst-port";
          leaf tcp-udp-src-min-port {
            type ios-types:acl-tcp-udp-port-type;
          }
          leaf tcp-udp-src-max-port {
            type ios-types:acl-tcp-udp-port-type;
          }
          leaf operator {
            
            type object-group-port-operator;
          }
          leaf tcp-udp-dst-port {
            type ios-types:acl-tcp-udp-port-type;
          }
        }
      }
      container tcp-udp-src-dst-range-port-list {
        list source {
          description
            "Source port number";
          key "tcp-udp-src-port tcp-udp-dst-min-port tcp-udp-dst-max-port";
          leaf operator {
            
            type object-group-port-operator;
          }
          leaf tcp-udp-src-port {
            type ios-types:acl-tcp-udp-port-type;
          }
          leaf tcp-udp-dst-min-port {
            type ios-types:acl-tcp-udp-port-type;
          }
          leaf tcp-udp-dst-max-port {
            type ios-types:acl-tcp-udp-port-type;
          }
        }
      }
      container tcp-udp-src-range-dst-range-port-list {
        list source {
          description
            "Source port number";
          key "tcp-udp-src-min-port tcp-udp-src-max-port tcp-udp-dst-min-port tcp-udp-dst-max-port";
          leaf tcp-udp-src-min-port {
            type ios-types:acl-tcp-udp-port-type;
          }
          leaf tcp-udp-src-max-port {
            type ios-types:acl-tcp-udp-port-type;
          }
          leaf tcp-udp-dst-min-port {
            type ios-types:acl-tcp-udp-port-type;
          }
          leaf tcp-udp-dst-max-port {
            type ios-types:acl-tcp-udp-port-type;
          }
        }
      }
    }
    leaf udp {
      type empty;
    }
    container udp-conf {
      container udp {
        description
          "User Datagram Protocol";
        list udp-port-list {
          key "udp-port";
          leaf udp-port {
            type ios-types:acl-udp-port-type;
          }
          leaf operator {
            type object-group-port-operator;
          }
        }
        container udp-range-port-list {
          list range {
            description
              "Match only packets in the range of port numbers";
            key "udp-min-port udp-max-port";
            leaf udp-min-port {
              type ios-types:acl-udp-port-type;
            }
            leaf udp-max-port {
              type ios-types:acl-udp-port-type;
            }
          }
        }
        container udp-src-port-list {
          list source {
            description
              "Source port number";
            key "udp-port";
            leaf udp-port {
              type ios-types:acl-udp-port-type;
            }
            leaf operator {
              type object-group-port-operator;
            }
          }
        }
        container udp-src-range-port-list {
          container source {
            description
              "Source port number";
            list range {
              description
                "Match only packets in the range of port numbers";
              key "udp-min-port udp-max-port";
              leaf udp-min-port {
                type ios-types:acl-udp-port-type;
              }
              leaf udp-max-port {
                type ios-types:acl-udp-port-type;
              }
            }
          }
        }
        container udp-src-dst-port-list {
          list source {
            description
              "Source port number";
            key "udp-src-port udp-dst-port";
            leaf src-operator {
              
              type object-group-port-operator;
            }
            leaf udp-src-port {
              type ios-types:acl-udp-port-type;
            }
            leaf dst-operator {
              
              type object-group-port-operator;
            }
            leaf udp-dst-port {
              type ios-types:acl-udp-port-type;
            }
          }
        }
        container udp-src-range-dst-port-list {
          list source {
            description
              "Source port number";
            key "udp-src-min-port udp-src-max-port udp-dst-port";
            leaf udp-src-min-port {
              type ios-types:acl-udp-port-type;
            }
            leaf udp-src-max-port {
              type ios-types:acl-udp-port-type;
            }
            leaf operator {
              
              type object-group-port-operator;
            }
            leaf udp-dst-port {
              type ios-types:acl-udp-port-type;
            }
          }
        }
        container udp-src-dst-range-port-list {
          list source {
            description
              "Source port number";
            key "udp-src-port udp-dst-min-port udp-dst-max-port";
            leaf operator {
              
              type object-group-port-operator;
            }
            leaf udp-src-port {
              type ios-types:acl-udp-port-type;
            }
            leaf udp-dst-min-port {
              type ios-types:acl-udp-port-type;
            }
            leaf udp-dst-max-port {
              type ios-types:acl-udp-port-type;
            }
          }
        }
        container udp-src-range-dst-range-port-list {
          list source {
            description
              "Source port number";
            key "udp-src-min-port udp-src-max-port udp-dst-min-port udp-dst-max-port";
            leaf udp-src-min-port {
              type ios-types:acl-udp-port-type;
            }
            leaf udp-src-max-port {
              type ios-types:acl-udp-port-type;
            }
            leaf udp-dst-min-port {
              type ios-types:acl-udp-port-type;
            }
            leaf udp-dst-max-port {
              type ios-types:acl-udp-port-type;
            }
          }
        }
      }
    }
  }

  grouping config-object-group-grouping {
    list network {
      description
        "network group";
      key "name";
      leaf name {
        description
          "WORD;;object-group name";
        type string {
          length "1..64";
        }
      }
      container obj-Mode-config-network-group {
        list network_address {
          key "ipv4_addr ipv4_mask";
          leaf ipv4_addr {
            description
              "A.B.C.D;;Network address of the group members";
            type inet:ipv4-address;
          }
          leaf ipv4_mask {
            description
              "A.B.C.D;;Network mask";
            type inet:ipv4-address;
          }
        }
        leaf description {
          description
            "Network object group description";
          type string {
            length "1..200";
          }
        }
        leaf group-object {
          description
            "Nested object group";
          type string;
        }
        list host {
          description
            "Host address of the object-group member";
          key "ipv4-host";
          leaf ipv4-host { 
            description
              "Host address of the object-group member";
            type inet:host;
          }
        }
        container range {
          leaf ip-addr-min {
            description
              "Starting IPv4 Address";
            type inet:ipv4-address;
          }
          leaf ip-addr-max {
            description
              "Ending IPv4 Address";
            type inet:ipv4-address;
          }
        }
      }
    }
    list security {
      description
        "security group";
      key "name";
      leaf name {
        type string {
          length "1..64";
        }
      }
      container security-group {
        leaf description {
          description
            "Network object group description";
          type string {
            length "1..200";
          }
        }
        leaf group-object {
          description
            "Nested object group";
          type string;
        }
        container security-group {
          description
            "Security Group Tag";
          leaf tag {
            type uint16 {
              range "1..65535";
            }
          }
        }
      }
    }
    list service {
      description
        "service group";
      key "name";
      leaf name {
        type string {
          length "1..64";
        }
      }
      uses object-group-service-grouping;
    }
  }

  /////////////////////////////////////////////////////////
  // native / object-group
  /////////////////////////////////////////////////////////
  augment "/ios:native/ios:object-group" {
    uses config-object-group-grouping;
  }
} //module
