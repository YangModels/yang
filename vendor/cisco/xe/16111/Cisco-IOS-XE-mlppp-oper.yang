module Cisco-IOS-XE-mlppp-oper {
  yang-version 1;
  namespace "http://cisco.com/ns/yang/Cisco-IOS-XE-mlppp-oper";
  prefix mlppp-ios-xe-oper;

  import ietf-yang-types {
    prefix yang;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for mlppp operational data.
     Copyright (c) 2017-2018 by Cisco Systems, Inc.
     All rights reserved.";

  revision 2018-10-29 {
    description
      "Cleaned up spelling errors in descriptions.";
    reference "1.1.0";
  }
  revision 2018-01-01 {
    description
      "Initial revision";
    reference "1.0.0";
  }

  typedef mlppp-bundle-mode-type {
    type enumeration {
      enum "mlppp-bundle-none" {
        value 0;
        description
          "Default None";
      }
      enum "mlppp-bundle-distributed" {
        value 1;
        description
          "Distributed";
      }
      enum "mlppp-bundle-interleaved" {
        value 2;
        description
          "Interleaved";
      }
    }
    description
      "MLPPP bundle traffic is Distributed or Interleaved.";
  }

  typedef mlppp-member-type {
    type enumeration {
      enum "mlppp-member-none" {
        value 0;
        description
          "Default None";
      }
      enum "mlppp-member-active" {
        value 1;
        description
          "Active";
      }
      enum "mlppp-member-inactive" {
        value 2;
        description
          "Inactive";
      }
    }
    description
      "Authentication type for the PPP session";
  }

  grouping mlppp-link-interface-up-time {
    description
      "MLPPP bundle for the interface";
    leaf if-name {
      type string;
      description
        "Interface name";
    }
    leaf up-time {
      type yang:date-and-time;
      description
        "Interface up time";
    }
    leaf member-type {
      type mlppp-ios-xe-oper:mlppp-member-type;
      description
        "Active or Inactive";
    }
  }

  grouping mlppp-data {
    description
      "mlppp data";
    leaf if-name {
      type string;
      description
        "Interface name";
    }
    leaf bundle-name {
      type string;
      description
        "Bundle name";
    }
    leaf bundle-mode {
      type mlppp-ios-xe-oper:mlppp-bundle-mode-type;
      description
        "Bundle mode";
    }
    leaf remote-username {
      type string;
      description
        "Remote user name ";
    }
    leaf local-username {
      type string;
      description
        "Local user name ";
    }
    leaf remote-endpoint-discriminator {
      type string;
      description
        "Remote end point discriminator";
    }
    leaf local-endpoint-discriminator {
      type string;
      description
        "Local end point discriminator";
    }
    leaf bundle-uptime {
      type yang:date-and-time;
      description
        "Bundle uptime duration";
    }
    leaf total-bandwidth {
      type uint32;
      description
        "Total bandwidth in bytes";
    }
    leaf load {
      type string;
      description
        "Multilink Load";
    }
    leaf receive-buffer-limit {
      type uint32;
      description
        "Receive buffer limit in bytes";
    }
    leaf frag-timeout {
      type uint32;
      description
        "Frag timeout in milliseconds";
    }
    leaf fragment-per-byte-in-reassembly-list {
      type string;
      description
        "Fragments per bytes in reassembly list";
    }
    leaf lost-fragments {
      type uint32;
      description
        "Lost fragment counter";
    }
    leaf reordered {
      type uint32;
      description
        "Reordered counter";
    }
    leaf discarded-fragments-per-byte {
      type string;
      description
        "Discarded fragments/bytes counter";
    }
    leaf lost-received {
      type uint32;
      description
        "Lost received counter";
    }
    leaf member-links {
      type uint32;
      description
        "Member links counter";
    }
    leaf member-link-max {
      type uint32;
      description
        "Member links maximum counter";
    }
    leaf member-link-min {
      type uint32;
      description
        "Member links minimum counter";
    }
    leaf member-type {
      type mlppp-ios-xe-oper:mlppp-member-type;
      description
        "Active or Inactive";
    }
    list interface-up-time {
      max-elements "10";
      description
        "List of MLPPP member interface up time";
      uses mlppp-ios-xe-oper:mlppp-link-interface-up-time;
    }
  }

  grouping mlppp-statistics {
    description
      "MLPPP statistics type definition";
    leaf mlppp-link-at-lcp-stage {
      type uint32;
      description
        "MLPPP link at lcp stage";
    }
    leaf mlppp-link-at-unauth-name-stage {
      type uint32;
      description
        "MLPPP links at unauthenticated name stage";
    }
    leaf mlppp-link-at-auth-name-stage {
      type uint32;
      description
        "MLPPP links at authenticated name stage";
    }
    leaf mlppp-link-at-post-lcp-noauth-stage {
      type uint32;
      description
        "MLPPP links at post-lcp no auth stage";
    }
    leaf mlppp-link-at-post-lcp-callback-stage {
      type uint32;
      description
        "MLPPP links at post-lcp callback stage";
    }
    leaf mlppp-link-at-forwarded-stage {
      type uint32;
      description
        "MLPPP links at forwarded stage";
    }
    leaf mlppp-link-at-local-termination-stage {
      type uint32;
      description
        "MLPPP links at local termination stage";
    }
    leaf non-mlppp-sessions {
      type uint32;
      description
        "Non-mlppp sessions";
    }
    leaf mlppp-sessions {
      type uint32;
      description
        "MLPPP sessions ";
    }
    leaf non-mlppp-links {
      type uint32;
      description
        "Non mlppp links";
    }
    leaf mlppp-links {
      type uint32;
      description
        "MLPPP links";
    }
    leaf mlppp-authorization-failed {
      type uint32;
      description
        "MLPPP authorization filed";
    }
    leaf removing-mlppp-bundle {
      type uint32;
      description
        "Removing mlppp bundle";
    }
    leaf mlppp-requires-authen-or-caller-id {
      type uint32;
      description
        "MLPPP requires authentication or caller ID";
    }
    leaf mlppp-drop-link {
      type uint32;
      description
        "MLPPP drop link";
    }
    leaf mlppp-kill-link {
      type uint32;
      description
        "MLPPP kill link";
    }
    leaf mlppp-add-link-failed {
      type uint32;
      description
        "MLPPP add link failed";
    }
    leaf mlppp-link-not-needed {
      type uint32;
      description
        "MLPPP link not needed";
    }
  }

  container mlppp-oper-data {
    config false;
    description
      "MLPPP operational data";
    container mlppp-statistics {
      presence "mlppp-statistics";
      description
        "MLPPP statistics";
      uses mlppp-ios-xe-oper:mlppp-statistics;
    }
    list mlppp-bundle {
      key "if-name";
      description
        "MLPPP data entry table";
      uses mlppp-ios-xe-oper:mlppp-data;
    }
  }
}
