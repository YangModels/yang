module Cisco-IOS-XE-crypto-oper {
  yang-version 1;
  namespace "http://cisco.com/ns/yang/Cisco-IOS-XE-crypto-oper";
  prefix crypto-ios-xe-oper;

  import ietf-inet-types {
    prefix inet;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for crypto operational data.
     Copyright (c) 2018-2019 by Cisco Systems, Inc.
     All rights reserved.";

  revision 2018-12-18 {
    description
      "Initial revision";
    reference "1.0.0";
  }

  typedef crypto-dir-type {
    type enumeration {
      enum "crypto-dir-inbound" {
        value 0;
        description
          "Inbound direction";
      }
      enum "crypto-dir-outbound" {
        value 1;
        description
          "Outbound direction";
      }
    }
    description
      "Traffic direction";
  }

  typedef crypto-prot-type {
    type enumeration {
      enum "crypto-prot-esp" {
        value 0;
        description
          "ESP protocol";
      }
      enum "crypto-prot-ah" {
        value 1;
        description
          "AH protocol";
      }
      enum "crypto-prot-pcp" {
        value 2;
        description
          "PCP protocol";
      }
    }
    description
      "Crypto Protocol Type";
  }

  typedef crypto-dh-group-type {
    type enumeration {
      enum "crypto-dh-grouptype-none" {
        value 0;
        description
          "No DH Group";
      }
      enum "crypto-dh-grouptype-group1" {
        value 1;
        description
          "DH group 1";
      }
      enum "crypto-dh-grouptype-group2" {
        value 2;
        description
          "DH group 2";
      }
      enum "crypto-dh-grouptype-group3" {
        value 3;
        description
          "DH group 3";
      }
      enum "crypto-dh-grouptype-group4" {
        value 4;
        description
          "DH group 4";
      }
      enum "crypto-dh-grouptype-group5" {
        value 5;
        description
          "DH group 5";
      }
      enum "crypto-dh-grouptype-group14" {
        value 6;
        description
          "DH group 14";
      }
      enum "crypto-dh-grouptype-group15" {
        value 7;
        description
          "DH group 15";
      }
      enum "crypto-dh-grouptype-group16" {
        value 8;
        description
          "DH group 16";
      }
      enum "crypto-dh-grouptype-group19" {
        value 9;
        description
          "DH group 19";
      }
      enum "crypto-dh-grouptype-group20" {
        value 10;
        description
          "DH group 20";
      }
      enum "crypto-dh-grouptype-group21" {
        value 11;
        description
          "DH group 21";
      }
      enum "crypto-dh-grouptype-group24" {
        value 12;
        description
          "DH group 24";
      }
    }
    description
      "DH group type";
  }

  typedef crypto-sa-status {
    type enumeration {
      enum "crypto-ipsec-sa-status-down" {
        value 0;
        description
          "IPSEC SA is down";
      }
      enum "crypto-sa-status-active" {
        value 1;
        description
          "SA is active";
      }
      enum "crypto-sa-status-standby" {
        value 2;
        description
          "SA is standby";
      }
      enum "crypto-sa-status-pending" {
        value 3;
        description
          "SA is pending";
      }
    }
    description
      "SA status";
  }

  typedef crypto-hash-alg {
    type enumeration {
      enum "crypto-hash-alg-auth-none" {
        value 0;
        description
          "No Hash";
      }
      enum "crypto-hash-alg-auth-hmac-md5-96" {
        value 1;
        description
          "Hash hmac md5";
      }
      enum "crypto-hash-alg-auth-hmac-sha1-96" {
        value 2;
        description
          "Hash hmac sha1 96";
      }
      enum "crypto-hash-alg-auth-hmac-des" {
        value 3;
        description
          "Hash hmac des";
      }
      enum "crypto-hash-alg-auth-kpdk-md5" {
        value 4;
        description
          "Hash hmac kpdk md5";
      }
      enum "crypto-hash-alg-auth-hmac-aes-xcbc-96" {
        value 5;
        description
          "Hash hmac aes xcbc 96";
      }
      enum "crypto-hash-alg-auth-hmac-sha256" {
        value 6;
        description
          "Hash hmac sha256";
      }
      enum "crypto-hash-alg-auth-hmac-sha384" {
        value 7;
        description
          "Hash hmac sha384";
      }
      enum "crypto-hash-alg-auth-hmac-sha512" {
        value 8;
        description
          "Hash hmac sha512";
      }
    }
    description
      "HASH algorithm";
  }

  typedef crypto-auth-method {
    type enumeration {
      enum "crypto-auth-no-method" {
        value 0;
        description
          "IKEV2 No Authentication Method";
      }
      enum "crypto-ikev2-auth-rsa-sig" {
        value 1;
        description
          "IKEv2 Authentication type RSA-SIG";
      }
      enum "crypto-ikev2-auth-psk" {
        value 2;
        description
          "IKEv2 Authentication type PSK";
      }
      enum "crypto-ikev2-auth-dss" {
        value 3;
        description
          "IKEv2 Authentication type DSS";
      }
      enum "crypto-ikev2-auth-ecdsa-256" {
        value 4;
        description
          "IKEv2 Authentication type ECDSA 256";
      }
      enum "crypto-ikev2-auth-ecdsa-384" {
        value 5;
        description
          "IKEv2 Authentication type ECDSA 384";
      }
      enum "crypto-ikev2-auth-anyconnect-eap" {
        value 6;
        description
          "IKEv2 Authentication type AnyConnect EAP";
      }
      enum "crypto-ikev2-auth-eap" {
        value 7;
        description
          "IKEv2 Authentication type EAP";
      }
    }
    description
      "IKEv2 Authentication Method";
  }

  typedef crypto-encryption-alg {
    type enumeration {
      enum "crypto-encr-alg-none" {
        value 0;
        description
          "No Encryption";
      }
      enum "crypto-encr-alg-des-iv64" {
        value 1;
        description
          "Encryption DES IV64";
      }
      enum "crypto-encr-alg-des" {
        value 2;
        description
          "Encryption DES";
      }
      enum "crypto-encr-alg-3des" {
        value 3;
        description
          "Encryption 3DES";
      }
      enum "crypto-encr-alg-rc5" {
        value 4;
        description
          "Encryption RC5";
      }
      enum "crypto-encr-alg-idea" {
        value 5;
        description
          "Encryption IDEA";
      }
      enum "crypto-encr-alg-cast" {
        value 6;
        description
          "Encryption CAST";
      }
      enum "crypto-encr-alg-blowfish" {
        value 7;
        description
          "Encryption BLOWFISH";
      }
      enum "crypto-encr-alg-3idea" {
        value 8;
        description
          "Encryption 3IDEA";
      }
      enum "crypto-encr-alg-iv32" {
        value 9;
        description
          "Encryption IV32";
      }
      enum "crypto-encr-alg-rc4" {
        value 10;
        description
          "Encryption RC4";
      }
      enum "crypto-encr-alg-null" {
        value 11;
        description
          "Encryption Null";
      }
      enum "crypto-encr-alg-aes-cbc" {
        value 12;
        description
          "Encryption AES CBC";
      }
      enum "crypto-encr-alg-aes-ctr" {
        value 13;
        description
          "Encryption AES CTR";
      }
      enum "crypto-encr-alg-aes-gcm" {
        value 14;
        description
          "Encryption AES GCM";
      }
      enum "crypto-encr-alg-aes-gmac" {
        value 15;
        description
          "Encryption AES GMAC";
      }
    }
    description
      "Encryption algorithm";
  }

  typedef crypto-transform-options {
    type bits {
      bit crypto-transform-ah-hmac-sha {
        position 0;
        description
          "AH-HMAC-SHA";
      }
      bit crypto-transform-ah-hmac-sha256 {
        position 1;
        description
          "AH-HMAC-SHA-256";
      }
      bit crypto-transform-ah-hmac-sha384 {
        position 2;
        description
          "AH-HMAC-SHA-384";
      }
      bit crypto-transform-ah-hmac-sha512 {
        position 3;
        description
          "AH-HMAC-SHA-512";
      }
      bit crypto-transform-ah-hmac-md5 {
        position 4;
        description
          "AH-HMAC-MD5";
      }
      bit crypto-transform-esp-des {
        position 5;
        description
          "ESP-DES";
      }
      bit crypto-transform-esp-3-des {
        position 6;
        description
          "ESP-3DES";
      }
      bit crypto-transform-esp-seal {
        position 7;
        description
          "ESP-SEAL";
      }
      bit crypto-transform-esp-aes-cbc {
        position 8;
        description
          "ESP-AES-CBC";
      }
      bit crypto-transform-esp-aes-cbc-192 {
        position 9;
        description
          "ESP-AES-CBC-192";
      }
      bit crypto-transform-esp-aes-cbc-256 {
        position 10;
        description
          "ESP-AES-CBC-256";
      }
      bit crypto-transform-esp-aes-gcm {
        position 11;
        description
          "ESP-AES-GCM";
      }
      bit crypto-transform-esp-aes-gcm-192 {
        position 12;
        description
          "ESP-AES-GCM-192";
      }
      bit crypto-transform-esp-aes-gcm-256 {
        position 13;
        description
          "ESP-AES-GCM-256";
      }
      bit crypto-transform-esp-aes-gmac {
        position 14;
        description
          "ESP-AES-GMAC";
      }
      bit crypto-transform-esp-aes-gmac-192 {
        position 15;
        description
          "ESP-AES-GMAC-192";
      }
      bit crypto-transform-esp-aes-gmac-256 {
        position 16;
        description
          "ESP-AES-GMAC-256";
      }
      bit crypto-transform-esp-null {
        position 17;
        description
          "ESP-NULL";
      }
      bit crypto-transform-esp-hmac-md5 {
        position 18;
        description
          "ESP-HMAC-MD5";
      }
      bit crypto-transform-esp-hmac-sha {
        position 19;
        description
          "ESP-HMAC-SHA";
      }
      bit crypto-transform-esp-hmac-sha256 {
        position 20;
        description
          "ESP-HMAC-SHA-256";
      }
      bit crypto-transform-esp-hmac-sha384 {
        position 21;
        description
          "ESP-HMAC-SHA-384";
      }
      bit crypto-transform-esp-hmac-sha512 {
        position 22;
        description
          "ESP-HMAC-SHA-512";
      }
      bit crypto-transform-pcp-lzs {
        position 23;
        description
          "PCP-LZS";
      }
    }
    description
      "The cryptographic transform set options available in the connection";
  }

  grouping crypto-ike-sa-data {
    description
      "Crypto IKE Security Association Data";
    leaf sa-id {
      type uint32;
      description
        "IKE security association identifier";
    }
    leaf sa-status {
      type crypto-ios-xe-oper:crypto-sa-status;
      description
        "IKE security association Status";
    }
    leaf local-ip-addr {
      type inet:ip-address;
      description
        "Local IP Address";
    }
    leaf local-port {
      type uint16;
      description
        "Local Port number";
    }
    leaf remote-ip-addr {
      type inet:ip-address;
      description
        "Remote IP Address";
    }
    leaf remote-port {
      type uint16;
      description
        "Remote Port number";
    }
    leaf dh-group {
      type crypto-ios-xe-oper:crypto-dh-group-type;
      description
        "DH group";
    }
    leaf init-spi {
      type binary;
      description
        "Initiator security parameter index";
    }
    leaf resp-spi {
      type binary;
      description
        "Responder security parameter index";
    }
    leaf ivrf {
      type string;
      description
        "IKE IVRF";
    }
    leaf fvrf {
      type string;
      description
        "IKE FVRF";
    }
    leaf lifetime {
      type uint32;
      units "seconds";
      description
        "Security association lifetime";
    }
    leaf hash-algo {
      type crypto-ios-xe-oper:crypto-hash-alg;
      description
        "HASH Algorithm";
    }
    leaf encr-alg {
      type crypto-ios-xe-oper:crypto-encryption-alg;
      description
        "Encryption algorithm";
    }
    leaf my-auth-method {
      type crypto-ios-xe-oper:crypto-auth-method;
      description
        "Self authentication method";
    }
    leaf peer-auth-method {
      type crypto-ios-xe-oper:crypto-auth-method;
      description
        "Peer authentication Method";
    }
  }

  grouping crypto-ikev2-sa-entry {
    description
      "Crypto IKEV2 Security Association Entry";
    leaf sa-id {
      type uint32;
      description
        "Security association identifier";
    }
    container sa-data {
      description
        "Security association Data";
      uses crypto-ios-xe-oper:crypto-ike-sa-data;
    }
  }

  grouping crypto-ikev1-sa-entry {
    description
      "Crypto IKEV1 Security association Entry";
    leaf sa-id {
      type uint32;
      description
        "Security association identifier";
    }
    container sa-data {
      description
        "Security association Data";
      uses crypto-ios-xe-oper:crypto-ike-sa-data;
    }
  }

  grouping crypto-ipsec-sa-entry {
    description
      "Crypto IPSEC SA entry";
    leaf spi {
      type uint32;
      description
        "IPSEC SPI number";
    }
    leaf dir {
      type crypto-ios-xe-oper:crypto-dir-type;
      description
        "Traffic Direction";
    }
    leaf protocol {
      type crypto-ios-xe-oper:crypto-prot-type;
      description
        "IPSEC Protocol";
    }
    leaf flow-id {
      type uint32;
      description
        "FLow ID";
    }
    leaf sa-status {
      type crypto-ios-xe-oper:crypto-sa-status;
      description
        "IPSEC SA status";
    }
    leaf transform-set {
      type crypto-ios-xe-oper:crypto-transform-options;
      description
        "Crypto transform set";
    }
  }

  grouping crypto-ipsec-ident-data {
    description
      "Crypto IPSEC Identity Data";
    leaf protected-vrf {
      type uint32;
      description
        "Protected VRF";
    }
    leaf local-ident-addr {
      type inet:ip-address;
      description
        "Local IPSEC Identity Address";
    }
    leaf local-ident-mask {
      type inet:ip-address;
      description
        "Local IPSEC Identity Mask";
    }
    leaf local-ident-protocol {
      type uint32;
      description
        "Local IPSEC Identity Protocol";
    }
    leaf remote-ident-addr {
      type inet:ip-address;
      description
        "Remote IPSEC Identity Address";
    }
    leaf remote-ident-mask {
      type inet:ip-address;
      description
        "Remote IPSEC Identity Mask";
    }
    leaf remote-ident-protocol {
      type uint32;
      description
        "Remote IPSEC Identity Protocol";
    }
    leaf plaintext-mtu {
      type uint16;
      description
        "Plain text MTU value";
    }
    leaf local-endpt-addr {
      type inet:ip-address;
      description
        "Local Endpoint Address";
    }
    leaf remote-endpt-addr {
      type inet:ip-address;
      description
        "Remote Endpoint Address";
    }
    leaf dh-group {
      type crypto-ios-xe-oper:crypto-dh-group-type;
      description
        "DH group";
    }
    container inbound-esp-sa {
      description
        "Inbound ESP SA";
      uses crypto-ios-xe-oper:crypto-ipsec-sa-entry;
    }
    container inbound-ah-sa {
      description
        "Inbound AH SA";
      uses crypto-ios-xe-oper:crypto-ipsec-sa-entry;
    }
    container inbound-pcp-sa {
      description
        "Inbound PCP SA";
      uses crypto-ios-xe-oper:crypto-ipsec-sa-entry;
    }
    container outbound-esp-sa {
      description
        "Outbound ESP SA";
      uses crypto-ios-xe-oper:crypto-ipsec-sa-entry;
    }
    container outbound-ah-sa {
      description
        "Outbound AH SA";
      uses crypto-ios-xe-oper:crypto-ipsec-sa-entry;
    }
    container outbound-pcp-sa {
      description
        "Outbound PCP SA";
      uses crypto-ios-xe-oper:crypto-ipsec-sa-entry;
    }
  }

  grouping crypto-ipsec-ident-entry {
    description
      "Crypto IPSEC Identity Entry";
    leaf interface {
      type string;
      description
        "Interface";
    }
    container ident-data {
      description
        "IPSEC Identity Data";
      uses crypto-ios-xe-oper:crypto-ipsec-ident-data;
    }
  }

  container crypto-oper-data {
    config false;
    description
      "crypto operatinal data";
    list crypto-ipsec-ident {
      key "interface";
      description
        "Crypto IPSEC Identity Entry";
      uses crypto-ios-xe-oper:crypto-ipsec-ident-entry;
    }
    list crypto-ikev2-sa {
      key "sa-id";
      description
        "Crypto IKEv2 SA Entry";
      uses crypto-ios-xe-oper:crypto-ikev2-sa-entry;
    }
    list crypto-ikev1-sa {
      key "sa-id";
      description
        "Crypto IKEv1 SA Entry";
      uses crypto-ios-xe-oper:crypto-ikev1-sa-entry;
    }
  }
}
