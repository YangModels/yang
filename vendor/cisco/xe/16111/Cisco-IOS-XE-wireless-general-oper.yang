module Cisco-IOS-XE-wireless-general-oper {
  yang-version 1;
  namespace "http://cisco.com/ns/yang/Cisco-IOS-XE-wireless-general-oper";
  prefix wireless-general-oper;

  import ietf-inet-types {
    prefix inet;
  }
  import ietf-yang-types {
    prefix yang;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for general operational data.
     Copyright (c) 2017 by Cisco Systems, Inc.
     All rights reserved.";

  revision 2018-09-04 {
    description
      "Initial revision";
    reference "1.0.0";
  }

  grouping st-wlmgmt-ipv6 {
    description
      "Controller management interface IPv6 information";
    leaf addr {
      type inet:ip-prefix;
      description
        "Controller management interface IPv6 prefix";
    }
  }

  grouping st-wlmgmt-intf {
    description
      "Controller management interface information";
    leaf intf-name {
      type string;
      description
        "Controller management interface name";
    }
    leaf intf-type {
      type string;
      description
        "Controller management interface type";
    }
    leaf intf-id {
      type uint32;
      description
        "Controller management interface id";
    }
    leaf mgmt-ip {
      type inet:ipv4-address;
      description
        "Controller management IPv4 address";
    }
    leaf net-mask {
      type inet:ipv4-address;
      description
        "Controller management interface netmask";
    }
    leaf mgmt-mac {
      type yang:mac-address;
      description
        "Controller management interface MAC";
    }
    list interface-ipv6-list {
      key "addr";
      description
        "Controller management interface IPv6 information";
      uses wireless-general-oper:st-wlmgmt-ipv6;
    }
  }

  container general-oper-data {
    config false;
    description
      "Controller general operational data";
    container mgmt-intf-data {
      presence "mgmt-intf-data";
      description
        "Controller wireless interface data";
      uses wireless-general-oper:st-wlmgmt-intf;
    }
  }
}
