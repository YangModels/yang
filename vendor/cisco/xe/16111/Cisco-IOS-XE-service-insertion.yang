module Cisco-IOS-XE-service-insertion {
  namespace "http://cisco.com/ns/yang/Cisco-IOS-XE-service-insertion";
  prefix ios-service-insertion;

  import ietf-inet-types {
    prefix inet;
  }


  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Service Insertion Yang model.
     Copyright (c) 2016, 2018 by Cisco Systems, Inc.
     All rights reserved.";

  // =========================================================================
  // REVISION
  // =========================================================================
  revision 2019-12-14 {
    description
      "Added service controller type appqoe: Application Quality Of Experience";
  }
 
  revision 2017-02-07 {
    description
      "Initial revision";
  }

  grouping config-service-insertion-grouping {
    leaf acg-reload-delay {
      description
        "Reload delay timer for ACG";
      type uint16 {
        range "120..450";
      }
    }
    list appnav-controller-group {
      description
        "AppNav Controller Group";
      key "group-name";
      leaf group-name {
        type string;
      }
      leaf-list appnav-controller {
        description
          "AppNav controller";
        type inet:ipv4-address;
      }
      leaf description {
        description
          "ACG description";
        type string;
      }
    }
    container service-context {
      description
        "Service Context";
      list waas {
        description
          "Service controller waas";
        
        key "name";
        leaf name {
          type string;
        }
        leaf appnav-controller-group {
          description
            "AppNav Controller Group";
          type string;
        }
        container authentication {
          description
            "Authentication key";
          leaf sha1 {
            description
              "Authentication type";
            type empty;
          }
          leaf key {
            description
              "Authentication Key";
            type empty;
          }
          leaf encrypt {
            type enumeration {
              enum "0";
              enum "7";
            }
          }
          leaf string {
            type string;
          }
        }
        leaf service-node-group {
          description
            "service node Group";
          type string;
        }
        leaf service-policy {
          description
            "Specify a service policy for the service context";
          type string;
        }
	leaf enable {
	  description
            "service context enable";
	  type empty;
	}
        container vrf {
          description
            "VRF";
          leaf default {
            description
              "default";
            type empty;
          }
          leaf global {
            description
              "global";
            type empty;
          }
          leaf name {
            description
              "vrf name";
            type string;
          }
        }
      }
      list appqoe {
        description
          "Service controller appqoe";
        
        key "name";
        leaf name {
          type string;
        }
        leaf appnav-controller-group {
          description
            "AppNav Controller Group";
          type string;
        }
        container authentication {
          description
            "Authentication key";
          leaf sha1 {
            description
              "Authentication type";
            type empty;
          }
          leaf key {
            description
              "Authentication Key";
            type empty;
          }
          leaf encrypt {
            type enumeration {
              enum "0";
              enum "7";
            }
          }
          leaf string {
            type string;
          }
        }
        leaf service-node-group {
          description
            "service node Group";
          type string;
        }
        leaf service-policy {
          description
            "Specify a service policy for the service context";
          type string;
        }
	leaf enable {
	  description
            "service context enable";
	  type empty;
	}
        container vrf {
          description
            "VRF";
          leaf default {
            description
              "default";
            type empty;
          }
          leaf global {
            description
              "global";
            type empty;
          }
          leaf name {
            description
              "vrf name";
            type string;
          }
        }
      }
    }
    list service-node-group {
      description
        "service node Group";
      key "name";
      leaf name {
        type string;
      }
      leaf description {
        description
          "Group Description";
        type string;
      }
      leaf node-discovery {
        description
          "service node auto discovery";
        type enumeration {
          enum "enable-nd";
        }
      }
      leaf-list service-node {
        description
          "service node";
        type inet:ipv4-address;
      }
    }
    container swap {
      description
        "Swap src-ip";
      leaf src-ip {
        description
          "Swap source-ip of service-insertion packets";
        type empty;
      }
    }
  }

  /////////////////////////////////////////////////////////
  // native / service-insertion
  /////////////////////////////////////////////////////////
  augment "/ios:native/ios:service-insertion" {
    uses config-service-insertion-grouping;
  }
}
