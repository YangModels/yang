module Cisco-IOS-XE-rip {
  namespace "http://cisco.com/ns/yang/Cisco-IOS-XE-rip";
  prefix ios-rip;

  import ietf-inet-types {
    prefix inet;
  }


  import Cisco-IOS-XE-types {
    prefix ios-types;
  }

  import Cisco-IOS-XE-native {
    prefix ios;
  }

  import Cisco-IOS-XE-interface-common {
    prefix ios-ifc;
  }

  import Cisco-IOS-XE-bgp {
    prefix ios-bgp;
  }

  import Cisco-IOS-XE-eigrp {
    prefix ios-eigrp;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Routing Information Protocol (RIP) Yang model.
     Copyright (c) 2016-2017 by Cisco Systems, Inc.
     All rights reserved.";

  // =========================================================================
  // REVISION
  // =========================================================================
  revision 2019-01-22 {
     description
      "Added leaf for App-hosting Gigabit Ethernet interface";
  }
  revision 2018-09-20 {
     description
       "Changed to leafref for interface ip rip id from type string";
  }
  revision 2018-06-28 {
     description
       "Added must constraints for deleting vrf";
  }

  revision 2017-11-27 {
     description
       "Added Change 25GE name";
  }

  revision 2017-11-14 {
    description
      "This revision has changes for new 40 and 100GE interface addition";
  }

  revision 2017-09-15 {
    description
      "This revision has changes for new 2gig interface addition";
  }
  revision 2017-08-16 {
    description
      "This revision has changes for new 5gig and 25gig interfaces addition";
  }

  revision 2017-04-12 {
    description
      "Send ipv6 rip vrf-mode enable before address-family in ipv6 router rip";
  }
  revision 2017-02-07 {
    description
      "Initial revision";
  }

  typedef default-access-list-id-type {
    type union {
      type uint32 {
        range "1 .. 199";
      }
      type uint32 {
        range "1300 .. 2699";
      }
    }
  }

  typedef access-list-id-type {
    type union {
      type default-access-list-id-type;
      type string {
        pattern "[a-zA-Z].*";
      }
    }
  }

  typedef default-offset-list-id-type {
    type union {
      type uint32 {
        range "0 .. 99";
      }
      type uint32 {
        range "1300 .. 1999";
      }
    }
  }

  typedef offset-list-id-type {
    type union {
      type default-offset-list-id-type;
      type string {
        pattern "[a-zA-Z].*";
      }
    }
  }
  typedef offset-list-in-out-type {
    type enumeration {
      enum "in";
      enum "out";
    }
  }

  grouping distribute-list-grouping {
    container distribute-list {
      description
        "Filter networks in routing updates";
      list accesslist {
        key "in-out";
        leaf in-out {
          type ios-types:access-list-in-out-type;
        }
      }
      list accesslist-ifname {
        key "in-out interface";
        leaf in-out {
          type ios-types:access-list-in-out-type;
        }
        leaf interface {
          // Note: interface name must be type string since part of key
          type string;
        }
        leaf interface-routing-id {
          type uint8;
        }
        leaf isis-tag {
          type string;
        }
        leaf vrf {
          description
            "VPN Routing/Forwarding Instance";
          type string;
        }
      }
      list accesslist-prefix-gateway {
        key "in-out";
        leaf in-out {
          type ios-types:access-list-in-out-type;
        }
        leaf prefix-gateway {
          mandatory true;
          type enumeration {
            enum "prefix";
            enum "gateway";
            enum "route-map";
          }
        }
        leaf name {
          mandatory true;
          type string;
        }
      }
      list accesslist-prefix-gateway-ifname {
        key "in-out interface";
        leaf in-out {
          type ios-types:access-list-in-out-type;
        }
        leaf interface {
          type string;
        }
        leaf prefix-gateway {
          mandatory true;
          type enumeration {
            enum "prefix";
            enum "gateway";
            enum "route-map";
          }
        }
        leaf name {
          mandatory true;
          type string;
        }
        leaf interface-routing-id {
          type uint8;
        }
        leaf isis-tag {
          type string;
        }
        leaf vrf {
          description
            "VPN Routing/Forwarding Instance";
          type string;
        }
      }
    }
  }

  grouping router-rip-grouping {
    uses address-family-vrf-grouping;
    leaf flash-update-threshold {
      description
        "Specify flash update threshold in second";
      type uint8 {
        range "0 .. 30";
      }
    }
    leaf input-queue {
      description
        "Specify input queue depth";
      type uint16 {
        range "0 .. 1024";
      }
    }
    leaf output-delay {
      description
        "Interpacket delay for RIP updates";
      type uint8 {
        range "8 .. 50";
      }
    }
    uses ios-ifc:passive-interface-grouping;
    container traffic-share {
      description
        "How to compute traffic share over alternate paths";
      container min {
        description
          "All traffic shared among min metric paths";
        leaf across-interfaces {
          description
            "Use different interfaces for equal-cost paths";
          type empty;
        }
      }
    }
  }

  grouping default-redistribute-grouping {
    container connected {
      presence "Connected";
      description
        "Connected";
      uses rip-metric-route-map-grouping;
    }
    list bgp {
      description
        "Border Gateway Protocol (BGP)";
      key "as-number";
      leaf as-number {
        type ios-types:bgp-as-number-type;
      }
      uses rip-metric-route-map-grouping;
    }
    list eigrp {
      description
        "Enhanced Interior Gateway Routing Protocol (EIGRP)";
      key "as-number";
      leaf as-number {
        type uint16 {
          range "1 .. 65535";
        }
      }
      uses rip-metric-route-map-grouping;
    }
    container isis {
      presence "ISO IS-IS";
      description
        "ISO IS-IS";
      list isis-area {
        key "name";
        leaf name {
          type string;
        }
        uses redist-isis-grouping;
      }
      uses redist-isis-grouping;
    }
    container iso-igrp {
      presence "IGRP for OSI networks";
      description
        "IGRP for OSI networks";
      list isoigrp-list {
        description
          "Border Gateway Protocol (BGP)";
        key "iso-area-tag";
        leaf iso-area-tag {
          type string;
        }
        uses rip-iso-igrp-metric-route-map-grouping;
      }
      uses rip-iso-igrp-metric-route-map-grouping;
    }
    container mobile {
      presence "Mobile routes";
      description
        "Mobile routes";
      uses rip-metric-route-map-grouping;
    }
    container odr {
      presence "On Demand stub Routes";
      description
        "On Demand stub Routes";
      uses rip-metric-route-map-grouping;
    }
    list ospf {
      description
        "Open Shortest Path First (OSPF)";
      key "process-id";
      leaf process-id {
        type uint16 {
          range "1 .. 65535";
        }
      }
      list vrf {
        description
          "VPN Routing/Forwarding Instance";
        key "name";
        leaf name {
	  must "/ios:native/ios:vrf/ios:definition[ios:name=current()] or /ios:native/ios:ip/ios:vrf[ios:name=current()]" {
	    error-message "VRF must be created 1st, deleted last";
          }
          type string;
        }
      }
      container match {
        description
          "Redistribution of OSPF routes";
        container internal {
          presence "Redistribute OSPF internal routes";
          description
            "Redistribute OSPF internal routes";
          uses rip-metric-route-map-grouping;
        }
        container external {
          description
            "Redistribute OSPF external routes";
          presence "Redistribute OSPF external routes";
          leaf external-routes {
            type ios-types:redist-ospf-external-type;
          }
          uses rip-metric-route-map-grouping;
        }
        container nssa-external {
          description
            "Redistribute OSPF NSSA external routes";
          presence "Redistribute OSPF NSSA external routes";
          leaf nssa-external-routes {
            type ios-types:redist-ospf-external-type;
          }
          uses rip-metric-route-map-grouping;
        }
      }
      uses rip-metric-route-map-grouping;
    }
    container static {
      presence "Static routes";
      description
        "Static routes";
      uses rip-metric-route-map-grouping;
    }
    container rip {
      presence "Routing Information Protocol (RIP)";
      description
        "Routing Information Protocol (RIP)";
      uses rip-metric-route-map-grouping;
    }
  }

  grouping ipv6-router-rip-redistribute-grouping {
    leaf include-connected {
      description
        "Include connected";
      type empty;
    }
    uses ios-bgp:metric-route-map-grouping;
  }

  grouping distance-grouping {
    container distance {
      description
        "Define an administrative distance";
      leaf distance-leaf {
        type uint8 {
          range "1..255";
        }
      }
      list distance-list {
        key "number ip mask";
        leaf number {
          type uint8 {
            range "1 .. 255";
          }
        }
        leaf ip {
          type inet:ipv4-address;
        }
        leaf mask {
          type inet:ipv4-address;
        }
      }
    }
  }

  grouping offset-list-grouping {
    list offset-list {
      description
        "Add or subtract offset from RIP metrics";
      key "in-out";
      leaf in-out {
        type offset-list-in-out-type;
      }
      leaf offset {
        mandatory true;
        type uint8 {
          range "0 .. 16";
        }
      }
    }
  }

  grouping default-router-rip-grouping {
    leaf auto-summary {
      description
        "Enable automatic network number summarization";
      type empty;
    }
    leaf maximum-paths {
      description
        "Forward packets over multiple paths";
      type uint8 {
        range "1 .. 32";
      }
    }
    list neighbor {
      description
        "Specify a neighbor router";
      key "ip";
      leaf ip {
        type inet:ipv4-address;
      }
    }
    list network {
      description
        "Enable routing on an IP network";
      key "ip";
      leaf ip {
        type inet:ipv4-address;
      }
    }
    leaf validate-update-source {
      description
        "Perform sanity checks against source address of routing updates";
      type boolean;
    }
  }

  grouping address-family-vrf-grouping {
    uses default-router-rip-grouping;
    container default-information {
      description
        "Control distribution of default information";
      container originate {
        presence "Distribute a default route";
        description
          "Distribute a default route";
        leaf route-map {
          description
            "Route-map reference";
          type string;
        }
      }
    }
    leaf default-metric {
      description
        "Set metric of redistributed routes";
      type uint32 {
        range "1..4294967295";
      }
    }
    uses distance-grouping;
    uses distribute-list-grouping;
    uses offset-list-grouping;
    container redistribute {
      description
        "Redistribute information from another routing protocol";
      uses rip-metric-route-map-grouping;
      uses default-redistribute-grouping;
    }
    container timers {
      description
        "Adjust routing timers";
      container basic {
        description
          "Basic routing protocol update timers";
        leaf updates {
          type uint32 {
            range "1 .. 4294967295";
          }
        }
        leaf invalid {
          type uint32 {
            range "1 .. 4294967295";
          }
        }
        leaf holddown {
          type uint32 {
            range "1 .. 4294967295";
          }
        }
        leaf flush {
          type uint32 {
            range "1 .. 4294967295";
          }
        }
        leaf sleep {
          type uint32 {
            range "1 .. 4294967295";
          }
        }
      }
    }
    leaf version {
      description
        "Set routing protocol version";
      type uint8 {
        range "1 .. 2";
      }
    }
  }

  grouping redist-isis-grouping {
    container rip-isis-redist {
      leaf isis-level-routes {
        type enumeration {
          enum "level-1";
          enum "level-2";
          enum "level-1-2";
        }
      }
      uses rip-metric-route-map-grouping;
    }
  }

  grouping rip-metric-route-map-grouping {
    container rip-metric-route-map {
      container metric {
        description
          "Metric for redistributed routes";
        choice metric-transparent-choice {
          leaf metric-value {
            description
              "Metric for redistributed routes";
            type uint32 {
              range "0 .. 16";
            }
          }
          leaf transparent {
            description
              "Transparently redistribute metric";
            type empty;
          }
        }
      }
      leaf route-map {
        description
          "Route map reference";
        type string;
      }
    }
  }

  grouping rip-iso-igrp-metric-route-map-grouping {
    container rip-metric-route-map {
      leaf route-map {
        description
          "Route map reference";
        type string;
      }
      container metric {
        description
          "Metric for redistributed routes";
        choice metric-transparent-choice {
          leaf metric-value {
            description
              "Metric for redistributed routes";
            type uint32 {
              range "0 .. 16";
            }
          }
          leaf transparent {
            description
              "Transparently redistribute metric";
            type empty;
          }
        }
      }
    }
  }

  grouping ipv6-router-rip-grouping {
      leaf distance {
        description
          "Administrative distance";
        type uint8 {
          range "1..254";
        }
      }
      uses ios-eigrp:ipv6-router-distribute-list-grouping;
      leaf maximum-paths {
        description
          "Forward packets over multiple paths";
        type uint32 {
          range "1..32";
        }
      }
      leaf poison-reverse {
        description
          "Poison reverse updates";
        type empty;
      }
      container redistribute {
        description
          "Redistribute IPv6 prefixes from another routing protocol";
        container application {
          description
            "Application Protocol";
          uses ipv6-router-rip-redistribute-grouping;
        }
        container lisp {
          description
            "Locator ID Separation Protocol (LISP)";
          uses ipv6-router-rip-redistribute-grouping;
        }
        container nd {
          description
            "Neighbor Discovery";
          uses ipv6-router-rip-redistribute-grouping;
        }
        uses default-redistribute-grouping;
      }
      leaf split-horizon {
        description
          "Split horizon updates";
        type empty;
      }
      container timers {
        description
          "Adjust routing timers";
        leaf update {
          description
            "Update period";
          type uint16 {
            range "5..65535";
          }
        }
        leaf timeout {
          description
            "Route timeout period";
          type uint16 {
            range "1..65535";
          }
        }
        leaf holddown {
          description
            "Route holddown period";
          type uint16 {
            range "0..65535";
          }
        }
        leaf garbage-collection {
          description
            "Route garbage collection period";
          type uint16 {
            range "1..65535";
          }
        }
      }
  }
  grouping config-ipv6-router-rip-grouping {
    list rip {
      description
        "IPv6 Routing Information Protocol (RIPv6)";
      key "id";
      leaf id {
        type string;
      }
      container address-family {
        description
          "Enter Address Family command mode";
        container ipv6 {
          description
            "Address family";
          list vrf {
            description
              "Specify parameters for a VPN Routing/Forwarding instance";
            key "name";
            leaf name {
	      must "/ios:native/ios:vrf/ios:definition[ios:name=current()] or /ios:native/ios:ip/ios:vrf[ios:name=current()]" {
	        error-message "VRF must be created 1st, deleted last";
              }
              type string;
            }
            uses ipv6-router-rip-grouping;
          }
        }
      }
      uses ipv6-router-rip-grouping;
    }
  }

  grouping config-router-rip-grouping {
    container rip { //69810
      presence true;
      description
        "Routing Information Protocol (RIP)";

      uses router-rip-grouping;
      container address-family {
        description
          "Enter Address Family command mode";
        container ipv4 {
          description
            "Address family";
          container unicast {
            uses router-rip-grouping;
          }
          list vrf {
            description
              "Specify parameters for a VPN Routing/Forwarding instance";
            key "name";
            leaf name {
	      must "/ios:native/ios:vrf/ios:definition[ios:name=current()] or /ios:native/ios:ip/ios:vrf[ios:name=current()]" {
	        error-message "VRF must be created 1st, deleted last";
              }
              type string;
            }
            uses address-family-vrf-grouping;
          }
        }
      }
      container default {
        description
          "Set a command to its defaults";
        container address-family {
          description
            "Enter Address Family command mode";
          container ipv4 {
            presence "true";
            description
              "Address family";
            leaf unicast {
              description
                "Address Family Modifier";
              type empty;
            }
            list vrf {
              description
                "Specify parameters for a VPN Routing/Forwarding instance";
              key "name";
              leaf name {
	        must "/ios:native/ios:vrf/ios:definition[ios:name=current()] or /ios:native/ios:ip/ios:vrf[ios:name=current()]";
                type string;
              }
            }
          }
        }
        uses default-router-rip-grouping;
        container default-information {
          description
            "Control distribution of default information";
          leaf originate {
            description
              "Distribute a default route";
            type empty;
          }
        }
        leaf default-metric {
          description
            "Set metric of redistributed routes";
          type empty;
        }
        uses distance-grouping;
        uses distribute-list-grouping;
        leaf flash-update-threshold {
          description
            "Specify flash update threshold in second";
          type empty;
        }
        leaf input-queue {
          description
            "Specify input queue depth";
          type empty;
        }
        uses offset-list-grouping;
        leaf output-delay {
          description
            "Interpacket delay for RIP updates";
          type empty;
        }
        uses ios-ifc:passive-interface-grouping;
        container redistribute {
          description
            "Redistribute information from another routing protocol";
          uses default-redistribute-grouping;
        }
        container timers {
          description
            "Adjust routing timers";
          leaf basic {
            description
              "Basic routing protocol update timers";
            type empty;
          }
        }
        container traffic-share {
          description
            "How to compute traffic share over alternate paths";
          container min {
            description
              "All traffic shared among min metric paths";
            leaf across-interfaces {
              description
                "Use different interfaces for equal-cost paths";
              type empty;
            }
          }
        }
        leaf version {
          description
            "Set routing protocol version";
          type empty;
        }
      }
    }
  }

  grouping config-interface-ip-rip-grouping {
    list rip {
      description
        "Configure RIP routing protocol";
      key "id";
      leaf id {
        type leafref {
	  path "/ios:native/ios:ipv6/ios:router/ios-rip:rip/ios-rip:id";
        }
      }
      leaf enable {
        description
          "Enable/disable RIP routing";
        type empty;
      }
      container default-information {
        description
          "Configure handling of default route";
        leaf route {
          type enumeration {
            enum "only";
            enum "originate";
          }
        }
        leaf metric {
          description
            "Default route metric";
          type uint8 {
            range "1..15";
          }
        }
      }
    }
  }

  grouping config-ipv6-rip-grouping {
    container rip {
      description
        "Configure ipv6 RIP settings";
      leaf vrf-mode {
        description
          "Enable RIPng VRF support";
        type enumeration {
          enum "enable";
        }
      }
    }
  }

  /////////////////////////////////////////////////////////
  // native / router / rip
  /////////////////////////////////////////////////////////
  augment "/ios:native/ios:router" {
    uses config-router-rip-grouping;
  }

  /////////////////////////////////////////////////////////
  // native / ipv6 / rip
  /////////////////////////////////////////////////////////
  augment "/ios:native/ios:ipv6" {
    uses config-ipv6-rip-grouping;
  }

  /////////////////////////////////////////////////////////
  // native / ipv6 / router / rip
  /////////////////////////////////////////////////////////
  augment "/ios:native/ios:ipv6/ios:router" {
    uses config-ipv6-router-rip-grouping;
  }

  augment "/ios:native/ios:router/ios-rip:rip/default/distribute-list/accesslist" {
    leaf id {
      mandatory true;
      type default-access-list-id-type;
    }
  }

  augment "/ios:native/ios:router/ios-rip:rip/distribute-list/accesslist" {
    leaf id {
      mandatory true;
      type access-list-id-type;
    }
  }

  augment "/ios:native/ios:router/ios-rip:rip/default/distribute-list/accesslist-ifname" {
    leaf id {
      mandatory true;
      type default-access-list-id-type;
    }
  }

  augment "/ios:native/ios:router/ios-rip:rip/distribute-list/accesslist-ifname" {
    leaf id {
      mandatory true;
      type access-list-id-type;
    }
  }

  augment "/ios:native/ios:router/ios-rip:rip/default/distance/distance-list" {
    leaf access-list {
      type ios-types:default-access-list-standard-id-type;
    }
  }

  augment "/ios:native/ios:router/ios-rip:rip/distance/distance-list" {
    leaf access-list {
      type ios-types:access-list-standard-id-type;
    }
  }

  augment "/ios:native/ios:router/ios-rip:rip/default/offset-list" {
    leaf id {
      
      mandatory true;
      type default-offset-list-id-type;
    }
  }

  augment "/ios:native/ios:router/ios-rip:rip/offset-list" {
    leaf id {
      
      mandatory true;
      type offset-list-id-type;
    }
  }

  /////////////////////////////////////////////////////////
  // interface * ipv6 rip
  /////////////////////////////////////////////////////////
  augment "/ios:native/ios:interface/ios:FastEthernet/ios:ipv6" {
    uses config-interface-ip-rip-grouping;
  }

  augment "/ios:native/ios:interface/ios:GigabitEthernet/ios:ipv6" {
    uses config-interface-ip-rip-grouping;
  }

  augment "/ios:native/ios:interface/ios:TenGigabitEthernet/ios:ipv6" {
    uses config-interface-ip-rip-grouping;
  }

  augment "/ios:native/ios:interface/ios:FiveGigabitEthernet/ios:ipv6" {
    uses config-interface-ip-rip-grouping;
  }

  augment "/ios:native/ios:interface/ios:AppGigabitEthernet/ios:ipv6" {
    uses config-interface-ip-rip-grouping;
  }

  augment "/ios:native/ios:interface/ios:TwentyFiveGigE/ios:ipv6" {
    uses config-interface-ip-rip-grouping;
  }

  augment "/ios:native/ios:interface/ios:FortyGigabitEthernet/ios:ipv6" {
    uses config-interface-ip-rip-grouping;
  }

  augment "/ios:native/ios:interface/ios:HundredGigE/ios:ipv6" {
    uses config-interface-ip-rip-grouping;
  }

  augment "/ios:native/ios:interface/ios:TwoGigabitEthernet/ios:ipv6" {
    uses config-interface-ip-rip-grouping;
  }

  augment "/ios:native/ios:interface/ios:Port-channel/ios:ipv6" {
    uses config-interface-ip-rip-grouping;
  }

  augment "/ios:native/ios:interface/ios:Loopback/ios:ipv6" {
    uses config-interface-ip-rip-grouping;
  }

  augment "/ios:native/ios:interface/ios:Tunnel/ios:ipv6" {
    uses config-interface-ip-rip-grouping;
  }
}
