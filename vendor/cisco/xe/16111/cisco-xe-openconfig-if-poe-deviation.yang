module cisco-xe-openconfig-if-poe-deviation {
  // namespace
  namespace "http://openconfig.net/yang/cisco-xe-openconfig-if-poe-deviation";

  prefix oc-if-poe-devs;

  import openconfig-interfaces {
    prefix oc-if;
  }
  import openconfig-if-ethernet {
    prefix oc-if-eth;
  }
  import openconfig-if-poe {
    prefix oc-if-poe;
  }

  organization
    "Cisco Systems, Inc.";

  contact
    " Cisco Systems, Inc.
    Customer Service

    Postal: 170 W Tasman Drive
    San Jose, CA 95134

    Tel: +1 1800 553-NETS

    E-mail: cs-yang@cisco.com";

  description
    "This module defines deviation statements for openconfig-if-poe module.";

  revision 2018-02-12 {
    description
      "Initial Revision";

    reference
      "RFC 6020: YANG - A Data Modeling Language for the
       Network Configuration Protocol (NETCONF)";
  }

  deviation "/oc-if:interfaces/oc-if:interface/oc-if-eth:ethernet" +
            "/oc-if-poe:poe/oc-if-poe:config" {
      deviate not-supported;
      description
        "We do not support poe config on the IOS XE devices.";
  }
}
