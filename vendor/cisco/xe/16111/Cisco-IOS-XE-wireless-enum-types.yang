module Cisco-IOS-XE-wireless-enum-types {
  yang-version 1;
  namespace "http://cisco.com/ns/yang/Cisco-IOS-XE-wireless-enum-types";
  prefix wireless-enum-types;

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for wireless common enum types.
     Copyright (c) 2016-2019 by Cisco Systems, Inc.
     All rights reserved.";

  revision 2019-02-19 {
    description
      "- Added new enum for Channel switch mode
       - Change EoGRE enum
       - Added support for Flex recovery (FT) EoGRE matching enum
       - Added support for secondary 80 channel for 80+80 MHz Channel width
       - Added enum for dot11ax MCS rate index
       - Cleaned up spelling errors in descriptions
       - Changed eogre-client-match-v2 to a clearer eogre-client-match-reason
       - Added new enum for NDP data type
       - Added enum for RRM channel change type
       - New enum showing if a wired vlan is associated to Guest-LAN profile
       - Added enum for DCA threshold and Data rate threshold of Optimized Roaming
       - Added new enum for Radio's neighbor channel width";
    reference "3.0.0";
  }
  revision 2018-05-18 {
    description
      "Removed enumerations for sip codec support";
    reference "2.2.0";
  }
  revision 2018-03-22 {
    description
      "Add enum for multicast support";
    reference "2.1.0";
  }
  revision 2018-01-24 {
    description
      "The first generally available version";
    reference "2.0.0";
  }
  revision 2017-05-05 {
    description
      "Initial revision";
    reference "1.0.0";
  }

  typedef apf-vap-p2p-blocking-action {
    type enumeration {
      enum "p2p-blocking-action-none" {
        value 0;
        description
          "This object specifies the Enable peer-to-peer blocking and set the action to None";
      }
      enum "p2p-blocking-action-fwdup" {
        value 1;
        description
          "This object specifies the Enable peer-to-peer blocking and set the action to Forward-Upstream";
      }
      enum "p2p-blocking-action-drop" {
        value 2;
        description
          "This object specifies the Enable peer-to-peer blocking and set the action to 'Drop'";
      }
    }
    description
      "Enables point to point communication - Not supported in EWLC";
  }

  typedef dot11ac-mcs-rate-index {
    type enumeration {
      enum "enm-dot11ac-mcs-idx-8" {
        value 8;
        description
          "MCS data rate for index 8";
      }
      enum "enm-dot11ac-mcs-idx-9" {
        value 9;
        description
          "MCS data rate for index 9";
      }
    }
    description
      "Enum for Dot11ac MCS Data rate index";
  }

  typedef rrm-chan-width {
    type enumeration {
      enum "rrm-channel-width-20-mhz" {
        value 20;
        description
          "Channel width 20 MHz";
      }
      enum "rrm-channel-width-40-mhz" {
        value 40;
        description
          "Channel width 40 MHz";
      }
      enum "rrm-channel-width-80-mhz" {
        value 80;
        description
          "Channel width 80 MHz";
      }
      enum "rrm-channel-width-160-mhz" {
        value 160;
        description
          "Channel width 160 MHz";
      }
      enum "rrm-channel-width-80-80-mhz" {
        value 188;
        description
          "Channel width 188 MHz";
      }
    }
    description
      "RRM channel width";
  }

  typedef radio-neighbor-chan-width {
    type enumeration {
      enum "radio-neighbor-chan-width-20-mhz" {
        value 0;
        description
          "Channel width 20 MHz";
      }
      enum "radio-neighbor-chan-width-40-mhz-above" {
        value 1;
        description
          "Channel width 40 MHz Above";
      }
      enum "radio-neighbor-chan-width-40-mhz-below" {
        value 2;
        description
          "Channel width 40 MHz Below";
      }
      enum "radio-neighbor-chan-width-80-mhz" {
        value 6;
        description
          "Channel width 80 MHz";
      }
      enum "radio-neighbor-chan-width-160-mhz" {
        value 7;
        description
          "Channel width 160 MHz";
      }
      enum "radio-neighbor-chan-width-8080-mhz" {
        value 8;
        description
          "Channel width 80+80 MHz";
      }
    }
    description
      "channel width of neighbor radio";
  }

  typedef apf-ms-data-upsd-bronze {
    type enumeration {
      enum "bk1" {
        value 0;
        description
          "Background data -1";
      }
      enum "bk2" {
        value 1;
        description
          "Background data -2";
      }
      enum "bk3" {
        value 2;
        description
          "Background data -3";
      }
      enum "bk4" {
        value 3;
        description
          "Background data -4";
      }
    }
    description
      "Enum type for data upsd bronze";
  }

  typedef apf-ms-data-upsd-silver {
    type enumeration {
      enum "be1" {
        value 0;
        description
          "Best effort data -1";
      }
      enum "be2" {
        value 1;
        description
          "Best effort data -2";
      }
      enum "be3" {
        value 2;
        description
          "Best effort data -3";
      }
      enum "be4" {
        value 3;
        description
          "Best effort data -4";
      }
    }
    description
      "Enum type for data upsd silver";
  }

  typedef apf-ms-data-upsd-gold {
    type enumeration {
      enum "vi1" {
        value 0;
        description
          "Video data -1";
      }
      enum "vi2" {
        value 1;
        description
          "Video data -2";
      }
      enum "vi3" {
        value 2;
        description
          "Video data -3";
      }
      enum "vi4" {
        value 3;
        description
          "Video data -4";
      }
    }
    description
      "Enum type for data upsd gold";
  }

  typedef apf-ms-data-upsd-platinum {
    type enumeration {
      enum "vo1" {
        value 0;
        description
          "Voice data -1";
      }
      enum "vo2" {
        value 1;
        description
          "Voice data -2";
      }
      enum "vo3" {
        value 2;
        description
          "Voice data -3";
      }
      enum "vo4" {
        value 3;
        description
          "Voice data -4";
      }
    }
    description
      "Enum type for data upsd platinum";
  }

  typedef enm-mcast-client-status {
    type enumeration {
      enum "mc-only" {
        value 0;
        description
          "MC only";
      }
      enum "mc2uc-pending" {
        value 1;
        description
          "MC-UC pending";
      }
      enum "mc2uc-allowed" {
        value 2;
        description
          "MC-UC allowed";
      }
      enum "mc2uc-deny" {
        value 3;
        description
          "MC-UC deny";
      }
      enum "re-rrc-deny" {
        value 4;
        description
          "Re RRC deny";
      }
      enum "re-rrc-demote" {
        value 5;
        description
          "Re RRC demote";
      }
      enum "mc2uc-deny-no-blacklist" {
        value 6;
        description
          "MC-UC deny no blacklist";
      }
    }
    description
      "Multicast client status";
  }

  typedef media-stream-qos {
    type enumeration {
      enum "mstream-besteffort" {
        value 0;
        description
          "best effort";
      }
      enum "mstream-background" {
        value 1;
        description
          "background";
      }
      enum "mstream-video" {
        value 4;
        description
          "This object specifies the Video QoS Over the Air";
      }
      enum "mstream-voice" {
        value 6;
        description
          "This object specifies the Voice QoS Over the Air";
      }
    }
    description
      "Specifies the type of media stream used";
  }

  typedef enm-radio-type {
    type enumeration {
      enum "radio-invalid" {
        value 0;
        description
          "Radio invalid";
      }
      enum "radio-80211bg" {
        value 1;
        description
          "Radio 80211bg";
      }
      enum "radio-80211a" {
        value 2;
        description
          "Radio 80211a";
      }
      enum "radio-80211abgn" {
        value 3;
        description
          "Radio 80211abgn";
      }
      enum "radio-uwb" {
        value 4;
        description
          "Radio UWB";
      }
      enum "radio-remote-lan" {
        value 8;
        description
          "Radio remote LAN";
      }
    }
    description
      "Radio type";
  }

  typedef media-stream-decision-status {
    type enumeration {
      enum "rrc-decision-denied" {
        value 1;
        description
          "RRC decision denied";
      }
      enum "rrc-decision-admit" {
        value 2;
        description
          "RRC decision admit";
      }
      enum "rrc-decision-bad-client-denied" {
        value 3;
        description
          "RRC decision bad client denied";
      }
      enum "rrc-decision-bad-client-demote" {
        value 4;
        description
          "RRC decision bad client demote";
      }
    }
    description
      "Media-stream decision status";
  }

  typedef rogue-class-type {
    type enumeration {
      enum "rogue-classtype-unknown" {
        value 0;
        description
          "Pending";
      }
      enum "rogue-classtype-friendly" {
        value 1;
        description
          "This object specifies a known and acknowledged rogue AP";
      }
      enum "rogue-classtype-malicious" {
        value 2;
        description
          "This object specifies an unknown AP that matches user defined malicious rule";
      }
      enum "rogue-classtype-unclassified" {
        value 3;
        description
          "This object specifies an unknown AP that did not match any classification rule";
      }
      enum "rogue-classtype-custom" {
        value 4;
        description
          "Custom";
      }
      enum "rogue-classtype-invalid" {
        value 5;
        description
          "Custom";
      }
    }
    description
      "represents the categorization of the identified rogues";
  }

  typedef rogue-security-level {
    type enumeration {
      enum "rogue-security-level-low" {
        value 0;
        description
          "This object specifies the security level is low";
      }
      enum "rogue-security-level-high" {
        value 1;
        description
          "This object specifies the security level is High";
      }
      enum "rogue-security-level-critical" {
        value 2;
        description
          "This object specifies the security level is critical";
      }
      enum "rogue-security-level-custom" {
        value 3;
        description
          "This object specifies the user can configure rogue detection parameters";
      }
    }
    description
      "This object specifies the specifies the rogue detection security level";
  }

  typedef rldp-config-mode {
    type enumeration {
      enum "rldp-cfg-mode-disable" {
        value 0;
        description
          "This object specifies that RLDP is disabled";
      }
      enum "rldp-cfg-mode-enable" {
        value 1;
        description
          "This object specifies that RLDP is enabled on all APs";
      }
      enum "rldp-cfg-mode-enable-monitor-only" {
        value 2;
        description
          "This object specifies that RLDP is enabled on monitor APs only";
      }
    }
    description
      "This object specifies the specifies the rogue detection security level";
  }

  typedef rogue-state {
    type enumeration {
      enum "rogue-state-init" {
        value 0;
        description
          "rogue state Init";
      }
      enum "rogue-state-pending" {
        value 1;
        description
          "Pending";
      }
      enum "rogue-state-alert" {
        value 2;
        description
          "This object specifies the Alert state means Rogue AP can be a potential threat";
      }
      enum "rogue-state-lrad" {
        value 3;
        description
          "rouge state Lrad";
      }
      enum "rogue-state-trusted" {
        value 4;
        description
          "This object specifies the Known state means its just internal
           AP which is not on the same Switch";
      }
      enum "rogue-state-acknowledged" {
        value 5;
        description
          "This object specifies the Acknowledge state means an external AP whose
           existence is acceptable and not a threat ";
      }
      enum "rogue-state-contained" {
        value 6;
        description
          "This object specifies the Contained means containment is initiated and ongoing";
      }
      enum "rogue-state-threat" {
        value 7;
        description
          "This object specifies the the state when the rogue is found
           on wired network";
      }
      enum "rogue-state-contained-pending" {
        value 8;
        description
          "This object specifies the will appear in known rogue list";
      }
      enum "rogue-state-deleted" {
        value 9;
        description
          "Delete";
      }
      enum "rogue-state-invalid" {
        value 10;
        description
          "Invalid";
      }
    }
    description
      "This object specifies the This attribute is used to specify the state in which the Rogue AP is";
  }

  typedef rrm-control-mode {
    type enumeration {
      enum "rrm-automatic" {
        value 0;
        description
          "This object specifies the Enables auto-RF";
      }
      enum "rrm-run-once" {
        value 1;
        description
          "This object specifies the Enables one-time auto-RF";
      }
      enum "rrm-static" {
        value 2;
        description
          "This object specifies the Disables 802.11b RF grouping selection";
      }
      enum "rrm-leader" {
        value 3;
        description
          "This object specifies the Sets the 802.11b RF group selection to leader mode";
      }
      enum "rrm-restart" {
        value 4;
        description
          "RESTART";
      }
    }
    description
      "This object specifies the indicates the mode for the RRM algorithm
       for the band";
  }

  typedef preferred-mode-type {
    type enumeration {
      enum "preferred-mode-unconfig" {
        value 0;
        description
          "option to denote the capwap preferred mode is not configured";
      }
      enum "preferred-mode-ipv4" {
        value 1;
        description
          "option to denote the capwap preferred mode is IPV4";
      }
      enum "preferred-mode-ipv6" {
        value 2;
        description
          "option to denote the capwap preferred mode is IPV6";
      }
    }
    description
      "enum to denote the capwap preferred mode type";
  }

  typedef rad-cert-type {
    type enumeration {
      enum "ap-cert-mic" {
        value 1;
        description
          "This object specifies the Manufacture Installed Certificate";
      }
      enum "ap-cert-ssc" {
        value 2;
        description
          "This object specifies the Self Signed Certificate type";
      }
      enum "ap-cert-lsc" {
        value 3;
        description
          "This object specifies the Local Significance";
      }
    }
    description
      "This object specifies the Enum values denoting AP Certificate Type";
  }

  typedef apf-rogue-rule-rule-match-op {
    type enumeration {
      enum "rule-match-none" {
        value 0;
        description
          "This object specifies the Requires no conditions to be met for
             the rule to be matched";
      }
      enum "rule-match-all" {
        value 1;
        description
          "This object specifies the Requires all conditions to be met for
            the rule to be matched";
      }
      enum "rule-match-any" {
        value 2;
        description
          "This object specifies the Requires any one condition to be met for the rule to be matched";
      }
      enum "rule-match-max" {
        value 3;
        description
          "Placeholder for the maximum number of rules that can match for the particular AP/client";
      }
    }
    description
      "specifies the type of rule matching that needs to be done";
  }

  typedef apf-vap-80211-encryption {
    type enumeration {
      enum "apf-vap-80211-encryp-wep104" {
        value 0;
        description
          "104-bit WEP";
      }
      enum "apf-vap-80211-encryp-wep40" {
        value 1;
        description
          "40-bit WEP";
      }
    }
    description
      "This object specifies the Type of Static WEP Encryption";
  }

  typedef apf-vap-8021x-encryption {
    type enumeration {
      enum "apf-vap-8021x-encryp-wep104" {
        value 0;
        description
          "104-bit WEP";
      }
      enum "apf-vap-8021x-encryp-none" {
        value 1;
        description
          "8021x Encryption None";
      }
      enum "apf-vap-8021x-encryp-wep40" {
        value 2;
        description
          "40-bit WEP";
      }
    }
    description
      "This object specifies the Type of 802.1X Encryption. This applies if
       bsnDot11Ess8021xSecurity is in enabled state";
  }

  typedef apf-vap-80211-authentication {
    type enumeration {
      enum "apf-vap-80211-auth-open" {
        value 0;
        description
          "This object specifies the Open system authentication";
      }
      enum "apf-vap-80211-auth-shared-key" {
        value 1;
        description
          "This object specifies the Shared key authentication";
      }
      enum "apf-vap-80211-auth-wpa-8021x" {
        value 2;
        description
          "This object specifies the Wi-Fi Protected Access key authentication";
      }
      enum "apf-vap-80211-auth-wpa-psk" {
        value 3;
        description
          "Protected System (WPA-PSK)";
      }
      enum "apf-vap-80211-auth-cckm-8021x" {
        value 4;
        description
          "Protected System (CCKM+802.1X)";
      }
      enum "apf-auth-alg-cisco-leap" {
        value 128;
        description
          "Protected System (Cisco LEAP)";
      }
    }
    description
      "This object specifies the Type of 802.11 system authentication";
  }

  typedef apf-vap-lan-sub-type {
    type enumeration {
      enum "apf-vap-wireless-lan" {
        value 1;
        description
          "specifies the sub-type of the LAN created.";
      }
      enum "apf-vap-guest-lan" {
        value 2;
        description
          "Lan subtype is guest";
      }
      enum "apf-vap-remote-lan" {
        value 3;
        description
          "Lan subtype is remote lan";
      }
    }
    description
      "This object specifies the specifies the sub-type of the LAN created";
  }

  typedef apf-vap-radio-policies {
    type enumeration {
      enum "apf-vap-radio-all" {
        value 0;
        description
          "This object specifies the Configures the WLAN on all Radio bands";
      }
      enum "apf-vap-radio-80211b-only" {
        value 1;
        description
          "This object specifies the Configures the WLAN on 802.11b only";
      }
      enum "apf-vap-radio-80211a-only" {
        value 2;
        description
          "This object specifies the Configures the WLAN on 802.11a only";
      }
      enum "apf-vap-radio-80211g-only" {
        value 3;
        description
          "This object specifies the Configures the WLAN on 802.11g only";
      }
      enum "apf-vap-radio-80211bg-only" {
        value 4;
        description
          "This object specifies the Configures the WLAN on 802.11b and 802.11g only";
      }
      enum "apf-vap-radio-80211ag-only" {
        value 5;
        description
          "This object specifies the Configures the WLAN on 802.11a and 802.11g only";
      }
      enum "apf-vap-radio-80211-ab-only" {
        value 6;
        description
          "This object specifies the Configures the WLAN on 802.11a and 802.11b only";
      }
      enum "apf-vap-radio-none" {
        value 7;
        description
          "This object specifies the Configures the Wlan to None";
      }
      enum "apf-vap-80211b-simulated-remote-lan" {
        value 8;
        description
          "This object specifies the Configures the WLAN on simulated remote lan";
      }
    }
    description
      "represents the radio policy in the wlan";
  }

  typedef apf-vap-wme-policies {
    type enumeration {
      enum "apf-vap-wme-disabled" {
        value 0;
        description
          "This object specifies the disable WMM on the WLAN";
      }
      enum "apf-vap-wme-allowed" {
        value 1;
        description
          "This object specifies the Allows WMM on the WLAN";
      }
      enum "apf-vap-wme-required" {
        value 2;
        description
          "This object specifies the Requires WMM enabled clients on the WLAN";
      }
      enum "apf-vap-wme-invalid" {
        value 3;
        description
          "This object specifies the WME is invalid clients on the WLAN";
      }
    }
    description
      "This object specifies the When enabled, WME Policy is applied on the packets";
  }

  typedef apf-vap-pmf-policies {
    type enumeration {
      enum "apf-vap-pmf-disabled" {
        value 0;
        description
          "This object specifies the Configures PMF as disabled";
      }
      enum "apf-vap-pmf-optional" {
        value 1;
        description
          "This object specifies the Configures PMF as optional";
      }
      enum "apf-vap-pmf-required" {
        value 2;
        description
          "This object specifies the Configures PMF as mandatory";
      }
    }
    description
      "This object specifies the specifies the 802.11w PFM configuration for a
         particular WLAN";
  }

  typedef apf-vap-auto-qos-profile {
    type enumeration {
      enum "apf-vap-auto-qos-disabled" {
        value 0;
        description
          "unknown";
      }
      enum "apf-vap-auto-qos-enterprise" {
        value 1;
        description
          "This object specifies the Enable AutoQos Wireless Enterprise Policy";
      }
      enum "apf-vap-auto-qos-voice" {
        value 2;
        description
          "This object specifies the Enabling Auto QoS Voice will enable call-snooping and voice acm";
      }
      enum "apf-vap-auto-qos-guest" {
        value 3;
        description
          "This object specifies the Enable AutoQoS Wireless Guest Policy";
      }
    }
    description
      "Enumeration specifies the group of auto QoS profile";
  }

  typedef apf-vap-wifi-direct-policies {
    type enumeration {
      enum "apf-vap-wifidirect-disable" {
        value 0;
        description
          " WFD is completely disabled";
      }
      enum "apf-vap-wifidirect-allowed" {
        value 1;
        description
          "This object specifies the Allow all the wifi direct clients to associate unconditionally";
      }
      enum "apf-vap-wifidirect-not-allowed" {
        value 2;
        description
          "This object specifies the Allow wifi direct clients to associate only on policy compliance";
      }
      enum "apf-vap-wifidirect-invalid" {
        value 3;
        description
          "Invalid wifi direct policy";
      }
    }
    description
      "This object specifies the is used to allow/disallow wi-fi
       direct clients to/from joining the infrastructure            
       network";
  }

  typedef mm-secure-cipher-list {
    type enumeration {
      enum "mm-secure-cipher-disable" {
        value 0;
        description
          "This object specifies the A value of 'disable' implies that controllers will continue 
           to use default ciphers for Mobility  tunnel";
      }
      enum "mm-secure-cipher-aes256-sha" {
        value 1;
        description
          "This object specifies the A value of 'aes256sha1' implies that controllers will use
           AES256_SHA cipher for Mobility tunnel";
      }
      enum "mm-secure-cipher-aes256-sha256" {
        value 2;
        description
          "This object specifies the A value of 'aes256sha2' implies that controllers will use 
           AES256_SHA256 cipher for Mobility tunnel";
      }
    }
    description
      "This object specifies the This object is used to configure secure ciphers, AES256+SHA
        or AES256+SHA2 for Mobility  tunnel";
  }

  typedef apf-80211-qos-mode {
    type enumeration {
      enum "apf-80211-qos-mode-default-wmm" {
        value 1;
        description
          "This object specifies the Enable WMM default parameters for 802.11b";
      }
      enum "apf-80211-qos-mode-spectralink" {
        value 2;
        description
          "This object specifies the Enable SpectraLink Voice Priority parameters for 802.11b";
      }
      enum "apf-80211-qos-mode-optimized-voice" {
        value 3;
        description
          "This object specifies the Enable non-spectralink voice-optimized parameters for 802.11b";
      }
      enum "apf-80211-qos-mode-optimized-voice-video" {
        value 4;
        description
          "This object specifies the Enable combined video-voice-optimized parameters for 802.11b";
      }
      enum "apf-80211-qos-mode-custom-voice" {
        value 5;
        description
          "This object specifies the Enable Custom Voice parameters for 802.11b";
      }
      enum "apf-80211-qos-mode-custom" {
        value 6;
        description
          "custom";
      }
      enum "apf-80211-qos-mode-invalid" {
        value 7;
        description
          "Invalid";
      }
    }
    description
      "This object specifies the This object specifies the EDCA profile to be used
       in EDCA Parameter set element";
  }

  typedef radio-type {
    type enumeration {
      enum "dot11-invalid-value" {
        value 0;
        description
          "Invalid";
      }
      enum "dot11-2-dot-4-ghz" {
        value 1;
        description
          "2.4 GHz";
      }
      enum "dot11-5-ghz" {
        value 2;
        description
          "5 GHz";
      }
      enum "dot11-dualband-radio" {
        value 3;
        description
          "Dual Band";
      }
      enum "dot11-4-dot-9-ghz" {
        value 4;
        description
          "4.9 GHz";
      }
      enum "dot11-5-dot-8-ghz" {
        value 5;
        description
          "5.8 GHz";
      }
    }
    description
      "This object specifies the this represents various radio band type";
  }

  typedef slot-id-type {
    type enumeration {
      enum "slot-0" {
        value 0;
        description
          "slot 0";
      }
      enum "slot-1" {
        value 1;
        description
          "slot 1";
      }
      enum "slot-2" {
        value 2;
        description
          "slot 2";
      }
      enum "slot-3" {
        value 3;
        description
          "slot 3";
      }
    }
    description
      "This object specifies the This subtype represents a various 
       Slot Id type of an AP";
  }

  typedef half-life-time {
    type enumeration {
      enum "half-life-time-0" {
        value 0;
        description
          "This object specifies the A value of 0 indicates that
           timeout is disabled";
      }
      enum "half-life-time-1" {
        value 1;
        description
          "slot 1";
      }
      enum "half-life-time-2" {
        value 2;
        description
          "slot 2";
      }
      enum "half-life-time-5" {
        value 5;
        description
          "slot 5";
      }
      enum "half-life-time-10" {
        value 10;
        description
          "half time is 10";
      }
      enum "half-life-time-20" {
        value 20;
        description
          "half time is 20";
      }
      enum "half-life-time-30" {
        value 30;
        description
          "half time is 30";
      }
      enum "half-life-time-60" {
        value 60;
        description
          "half time is 60";
      }
      enum "half-life-time-90" {
        value 90;
        description
          "half time is 90";
      }
      enum "half-life-time-120" {
        value 120;
        description
          "half time is 120";
      }
      enum "half-life-time-180" {
        value 180;
        description
          "half time is 180";
      }
      enum "half-life-time-300" {
        value 300;
        description
          "half time is 300";
      }
    }
    description
      "This object specifies the This object specifies the half-life timeout
       for the client";
  }

  typedef ap-eth-port-speed {
    type enumeration {
      enum "ap-ethernet-port-speed-auto" {
        value 0;
        description
          "This object specifies the this subtype represents ethernet port speed
           with auto adjustable";
      }
      enum "ap-ethernet-port-speed-10-mbps" {
        value 1;
        description
          "This object specifies the this subtype represents ethernet port speed
           with speed of 10 Mbps";
      }
      enum "ap-ethernet-port-speed-100-mbps" {
        value 2;
        description
          "This object specifies the this subtype represents ethernet port speed
                     with speed of 100 mbps";
      }
      enum "ap-ethernet-port-speed-1000-mbps" {
        value 3;
        description
          "This object specifies the this subtype represents ethernet port speed
                     with speed of 1000 mbps";
      }
      enum "ap-ethernet-port-speed-2500-mbps" {
        value 4;
        description
          "This object specifies the this subtype represents ethernet port speed
                     with speed of 2500 mbps";
      }
      enum "ap-ethernet-port-speed-5000-mbps" {
        value 5;
        description
          "This object specifies the this subtype represents ethernet port speed
                     with speed of 5000 mbps";
      }
      enum "ap-ethernet-port-speed-invalid" {
        value 6;
        description
          "Ethernet port speed is invalid";
      }
    }
    description
      "This object specifies the this subtype represents ethernet port speed";
  }

  typedef ap-eth-port-duplex {
    type enumeration {
      enum "ap-ethernet-port-duplex-auto" {
        value 0;
        description
          "ethernet port duplex Auto";
      }
      enum "ap-ethernet-port-duplex-half" {
        value 1;
        description
          "ethernet port duplex Half";
      }
      enum "ap-ethernet-port-duplex-full" {
        value 2;
        description
          "ethernet port duplex Full";
      }
    }
    description
      "enumeration for mode of the ethernet port";
  }

  typedef memory-core-dump-flag {
    type enumeration {
      enum "tftp-coredump-uncompress" {
        value 0;
        description
          "This object specifies the Do not compress the core dump file";
      }
      enum "tftp-coredump-compress" {
        value 1;
        description
          "This object specifies the Compress the core dump file";
      }
      enum "tftp-coredump-disable" {
        value 2;
        description
          "This object specifies the disable the core dump file";
      }
    }
    description
      "enumeration listing the treatment to the coredump generated at the AP";
  }

  typedef rate-state {
    type enumeration {
      enum "apf-tx-rate-unsupported" {
        value 0;
        description
          "This object specifies the Disables a rate";
      }
      enum "apf-tx-rate-supported" {
        value 1;
        description
          "This object specifies the Configures a rate to supported";
      }
      enum "apf-tx-rate-basic" {
        value 2;
        description
          "This object specifies the Configures a rate to mandatory";
      }
      enum "apf-tx-rate-not-applicable" {
        value 3;
        description
          "Not applicable";
      }
    }
    description
      "enumeration listing the type of Tx rate supported";
  }

  typedef apf-80211n-amsdu {
    type enumeration {
      enum "apf-80211n-amsdu-disable" {
        value 0;
        description
          " 80211N AMSDU is disabled";
      }
      enum "apf-80211n-amsdu-enable" {
        value 1;
        description
          "80211N AMSDU is enabled";
      }
      enum "apf-80211n-amsdu-invalid" {
        value 2;
        description
          "80211N AMSDU is invalid";
      }
    }
    description
      "Specifies the 80211n aggregation msd unit";
  }

  typedef apf-80211n-ampdu {
    type enumeration {
      enum "apf-80211n-ampdu-disable" {
        value 0;
        description
          "80211N AMPDU is disabled";
      }
      enum "apf-80211n-ampdu-enabled" {
        value 1;
        description
          "80211N AMPDU enabled";
      }
      enum "apf-80211n-ampdu-invalid" {
        value 2;
        description
          "80211N AMPDU is invalid";
      }
    }
    description
      "80211n AMPDU is present";
  }

  typedef ndp-type {
    type enumeration {
      enum "ndp-type-transparent" {
        value 0;
        description
          "NDP type is Transparent";
      }
      enum "ndp-type-protected" {
        value 1;
        description
          "NDP type is Protected";
      }
    }
    description
      "Enum for NDP type";
  }

  typedef rrm-group-member {
    type enumeration {
      enum "group-member-noaction" {
        value 0;
        description
          "No-operation on the Rrm group member";
      }
      enum "group-member-add" {
        value 1;
        description
          "Operation representing Rrm group member to be added";
      }
      enum "group-member-delete" {
        value 2;
        description
          "Operation representing Rrm group member to be deleted";
      }
    }
    description
      "enumeration listing the operation on the RRM group member";
  }

  typedef datarate {
    type enumeration {
      enum "optroam-rate-1-m" {
        value 1;
        description
          "1 Mbps data rate threshold";
      }
      enum "optroam-rate-2-m" {
        value 2;
        description
          "2 Mbps data rate threshold";
      }
      enum "optroam-rate-5-5-m" {
        value 5;
        description
          "5 Mbps data rate threshold";
      }
      enum "optroam-rate-6-m" {
        value 6;
        description
          "6 Mbps data rate threshold";
      }
      enum "optroam-rate-9-m" {
        value 9;
        description
          "9 Mbps data rate threshold";
      }
      enum "optroam-rate-11-m" {
        value 11;
        description
          "11 Mbps data rate threshold";
      }
      enum "optroam-rate-12-m" {
        value 12;
        description
          "12 Mbps data rate threshold";
      }
      enum "optroam-rate-18-m" {
        value 18;
        description
          "18 Mbps data rate threshold";
      }
      enum "optroam-rate-24-m" {
        value 24;
        description
          "24 Mbps data rate threshold";
      }
      enum "optroam-rate-36-m" {
        value 36;
        description
          "36 Mbps data rate threshold";
      }
      enum "optroam-rate-48-m" {
        value 48;
        description
          "48 Mbps data rate threshold";
      }
      enum "optroam-rate-54-m" {
        value 54;
        description
          "54 Mbps data rate threshold";
      }
      enum "optroam-rate-0" {
        value 0;
        description
          "0 Mbps data rate threshold";
      }
    }
    description
      "Enum for data rate threshold of 802.11 Optimized Roaming";
  }

  typedef dca-threshold {
    type enumeration {
      enum "dca-threshold-low" {
        value 0;
        description
          "Low DCA sensitivity level";
      }
      enum "dca-threshold-medium" {
        value 1;
        description
          "Medium DCA sensitivity level";
      }
      enum "dca-threshold-high" {
        value 2;
        description
          "High DCA sensitivity level";
      }
    }
    description
      "Enum for DCA sensitivity levels";
  }

  typedef apf-location-algorithm-type {
    type enumeration {
      enum "loc-alg-simple" {
        value 1;
        description
          "This object specifies the A faster algorithm with smaller 
            CPU overhead but less accuracy";
      }
      enum "loc-alg-average" {
        value 2;
        description
          "This object specifies the A more accurate algorithm but with more CPU overhead";
      }
    }
    description
      "This object specifies the this represents algorithm type
          and CPU overhead";
  }

  typedef ant-band-mode {
    type enumeration {
      enum "ant-band-mode-unknown" {
        value 1;
        description
          "antenna mode unknown";
      }
      enum "ant-band-mode-single" {
        value 2;
        description
          "This object specifies the antenna is operating in single band";
      }
      enum "ant-band-mode-dual" {
        value 3;
        description
          "This object specifies the antenna is operating in dual band";
      }
    }
    description
      "This object specifies the This object specifies the mode of Antenna band";
  }

  typedef power-injector-state {
    type enumeration {
      enum "pwrinj-state-disable" {
        value 0;
        description
          "Disable one radio for ither to receive full power";
      }
      enum "pwrinj-state-specify-mac" {
        value 1;
        description
          "Specify the mac address of the connected switch port used as power injector";
      }
      enum "pwrinj-state-override-mac" {
        value 66;
        description
          "Override the mac address of the connected switch port used as power injector";
      }
      enum "pwrinj-state-unsupported" {
        value 68;
        description
          "Power injector state is not supported for the particular AP";
      }
    }
    description
      "List all the  types of power injector modes/options";
  }

  typedef power-injector-selection {
    type enumeration {
      enum "pwrinj-selection-unknown" {
        value 1;
        description
          "mode of the power injector selection is unknown";
      }
      enum "pwrinj-selection-installed" {
        value 2;
        description
          "This object specifies the configure the MAC address of the 
           switch port that has a Power Injector";
      }
      enum "pwrinj-selection-override" {
        value 3;
        description
          "This object specifies the override the safety checks and assume 
           a Power Injector is always installed.";
      }
    }
    description
      "This object specifies the This object specifies the Power Injector selection
          value of the AP";
  }

  typedef apf-qos-def-pm-create-status {
    type enumeration {
      enum "qos-def-pm-status-none" {
        value 0;
        description
          "QOS def PM status none";
      }
      enum "qos-def-pm-status-created" {
        value 1;
        description
          "QOS def PM status created";
      }
      enum "qos-def-pm-status-valid-pending" {
        value 2;
        description
          "QOS def PM status valid pending";
      }
      enum "qos-def-pm-status-valid-requested" {
        value 3;
        description
          "QOS def PM status valid requested";
      }
      enum "qos-def-pm-status-valid-failed" {
        value 4;
        description
          "QOS def PM status valid failed";
      }
      enum "qos-def-pm-status-valid-success" {
        value 5;
        description
          "QOS def PM status valid success";
      }
      enum "qos-def-pm-status-install-requested" {
        value 6;
        description
          "QOS def PM status install requested";
      }
      enum "qos-def-pm-status-install-failed" {
        value 7;
        description
          "QOS def PM status install failed";
      }
      enum "qos-def-pm-status-install-success" {
        value 8;
        description
          "QOS def PM status install success";
      }
      enum "qos-def-pm-status-max" {
        value 9;
        description
          "QOS def PM status max";
      }
    }
    description
      "QOS def PM create status";
  }

  typedef work-day {
    type enumeration {
      enum "monday" {
        value 1;
        description
          "Configures Monday as the day for rldp scheduling";
      }
      enum "tuesday" {
        value 2;
        description
          "Configures Tuesday as the day for rldp scheduling";
      }
      enum "wednesday" {
        value 3;
        description
          "Configures Wednesday as the day for rldp scheduling";
      }
      enum "thursday" {
        value 4;
        description
          "Configures Thursday as the day for rldp scheduling";
      }
      enum "friday" {
        value 5;
        description
          "Configures Friday as the day for rldp scheduling";
      }
      enum "saturday" {
        value 6;
        description
          "Configures Saturday as the day for rldp scheduling";
      }
      enum "sunday" {
        value 7;
        description
          "Configures Sunday as the day for rldp scheduling";
      }
    }
    description
      "Lists all the days when rldp can be scheduled";
  }

  typedef crypt-type {
    type enumeration {
      enum "clear" {
        value 0;
        description
          "This is to indicate the string encryption type is clear";
      }
      enum "sha" {
        value 4;
        description
          "This is to indicate the string encryption of type SHA";
      }
      enum "md5" {
        value 5;
        description
          "This is to indicate the string encryption of type MD5";
      }
      enum "ike-aes" {
        value 6;
        description
          "This is to indicate the string encryption of type IKE-AES";
      }
      enum "type7" {
        value 7;
        description
          "This is to indicate the string encryption of type-7";
      }
      enum "aes" {
        value 8;
        description
          "This is to indicate the string encryption of type AES";
      }
      enum "clear-to-sha" {
        value 40;
        description
          "This is to indicate the string encryption of type Clear to SHA";
      }
      enum "clear-to-md5" {
        value 50;
        description
          "This is to indicate the string encryption of type clear to MD5";
      }
      enum "clear-to-ike-aes" {
        value 60;
        description
          "This is to indicate the string encryption of type clear to IKE-AES";
      }
      enum "clear-to-type7" {
        value 70;
        description
          "This is to indicate the string encryption of type clear to type-7";
      }
      enum "clear-to-aes" {
        value 80;
        description
          "This is to indicate the string encryption of type clear to AES";
      }
    }
    description
      "This object specifies the This is to indicate the string encryption type";
  }

  typedef lomm-mode-type {
    type enumeration {
      enum "mode-type-all" {
        value 1;
        description
          "This object specifies the All optimization is enabled";
      }
      enum "tracking" {
        value 2;
        description
          "This object specifies the Tracking is optimized";
      }
      enum "wips" {
        value 3;
        description
          "This object specifies the WIPS optimization is enabled";
      }
      enum "mode-type-none" {
        value 4;
        description
          "Default";
      }
    }
    description
      "This object specifies the This object represents the monitor mode optimization
       on this device";
  }

  typedef dot11-min-phy-rate {
    type enumeration {
      enum "one" {
        value 1;
        description
          "Phy rate is 1000";
      }
      enum "two" {
        value 2;
        description
          "Phy rate is 2000";
      }
      enum "five-point-five" {
        value 5;
        description
          "Phy rate is 5500";
      }
      enum "six" {
        value 6;
        description
          "Phy rate is 6000";
      }
      enum "nine" {
        value 9;
        description
          "Phy rate is 9000";
      }
      enum "eleven" {
        value 11;
        description
          "Phy rate is 11000";
      }
      enum "twelve" {
        value 12;
        description
          "Phy rate is 1200";
      }
      enum "eighteen" {
        value 18;
        description
          "Phy rate is 18000";
      }
      enum "twenty-four" {
        value 24;
        description
          "Phy rate is 24000";
      }
      enum "thirty-six" {
        value 36;
        description
          "Phy rate is 36000";
      }
      enum "forty-eight" {
        value 48;
        description
          "Phy rate is 48000";
      }
      enum "fifty-four" {
        value 54;
        description
          "Phy rate is 54000";
      }
      enum "sixty-five" {
        value 65;
        description
          "Phy rate is 65000";
      }
      enum "seventy-two-point-two" {
        value 72;
        description
          "Phy rate is 72200";
      }
      enum "one-thirty" {
        value 130;
        description
          "Phy rate is 13000";
      }
      enum "one-thirty-five" {
        value 135;
        description
          "Phy rate is 13500";
      }
      enum "one-forty-four-point-four" {
        value 144;
        description
          "Phy rate is 144400";
      }
      enum "one-fifty" {
        value 150;
        description
          "Phy rate is 150000";
      }
      enum "two-seventy" {
        value 270;
        description
          "Phy rate is 270000";
      }
      enum "three-hundred" {
        value 300;
        description
          "Phy rate is 300000";
      }
    }
    description
      "This object specifies the This object specifies the minimum physical rate
       that should be enabled by a client to successfully join a media
       stream";
  }

  typedef power-mode-type {
    type enumeration {
      enum "dot11-default-low-pwr" {
        value 0;
        description
          "This object specifies the The AP is drawing default power from 
           Ethernet";
      }
      enum "dot11-set-low-pwr" {
        value 1;
        description
          "This object specifies the The AP is drawing low power from
           Ethernet";
      }
      enum "dot11-set-15-4-pwr" {
        value 2;
        description
          "This object specifies the The AP is drawing 15.4 watts from 
             Ethernet";
      }
      enum "dot11-set-16-8-pwr" {
        value 3;
        description
          "This object specifies the The AP is drawing 16.8 watts from
            Ethernet";
      }
      enum "dot11-set-high-pwr" {
        value 4;
        description
          "This object specifies the The AP is drawing high power from
           Ethernet";
      }
      enum "dot11-default-high-pwr" {
        value 5;
        description
          "Power mode type is high";
      }
      enum "dot11-set-no-pwr" {
        value 6;
        description
          "This object specifies the The AP is drawing no power from ethernet";
      }
      enum "dot11-set-25-5-pwr" {
        value 7;
        description
          "This object specifies the The AP is drawing 25.5 watts from
           Ethernet";
      }
      enum "unknown-pwr" {
        value 255;
        description
          "unknown power mode type";
      }
    }
    description
      "This object specifies the This object represents the power status of the AP";
  }

  typedef power-type {
    type enumeration {
      enum "pwr-src-brick-old" {
        value 0;
        description
          "AP uses a local brick style power supply";
      }
      enum "pwr-src-brick-new" {
        value 1;
        description
          "AP uses a local new brick style power supply";
      }
      enum "pwr-src-inj" {
        value 2;
        description
          "uses power injector for power supply";
      }
      enum "pwr-src-poe-lgcy" {
        value 3;
        description
          "AP uses legacy POE mechanism";
      }
      enum "pwr-src-poe-plus" {
        value 4;
        description
          "AP uses advanced POE mechanism";
      }
      enum "pwr-src-unknown" {
        value 255;
        description
          "AP's power source is known";
      }
    }
    description
      "lists all the supported power mode types";
  }

  typedef rrm-ed-threshold-level {
    type enumeration {
      enum "rrm-cleanair-event-low" {
        value 1;
        description
          "This object specifies the low level event driven RRM threshold value";
      }
      enum "rrm-cleanair-event-medium" {
        value 2;
        description
          "This object specifies the medium level event driven RRM threshold value";
      }
      enum "rrm-cleanair-event-high" {
        value 3;
        description
          "This object specifies the high level event driven RRM threshold value";
      }
      enum "rrm-cleanair-event-custom" {
        value 4;
        description
          "This object specifies the user specified value of even driven RRM threshold";
      }
    }
    description
      "This object specifies the This object represents the event driven
        RRM threshold level";
  }

  typedef apf-vap-key-type {
    type enumeration {
      enum "key-ascii" {
        value 0;
        description
          "Represents that the PSK key is specified in ascii";
      }
      enum "key-hex" {
        value 1;
        description
          "Represents that the PSK key specified in hex";
      }
      enum "key-invalid" {
        value 2;
        description
          "Represents that the PSK key format type is invalid";
      }
    }
    description
      "List all the types of key specified for PSK";
  }

  typedef spam-ap-modes {
    type enumeration {
      enum "spam-ap-mode-local" {
        value 0;
        description
          "This object specifies the wireless local mode";
      }
      enum "spam-ap-mode-monitor" {
        value 1;
        description
          " wireless monitor mode ";
      }
      enum "spam-ap-mode-remote" {
        value 2;
        description
          "This object specifies the wireless remote mode";
      }
      enum "spam-ap-mode-rogue-detector" {
        value 3;
        description
          "This object specifies the wireless rogue detector mode";
      }
      enum "spam-ap-mode-sniffer" {
        value 4;
        description
          "This object specifies the wireless sniffer mode";
      }
      enum "spam-ap-mode-bridge" {
        value 5;
        description
          "This object specifies the wireless mode bride";
      }
      enum "spam-ap-mode-seconnect" {
        value 6;
        description
          "This object specifies the Spectrum Expert Only Connect mode";
      }
      enum "spam-ap-mode-hybrid-remote" {
        value 7;
        description
          "This object specifies the Hybrid Remode Edge AP (H-REAP) mode";
      }
      enum "spam-ap-mode-sensor" {
        value 8;
        description
          "Sensor";
      }
      enum "spam-ap-mode-remote-bridge" {
        value 9;
        description
          "Not supported - Is used for mesh";
      }
    }
    description
      "This object specifies the Monitor Only Mode Setting";
  }

  typedef rrm-dca-chan-width {
    type enumeration {
      enum "rrm-dca-chan-width-20-mhz" {
        value 0;
        description
          "Channel RF Width 20 MZ";
      }
      enum "rrm-dca-chan-width-40-mhz" {
        value 1;
        description
          "Channel RF Width 40 MZ";
      }
      enum "rrm-dca-chan-width-80-mhz" {
        value 2;
        description
          "Channel RF Width 80 MZ";
      }
      enum "rrm-dca-chan-width-best" {
        value 3;
        description
          "Channel RF Width best";
      }
    }
    description
      "This object specifies the this object specifies how the system performs DCA
       channel width selection";
  }

  typedef dca-chan-width {
    type enumeration {
      enum "dca-chan-width-20-mhz" {
        value 0;
        description
          "20 Mhz";
      }
      enum "dca-chan-width-40-mhz" {
        value 1;
        description
          "40 Mhz";
      }
      enum "dca-chan-width-80-mhz" {
        value 2;
        description
          "80 Mhz";
      }
      enum "dca-chan-width-best" {
        value 3;
        description
          "best chan width";
      }
      enum "dca-chan-width-160-mhz" {
        value 4;
        description
          "160 Mhz";
      }
      enum "dca-chan-width-8080-mhz" {
        value 5;
        description
          "8080 Mhz";
      }
    }
    description
      "enumeration describing channel width";
  }

  typedef rrm-dca-chan-width-cap {
    type enumeration {
      enum "rrm-dca-chan-width-cap-20-mhz" {
        value 0;
        description
          "This object specifies the Chan Width 20 Mhz";
      }
      enum "rrm-dca-chan-width-cap-40-mhz" {
        value 1;
        description
          "This object specifies the Chan Width 40 Mhz";
      }
      enum "rrm-dca-chan-width-cap-80-mhz" {
        value 2;
        description
          "This object specifies the Chan Width 80 Mhz";
      }
      enum "rrm-dca-chan-width-cap-best" {
        value 3;
        description
          "This object specifies the Chan Width best";
      }
      enum "rrm-dca-chan-width-cap-160-mhz" {
        value 4;
        description
          "This object specifies the Chan Width 160";
      }
      enum "rrm-dca-chan-width-cap-max" {
        value 5;
        description
          "This object specifies the Chan Width max";
      }
    }
    description
      "This object specifies the config 802.11a dynamic channel 
        assignment algorithm parameters";
  }

  typedef dca-chan-width-cap {
    type enumeration {
      enum "dca-chan-width-cap-20-mhz" {
        value 0;
        description
          "20 MHz";
      }
      enum "dca-chan-width-cap-40-mhz" {
        value 1;
        description
          "40 MHz";
      }
      enum "dca-chan-width-cap-80-mhz" {
        value 2;
        description
          "80 MHz";
      }
      enum "dca-chan-width-cap-best" {
        value 3;
        description
          "best chan width";
      }
      enum "dca-chan-width-cap-160-mhz" {
        value 4;
        description
          "160 Mhz";
      }
      enum "dca-chan-width-cap-max" {
        value 5;
        description
          "MAX ALLOWED";
      }
    }
    description
      "enumeration describing channel width";
  }

  typedef rf-rrm-dca-chan-width {
    type enumeration {
      enum "rf-rrm-dca-chan-width-20-mhz" {
        value 0;
        description
          "This object specifies the 20 MHz channel width supported by this radio";
      }
      enum "rf-rrm-dca-chan-width-40-mhz" {
        value 1;
        description
          "This object specifies the 40 MHz channel width supported by this radio";
      }
      enum "rf-rrm-dca-chan-width-80-mhz" {
        value 2;
        description
          "This object specifies the 80 MHz channel width supported by this radio";
      }
      enum "rf-rrm-dca-chan-width-best" {
        value 3;
        description
          "This object specifies the Dynamic channel width(160 MHz, 80 MHz, 40 MHz or 20 MHz)
                supported by this radio";
      }
    }
    description
      "This object specifies the This object specifies how the system performs DCA
       channel width selection for the RFProfile";
  }

  typedef rf-dca-chan-width {
    type enumeration {
      enum "rf-dca-chan-width-20-mhz" {
        value 0;
        description
          "20 MHz";
      }
      enum "rf-dca-chan-width-40-mhz" {
        value 1;
        description
          "40 MHz";
      }
      enum "rf-dca-chan-width-80-mhz" {
        value 2;
        description
          "80 MHz";
      }
      enum "rf-dca-chan-width-best" {
        value 3;
        description
          "best chan width";
      }
      enum "rf-dca-chan-width-160-mhz" {
        value 4;
        description
          "160 MHz";
      }
      enum "rf-dca-chan-width-8080-mhz" {
        value 5;
        description
          "80+80 MHz";
      }
    }
    description
      "enumeration describing channel width";
  }

  typedef channel-monitor-mode {
    type enumeration {
      enum "rrm-channels-country" {
        value 1;
        description
          "This object specifies the Monitor channels used in configured country code";
      }
      enum "rrm-channels-all" {
        value 2;
        description
          "This object specifies the Monitor all channels";
      }
      enum "rrm-channels-dca" {
        value 3;
        description
          "This object specifies the Monitor channels used by dynamic channel assignment";
      }
    }
    description
      "This object specifies the Sets the noise/interference/rogue monitoring channel-list";
  }

  typedef nw-leg-beam-form {
    type enumeration {
      enum "nw-leg-bf-disable" {
        value 0;
        description
          "This object specifies the Disable 802.11b tx beamforming - 2.4 GHz";
      }
      enum "nw-leg-bf-enable" {
        value 1;
        description
          "This object specifies the Enable 802.11b tx beamforming - 2.4 GHz";
      }
      enum "nw-leg-bf-na" {
        value 2;
        description
          "This object specifies the beamforming is not applicable";
      }
    }
    description
      "Enables/disables beam forming  on 11g";
  }

  typedef admin-state {
    type enumeration {
      enum "adminstate-enabled" {
        value 1;
        description
          "This object specifies the A value of 'true' enables the Admin State";
      }
      enum "adminstate-disabled" {
        value 2;
        description
          "This object specifies the A value of 'false' disables the Admin State";
      }
    }
    description
      "This object specifies the This object specifies the Admin State of the AP";
  }

  typedef ap-role {
    type enumeration {
      enum "role-normal" {
        value 0;
        description
          "Normal";
      }
      enum "role-root" {
        value 1;
        description
          "Root AP";
      }
      enum "role-mesh" {
        value 2;
        description
          "Mesh AP";
      }
    }
    description
      "Lists all the roles of AP for the case of mesh";
  }

  typedef cdp-cache-duplex {
    type enumeration {
      enum "cdp-cache-duplex-unknown" {
        value 1;
        description
          "This object specifies the The value unknown(1) indicates no duplex
           mode field (TLV) was reported in the most recent CDP
           message or the neighboring device is not connected to the
           AP though ethernet interface";
      }
      enum "cdp-cache-duplex-full" {
        value 2;
        description
          "CDP cache duplex Full";
      }
      enum "cdp-cache-duplex-half" {
        value 3;
        description
          "CDP cache duplex Half";
      }
    }
    description
      "This object specifies the this object denotes the duplex mode of the
       Ethernet interface between the AP and it's 
       neighboring CDP device, as reported in the most recent 
       CDP message";
  }

  typedef console-login-status {
    type enumeration {
      enum "login-status-success" {
        value 1;
        description
          "Success";
      }
      enum "login-status-failure" {
        value 2;
        description
          "Failure";
      }
      enum "login-status-logoff" {
        value 3;
        description
          "Logoff";
      }
      enum "login-status-timeout" {
        value 4;
        description
          "Timeout";
      }
    }
    description
      "Lists the result of operation to dump logs on the AP console";
  }

  typedef enm-antenna-selection {
    type enumeration {
      enum "antenna-side-a" {
        value 0;
        description
          "Antenna side A";
      }
      enum "antenna-side-b" {
        value 1;
        description
          "Antenna side B";
      }
      enum "antenna-diversity-enabled" {
        value 255;
        description
          "Antenna Diversity enabled";
      }
    }
    description
      "Enum for Antenna Selection";
  }

  typedef slot-radio-sub-band {
    type enumeration {
      enum "radio-sub-band-all" {
        value 1;
        description
          "All(SLOT_RADIO_SUB_BAND_ALL)";
      }
      enum "4-dot-9-ghz" {
        value 2;
        description
          "4.9 GHz";
      }
      enum "5-dot-2-ghz" {
        value 3;
        description
          "5.2 GHz";
      }
      enum "5-dot-4-ghz" {
        value 4;
        description
          "5.4 GHz";
      }
      enum "5-dot-8-ghz" {
        value 5;
        description
          "5.8 GHz";
      }
    }
    description
      "This object specifies the This object indicates the sub band on which
       this radio operates";
  }

  typedef oper-state {
    type enumeration {
      enum "oper-state-up" {
        value 1;
        description
          "oper state is UP";
      }
      enum "oper-state-down" {
        value 2;
        description
          "oper state is DOWN";
      }
      enum "oper-state-na" {
        value 3;
        description
          "Not available";
      }
    }
    description
      "This object specifies the This object represents the operational state
       of the physical Ethernet interface on the AP";
  }

  typedef enm-antenna-mode {
    type enumeration {
      enum "antenna-mode-sector-a" {
        value 1;
        description
          "Antenna mode sector A";
      }
      enum "antenna-mode-sector-b" {
        value 2;
        description
          "Antenna mode sector B";
      }
      enum "antenna-mode-omni" {
        value 3;
        description
          "Antenna mode omni";
      }
      enum "antenna-mode-mimo" {
        value 4;
        description
          "Antenna mode mimo";
      }
    }
    description
      "Enum for Antenna Mode";
  }

  typedef frame-burst-mode {
    type enumeration {
      enum "frame-burst-automatic" {
        value 0;
        description
          "This object specifies the Use optimal settings for bursting of 802.11ac A-MPDUs";
      }
      enum "frame-burst-enabled" {
        value 1;
        description
          "Enabled";
      }
      enum "frame-burst-disabled" {
        value 2;
        description
          "Disabled";
      }
    }
    description
      "This object specifies the Configure 802.11ac Frame Burst";
  }

  typedef rx-sen-sop-threshold-level {
    type enumeration {
      enum "rrm-rxsensop-threshold-auto" {
        value 0;
        description
          "rrm rx sensitivity threshold is auto";
      }
      enum "rrm-rxsensop-threshold-low" {
        value 1;
        description
          "low (-80 dbm)";
      }
      enum "rrm-rxsensop-threshold-medium" {
        value 2;
        description
          "medium (-78 dbm)";
      }
      enum "rrm-rxsensop-threshold-high" {
        value 3;
        description
          "high (-76 dbm)";
      }
    }
    description
      "rx sensitivity threshold level";
  }

  typedef apf-ate-mode {
    type enumeration {
      enum "apf-atf-mode-disable" {
        value 0;
        description
          "Disable";
      }
      enum "apf-atf-mode-ssid" {
        value 1;
        description
          "This object specifies the Configure airtime-fairness in enforce-policy mode";
      }
      enum "apf-atf-mode-monitor" {
        value 2;
        description
          "This object specifies the Monitor Mode represented by  cLApDot11IfType
           of ATF supported APs joined in the controller";
      }
    }
    description
      "This object specifies the This object is used to set the airtime-fairness mode";
  }

  typedef apf-ate-stealing-policy {
    type enumeration {
      enum "apf-atf-stealing-policy-disable" {
        value 0;
        description
          "This object specifies the Disable airtime-fairness optimization";
      }
      enum "apf-atf-stealing-policy-enable" {
        value 1;
        description
          "This object specifies the Enable airtime-fairness optimization";
      }
    }
    description
      "This object specifies the This object is used to configure the Optimization Policy
       represented by cLApDot11IfType of ATF supported APs, joined
       in the controller";
  }

  typedef edca-profile {
    type enumeration {
      enum "edca-wmm" {
        value 1;
        description
          "default-wmm";
      }
      enum "edca-spectralink-voice-priority" {
        value 2;
        description
          "This object specifies the Enable SpectraLink Voice Priority parameters for 802.11b";
      }
      enum "edca-voice-optimized" {
        value 3;
        description
          "This object specifies the Enable non-spectralink voice-optimized parameters for 802.11b";
      }
      enum "edca-video-voice-optimized" {
        value 4;
        description
          "This object specifies the Enable combined video-voice-optimized parameters for 802.11b";
      }
      enum "edca-custom-voice" {
        value 5;
        description
          "This object specifies the Enable Custom Voice parameters for 802.11b";
      }
      enum "edca-custom" {
        value 6;
        description
          "custom";
      }
      enum "edca-fastlane" {
        value 7;
        description
          "This object specifies the Enable Fastlane parameters for 802.11b";
      }
      enum "edca-invalid" {
        value 8;
        description
          "Specifies the Enhanced Distribution is invalid";
      }
    }
    description
      "This object specifies the Configure 802.11b EDCA 
        (Enhanced Distributed Channel Access) parameters";
  }

  typedef autoqos-profile {
    type enumeration {
      enum "autoqos-disabled" {
        value 0;
        description
          "This object specifies the Disable of AutoQos Wireless Enterprise Policy";
      }
      enum "autoqos-enterprise" {
        value 1;
        description
          "This object specifies the Enable AutoQos Wireless Enterprise Policy";
      }
      enum "autoqos-voice" {
        value 2;
        description
          "This object specifies the Enabling Auto QoS Voice will enable call-snooping";
      }
      enum "autoqos-guest" {
        value 3;
        description
          "This object specifies the Enable AutoQos Wireless Guest Policy";
      }
      enum "autoqos-fastlane" {
        value 4;
        description
          "This object specifies the Enable AutoQos Wireless Fastlane Policy";
      }
    }
    description
      "Enumeration Specifies the group of Auto qos profile";
  }

  typedef eap-method-type {
    type enumeration {
      enum "eap-type-none" {
        value 0;
        description
          "EAP-None";
      }
      enum "eap-type-md5" {
        value 4;
        description
          "EAP-MD5";
      }
      enum "eap-type-eap-tls" {
        value 13;
        description
          "EAP-TLS";
      }
      enum "eap-type-leap" {
        value 17;
        description
          "EAP-LEAP";
      }
      enum "eap-type-sim" {
        value 18;
        description
          "EAP-SIM";
      }
      enum "eap-type-ttls" {
        value 21;
        description
          "EAP-TTLS";
      }
      enum "eap-type-aka" {
        value 23;
        description
          "EAP-AKA";
      }
      enum "eap-type-peap" {
        value 25;
        description
          "EAP-PEAP";
      }
      enum "eap-type-speke" {
        value 41;
        description
          "SPEKE";
      }
      enum "eap-type-eap-fast" {
        value 43;
        description
          "EAP-FAST";
      }
    }
    description
      "Lists all supported EAP types in the device";
  }

  typedef enm-apf-xor-roam-probe-suppression {
    type enumeration {
      enum "apf-xor-suppress-opmode-disabled" {
        value 0;
        description
          "Disabled";
      }
      enum "apf-xor-suppress-opmode-probe-suppress" {
        value 1;
        description
          "This object specifies the Enables mode to suppress only probes";
      }
      enum "apf-xor-suppress-opmode-authprobe-suppress" {
        value 2;
        description
          "This object specifies the Enables mode to suppress probes and single auth";
      }
      enum "apf-xor-suppress-opmode-invalid" {
        value 3;
        description
          "Invalid";
      }
    }
    description
      "This object specifies the Configures micro-Macro probe suppression arguments";
  }

  typedef rogue-rldp-result {
    type enumeration {
      enum "rogue-rldp-none" {
        value 0;
        description
          "Unknown rldp result";
      }
      enum "rogue-rldp-no-rogue" {
        value 1;
        description
          "This object specifies the Rogue not found in DB";
      }
      enum "rogue-rldp-managed-ap" {
        value 2;
        description
          "This object specifies the Trying to run RLDP on a managed AP";
      }
      enum "rogue-rldp-friendly" {
        value 3;
        description
          "This object specifies the Trying to run RLDP on a friendly rogue";
      }
      enum "rogue-rldp-no-ap" {
        value 4;
        description
          "This object specifies the No AP found to run RLDP";
      }
      enum "rogue-rldp-ap-in-use" {
        value 5;
        description
          "This object specifies the The selected AP is already in use for another RLDP";
      }
      enum "rogue-rldp-already-in-progress" {
        value 6;
        description
          "This object specifies the RLDP is already in progress on this rogue";
      }
      enum "rogue-rldp-encr-enabled" {
        value 7;
        description
          "This object specifies the Rogue is using an encrypted SSID";
      }
      enum "rogue-rldp-no-ssid" {
        value 8;
        description
          "This object specifies the The SSID of the rogue is hidden";
      }
      enum "rogue-rldp-ssid-too-long" {
        value 9;
        description
          "This object specifies the The SSID name of the rogue is too long";
      }
      enum "rogue-rldp-state-changed-auto" {
        value 10;
        description
          "This object specifies the Rogue state changed because of autocontainment";
      }
      enum "rogue-rldp-auth-timeout" {
        value 11;
        description
          "This object specifies the Auth failed";
      }
      enum "rogue-rldp-assoc-timeout" {
        value 12;
        description
          "This object specifies the association timeout";
      }
      enum "rogue-rldp-dhcp-timeout" {
        value 13;
        description
          "This object specifies the DHCP failed";
      }
      enum "rogue-rldp-not-connected" {
        value 14;
        description
          "This object specifies the Special case for UDP timeout";
      }
      enum "rogue-rldp-connected" {
        value 15;
        description
          "This object specifies the the rogue AP is connected to our network";
      }
      enum "rogue-rldp-error" {
        value 16;
        description
          "This object specifies the the generic error occured";
      }
    }
    description
      "Lists all possible results of the rldp operation";
  }

  typedef ft-dot11r-mode {
    type enumeration {
      enum "dot11r-disabled" {
        value 0;
        description
          "FT mode is 11r disabled";
      }
      enum "dot11r-enabled" {
        value 1;
        description
          "FT mode is 11r enabled";
      }
      enum "dot11r-adaptive-enabled" {
        value 2;
        description
          "This object specifies the Configures Fast Transition Adaptive support";
      }
    }
    description
      "This object specifies the This object specifies the 802.11r Fast Transition Mode";
  }

  typedef ap-misconfig-state {
    type enumeration {
      enum "not-misconfigured" {
        value 0;
        description
          "Profile-tag is not misconfigured";
      }
      enum "misconfigured" {
        value 1;
        description
          "Profile-tag is misconfigured";
      }
    }
    description
      "Enum for profile-tag misconfigure state";
  }

  typedef ap-tag-register-state {
    type enumeration {
      enum "ap-tag-reg-not-done" {
        value 0;
        description
          "AP tag registration is not done";
      }
      enum "ap-tag-reg-done" {
        value 1;
        description
          "AP tag registration is done";
      }
    }
    description
      "Enum for ap tag registration";
  }

  typedef enm-export-anchor-priority-type {
    type enumeration {
      enum "export-anchor-primary" {
        value 1;
        description
          "export anchor primary";
      }
      enum "export-anchor-secondary" {
        value 2;
        description
          "export anchor secondary";
      }
      enum "export-anchor-tertiary" {
        value 3;
        description
          "export anchor tertiary";
      }
    }
    description
      "Enum for export anchor priority";
  }

  typedef ewlc-guest-lan-has-wired-vlan {
    type enumeration {
      enum "ewlc-guest-lan-without-wired-vlan" {
        value 1;
        description
          "Value indicating Guest Anchor";
      }
      enum "ewlc-guest-lan-with-wired-vlan" {
        value 2;
        description
          "Value indicating Guest Foreign";
      }
    }
    description
      "Enum for Wired Guest controller parameter has_wired_vlan";
  }

  typedef client-type {
    type enumeration {
      enum "tspec-client" {
        value 1;
        description
          "TSPEC voice client type";
      }
      enum "sip-client" {
        value 2;
        description
          "SIP voice client";
      }
    }
    description
      "Enum for voice client type";
  }

  typedef eogre-client-match-reason {
    type enumeration {
      enum "match-pending-classify" {
        value 0;
        description
          "client pending classification";
      }
      enum "match-simple-client" {
        value 1;
        description
          "simple client";
      }
      enum "match-eogre-client-rule" {
        value 2;
        description
          "EoGRE client matching profile";
      }
      enum "match-eogre-client-aaa-override" {
        value 3;
        description
          "EoGRE client with aaa data";
      }
      enum "match-eogre-client-handoff" {
        value 4;
        description
          "EoGRE client mobility handoff";
      }
      enum "match-eogre-client-ft-info" {
        value 5;
        description
          "EoGRE client standalone AP recover";
      }
      enum "match-error" {
        value 6;
        description
          "client classification error";
      }
    }
    description
      "Enum for matching client type to eogre";
  }

  typedef mcs-index {
    type enumeration {
      enum "he-mcs-index-7" {
        value 7;
        description
          "Config MCS data rate for index 7";
      }
      enum "he-mcs-index-9" {
        value 9;
        description
          "Config MCS data rate for index 9";
      }
      enum "he-mcs-index-11" {
        value 11;
        description
          "Config MCS data rate for index 11";
      }
    }
    description
      "Enum for Dot11ax MCS Data rate index";
  }

  typedef enm-wlan-mdns-sd-cfg {
    type enumeration {
      enum "mdns-sd-bridging" {
        value 0;
        description
          "Option for enabling MDNS bridging on WLAN";
      }
      enum "mdns-sd-drop" {
        value 1;
        description
          "Option for dropping MDNS packets on WLAN";
      }
      enum "mdns-sd-gateway" {
        value 2;
        description
          "Option for enabling MDNS gateway on WLAN";
      }
    }
    description
      "enum for MDNS mode configuration";
  }

  typedef enm-channel-switch-mode {
    type enumeration {
      enum "chan-switch-mode-loud" {
        value 0;
        description
          "Channel switch mode loud";
      }
      enum "chan-switch-mode-quiet" {
        value 1;
        description
          "Channel switch mode quiet";
      }
    }
    description
      "Enum for channel switch mode";
  }

  typedef rrm-channel-change-reason {
    type enumeration {
      enum "chan-change-local" {
        value 0;
        description
          "RRM channel change reason is local";
      }
      enum "chan-change-auto" {
        value 1;
        description
          "RRM channel change reason is auto";
      }
      enum "chan-change-auto-default" {
        value 2;
        description
          "RRM channel change reason is auto default";
      }
      enum "chan-change-static" {
        value 3;
        description
          "RRM channel change reason is static";
      }
      enum "chan-change-static-default" {
        value 4;
        description
          "RRM channel change reason is static default";
      }
      enum "chan-change-radar" {
        value 5;
        description
          "RRM channel change reason is radar";
      }
      enum "chan-change-radar-clear" {
        value 6;
        description
          "RRM channel change reason is radar clear";
      }
      enum "chan-change-edrrm" {
        value 7;
        description
          "RRM channel change reason is Event-driven RRM";
      }
      enum "chan-change-rldp" {
        value 8;
        description
          "RRM channel change reason is RLDP";
      }
      enum "chan-change-intf" {
        value 9;
        description
          "RRM channel change reason is Interference";
      }
      enum "chan-change-unknown" {
        value 10;
        description
          "RRM channel change reason is unknown";
      }
    }
    description
      "RRM channel change reason";
  }

  typedef enm-multicast-data-rate {
    type enumeration {
      enum "mcast-data-rate-default" {
        value 0;
        description
          "Multicast data rate default";
      }
      enum "mcast-data-rate-6m" {
        value 6;
        description
          "Multicast data rate 6M";
      }
      enum "mcast-data-rate-9m" {
        value 9;
        description
          "Multicast data rate 9M";
      }
      enum "mcast-data-rate-12m" {
        value 12;
        description
          "Multicast data rate 12M";
      }
      enum "mcast-data-rate-18m" {
        value 18;
        description
          "Multicast data rate 18M";
      }
      enum "mcast-data-rate-24m" {
        value 24;
        description
          "Multicast data rate 24M";
      }
      enum "mcast-data-rate-36m" {
        value 36;
        description
          "Multicast data rate 36M";
      }
      enum "mcast-data-rate-48m" {
        value 48;
        description
          "Multicast data rate 48M";
      }
      enum "mcast-data-rate-54m" {
        value 54;
        description
          "Multicast data rate 54M";
      }
    }
    description
      "Enum for Multicast data rate";
  }

  typedef reg-domain-status {
    type enumeration {
      enum "regulatory-domain-check-status-not-set" {
        value 0;
        description
          "Regulatory Domain check status is Set";
      }
      enum "regulatory-domain-check-status-set" {
        value 1;
        description
          "Regulatory Domain check status is Not Set";
      }
    }
    description
      "Rgulatory domain check status";
  }
}
