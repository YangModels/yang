module Cisco-IOS-XE-bfd {
  namespace "http://cisco.com/ns/yang/Cisco-IOS-XE-bfd";
  prefix ios-bfd;

  import ietf-inet-types {
    prefix inet;
  }


  import Cisco-IOS-XE-native {
    prefix ios;
  }

  import Cisco-IOS-XE-types {
    prefix ios-types;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE Bidirectional Forwarding Detection (BFD) Yang Model.
     Copyright (c) 2016-2018 by Cisco Systems, Inc.
     All rights reserved.";

  // =========================================================================
  // REVISION
  // =========================================================================
  revision 2019-01-22 {
     description
      "Added leaf for App-hosting Gigabit Ethernet interface";
  }
  revision 2018-10-10 {
     description
       "Added dependency for interface bfd echo";
  }

  revision 2017-11-27 {
     description
       "Added Change 25GE name";
  }

  revision 2017-11-14 {
     description
       "Added 40 and 100GE augmentations";
  }

  revision 2017-09-14 {
     description
       "Modify yang model for new 2gig interface addition";
  }
  revision 2017-08-23 {
     description
       "Modify yang model for interval * command under bfd-template";
  }
  revision 2017-08-16 {
    description
      "This revision has changes for new 5gig and 25gig interfaces addition";
  }
  revision 2017-07-20 {
    description
      "Add interface BDI bfd";
  }
  revision 2017-04-28 {
    description
      "inet:ipv6-prefix changed to ios-types:ipv6-prefix";
  }
  revision 2017-02-07 {
    description
      "Initial revision";
  }


  grouping config-interface-bfd-grouping {
    leaf template {
      description
        "BFD template";
      type string;
    }
    container interval {
      description
        "Transmit interval between BFD packets";
      leaf msecs {
        type uint16 {
          range "50..9999";
        }
      }
      leaf min_rx {
        description
          "Minimum receive interval capability";
        type uint16 {
          range "50..9999";
        }
      }
      leaf multiplier {
        description
          "Multiplier value used to compute holddown";
        type uint8 {
          range "3..50";
        }
      }
    }
    leaf echo {
      description
        "Use echo adjunct as bfd detection mechanism";
      when "../interval/msecs" {
      }
      type boolean;
      default true;
    }
  }

  grouping config-bfd-grouping {
    leaf l2cos {
      description
        "Value of L2 COS for BFD Pkts over VLAN interfaces";
      type uint8 {
        range "0..6";
      }
    }
    container map {
      description
        "configure bfd map entry for multi-hop sessions";
      container ipv4 {
        description
          "IPv4 Address Family";
        container no-vrf {
          leaf dest-ip {
            type inet:ipv4-prefix;
          }
          leaf src-ip {
            type inet:ipv4-prefix;
          }
          leaf template-name {
            type string;
          }
        }
        container vrf {
          description
            "Destination VRF name";
          list dst-vrf {
            key "dst-vrf";
            leaf dst-vrf {
              description
                "Destination VRF instance name";
              type string;
            }
            leaf A_PERIOD_B_PERIOD_C_PERIOD_D_SLASH_nn {
              description
                "Destination IP prefix/len";
              type empty;
            }
          }
        }
      }
      container ipv6 {
        description
          "IPv6 Address Family";
        list dp-ipv6_prefix {
          key "dp-ipv6_prefix";
          leaf dp-ipv6_prefix {
            description
              "Destination IPv6 prefix/len";
            type ios-types:ipv6-prefix;
          }
          leaf bfd-nm {
            description
              "bfd template name";
            type string;
          }
          list src-ipv6_prefix0 {
            key "src-ipv6_prefix0";
            leaf src-ipv6_prefix0 {
              description
                "Source IPv6 prefix/len";
              type ios-types:ipv6-prefix;
            }
            leaf bfd-name {
              description
                "bfd template name";
              type string;
            }
          }
          container vrf {
            description
              "Source VRF name";
            list src-vrf {
              key "src-vrf";
              leaf src-vrf {
                description
                  "Source VRF instance name";
                type string;
              }
              leaf src-ipv6_prefix {
                description
                  "Source IPv6 prefix/len";
                type ios-types:ipv6-prefix;
              }
            }
          }
        }
        container vrf {
          description
            "Destination VRF name";
          list dst-vrf {
            key "dst-vrf";
            leaf dst-vrf {
              description
                "Destination VRF instance name";
              type string;
            }
            leaf dst-ipv6_prefix {
              description
                "Destination IPv6 prefix/len";
              type ios-types:ipv6-prefix;
            }
          }
        }
      }
    }
    leaf slow-timers {
      description
        "Value in ms to use for slow timers";
      type uint16 {
        range "1000..30000";
      }
    }
  }

  typedef range-type {
    type union {
      type uint32 {
        range "4..9999";
      }
      type uint32 {
        range "3300..9999000";
      }
    }
  }

  grouping config-bfd-template-grouping {
    list single-hop {
      description
        "Single-hop template";
      key "name";
      leaf name {
        type string;
      }
      container interval {
        description
          "Transmit interval between BFD packets";
        leaf microseconds {
          description
            "Specify BFD timers in microseconds";
          type empty;
        }
        choice both-or-tx-rx {
          case both {
            leaf both {
              description
                "Minimum transmit and receive interval capability";
              type range-type;  
            }
          }  
          case tx-rx {
            leaf min-tx {
              description
                "Minimum transmit interval capability";
              type range-type;
            }
            leaf min-rx {
              description
                "Minimum receive interval capability";
              type range-type;
            }
          }
        }
        leaf multiplier {
          description
            "Multiplier value used to compute holddown";
          type uint8 {
            range "3..50";
          }
        }
      }        
    }
    list multi-hop {
      description
        "Multi-hop template";
      key "name";
      leaf name {
        type string;
      }
      container interval {
        description
          "Transmit interval between BFD packets";
        leaf microseconds {
          description
            "Specify BFD timers in microseconds";
          type empty;
        }
        choice both-or-tx-rx {
          case both {
            leaf both {
              description
                "Minimum transmit and receive interval capability";
              type range-type;  
            }
          }  
          case tx-rx {
            leaf min-tx {
              description
                "Minimum transmit interval capability";
              type range-type;
            }
            leaf min-rx {
              description
                "Minimum receive interval capability";
              type range-type;
            }
          }
        }
        leaf multiplier {
          description
            "Multiplier value used to compute holddown";
          type uint8 {
            range "3..50";
          }
        }
      }        
    }  
  }

  /////////////////////////////////////////////////////////
  // bfd
  /////////////////////////////////////////////////////////
  augment "/ios:native/ios:bfd" {
    uses config-bfd-grouping;
  }

  /////////////////////////////////////////////////////////
  // bfd-template
  /////////////////////////////////////////////////////////
  augment "/ios:native/ios:bfd-template" {
    uses config-bfd-template-grouping;
  }

  /////////////////////////////////////////////////////////
  // interface * / bfd
  /////////////////////////////////////////////////////////
  augment "/ios:native/ios:interface/ios:FastEthernet/ios:bfd" {
    uses config-interface-bfd-grouping;
  }

  augment "/ios:native/ios:interface/ios:GigabitEthernet/ios:bfd" {
    uses config-interface-bfd-grouping;
  }

  augment "/ios:native/ios:interface/ios:TenGigabitEthernet/ios:bfd" {
    uses config-interface-bfd-grouping;
  }

  augment "/ios:native/ios:interface/ios:TwoGigabitEthernet/ios:bfd" {
    uses config-interface-bfd-grouping;
  }

  augment "/ios:native/ios:interface/ios:FiveGigabitEthernet/ios:bfd" {
    uses config-interface-bfd-grouping;
  }

  augment "/ios:native/ios:interface/ios:AppGigabitEthernet/ios:bfd" {
    uses config-interface-bfd-grouping;
  }

  augment "/ios:native/ios:interface/ios:TwentyFiveGigE/ios:bfd" {
    uses config-interface-bfd-grouping;
  }

  augment "/ios:native/ios:interface/ios:FortyGigabitEthernet/ios:bfd" {
    uses config-interface-bfd-grouping;
  }

  augment "/ios:native/ios:interface/ios:HundredGigE/ios:bfd" {
    uses config-interface-bfd-grouping;
  }

  augment "/ios:native/ios:interface/ios:Vlan/ios:bfd" {
    uses config-interface-bfd-grouping;
  }

  augment "/ios:native/ios:interface/ios:Tunnel/ios:bfd" {
    uses config-interface-bfd-grouping;
  }

  augment "/ios:native/ios:interface/ios:Port-channel/ios:bfd" {
    uses config-interface-bfd-grouping;
  }

  augment "/ios:native/ios:interface/ios:VirtualPortGroup/ios:bfd" {
    uses config-interface-bfd-grouping;
  }
  augment "/ios:native/ios:interface/ios:BDI/ios:bfd" {
    uses config-interface-bfd-grouping;
  }
}
