module Cisco-IOS-XE-eigrp-oper {
  yang-version 1;
  namespace "http://cisco.com/ns/yang/Cisco-IOS-XE-eigrp-oper";
  prefix eigrp-ios-xe-oper;

  import ietf-inet-types {
    prefix inet;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for EIGRP operational data.
     Copyright (c) 2019 by Cisco Systems, Inc.
     All rights reserved.";

  revision 2019-01-11 {
    description
      "Initial revision";
    reference "1.0.0";
  }

  typedef eigrp-ios-oper-afi {
    type enumeration {
      enum "eigrp-af-illegal" {
        value 0;
        description
          "Unsupported Address Family";
      }
      enum "eigrp-af-ipv4" {
        value 1;
        description
          "Address Family IPv4";
      }
      enum "eigrp-af-ipv6" {
        value 2;
        description
          "Address Family IPv6";
      }
      enum "eigrp-af-sf-ipv4" {
        value 3;
        description
          "Service Family IPv4";
      }
      enum "eigrp-af-sf-ipv6" {
        value 4;
        description
          "Service Family IPv6";
      }
    }
    description
      "Address Family";
  }

  typedef eigrp-ios-oper-authentication-mode {
    type enumeration {
      enum "eigrp-auth-none" {
        value 0;
        description
          "No Authentication";
      }
      enum "eigrp-auth-md5" {
        value 1;
        description
          "MD5 Authentication";
      }
      enum "eigrp-auth-hmac-sha-256" {
        value 2;
        description
          "HMAC SHA256 Authentication";
      }
    }
    description
      "EIGRP authentication mode";
  }

  typedef eigrp-ios-oper-origin-type {
    type enumeration {
      enum "eigrp-origin-connected" {
        value 0;
        description
          "Origin - Connected";
      }
      enum "eigrp-origin-rediststatic" {
        value 1;
        description
          "Origin - Redistributed Static";
      }
      enum "eigrp-origin-redistconnect" {
        value 2;
        description
          "Origin - Redistributed Connected";
      }
      enum "eigrp-origin-redistributed" {
        value 3;
        description
          "Origin - Redistributed";
      }
      enum "eigrp-origin-vpnv4" {
        value 4;
        description
          "Origin - VPNv4";
      }
      enum "eigrp-origin-summary" {
        value 5;
        description
          "Origin - Summary";
      }
      enum "eigrp-origin-dummy" {
        value 6;
        description
          "Origin - Dummy";
      }
      enum "eigrp-origin-igrp2" {
        value 7;
        description
          "Origin - EIGRP";
      }
      enum "eigrp-origin-vpnv6" {
        value 8;
        description
          "Origin - VPNv6";
      }
      enum "eigrp-origin-count" {
        value 9;
        description
          "Count of Origins";
      }
    }
    description
      "EIGRP origin type";
  }

  grouping eigrp-ios-oper-instance-key {
    description
      "Key to uniquely identify a EIGRP instance";
    leaf afi {
      type eigrp-ios-xe-oper:eigrp-ios-oper-afi;
      description
        "Address Family";
    }
    leaf vrf-name {
      type string;
      description
        "VRF Name";
    }
    leaf as-num {
      type uint16;
      description
        "Autonomous System Number";
    }
  }

  grouping eigrp-ios-oper-instance {
    description
      "EIGRP Instance";
    leaf router-id {
      type uint32;
      description
        "Router-ID";
    }
    leaf named-mode {
      type empty;
      description
        "Named or Classic Mode";
    }
    leaf name {
      type string;
      description
        "EIGRP Virtual-Instance Name";
    }
    list eigrp-interface {
      key "name";
      description
        "EIGRP Interface";
      uses eigrp-ios-xe-oper:eigrp-ios-oper-intf;
    }
    list eigrp-topo {
      key "topo-id";
      description
        "EIGRP Topology";
      uses eigrp-ios-xe-oper:eigrp-ios-oper-topo;
    }
  }

  grouping eigrp-ios-oper-auth-key {
    description
      "EIGRP Authentication Key";
    leaf key-chain {
      type string;
      description
        "Key-Chain";
    }
    leaf sha256-password {
      type string;
      description
        "HMAC-SHA-256 Password";
    }
  }

  grouping eigrp-ios-oper-auth {
    description
      "EIGRP Authentication";
    leaf auth-mode {
      type eigrp-ios-xe-oper:eigrp-ios-oper-authentication-mode;
      description
        "Authentication Mode";
    }
    container auth-key {
      description
        "Authentication Key";
      uses eigrp-ios-xe-oper:eigrp-ios-oper-auth-key;
    }
  }

  grouping eigrp-ios-oper-intf {
    description
      "EIGRP Interface";
    leaf name {
      type string;
      description
        "Interface Name";
    }
    leaf passive {
      type empty;
      description
        "Passive Enabled/Disabled";
    }
    leaf hello-interval {
      type uint16;
      units "seconds";
      description
        "Hello Interval in Seconds";
    }
    leaf hold-timer {
      type uint16;
      units "seconds";
      description
        "Hold Timer in Seconds";
    }
    container auth-val {
      description
        "Authentication";
      uses eigrp-ios-xe-oper:eigrp-ios-oper-auth;
    }
    list eigrp-nbr {
      key "afi nbr-address";
      description
        "EIGRP Neighbor";
      uses eigrp-ios-xe-oper:eigrp-ios-oper-nbr-key;
      uses eigrp-ios-xe-oper:eigrp-ios-oper-nbr;
    }
  }

  grouping eigrp-ios-oper-nbr-sw-version {
    description
      "EIGRP Neighbor Software Version";
    leaf os-majorver {
      type uint8;
      description
        "EIGRP OS Major Version";
    }
    leaf os-minorver {
      type uint8;
      description
        "EIGRP OS Minor Version";
    }
    leaf tlv-majorrev {
      type uint8;
      description
        "EIGRP TLV Major Version";
    }
    leaf tlv-minorrev {
      type uint8;
      description
        "EIGRP TLV Minor Version";
    }
  }

  grouping eigrp-ios-oper-nbr-stubinfo {
    description
      "EIGRP Neighbor Stub Information";
    leaf stubbed {
      type empty;
      description
        "Stub Enabled/Disabled";
    }
    leaf receive-only {
      type empty;
      description
        "Receive-Only mode Enabled/Disabled";
    }
    leaf allow-connected {
      type empty;
      description
        "Allow Connected Routes";
    }
    leaf allow-static {
      type empty;
      description
        "Allow Static Routes";
    }
    leaf allow-summary {
      type empty;
      description
        "Allow Summary Routes";
    }
    leaf static-nbr {
      type empty;
      description
        "Static Neighbor";
    }
    leaf allow-redist {
      type empty;
      description
        "Allow Redistributed Routes";
    }
    leaf allow-leaking {
      type empty;
      description
        "Allow Leaking of Routes";
    }
  }

  grouping eigrp-ios-oper-nbr-key {
    description
      "Key to Uniquely Identify a EIGRP Neighbor";
    leaf afi {
      type eigrp-ios-xe-oper:eigrp-ios-oper-afi;
      description
        "Address Family";
    }
    leaf nbr-address {
      type inet:ip-address;
      description
        "Neighbor Address";
    }
  }

  grouping eigrp-ios-oper-nbr {
    description
      "EIGRP Neighbor";
    container nbr-sw-ver {
      description
        "Neighbor Software Version";
      uses eigrp-ios-xe-oper:eigrp-ios-oper-nbr-sw-version;
    }
    container nbr-stubinfo {
      description
        "Neighbor Stub Information";
      uses eigrp-ios-xe-oper:eigrp-ios-oper-nbr-stubinfo;
    }
    leaf retransmit-count {
      type uint32;
      description
        "Retransmission Count";
    }
    leaf retry-count {
      type uint16;
      description
        "Retry Count";
    }
    leaf last-seq-number {
      type uint32;
      description
        "Last Sequence Number";
    }
    leaf srtt {
      type uint32;
      description
        "Smooth Round Trip Time";
    }
    leaf rto {
      type uint32;
      description
        "Retransmission Time Out";
    }
  }

  grouping eigrp-ios-oper-topo {
    description
      "EIGRP Topology";
    leaf topo-id {
      type uint32;
      description
        "Topology ID";
    }
    list eigrp-network {
      key "afi ip-prefix";
      description
        "EIGRP Network";
      uses eigrp-ios-xe-oper:eigrp-ios-oper-network-key;
      uses eigrp-ios-xe-oper:eigrp-ios-oper-network;
    }
  }

  grouping eigrp-ios-oper-network-key {
    description
      "Key to Uniquely Identify a EIGRP Network";
    leaf afi {
      type eigrp-ios-xe-oper:eigrp-ios-oper-afi;
      description
        "Address Family";
    }
    leaf ip-prefix {
      type inet:ip-prefix;
      description
        "IP Prefix";
    }
  }

  grouping eigrp-ios-oper-metric {
    description
      "EIGRP Vector Metric";
    leaf bandwidth {
      type uint64;
      description
        "Bandwidth";
    }
    leaf delay {
      type uint64;
      description
        "Delay";
    }
    leaf tag {
      type uint32;
      description
        "Route Tag";
    }
    leaf routerid {
      type uint32;
      description
        "Router-ID";
    }
    leaf mtu {
      type uint16;
      description
        "IP MTU";
    }
    leaf hopcount {
      type uint8;
      description
        "Hop Count";
    }
    leaf reliability {
      type uint8;
      description
        "Reliability";
    }
    leaf load {
      type uint8;
      description
        "Link Load";
    }
  }

  grouping eigrp-ios-oper-network {
    description
      "EIGRP Network";
    leaf rd-metric {
      type uint64;
      description
        "Reported Distance Metric";
    }
    container rd-vecmetric {
      description
        "Reported Distance Vector Metric";
      uses eigrp-ios-xe-oper:eigrp-ios-oper-metric;
    }
    leaf fd-metric {
      type uint64;
      description
        "Feasible Distance Metric";
    }
    leaf successor-count {
      type uint16;
      description
        "Successor Count";
    }
    leaf active {
      type empty;
      description
        "Active State of the Network";
    }
    list eigrp-route {
      key "afi infosource";
      description
        "EIGRP Route";
      uses eigrp-ios-xe-oper:eigrp-ios-oper-route-key;
      uses eigrp-ios-xe-oper:eigrp-ios-oper-route;
    }
  }

  grouping eigrp-ios-oper-extdatatype {
    description
      "EIGRP External Data";
    leaf routerid {
      type uint32;
      description
        "Router-ID";
    }
    leaf asystem {
      type uint32;
      description
        "Autonomous System";
    }
    leaf tag {
      type uint32;
      description
        "Route Tag";
    }
    leaf ext-metric {
      type uint32;
      description
        "External Metric";
    }
    leaf protocol {
      type uint8;
      description
        "External Protocol";
    }
    leaf flag {
      type uint8;
      description
        "Flags";
    }
  }

  grouping eigrp-ios-oper-route-key {
    description
      "Key to Uniquely Identify a EIGRP Route";
    leaf afi {
      type eigrp-ios-xe-oper:eigrp-ios-oper-afi;
      description
        "Address Family";
    }
    leaf infosource {
      type inet:ip-address;
      description
        "Info Source";
    }
  }

  grouping eigrp-ios-oper-route {
    description
      "EIGRP Route";
    leaf nexthop {
      type inet:ip-address;
      description
        "Next Hop";
    }
    leaf originating-interface {
      type string;
      description
        "Originating Interface";
    }
    leaf metric {
      type uint64;
      description
        "Route Metric";
    }
    container vecmetric {
      description
        "Route Vector Metric";
      uses eigrp-ios-xe-oper:eigrp-ios-oper-metric;
    }
    leaf succ-metric {
      type uint64;
      description
        "Successor Metric";
    }
    container succ-vecmetric {
      description
        "Successor Vector Metric";
      uses eigrp-ios-xe-oper:eigrp-ios-oper-metric;
    }
    leaf origin {
      type eigrp-ios-xe-oper:eigrp-ios-oper-origin-type;
      description
        "Route Origin";
    }
    leaf omp-tag {
      type uint32;
      description
        "OMP tag";
    }
    leaf in-rib {
      type empty;
      description
        "Route in RIB";
    }
    leaf external {
      type empty;
      description
        "External Route";
    }
    container ext-data {
      description
        "External Route";
      uses eigrp-ios-xe-oper:eigrp-ios-oper-extdatatype;
    }
  }

  container eigrp-oper-data {
    config false;
    description
      "EIGRP operational data";
    list eigrp-instance {
      key "afi vrf-name as-num";
      description
        "The EIGRP Instance";
      uses eigrp-ios-xe-oper:eigrp-ios-oper-instance-key;
      uses eigrp-ios-xe-oper:eigrp-ios-oper-instance;
    }
  }
}
