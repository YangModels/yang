module Cisco-IOS-XE-arp {
  namespace "http://cisco.com/ns/yang/Cisco-IOS-XE-arp";
  prefix ios-arp;

  import cisco-semver {
    prefix cisco-semver;
  }
  import ietf-inet-types {
    prefix inet;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Access Point (AP) Group Yang model.
     Copyright (c) 2018-2019 by Cisco Systems, Inc.
     All rights reserved.";

  revision 2019-07-01 {
    description
      "Establish semantic version baseline";
    cisco-semver:module-version "1.0.0";
  }
  revision 2018-06-28 {
    description
      "Added must constraints for deleting vrf";
  }
  revision 2018-06-17 {
    description
      "Add arp alias";
  }
  revision 2017-11-07 {
    description
      "Add arp vrf";
  }
  revision 2017-01-16 {
    description
      "Initial Revision";
  }

  grouping arp-entry-grouping {
    list arp-entry {
      description
        "Configure an arp entry";
      key "ip";
      leaf ip {
        description
          "IP address of ARP entry";
        type inet:ip-address;
      }
      leaf hardware-address {
        description
          "48-bit hardware address of ARP entry";
        type string;
      }
      leaf arp-type {
        type enumeration {
          enum ARPA;
          enum SAP;
          enum SMDS;
          enum SNAP;
          enum SRP-A;
          enum SRP-B;
        }
      }
      leaf alias {
        description
          "Respond to ARP requests for the IP address";
        type empty;
      }
    }
  }

  grouping config-arp-grouping {
    container arp {
      description
        "Set a static ARP entry";
      uses arp-entry-grouping;
      list vrf {
        description
          "Configure static ARP for a VPN Routing/Forwarding instance";
        key "vrf-name";
        leaf vrf-name {
          description
            "VPN Routing/Forwarding instance name";
          must '/ios:native/ios:vrf/ios:definition[ios:name=current()] or /ios:native/ios:ip/ios:vrf[ios:name=current()]' {
            error-message "VRF must be created 1st, deleted last";
          }
          type string;
        }
        uses arp-entry-grouping;
      }
    }
  }

  augment "/ios:native" {
    uses config-arp-grouping;
  }
}
