module Cisco-IOS-XE-netconf-diag-rpc {
  yang-version 1;
  namespace "http://cisco.com/ns/yang/Cisco-IOS-XE-netconf-diag-rpc";
  prefix ios-xe-netconf-diag-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for NETCONF Message Diagnostics RPC.
     Copyright (c) 2020-2021 by Cisco Systems, Inc.
     All rights reserved.";

  revision 2022-03-01 {
    description
      "- Remove Diagnostics logs archive
       - Update description of diag-basic level";
    reference
      "2.0.0";
    cisco-semver:module-version "2.0.0";
  }
  revision 2021-03-01 {
    description
      "Initial revision";
    reference
      "1.0.0";
    cisco-semver:module-version "1.0.0";
  }

  typedef diagnostic-level {
    type enumeration {
      enum diag-disabled {
        value 0;
        description
          "No diagnostic data collection (default).";
      }
      enum diag-basic {
        value 1;
        description
          "Include debugging logs.";
      }
      enum diag-maximum {
        value 2;
        description
          "Include the basic diagnostics plus before and after
           running-config snapshots.";
      }
    }
    description
      "Levels of diagnostic reporting.";
  }

  grouping enable-netconf-diag {
    description
      "NETCONF Message Diagnostics data.";
    leaf diag-level {
      type ios-xe-netconf-diag-rpc:diagnostic-level;
      mandatory true;
      description
        "Choose diagnostic level.";
    }
  }

  rpc enable-netconf-diag {
    description
      "Enable NETCONF Message Diagnostics for providing
       easy access to all information required to diagnose
       NETCONF transaction failures on NED models.";
    input {
      uses ios-xe-netconf-diag-rpc:enable-netconf-diag;
    }
  }
}
