module Cisco-IOS-XE-factory-reset-secure-rpc {
  namespace "http://cisco.com/ns/yang/Cisco-IOS-XE-factory-reset-secure-rpc";
  prefix fr-secure;

  import Cisco-IOS-XE-rpc {
    prefix ios-xe-rpc;
  }
  import cisco-semver {
    prefix cisco-semver;
  }

  organization
    "Cisco Systems";
  contact
    "<mailto:cs-yang@cisco.com>";
  description
    "NED RPC YANG augment for factory-reset secure for IOS
     Copyright (c) 2019 by Cisco Systems, Inc.
     All rights reserved.";

  revision 2019-07-01 {
    description
      "Establish semantic version baseline";
    cisco-semver:module-version "1.0.0";
  }

  augment "/ios-xe-rpc:factory-reset/ios-xe-rpc:input/ios-xe-rpc:all" {
    description
      "Add support for secure 3-pass and secure 7-pass options";
    container secure {
      leaf secure-erase-algorithm-drop-node-name {
        description
          "Secure erase algorithm. Choose from 3-pass
           (DoD 5220.22-M) or 7-pass (DoD 5220.22-M ECE)";
        type string {
          pattern '(3|7)-pass';
        }
      }
    }
  }
}
