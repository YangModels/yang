module cisco-xe-ietf-yang-push-ext {
  /*
   * ---------------------------------------------------
   * Not Supported

  yang-version 1.1;
   * ---------------------------------------------------
   */

  namespace "urn:cisco:params:xml:ns:yang:cisco-xe-ietf-yang-push-ext";

  prefix cyp;
	
  import ietf-event-notifications {
    prefix sn;
  }
  import ietf-yang-push {
    prefix yp;
  }

    organization
        "Cisco Systems, Inc.";

    contact
        " Cisco Systems, Inc.
          Customer Service
          Postal: 170 W Tasman Drive
          San Jose, CA 95134
          Tel: +1 1800 553-NETS
          E-mail: cs-yang@cisco.com";
               
  description
    "This module contains augmentations on top of IETF yang push.";

  revision 2020-04-27 {
    description
      "Removed augments for modify-subscription nodes";
  }

  revision 2019-03-26 {
    description
      "Add cloud-native transport identity";
	reference
      "Adds a new transport identity cloud-native.";
  }

  revision 2018-08-29 {
    description
      "Add KVGPB encoding and grpc-tcp, cntp-tcp, native transport.";
    reference
      "YANG Datastore Push, draft-ietf-netconf-yang-push-04 and
       draft-ietf-netconf-rfc5277bis-01";
  }

  revision 2018-06-06 {
    description
      "Add yang-notif-native";
	reference
      "Adds to new stream identity yang-notif-native.";
  }

  revision 2017-08-14 {
    description
      "Initial version";
	reference 
      "adds to YANG Datastore Push, draft-ietf-netconf-yang-push-04
	  and draft-ietf-netconf-5277bis-01";
  }

 /*
  * IDENTITIES
  */
  
  identity encode-tdl {
    base sn:encodings;
    description
      "Encode data using TDL.";
  }
  
  identity encode-kvgpb {
    base sn:encodings;
    description
      "Encode data using KVGPB.";
  }

  /* Additional types of protocols */
  identity grpc-tcp {
    base sn:transport;
    description
      "gRPC notifications in TCP as a transport";
  }
  
  identity native {
    base sn:transport;
    description
      "native notifications in TCP as a transport";
  }

  identity cntp-tcp {
    base sn:transport;
    description
      "CNTP notifications in TCP as a transport";
  }

  identity cloud-native {
    base sn:transport;
    description
      "Cisco native notifications over a secure tunnel 
       to cloud management service";
  }

  /* Additional types of streams */

  identity tdl-stream {
    base sn:stream;
    description
      "Stream for native TDL datastore updates.";
  }
  
  identity yang-notif-native {
    base sn:stream;
    description
      "Stream for native platform RFC7950 notifications.";
  }

  /*
   * GROUPINGS
   */
  
    grouping tdl-uri-filter {
	  description
	    "Same definition of tdl filter for many places.";
      leaf tdl-uri-filter {
        type string;
        description
          "Filter to support tdl in XE";
      }
    }
  
  /*
   * DATA NODES
   */
  
    augment "/sn:filters/sn:filter/"+
            "sn:filter-type/yp:update-filter/yp:update-filter"	 {
      description
        "This augmentation add native platform filters
         to the list of configurable filters
         that can be applied to subscriptions.";
      case native-filter {
        uses tdl-uri-filter;
      }
    }
    augment "/sn:subscription-config/sn:subscription/"+
            "sn:filter-type/yp:update-filter/yp:update-filter"	 {
      description
        "Add native selection filters to filter types.";
      case native-filter {
        uses tdl-uri-filter;
      }
    }
    augment "/sn:subscriptions/sn:subscription/"+
            "sn:filter-type/yp:update-filter/yp:update-filter"	 {
      description
        "Add native selection filters to filter types.";
      case native-filter {
        uses tdl-uri-filter;
      }
    }

	
  /*
   * RPC
   */


    augment "/sn:establish-subscription/sn:input/"+
            "sn:filter-type/yp:update-filter/yp:update-filter"	 {
      description
        "Add native selection filters to filter types.";
      case native-filter {
        uses tdl-uri-filter;
      }
    }
    augment "/sn:establish-subscription/sn:output/"+
            "sn:result/sn:no-success/" +
            "sn:filter-type/yp:update-filter/yp:update-filter"	 {
      description
        "Add native selection filters to filter types.";
      case native-filter {
        uses tdl-uri-filter;
      }
    }

  /*
   * NOTIFICATIONS
   */	
	
    augment "/sn:subscription-started/" +
            "sn:filter-type/yp:update-filter/yp:update-filter"	 {
      description
        "This augmentation allows native platform filter
         options to be included as part of the notification that a
         subscription has started.";
      case native-filter {
        uses tdl-uri-filter;
      }
    }
    augment "/sn:subscription-modified/" +
            "sn:filter-type/yp:update-filter/yp:update-filter"	 {
      description
        "This augmentation allows native platform filter
         options to be included as part of the notification
         that a subscription has been modified.";
      case native-filter {
        uses tdl-uri-filter;
      }
    }
}
