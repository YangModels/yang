module Cisco-IOS-XE-cable-diag-rpc {
  namespace "http://cisco.com/ns/yang/Cisco-IOS-XE-cable-diag-rpc";
  prefix ios-xe-cable-rpc;

  import cisco-semver {
    prefix cisco-semver;
  }
  import Cisco-IOS-XE-rpc {
    prefix ios-xe-rpc;
  }

  organization
    "Cisco Systems";
  contact
    "<mailto:cs-yang@cisco.com>";
  description
    "NED Zone RPC YANG module for IOS
     Copyright (c) 2016-2019 by Cisco Systems, Inc.
     All rights reserved.";

  revision 2019-11-01 {
    description
      "Added support of two and five gig ports";
  }
  revision 2019-07-01 {
    description
      "- Establish semantic version baseline
       - Created for NED RPC modularisation";
    cisco-semver:module-version "1.0.0";
  }

  augment "/ios-xe-rpc:test/ios-xe-rpc:input/ios-xe-rpc:test-feature" {
    container cable-diagnostics {
      container tdr {
        container interface {
          choice interface-choice {
            leaf GigabitEthernet {
              description
                "Gigabit Ethernet IEEE 802.3z";
              type string;
            }
            leaf TwoGigabitEthernet {
              description
                "Two Gigabit Ethernet";
              type string;
            }
            leaf FiveGigabitEthernet {
              description
                "Five Gigabit Ethernet";
              type string;
            }
            leaf TenGigabitEthernet {
              description
                "Ten Gigabit Ethernet";
              type string;
            }
          }
        }
      }
    }
  }
}
