module Cisco-IOS-XE-wireless-ap-global-oper {
  yang-version 1;
  namespace "http://cisco.com/ns/yang/Cisco-IOS-XE-wireless-ap-global-oper";
  prefix wireless-ap-global-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains access point operational data aggregated across wireless processes.
     Copyright (c) 2020-2022 by Cisco Systems, Inc.
     All rights reserved.";

  revision 2022-07-01 {
    description
      "- Added AP statistics";
    reference
      "1.2.0";
    cisco-semver:module-version "1.2.0";
  }
  revision 2021-07-01 {
    description
      "- Added AP join statistics";
    reference
      "1.1.0";
    cisco-semver:module-version "1.1.0";
  }
  revision 2021-03-01 {
    description
      "Initial revision";
    reference
      "1.0.0";
    cisco-semver:module-version "1.0.0";
  }

  typedef last-failure-phase {
    type enumeration {
      enum ap-con-failure-unknown {
        value 0;
        description
          "Unknown failure";
      }
      enum ap-con-failure-discovery {
        value 1;
        description
          "Failed during discovery phase";
      }
      enum ap-con-failure-dtls {
        value 2;
        description
          "Failed during DTLS phase";
      }
      enum ap-con-failure-join {
        value 3;
        description
          "Failed during join phase";
      }
      enum ap-con-failure-config {
        value 4;
        description
          "Failed during config phase";
      }
      enum ap-con-failure-imgdwnld {
        value 5;
        description
          "Failed during image download phase";
      }
      enum ap-con-failure-run {
        value 6;
        description
          "Failed during run state";
      }
    }
    description
      "Last failure phase of AP connection";
  }

  grouping st-ap-join-info {
    description
      "AP join data";
    leaf ap-ip-addr {
      type string;
      description
        "IP address of the AP";
    }
    leaf ap-ethernet-mac {
      type yang:mac-address;
      description
        "AP ethernet MAC address";
    }
    leaf ap-name {
      type string;
      description
        "Name of the AP";
    }
    leaf is-joined {
      type boolean;
      description
        "AP join status";
    }
    leaf last-error-type {
      type wireless-ap-global-oper:last-failure-phase;
      description
        "Last failure phase of AP connection";
    }
  }

  grouping st-radio-stats {
    description
      "AP radio stats";
    leaf total-radios {
      type uint32;
      description
        "Total number of radios";
    }
    leaf radios-up {
      type uint32;
      description
        "Total number of radios up";
    }
    leaf radios-down {
      type uint32;
      description
        "Total number of radios down";
    }
  }

  grouping ewlc-ap-statistics {
    description
      "AP radio statistics";
    container stats-80211-a-rad {
      description
        "802.11 5 GHz radio stats";
      uses wireless-ap-global-oper:st-radio-stats;
    }
    container stats-80211-bg-rad {
      description
        "802.11 2.4 GHz radio stats";
      uses wireless-ap-global-oper:st-radio-stats;
    }
    container stats-80211-xor-rad {
      description
        "802.11 dual band radio stats";
      uses wireless-ap-global-oper:st-radio-stats;
    }
    container stats-80211-rx-only-rad {
      description
        "802.11 RX radio stats";
      uses wireless-ap-global-oper:st-radio-stats;
    }
    container stats-80211-all-rad {
      description
        "All radio stats";
      uses wireless-ap-global-oper:st-radio-stats;
    }
    container stats-80211bg-clnt-srvg {
      description
        "802.11 2.4 GHz client serving radio stats";
      uses wireless-ap-global-oper:st-radio-stats;
    }
    container stats-80211a-clnt-srvg {
      description
        "802.11 5 GHz client serving radio stats";
      uses wireless-ap-global-oper:st-radio-stats;
    }
    container stats-rad-mon-mode {
      description
        "Monitor radio stats";
      uses wireless-ap-global-oper:st-radio-stats;
    }
    leaf stats-misconfigured-aps {
      type uint32;
      description
        "Total number of misconfigured APs";
    }
    container stats-80211-6ghz-radios {
      description
        "802.11 6 GHz radio stats";
      uses wireless-ap-global-oper:st-radio-stats;
    }
    container stats-80211-6ghz-clnt-srvg {
      description
        "802.11 6 GHz client serving radio stats";
      uses wireless-ap-global-oper:st-radio-stats;
    }
    container dual-band-rad-mon-mode {
      description
        "802.11 dual band monitor radio stats";
      uses wireless-ap-global-oper:st-radio-stats;
    }
    container stats-80211bg-rad-mon-mode {
      description
        "802.11 2.4 GHz monitor radio stats";
      uses wireless-ap-global-oper:st-radio-stats;
    }
    container stats-80211a-rad-mon-mode {
      description
        "802.11 5 GHz monitor radio stats";
      uses wireless-ap-global-oper:st-radio-stats;
    }
    container rad-mon-mode-80211-6ghz {
      description
        "802.11 6 GHz monitor radio stats";
      uses wireless-ap-global-oper:st-radio-stats;
    }
    leaf stats-dtls-lsc-fbk-aps {
      type uint32;
      description
        "Total number of DTLS LSC fallback APs";
    }
    leaf total-high-cpu-reload {
      type uint32;
      description
        "Total number of AP reloads due to high CPU";
    }
    leaf total-high-mem-reload {
      type uint32;
      description
        "Total number of AP reloads due to high memory";
    }
    leaf total-radio-stuck-reset {
      type uint32;
      description
        "Total number of radio stuck resets";
    }
    container dual-band-rad-snfr-mode {
      description
        "802.11 dual band sniffer radio stats";
      uses wireless-ap-global-oper:st-radio-stats;
    }
    container radio-snfr-mode-80211bg {
      description
        "802.11 2.4 GHz sniffer radio stats";
      uses wireless-ap-global-oper:st-radio-stats;
    }
    container radio-snfr-mode-80211a {
      description
        "802.11 5 GHz sniffer radio stats";
      uses wireless-ap-global-oper:st-radio-stats;
    }
    container radio-snfr-mode-80211-6ghz {
      description
        "802.11 6 GHz sniffer radio stats";
      uses wireless-ap-global-oper:st-radio-stats;
    }
    container radio-snfr-mode {
      description
        "All sniffer radio stats";
      uses wireless-ap-global-oper:st-radio-stats;
    }
    container total-80211-xor-5-6ghz-rad {
      description
        "802.11 dual band 5/6 GHz radio stats";
      uses wireless-ap-global-oper:st-radio-stats;
    }
  }

  grouping predownload-stats {
    description
      "AP image predownload statistics";
    leaf num-initiated {
      type uint32;
      description
        "Total number of AP predownload initiated";
    }
    leaf num-in-progress {
      type uint32;
      description
        "Total number of AP predownload in-progress";
    }
    leaf num-complete {
      type uint32;
      description
        "Total number of AP predownload completed";
    }
    leaf num-unsupported {
      type uint32;
      description
        "Total number of AP predownload not supported";
    }
    leaf num-failed {
      type uint32;
      description
        "Total number of AP predownload failed";
    }
    leaf is-predownload-in-progress {
      type boolean;
      description
        "Status of AP image predownload";
    }
    leaf num-total {
      type uint32;
      description
        "Total number of AP connected";
    }
  }

  grouping global-ap-stats {
    description
      "AP aggregated statistics";
    container predownload-stats {
      description
        "AP predownload statistics";
      uses wireless-ap-global-oper:predownload-stats;
    }
    leaf downloads-in-progress {
      type uint32;
      description
        "Total number of APs download in-progress";
    }
    leaf downloads-complete {
      type uint32;
      description
        "Total number of APs download completed";
    }
    container wlc-predownload-stats {
      description
        "Wireless controller predownload statistics";
      uses wireless-ap-global-oper:predownload-stats;
    }
  }

  grouping st-emltd-ap-stats-info {
    description
      "AP join statistics";
    container ap-join-info {
      description
        "AP join information";
      uses wireless-ap-global-oper:st-ap-join-info;
    }
    leaf ap-disconnect-reason {
      type string;
      description
        "Last disconnect reason of AP";
    }
    leaf wtp-mac {
      type yang:mac-address;
      description
        "AP radio MAC address";
    }
  }

  container ap-global-oper-data {
    config false;
    description
      "Root container for AP operational data aggregated across wireless processes";
    container ewlc-ap-stats {
      presence "ewlc-ap-stats";
      description
        "AP radio statistics";
      uses wireless-ap-global-oper:ewlc-ap-statistics;
    }
    container ap-img-predownload-stats {
      presence "ap-img-predownload-stats";
      description
        "AP image predownload stats";
      uses wireless-ap-global-oper:global-ap-stats;
    }
    list ap-join-stats {
      key "wtp-mac";
      description
        "AP join statistics";
      uses wireless-ap-global-oper:st-emltd-ap-stats-info;
    }
  }
}
