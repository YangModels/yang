module Cisco-IOS-XE-wireless-mesh-global-oper {
  yang-version 1;
  namespace "http://cisco.com/ns/yang/Cisco-IOS-XE-wireless-mesh-global-oper";
  prefix wireless-mesh-global-oper;

  import Cisco-IOS-XE-wireless-types {
    prefix wireless-types;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains mesh operational data aggregated across wireless processes.
     Copyright (c) 2021 by Cisco Systems, Inc.
     All rights reserved.";

  revision 2022-03-01 {
    description
      "Initial revision";
    reference
      "1.0.0";
    cisco-semver:module-version "1.0.0";
  }

  grouping st-mesh-global-stats {
    description
      "Statistics of mesh AP's joined to the controller";
    leaf num-of-bridge-aps {
      type uint32;
      description
        "Number of bridge mode AP's";
    }
    leaf num-of-maps {
      type uint32;
      description
        "Number of mesh AP's";
    }
    leaf num-of-raps {
      type uint32;
      description
        "Number of root AP's";
    }
    leaf num-of-flex-bridge-aps {
      type uint32;
      description
        "Number of flex bridge mode AP's";
    }
    leaf num-of-flex-bridge-maps {
      type uint32;
      description
        "Number of flex mesh AP's";
    }
    leaf num-of-flex-bridge-raps {
      type uint32;
      description
        "Number of flex root AP's";
    }
  }

  grouping st-emltd-mesh-ap-info {
    description
      "Mesh AP tree info";
    leaf ap-name {
      type string;
      description
        "AP name";
    }
    leaf ap-role {
      type wireless-types:ap-role;
      description
        "Mesh AP role";
    }
    leaf bridge-group-name {
      type string;
      description
        "Bridge group name configured on this Access Point";
    }
    leaf pref-parent-ap-name {
      type string;
      description
        "Mesh AP parent";
    }
    leaf depth {
      type uint8;
      description
        "Depth of mesh AP in the mesh tree";
    }
    leaf link-snr {
      type uint8;
      units "dB";
      description
        "Calculated SNR of the link";
    }
    leaf curr-freq {
      type uint16;
      description
        "Current operating channel on the AP radio";
    }
    leaf chan-util {
      type uint16;
      units "percentage";
      description
        "Channel utilization";
    }
    leaf clients-count {
      type uint16;
      description
        "Total number of clients connected to the mesh AP";
    }
    leaf not-in-this-wlc {
      type boolean;
      description
        "Indicates mesh AP connected to other controller";
    }
    leaf parent-info-not-avail {
      type boolean;
      description
        "Indicates mesh AP connected to other controller";
    }
  }

  grouping st-emltd-mesh-ap-tree-data {
    description
      "Mesh tree info";
    leaf mesh-ap-count {
      type uint32;
      description
        "Number of Bridge AP's";
    }
    leaf rap-count {
      type uint32;
      description
        "Number of root AP's";
    }
    leaf map-count {
      type uint32;
      description
        "Number of mesh AP's";
    }
    list mesh-ap-list {
      description
        "List of Mesh AP's with path info";
      uses wireless-mesh-global-oper:st-emltd-mesh-ap-info;
    }
  }

  grouping st-emltd-mesh-path-info {
    description
      "Path info of a mesh AP";
    leaf ap-name {
      type string;
      description
        "AP name";
    }
    leaf ap-role {
      type wireless-types:ap-role;
      description
        "Mesh AP role";
    }
    leaf depth {
      type uint8;
      description
        "Depth of mesh AP in the mesh tree";
    }
    leaf link-snr {
      type uint8;
      units "dB";
      description
        "Calculated SNR of the link";
    }
    leaf curr-freq {
      type uint16;
      description
        "Current operating channel on the AP radio";
    }
    leaf rate {
      type string;
      units "Mbps";
      description
        "Mesh backhaul date rate";
    }
    leaf flags {
      type uint32;
      description
        "Indicates mesh node status";
    }
    leaf state {
      type string;
      description
        "State of the mesh AP";
    }
    leaf not-in-this-wlc {
      type boolean;
      description
        "Indicates mesh AP connected to other controller";
    }
  }

  grouping st-emltd-mesh-ap-path-info {
    description
      "List of mesh AP's path info";
    leaf wtp-name {
      type string;
      description
        "AP name";
    }
    list mesh-ap-list {
      description
        "Mesh AP's with path info";
      uses wireless-mesh-global-oper:st-emltd-mesh-path-info;
    }
  }

  grouping st-emltd-mesh-cac-info {
    description
      "Call admission control information of the mesh AP";
    leaf ap-name {
      type string;
      description
        "AP name";
    }
    leaf depth {
      type uint8;
      description
        "Depth of mesh AP in the mesh tree";
    }
    leaf radio-type-slot-id-0 {
      type uint8;
      description
        "Radio slot-0";
    }
    leaf radio-type-slot-id-1 {
      type uint8;
      description
        "Radio slot-1";
    }
    leaf access-call-bw-24ghz {
      type uint16;
      units "MHz";
      description
        "Access call bandwidth at 24 ghz";
    }
    leaf access-call-bw-5ghz {
      type uint16;
      units "MHz";
      description
        "Access call bandwidth at 5 ghz";
    }
    leaf voice-bw-allocated-24ghz {
      type uint32;
      units "MHz";
      description
        "Voice bandwidth being allocated for 24 ghz radio";
    }
    leaf voice-bw-allocated-5ghz {
      type uint32;
      units "MHz";
      description
        "Voice bandwidth being allocated for 5 ghz radio";
    }
    leaf mesh-call-in-progress-5ghz {
      type uint16;
      description
        "Number of access and mesh calls in progress on radio 5 ghz";
    }
    leaf mesh-call-rejected-24ghz {
      type uint16;
      description
        "Number of mesh calls rejected on radio 24 ghz";
    }
    leaf mesh-call-rejected-5ghz {
      type uint16;
      description
        "Number of mesh calls rejected on radio 5 ghz";
    }
    leaf total-active-calls-24ghz {
      type uint16;
      description
        "Number of active calls on radio 24 ghz";
    }
    leaf total-active-calls-5ghz {
      type uint16;
      description
        "Number of active calls on radio 5 ghz";
    }
    leaf call-in-progress-24ghz {
      type uint16;
      description
        "Number of access and mesh calls in progress on radio 24 ghz";
    }
  }

  grouping st-emltd-mesh-ap-cac-info {
    description
      "List mesh AP's Call admission control information";
    leaf wtp-name {
      type string;
      description
        "AP name";
    }
    list cac-info-list {
      description
        "Mesh AP's with cac info";
      uses wireless-mesh-global-oper:st-emltd-mesh-cac-info;
    }
  }

  container mesh-global-oper-data {
    config false;
    description
      "Root container for mesh operational data aggregated across wireless processes";
    container mesh-global-stats {
      presence "mesh-global-stats";
      description
        "Summary of mesh AP statistics";
      uses wireless-mesh-global-oper:st-mesh-global-stats;
    }
    list mesh-ap-cac-info {
      key "wtp-name";
      description
        "Summary of mesh voice call statistics";
      uses wireless-mesh-global-oper:st-emltd-mesh-ap-cac-info;
    }
    list mesh-ap-path-info {
      key "wtp-name";
      description
        "Mesh AP path from root AP to mesh AP";
      uses wireless-mesh-global-oper:st-emltd-mesh-ap-path-info;
    }
    list mesh-ap-tree-data {
      key "sector-number wtp-mac";
      description
        "Mesh AP tree view";
      uses wireless-types:ewlc-mesh-sector-root-key;
      uses wireless-mesh-global-oper:st-emltd-mesh-ap-tree-data;
    }
  }
}
