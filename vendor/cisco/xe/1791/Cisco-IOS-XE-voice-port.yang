module Cisco-IOS-XE-voice-port {
  namespace "http://cisco.com/ns/yang/Cisco-IOS-XE-voice-port";
  prefix ios-voice-port;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Voice Port Yang model.
     Copyright (c) 2019-2020 by Cisco Systems, Inc.
     All rights reserved.";

  revision 2022-03-01 {
    description
      "- add caller ID CLIs
       - change leaf block to be type empty";
    cisco-semver:module-version "1.2.0";
  }
  revision 2020-07-01 {
    description
      "- add default value to delay-connect
       - change trunk-group string length to 1..64
       - add a when statement in impedance container to block PRI voice port";
    cisco-semver:module-version "1.1.0";
  }
  revision 2020-03-01 {
    description
      "Initial revision";
    cisco-semver:module-version "1.0.0";
  }

  typedef caller-id-start-end-type {
    type enumeration {
      enum #;
      enum *;
      enum A;
      enum B;
      enum C;
      enum D;
    }
  }

  grouping config-voice-port-grouping {
    list voice-port {
      description
        "Voice port configuration";
      key "id";
      leaf id {
        type string;
      }
      leaf description {
        description
          "Description of what this port is connected to";
        type string {
          pattern '.*';
          length "1..64";
        }
      }
      container signal {
        description
          "Configure signaling parameters for the voice port";
        choice signal-choice {
          leaf groundStart {
            description
              "Ground Start signaling type";
            type empty;
          }
          container loopStart-config {
            choice loopStart-choice {
              default "loopStart";
              container loopStart-conf {
                container loopStart {
                  description
                    "Loop Start live feed signaling type";
                  leaf live-feed {
                    description
                      "Live Feed option";
                    type empty;
                  }
                }
              }
              leaf loopStart {
                description
                  "Loop Start signaling type";
                type boolean;
                default "true";
              }
            }
          }
          container did {
            description
              "Direct Inward Dialing signaling type";
            leaf did-type {
              type enumeration {
                enum delay-dial;
                enum immediate;
                enum wink-start;
              }
            }
          }
        }
      }
      leaf compand-type {
        description
          "The quantization and coding type for this voice port";
        type enumeration {
          enum a-law;
          enum u-law;
        }
      }
      container busyout {
        description
          "Configure busyout trigger event and procedure";
        choice busyout-choice {
          leaf forced {
            description
              "Force the voice port in busyout";
            type empty;
          }
          leaf graceful {
            description
              "Put the voice port in graceful busyout mode";
            type empty;
          }
        }
      }
      container caller-id {
        description
          "Configure port caller id parameters";
        leaf enable {
          description
            "Enable caller id on this port";
          type empty;
        }
        leaf block {
          description
            "Block the caller id of the calls made from this port";
          when '../enable';
          type empty;
        }
        container format {
          description
            "Change caller id format";
          when '../enable';
          leaf e911 {
            description
              "Enhanced 911 format";
            type empty;
          }
        }
        container mode {
          description
            "Custom caller ID mode if different from CP tone";
          when '../enable';
          choice mode-choice {
            case BT-case {
              leaf BT {
                description
                  "FSK with DTAS used by British Telecom";
                type empty;
              }
            }
            case FSK-case {
              leaf FSK {
                description
                  "FSK Before or During ring";
                type empty;
              }
            }
            case DTMF-case {
              container DTMF {
                description
                  "DTMF digits with start and end digit code";
                presence "true";
                leaf start {
                  description
                    "DTMF start code";
                  type caller-id-start-end-type;
                }
                leaf end {
                  description
                    "DTMF end code";
                  type caller-id-start-end-type;
                }
              }
            }
          }
        }
        container alerting {
          description
            "Define caller id alerting method";
          when '../enable';
          choice alerting-choice {
            case line-reversal-dsp-case {
              leaf line-reversal {
                description
                  "Line reversal alerting";
                when "../../mode/BT or ../../mode/DTMF or ../../mode/FSK or
                      ../../../cptone = 'FR' or ../../../cptone = 'DE' or
                      ../../../cptone = 'NO' or ../../../cptone = 'IT' or
                      ../../../cptone = 'ES' or ../../../cptone = 'ZA' or
                      ../../../cptone = 'TR' or ../../../cptone = 'GB' or
                      ../../../cptone = 'AT' or ../../../cptone = 'CN' or
                      ../../../cptone = 'HU' or ../../../cptone = 'KR' or
                      ../../../cptone = 'BR' or ../../../cptone = 'SE' or
                      ../../../cptone = 'DK' or ../../../cptone = 'IS' or
                      ../../../cptone = 'NL' or ../../../cptone = 'BE' or
                      ../../../cptone = 'IN' or ../../../cptone = 'SA'";
                type empty;
              }
              leaf dsp-pre-allocate {
                description
                  "Configure DSP pre-allocation";
                type empty;
              }
            }
            case pre-ring-case {
              leaf pre-ring {
                description
                  "Short ring pulse alerting";
                when "../../mode/BT or ../../mode/DTMF or ../../mode/FSK or
                      ../../../cptone = 'FR' or ../../../cptone = 'DE' or
                      ../../../cptone = 'NO' or ../../../cptone = 'IT' or
                      ../../../cptone = 'ES' or ../../../cptone = 'ZA' or
                      ../../../cptone = 'TR' or ../../../cptone = 'GB' or
                      ../../../cptone = 'AT' or ../../../cptone = 'CN' or
                      ../../../cptone = 'HU' or ../../../cptone = 'KR' or
                      ../../../cptone = 'BR' or ../../../cptone = 'SE' or
                      ../../../cptone = 'DK' or ../../../cptone = 'IS' or
                      ../../../cptone = 'NL' or ../../../cptone = 'BE' or
                      ../../../cptone = 'IN' or ../../../cptone = 'SA'";
                type empty;
              }
            }
            case ring-case {
              leaf ring {
                description
                  "Number of ring on cycles";
                type uint8 {
                  range "1..4";
                }
                default "1";
              }
            }
          }
        }
      }
      container connection {
        description
          "Specify Connection Parameters";
        choice conn-choice {
          case tie-line-case {
            leaf tie-line {
              description
                "A tie line";
              type string {
                length "1..32";
              }
            }
          }
          case trunk-case {
            container trunk {
              description
                "A Straight Tie Line";
              leaf trunk-num {
                description
                  "Connection trunk calling number";
                type string {
                  length "1..32";
                }
              }
              choice additional-choice {
                leaf answer-mode {
                  description
                    "Slave mode trunking";
                  type empty;
                }
                leaf retry-timer {
                  description
                    "Timer value for retry connection";
                  type uint8 {
                    range "0..5";
                  }
                }
              }
            }
          }
          case plar-case {
            container plar {
              description
                "Private Line Auto Ring down";
              choice plar-choice {
                leaf plar-num {
                  type string {
                    length "1..32";
                  }
                }
                container opx {
                  description
                    "Off-Premises eXtension option";
                  choice opx-choice {
                    case immediate-case {
                      leaf immediate {
                        description
                          "Ring the destination immediately";
                        type string {
                          length "1..32";
                        }
                      }
                    }
                    case opx-num-only-case {
                      leaf opx-num-only {
                        description
                          "Off-Premises eXtension number";
                        type string {
                          length "1..32";
                        }
                      }
                    }
                    case opx-cut-through-case {
                      leaf opx-num {
                        description
                          "Off-Premises eXtension number";
                        type string {
                          length "1..32";
                        }
                      }
                      leaf cut-through-wait {
                        description
                          "Cut through audio after off hook to Central Office on inbound calls";
                        type uint16 {
                          range "150..750";
                        }
                      }
                    }
                  }
                }
              }
            }
          }
        }
      }
      leaf cptone {
        description
          "Configure voice call progress tone locale";
        type enumeration {
          enum AR;
          enum AU;
          enum AT;
          enum BE;
          enum BR;
          enum CA;
          enum CL;
          enum CN;
          enum CO;
          enum C1;
          enum C2;
          enum CY;
          enum CZ;
          enum DK;
          enum EG;
          enum FI;
          enum FR;
          enum DE;
          enum GH;
          enum GR;
          enum HK;
          enum HU;
          enum IS;
          enum IN;
          enum ID;
          enum IE;
          enum IL;
          enum IT;
          enum JP;
          enum JO;
          enum KE;
          enum KR;
          enum KW;
          enum LB;
          enum LU;
          enum MY;
          enum MT;
          enum MX;
          enum NP;
          enum NL;
          enum NZ;
          enum NG;
          enum NO;
          enum OM;
          enum PK;
          enum PA;
          enum PE;
          enum PH;
          enum PL;
          enum PT;
          enum RU;
          enum SA;
          enum SG;
          enum SK;
          enum SI;
          enum ZA;
          enum ES;
          enum SE;
          enum CH;
          enum TW;
          enum TH;
          enum TR;
          enum AE;
          enum GB;
          enum US;
          enum VE;
          enum ZW;
        }
        default "US";
      }
      container impedance {
        when "not (contains(../id, ':'))";
        description
          "Specify the terminating impedance of the interface";
        leaf imp-type {
          type enumeration {
            enum 600c;
            enum 600r;
            enum 900c;
            enum 900r;
            enum complex1;
            enum complex2;
            enum complex3;
            enum complex4;
            enum complex5;
            enum complex6;
          }
          default "600r";
        }
      }
      container battery-reversal-config {
        choice battery-reversal-choice {
          default "battery-reversal";
          container battery-reversal-conf {
            container battery-reversal {
              description
                "Enable battery-reversal detection";
              leaf answer {
                description
                  "Enable answer supervision";
                type empty;
              }
              leaf detection-delay {
                description
                  "Battery Reversal Detection Delay";
                type uint16 {
                  range "0..800";
                }
                default "0";
              }
            }
          }
          leaf battery-reversal {
            type boolean;
            default "true";
          }
        }
      }
      leaf dial-type {
        description
          "Configure digit forward tone type";
        type enumeration {
          enum dtmf;
          enum mf;
          enum pulse;
        }
        default "dtmf";
      }
      container echo-cancel {
        description
          "Echo-cancellation option";
        leaf enable {
          description
            "Echo Cancel Enable";
          type boolean;
          default "true";
        }
      }
      container input {
        description
          "Configure input gain for voice";
        leaf gain {
          description
            "Configure gain in db for voice input";
          type int8 {
            range "-6..14";
          }
          default "0";
        }
      }
      leaf loop-length {
        description
          "Configure loop length";
        type enumeration {
          enum long;
          enum short;
        }
        default "short";
      }
      container output {
        description
          "Configure output attenuation for voice";
        leaf attenuation {
          description
            "Amount of attenuation inserted at transmit side of the interface";
          type int8 {
            range "-6..14";
          }
        }
      }
      leaf pre-dial-delay {
        description
          "Pre-dial Delay";
        type uint8 {
          range "0..10";
        }
        default "1";
      }
      leaf pulse-digit-detection {
        description
          "Enable/Disable pulse digit detection";
        type boolean;
        default "true";
      }
      container trunk-group {
        description
          "Configure interface to be in a trunk group";
        leaf trunk-group-label {
          description
            "Trunk group label";
          type string {
            length "1..64";
          }
        }
        leaf trunk-group-preference {
          description
            "trunk group preference value";
          type uint8 {
            range "1..64";
          }
        }
      }
      leaf ren {
        description
          "Ringer Equivalence Number";
        type uint8 {
          range "1..5";
        }
        default "1";
      }
      container ring {
        description
          "Ringing parameters";
        leaf frequency {
          description
            "The ring frequency to be used in this voice port";
          type enumeration {
            enum 20;
            enum 25;
            enum 30;
            enum 50;
          }
          default "25";
        }
        leaf dc-offset {
          description
            "Ringing DC-offset values";
          when "../../loop-length = 'long'";
          type enumeration {
            enum 10-volts;
            enum 20-volts;
            enum 24-volts;
            enum 30-volts;
            enum 35-volts;
          }
        }
      }
      container idle-detection {
        description
          "Idle code detection for digital voice";
        leaf code {
          description
            "Idle code to detect";
          type string {
            pattern '0[xX][0-9a-fA-F]{1,2}';
          }
        }
        leaf duration {
          description
            "Idle duration range in seconds, default 6 seconds";
          type uint8 {
            range "1..7";
          }
          default "6";
        }
      }
      container secondary {
        description
          "Secondary call service";
        leaf dialtone {
          description
            "Secondary dial tone option";
          type empty;
        }
      }
      container station-id {
        description
          "Configure station ID";
        leaf name {
          description
            "A string describing station name";
          type string {
            pattern '.*';
            length "1..50";
          }
        }
        leaf number {
          description
            "A full E.164 telephone number";
          type string {
            length "1..24";
          }
        }
      }
      container supervisory {
        description
          "Configure disconnect supervision options";
        leaf custom-cptone {
          description
            "Configure custom call progress tones for call supervision";
          type string {
            length "1..20";
          }
        }
        container disconnect {
          description
            "Configure supervisory disconnect signal";
          choice disconnect-type {
            leaf anytone {
              description
                "All call progressing tones will be detected";
              type empty;
            }
            leaf dualtone {
              description
                "Specify dual tone will be detected";
              type enumeration {
                enum mid-call;
                enum pre-connect;
              }
            }
            leaf signal {
              description
                "Configure supervisory disconnect signal";
              type empty;
            }
          }
        }
        leaf dualtone-detect-params {
          description
            "Configure dual tone detection parameters for call supervision";
          type uint32 {
            range "1..10000";
          }
        }
      }
      container timing {
        description
          "Configure voice timing parameters";
        leaf delay-connect {
          description
            "Delay TDM hair pin connection to avoid race condition";
          type uint8 {
            range "0..200";
          }
          default "20";
        }
        container hookflash-in {
          description
            "Hook flash input duration in milliseconds";
          leaf max-value {
            description
              "Maximum time";
            type uint16 {
              range "50..1550";
            }
            default "1000";
          }
          leaf min-value {
            description
              "Minimum time";
            type uint16 {
              range "0..400";
            }
            default "150";
          }
        }
        leaf guard-out {
          description
            "A time window after call disconnect, no outgoing cal is allowed";
          type uint16 {
            range "300..3000";
          }
          default "2000";
        }
        leaf hookflash-out {
          description
            "Hook flash output duration in milliseconds";
          type uint16 {
            range "50..1550";
          }
          default "400";
        }
        leaf pulse-inter-digit {
          description
            "Pulse dialing inter-digit timing in milliseconds";
          type uint16 {
            range "100..1000";
          }
          default "750";
        }
        leaf sup-disconnect {
          description
            "Minimum timing for supervisory disconnect";
          type uint16 {
            range "50..1500";
          }
          default "350";
        }
        leaf answer-winkwidth {
          description
            "Min time delay between start of incoming seizure and wink in msecs, DID only";
          type uint16 {
            range "110..290";
          }
          default "210";
        }
        leaf clear-wait {
          description
            "Time of inactive seizure signal to declare call cleared in msecs. DID only";
          type uint16 {
            range "200..2000";
          }
          default "400";
        }
        leaf dialout-delay {
          description
            "Delay before sending out digit or cut-thru. DID only";
          type uint16 {
            range "50..5000";
          }
        }
        leaf delay-duration {
          description
            "Max delay signal duration for delay dial signalling in msecs. DID only";
          type uint16 {
            range "100..5000";
          }
          default "2000";
        }
        leaf delay-start {
          description
            "Timing of generation of delay start sig from detect incoming seizure. DID only";
          type uint16 {
            range "20..2000";
          }
          default "300";
        }
        container dial-pulse {
          description
            "Dial pulse. DID only";
          leaf min-delay {
            description
              "Minimum delay";
            type uint16 {
              range "0 | 140..5000";
            }
            default "140";
          }
        }
        leaf wait-wink {
          description
            "Max time to wait for wink signal after sending outgoing seizure. DID only";
          type uint16 {
            range "100..6500";
          }
          default "550";
        }
        leaf wink-duration {
          description
            "Wink duration for wink start signalling in msecs. DID only";
          type uint16 {
            range "50..3000";
          }
          default "200";
        }
        leaf wink-wait {
          description
            "Time to wait before sending wink signal after detecting incoming seizure. DID only";
          type uint16 {
            range "100..6500";
          }
          default "200";
        }
      }
      container translation-profile {
        description
          "Translation profile";
        leaf incoming {
          description
            "Translation Profile for incoming call leg";
          type string {
            length "1..31";
          }
        }
        leaf outgoing {
          description
            "Translation Profile for outgoing call leg";
          type string {
            length "1..31";
          }
        }
      }
      leaf vad {
        description
          "Voice Activity Detection";
        type boolean;
        default "true";
      }
      leaf shutdown {
        description
          "Take voice-port offline";
        type boolean;
        default "false";
      }
    }
  }

  augment "/ios:native" {
    uses config-voice-port-grouping;
  }
}
