module Cisco-IOS-XE-switch-cp-svl-oper {
  yang-version 1;
  namespace "http://cisco.com/ns/yang/Cisco-IOS-XE-switch-cp-svl-oper";
  prefix switch-cp-svl-ios-xe-oper;

  import Cisco-IOS-XE-common-types {
    prefix common-types-ios-xe;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "A collection of YANG definitions for switch control path
     StackWise Virtual operational data.
     Copyright (c) 2020 by Cisco Systems, Inc.
     All rights reserved.";

  revision 2021-03-01 {
    description
      "Initial revision";
    reference
      "1.0.0";
    cisco-semver:module-version "1.0.0";
  }

  grouping svl-member-port-info {
    description
      "Identification and statistics for each port in a StackWise Virtual link";
    leaf if-name {
      type string;
      description
        "Name of the interface";
    }
    leaf bundled {
      type boolean;
      description
        "Port is part of the stack etherchannel";
    }
    leaf is-control-port {
      type boolean;
      description
        "Port is control port of this link";
    }
    leaf total-lmp-tx {
      type uint64;
      description
        "Count of all Link Management Protocol packets sent to peer";
    }
    leaf total-lmp-rx {
      type uint64;
      description
        "Count of all Link Management Protocol packets received from peer";
    }
    leaf last-lmp-tx-seq {
      type uint64;
      description
        "Sequence number of the last Link Management Protocol packet sent to peer";
    }
    leaf last-lmp-rx-seq {
      type uint64;
      description
        "Sequence number of the last Link Management Protocol packet received from peer";
    }
    leaf lmp-latency-tx {
      type uint32;
      description
        "Count of Link Management Protocol latency error packets sent to peer";
    }
    leaf lmp-latency-rx {
      type uint32;
      description
        "Count of Link Management Protocol latency error packets received from peer";
    }
    leaf lmp-seq-err-tx {
      type uint32;
      description
        "Count of Link Management Protocol sequence error packets sent to peer";
    }
    leaf lmp-seq-err-rx {
      type uint32;
      description
        "Count of Link Management Protocol sequence error packets received from peer";
    }
  }

  grouping svl-link-info {
    description
      "StackWise Virtual link information";
    leaf link-num {
      type uint16;
      description
        "StackWise Virtual link number";
    }
    leaf total-sdp-tx {
      type uint64;
      description
        "Count of all StackWise Discovery Protocol packets sent to peer";
    }
    leaf total-sdp-rx {
      type uint64;
      description
        "Count of all StackWise Discovery Protocol packets received from peer";
    }
    leaf last-sdp-tx-seq {
      type uint64;
      description
        "Sequence number of the last StackWise Discovery Protocol packet sent to peer";
    }
    leaf last-sdp-rx-seq {
      type uint64;
      description
        "Sequence number of the last StackWise Discovery Protocol packet received from peer";
    }
    leaf oob1-tx-counter {
      type uint64;
      description
        "Count of Out-of-Band 1 thread packets sent to peer";
    }
    leaf oob1-rx-counter {
      type uint64;
      description
        "Count of Out-of-Band 1 thread packets received from peer";
    }
    leaf oob2-tx-counter {
      type uint64;
      description
        "Count of Out-of-Band 2 thread packets sent to peer";
    }
    leaf oob2-rx-counter {
      type uint64;
      description
        "Count of Out-of-Band 2 thread packets received from peer";
    }
    list member-port {
      description
        "List of the interfaces that are members of this link";
      uses switch-cp-svl-ios-xe-oper:svl-member-port-info;
    }
  }

  container switch-cp-svl-oper-data {
    config false;
    description
      "Switch control path StackWise Virtual operational data";
    list location {
      key "fru slot bay chassis node";
      description
        "A list of data provider locations";
      uses common-types-ios-xe:extended-location;
      list svl-link-info {
        key "link-num";
        description
          "StackWise Virtual link information";
        uses switch-cp-svl-ios-xe-oper:svl-link-info;
      }
    }
  }
}
