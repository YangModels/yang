module Cisco-IOS-XE-ospf-deviation {
  namespace "http://cisco.com/ns/yang/Cisco-IOS-XE-ospf-ann";
  prefix ios-ospf-deviation;

  import Cisco-IOS-XE-native {
    prefix ios;
  }
  import Cisco-IOS-XE-ospf {
    prefix ios-ospf;
  }
  import cisco-semver {
    prefix cisco-semver;
  }

  description
    "Copyright (c) 2021 by Cisco Systems, Inc.All rights reserved.";

  revision 2021-11-01 {
    description
      "Adding deviation for microloop avoidance for VRF instance";
    cisco-semver:module-version "1.0.0";
  }

  deviation "/ios:native/ios:router/ios-ospf:router-ospf/ios-ospf:ospf/ios-ospf:process-id-vrf/ios-ospf:microloop" {
    deviate not-supported;
  }
}
