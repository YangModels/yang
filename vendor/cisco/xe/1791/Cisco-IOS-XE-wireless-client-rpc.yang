module Cisco-IOS-XE-wireless-client-rpc {
  yang-version 1;
  namespace "http://cisco.com/ns/yang/Cisco-IOS-XE-wireless-client-rpc";
  prefix wireless-client-rpc;

  import Cisco-IOS-XE-wireless-enum-types {
    prefix wireless-enum-types;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for wireless client features.
     Copyright (c) 2022 by Cisco Systems, Inc.
     All rights reserved.";

  revision 2022-07-01 {
    description
      "Initial revision";
    reference
      "1.0.0";
    cisco-semver:module-version "1.0.0";
  }

  grouping clear-sisf-binding-state {
    description
      "Delete client binding entry based on client MAC and entry state";
    leaf entry-mac-address {
      type yang:mac-address;
      mandatory true;
      description
        "Wireless Client MAC address";
    }
    leaf binding-state {
      type wireless-enum-types:enm-sisf-binding-state;
      mandatory true;
      description
        "Client binding state";
    }
  }

  grouping clear-sisf-binding-ip {
    description
      "Delete client binding entry based on client MAC and IP address";
    leaf entry-mac-address {
      type yang:mac-address;
      mandatory true;
      description
        "Wireless Client MAC address";
    }
    leaf ip-addr {
      type inet:ip-address;
      mandatory true;
      description
        "Binding entry IP address";
    }
  }

  rpc clear-sisf-binding-state {
    description
      "Delete client binding entry based on client MAC and entry state";
    input {
      uses wireless-client-rpc:clear-sisf-binding-state;
    }
  }

  rpc clear-sisf-binding-ip {
    description
      "Delete client binding entry based on client MAC and IP address";
    input {
      uses wireless-client-rpc:clear-sisf-binding-ip;
    }
  }
}
