module Cisco-IOS-XE-wireless-power-cfg {
  yang-version 1;
  namespace "http://cisco.com/ns/yang/Cisco-IOS-XE-wireless-power-cfg";
  prefix wireless-power-cfg;

  import Cisco-IOS-XE-wireless-types {
    prefix wireless-types;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for wireless power policy configuration data.
     Copyright (c) 2021 by Cisco Systems, Inc.
     All rights reserved.";

  revision 2022-03-01 {
    description
      "Initial revision";
    reference
      "1.0.0";
    cisco-semver:module-version "1.0.0";
  }

  grouping ap-ppe-list {
    description
      "Power policy entry list";
    leaf seq-number {
      type uint32;
      description
        "Interface sequence number";
    }
    choice intf-choice {
      default "ap-pp-intf-unset";
      description
        "Interface type";
      case ap-pp-intf-unset {
        leaf intf-unset {
          type boolean;
          default "true";
          description
            "Interface is not configured";
        }
      }
      case ap-pp-intf-eth {
        container ethernet {
          description
            "Configure ethernet interface";
          uses wireless-types:ap-pp-intf-ethernet;
        }
      }
      case ap-pp-intf-radio {
        container radio {
          description
            "Configure radio interface";
          uses wireless-types:ap-pp-intf-radio;
        }
      }
      case ap-pp-intf-usb {
        container usb {
          description
            "Configure USB interface";
          uses wireless-types:ap-pp-intf-usb;
        }
      }
    }
  }

  grouping ap-power-profile {
    description
      "Power policy configuration";
    leaf profile-name {
      type string {
        length "1..128" {
          error-message "Power profile-name should not be greater than 128 characters";
          error-app-tag "must-violation";
        }
        pattern '[!-~]([ -~]*[!-~])?';
        pattern '[!-~]([ -~]*[!-~])?' {
          error-message "Power profile name must use ASCII 32-126 characters and must not contain leading or trailing spaces";
          error-app-tag "pattern-violation";
        }
      }
      description
        "Power profile name";
    }
    leaf description {
      type string {
        length "0..128";
      }
      description
        "Description for power profile";
    }
    container ap-ppes {
      description
        "Power profile entry lists";
      list ap-ppe {
        key "seq-number";
        max-elements 32;
        description
          "Power profile entry list";
        uses wireless-power-cfg:ap-ppe-list;
      }
    }
  }

  container power-cfg-data {
    description
      "Power policy configuration data";
    container ap-power-profiles {
      description
        "Power policy configuration for APs";
      list ap-power-profile {
        key "profile-name";
        description
          "Power policy configuration for AP";
        uses wireless-power-cfg:ap-power-profile;
      }
    }
  }
}
