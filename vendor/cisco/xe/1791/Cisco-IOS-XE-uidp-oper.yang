module Cisco-IOS-XE-uidp-oper {
  yang-version 1;
  namespace "http://cisco.com/ns/yang/Cisco-IOS-XE-uidp-oper";
  prefix uidp-ios-xe-oper;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     monitoring the Identity Policy feature.
     Copyright (c) 2022 by Cisco Systems, Inc.
     All rights reserved.";

  revision 2022-07-01 {
    description
      "Initial revision";
    reference
      "1.0.0";
    cisco-semver:module-version "1.0.0";
  }

  grouping uidp-user {
    description
      "Identity Policy User to IP";
    leaf id {
      type uint32;
      description
        "Identity Policy User ID";
    }
    leaf username {
      type string;
      description
        "Identity Policy User-IP binding username";
    }
    leaf-list addresses {
      type inet:ip-address;
      ordered-by user;
      description
        "Identity Policy addresses associated with user";
    }
  }

  grouping uidp-user-group {
    description
      "Identity Policy User-Group";
    leaf id {
      type uint32;
      description
        "Identity Policy User-Group ID";
    }
    leaf usergroup-name {
      type string;
      description
        "Identity Policy User-Group name";
    }
  }

  container uidp-oper-data {
    config false;
    description
      "Identity Policy operational data";
    list uidp-user {
      key "username";
      description
        "Identity Policy User to IP binding table";
      uses uidp-ios-xe-oper:uidp-user;
    }
    list uidp-user-group {
      key "usergroup-name";
      description
        "Identity Policy User-Group binding table";
      uses uidp-ios-xe-oper:uidp-user-group;
    }
  }
}
