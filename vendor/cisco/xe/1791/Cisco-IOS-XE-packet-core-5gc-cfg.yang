module Cisco-IOS-XE-packet-core-5gc-cfg {
  yang-version 1;
  namespace "http://cisco.com/ns/yang/Cisco-IOS-XE-packet-core-5gc-cfg";
  prefix packet-core-5gc-cfg;

  import Cisco-IOS-XE-packet-core-types {
    prefix packet-core-types;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Packet-Core 5G Core configuration.
     Copyright (c) 2021 by Cisco Systems, Inc.
     All rights reserved.";

  revision 2021-11-01 {
    description
      "Initial revision";
    reference
      "1.0.0";
    cisco-semver:module-version "1.0.0";
  }

  grouping dnn {
    description
      "Data Network Name (DNN) configuration";
    leaf status {
      type boolean;
      default "false";
      description
        "Administrative status of DNN";
    }
    leaf name {
      type string {
        length "1..128" {
          error-message "DNN must be between 1 and 128 characters";
          error-app-tag "must-violation";
        }
        pattern '[a-z0-9]([-a-z0-9]*[a-z0-9])?' {
          error-message "DNN must be in the format defined in 3GPP TS 23.003";
          error-app-tag "pattern-violation";
        }
      }
      description
        "Data Network Name (DNN)";
    }
    leaf ip-pool-name {
      type string {
        length "0..32";
      }
      default "";
      description
        "IPv4 pool name";
    }
    leaf ipv6-pool-name {
      type string {
        length "0..32";
      }
      default "";
      description
        "IPv6 pool name";
    }
    container sess-ambr {
      description
        "Aggregate maximum bit rate for PDU sessions";
      uses packet-core-types:bitrate;
    }
    leaf policy-profile-uplink {
      type string {
        length "0..32";
      }
      default "";
      description
        "Uplink policy profile name";
    }
    leaf policy-profile-downlink {
      type string {
        length "0..32";
      }
      default "";
      description
        "Downlink policy profile name";
    }
    leaf qos-flow-5qi {
      type uint8 {
        range "1 .. 86";
      }
      must "((current() >= 5 and current() <= 9) or
             (current() >= 69 and current() <= 70) or
             (current() >= 79 and current() <= 80))" {
        error-message "Default QOS flow 5QI value must be within 5-9 or 69-70 or 79-80";
        error-app-tag "must-violation";
      }
      default "9";
      description
        "5QI value to be used for default QoS Flow of PDU sessions";
    }
    container qos-flow-arp {
      description
        "Allocation and retention priority values to be used for default QoS Flow of PDU sessions";
      uses packet-core-types:arp;
    }
    leaf up-int-protection {
      type packet-core-types:userplane-int-protection;
      default "up-int-protect-not-required";
      description
        "User plane integrity protection";
    }
    leaf up-cipher-protection {
      type packet-core-types:userplane-cipher-protection;
      default "up-cipher-protect-not-required";
      description
        "User plane cipher protection";
    }
    leaf ip-mtu {
      type uint16 {
        range "1280 .. 1500";
      }
      default "1424";
      description
        "IPv4 and IPv6 MTU";
    }
  }

  grouping cipher-algo {
    description
      "Priority ordered ciphering algorithms";
    leaf prio-1-alg {
      type packet-core-types:ciphering-algorithm;
      default "encr-alg-128-nea1";
      description
        "Priority 1 ciphering algorithm";
    }
    leaf prio-2-alg {
      type packet-core-types:ciphering-algorithm;
      default "encr-alg-128-nea2";
      description
        "Priority 2 ciphering algorithm";
    }
    leaf prio-3-alg {
      type packet-core-types:ciphering-algorithm;
      default "encr-alg-128-nea3";
      description
        "Priority 3 ciphering algorithm";
    }
    leaf prio-4-alg {
      type packet-core-types:ciphering-algorithm;
      default "encr-alg-nea0";
      description
        "Priority 4 ciphering algorithm";
    }
  }

  grouping integrity-algo {
    description
      "Priority ordered integrity protection algorithms";
    leaf prio-1-alg {
      type packet-core-types:integrity-algorithm;
      default "int-alg-128-nia1";
      description
        "Priority 1 integrity protection algorithm";
    }
    leaf prio-2-alg {
      type packet-core-types:integrity-algorithm;
      default "int-alg-128-nia2";
      description
        "Priority 2 integrity protection algorithm";
    }
    leaf prio-3-alg {
      type packet-core-types:integrity-algorithm;
      default "int-alg-128-nia3";
      description
        "Priority 3 integrity protection algorithm";
    }
    leaf prio-4-alg {
      type packet-core-types:integrity-algorithm;
      default "int-alg-nia0";
      description
        "Priority 4 integrity protection algorithm";
    }
  }

  grouping core-5g {
    description
      "5G Core configuration";
    leaf status {
      type boolean;
      default "false";
      description
        "Administrative status of 5G Core";
    }
    container amf {
      description
        "Access and Mobility Management Function (AMF) identifiers";
      uses packet-core-types:amf;
    }
    leaf sctp-profile-name {
      type string {
        length "0..32" {
          error-message "SCTP profile name must be between 0 and 32 characters";
          error-app-tag "must-violation";
        }
        pattern '([!-~]([ -~]*[!-~])?)?' {
          error-message "SCTP profile name must use ASCII 32-126 characters and must not contain leading or trailing spaces";
          error-app-tag "must-violation";
        }
      }
      default "";
      description
        "SCTP profile to be used for 5G Core";
    }
    leaf gtpu-profile-name {
      type string {
        length "0..32" {
          error-message "GTP-U profile name must be between 0 and 32 characters";
          error-app-tag "must-violation";
        }
        pattern '([!-~]([ -~]*[!-~])?)?' {
          error-message "GTP-U profile name must use ASCII 32-126 characters and must not contain leading or trailing spaces";
          error-app-tag "must-violation";
        }
      }
      default "";
      description
        "GTP-U profile to be used on standalone CPF";
    }
    leaf timer-profile-name {
      type string {
        length "0..32" {
          error-message "Timer profile name must be between 0 and 32 characters";
          error-app-tag "must-violation";
        }
        pattern '([!-~]([ -~]*[!-~])?)?' {
          error-message "Timer profile name must use ASCII 32-126 characters and must not contain leading or trailing spaces";
          error-app-tag "must-violation";
        }
      }
      default "";
      description
        "Timer profile to be used for 5G Core";
    }
    container ue-ambr {
      description
        "Aggregate maximum bit rate for user equipment";
      uses packet-core-types:bitrate;
    }
    leaf authen-mlist-name {
      type string {
        length "0..32" {
          error-message "AAA authentication method list name must be between 0 and 32 characters";
          error-app-tag "must-violation";
        }
        pattern '([!-~]([ -~]*[!-~])?)?' {
          error-message "AAA authentication method list name must use ASCII 32-126 characters and must not contain leading or trailing spaces";
          error-app-tag "must-violation";
        }
      }
      default "";
      description
        "AAA authentication method list";
    }
    container encr-alg {
      description
        "Ciphering algorithms configuration";
      uses packet-core-5gc-cfg:cipher-algo;
    }
    container int-alg {
      description
        "Integrity protection algorithms configuration";
      uses packet-core-5gc-cfg:integrity-algo;
    }
    container dnns {
      description
        "A list of Data Network Names (DNN) served by 5G Core";
      list dnn {
        key "name";
        description
          "Data Network Name (DNN)";
        uses packet-core-5gc-cfg:dnn {
          refine "sess-ambr/downlink" {
            default "2500000";
          }
          refine "sess-ambr/uplink" {
            default "2500000";
          }
          refine "qos-flow-arp/priority" {
            default "1";
          }
          refine "qos-flow-arp/capability" {
            default "preemption-not-capable";
          }
          refine "qos-flow-arp/vulnerability" {
            default "preemption-vulnerable";
          }
        }
      }
    }
  }

  grouping ip-pool-network {
    description
      "Network configuration";
    leaf nw-prefix {
      type inet:ip-prefix;
      description
        "IPv4 pool network prefix configuration";
    }
  }

  grouping ip-pool {
    description
      "IPv4 pool configuration";
    leaf pool-name {
      type string {
        length "1..32" {
          error-message "IPv4 pool name must be between 1 and 32 characters";
          error-app-tag "must-violation";
        }
        pattern '[!-~]([ -~]*[!-~])?' {
          error-message "IPv4 pool name must use ASCII 32-126 characters and must not contain leading or trailing spaces";
          error-app-tag "pattern-violation";
        }
      }
      description
        "IPv4 pool name";
    }
    leaf vrf {
      type string {
        length "0..32";
        pattern '([!-~]([ -~]*[!-~])?)?' {
          error-message "VRF name must use ASCII 32-126 characters and must not contain leading or trailing spaces";
          error-app-tag "pattern-violation";
        }
      }
      default "";
      description
        "VRF name";
    }
    container dns {
      description
        "IPv4 DNS server addresses";
      uses packet-core-types:v4-dns-addrs;
    }
    leaf status {
      type boolean;
      default "false";
      description
        "Administrative status of IPv4 pool";
    }
    container ip-pool-networks {
      description
        "IPv4 networks and subnet masks associated with IPv4 pool";
      list ip-pool-network {
        key "nw-prefix";
        description
          "IPv4 network and subnet mask configuration data";
        uses packet-core-5gc-cfg:ip-pool-network;
      }
    }
  }

  grouping ipv6-pool-network {
    description
      "Network configuration";
    leaf nw-prefix {
      type inet:ip-prefix;
      description
        "IPv6 pool network configuration";
    }
  }

  grouping ipv6-pool {
    description
      "IPv6 pool configuration";
    leaf pool-name {
      type string {
        length "1..32" {
          error-message "IPv6 pool name must be between 1 and 32 characters";
          error-app-tag "must-violation";
        }
        pattern '[!-~]([ -~]*[!-~])?' {
          error-message "IPv6 pool name must use ASCII 32-126 characters and must not contain leading or trailing spaces";
          error-app-tag "pattern-violation";
        }
      }
      description
        "IPv6 pool name";
    }
    leaf vrf {
      type string {
        length "0..32";
        pattern '([!-~]([ -~]*[!-~])?)?' {
          error-message "VRF name must use ASCII 32-126 characters and must not contain leading or trailing spaces";
          error-app-tag "pattern-violation";
        }
      }
      default "";
      description
        "VRF name";
    }
    container dns {
      description
        "IPv6 DNS server addresses";
      uses packet-core-types:v6-dns-addrs;
    }
    leaf status {
      type boolean;
      default "false";
      description
        "Administrative status of IPv6 pool";
    }
    container ipv6-pool-networks {
      description
        "IPv6 network prefix associated with IPv6 pool";
      list ipv6-pool-network {
        must "not(contains(substring(./nw-prefix, 1, 4), 'fe80'))" {
          error-message "IPv6 network address must not be a link-local address";
          error-app-tag "must-violation";
        }
        key "nw-prefix";
        description
          "IPv6 network and prefix length configuration data";
        uses packet-core-5gc-cfg:ipv6-pool-network;
      }
    }
  }

  grouping allowed-dnn {
    description
      "Allowed DNN configuration";
    leaf name {
      type string {
        length "0..128" {
          error-message "Allowed DNN name must be between 0 and 128 characters";
          error-app-tag "must-violation";
        }
        pattern '([a-z0-9]([-a-z0-9]*[a-z0-9])?)?' {
          error-message "Allowed DNN name must be in the format defined in 3GPP TS 23.003";
          error-app-tag "pattern-violation";
        }
      }
      description
        "Allowed Data Network Name (DNN)";
    }
  }

  grouping network-slice {
    description
      "Network slice configuration";
    leaf status {
      type boolean;
      default "false";
      description
        "Administrative status of Network slice";
    }
    leaf name {
      type string {
        length "0..32" {
          error-message "Network slice name must be between 0 and 32 characters";
          error-app-tag "must-violation";
        }
        pattern '[!-~]([ -~]*[!-~])?' {
          error-message "Network slice name must use ASCII 32-126 characters and must not contain leading or trailing spaces";
          error-app-tag "pattern-violation";
        }
      }
      description
        "Network slice name";
    }
    container s-nssai {
      description
        "Single - Network Slice Selection Assistance Information";
      uses packet-core-types:s-nssai;
    }
    leaf default-dnn {
      type string {
        length "0..128" {
          error-message "DNN must be between 0 and 128 characters";
          error-app-tag "must-violation";
        }
        pattern '([a-z0-9]([-a-z0-9]*[a-z0-9])?)?' {
          error-message "DNN must be in the format defined in 3GPP TS 23.003";
          error-app-tag "pattern-violation";
        }
      }
      default "";
      description
        "Default DNN to be used for this slice name";
    }
    container allowed-dnns {
      description
        "A list of Data Network Names (DNN) allowed for this slice";
      list allowed-dnn {
        key "name";
        description
          "Data Network Name (DNN) allowed for this slice";
        uses packet-core-5gc-cfg:allowed-dnn;
      }
    }
  }

  container packet-core-5gc-cfg-data {
    description
      "Packet-Core 5GC configuration data model";
    container packet-core-5g {
      presence "packet-core-5g";
      description
        "5G Core configuration data";
      uses packet-core-5gc-cfg:core-5g {
        refine "ue-ambr/downlink" {
          default "2500000";
        }
        refine "ue-ambr/uplink" {
          default "2500000";
        }
      }
    }
    container slices {
      description
        "A list of network slices served by 5G Core";
      list slice {
        key "name";
        description
          "Network slice";
        uses packet-core-5gc-cfg:network-slice;
      }
    }
    container ip-pools {
      description
        "IPv4 pool configuration";
      list ip-pool {
        key "pool-name";
        description
          "IPv4 pool configuration data";
        uses packet-core-5gc-cfg:ip-pool {
          refine "dns/primary" {
            default "0.0.0.0";
          }
          refine "dns/secondary" {
            default "0.0.0.0";
          }
        }
      }
    }
    container ipv6-pools {
      description
        "IPv6 pool configuration";
      list ipv6-pool {
        key "pool-name";
        description
          "IPv6 pool configuration data";
        uses packet-core-5gc-cfg:ipv6-pool {
          refine "dns/primary" {
            default "0::0";
          }
          refine "dns/secondary" {
            default "0::0";
          }
        }
      }
    }
  }
}
