module Cisco-IOS-XE-wireless-rrm-global-oper {
  yang-version 1;
  namespace "http://cisco.com/ns/yang/Cisco-IOS-XE-wireless-rrm-global-oper";
  prefix wireless-rrm-global-oper;

  import Cisco-IOS-XE-wireless-rrm-types {
    prefix wireless-rrm-types;
  }
  import Cisco-IOS-XE-wireless-types {
    prefix wireless-types;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains rrm operational data.
     Copyright (c) 2021-2022 by Cisco Systems, Inc.
     All rights reserved.";

  revision 2022-07-01 {
    description
      "Initial revision";
    reference
      "1.0.0";
    cisco-semver:module-version "1.0.0";
  }

  grouping st-rrm-channel-params-data {
    description
      "RRM channel parameter data";
    leaf phy-type {
      type wireless-rrm-types:enm-rrm-phy-type;
      description
        "Radio type";
    }
    leaf min-dwell {
      type uint32;
      units "seconds";
      description
        "Minimum channel dwell time";
    }
    leaf avg-dwell {
      type uint32;
      units "seconds";
      description
        "Average channel dwell time";
    }
    leaf max-dwell {
      type uint32;
      units "seconds";
      description
        "Maximum channel dwell time";
    }
    leaf channel-counter {
      type uint32;
      description
        "Channel Update Count";
    }
  }

  grouping st-spectrum-band-data {
    description
      "AP spectrum config for band";
    leaf band-id {
      type wireless-types:enm-ewlc-dot11-radio-band;
      description
        "Band of AP for configuration";
    }
    leaf spectrum-admin-state {
      type boolean;
      description
        "Spectrum admin state";
    }
  }

  grouping st-spectrum-ap-band-config {
    description
      "AP spectrum band config";
    leaf ap-mac {
      type yang:mac-address;
      description
        "MAC address of the AP";
    }
    list spectrum-band-config {
      description
        "Spectrum band config";
      uses wireless-rrm-global-oper:st-spectrum-band-data;
    }
  }

  container rrm-global-oper-data {
    config false;
    description
      "RRM operational data";
    list rrm-channel-params {
      key "phy-type";
      description
        "RRM channel parameter data";
      uses wireless-rrm-global-oper:st-rrm-channel-params-data;
    }
    list spectrum-band-config-data {
      key "ap-mac";
      description
        "AP spectrum config";
      uses wireless-rrm-global-oper:st-spectrum-ap-band-config;
    }
  }
}
