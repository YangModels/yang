module Cisco-IOS-XE-cef-deviation {
  namespace "http://cisco.com/ns/yang/Cisco-IOS-XE-cef-deviation";
  prefix ios-cef-d;

  import Cisco-IOS-XE-native {
    prefix ios;
  }
  import Cisco-IOS-XE-cef {
    prefix ios-cef;
  }

  organization
    "Cisco Systems, Inc.";
  description
    "Cisco XE Native Cisco Express Forwarding (CEF) Deviation Yang model.
     Copyright (c) 2021 by Cisco Systems, Inc.
     All rights reserved.";

  revision 2021-11-01 {
    description
      "Added 'ip[v6] cef distributed' deviation";
  }

  deviation "/ios:native/ios:ip/ios:cef/ios-cef:distributed-boolean" {
    deviate not-supported;
  }

  deviation "/ios:native/ios:ipv6/ios:cef/ios-cef:distributed-boolean" {
    deviate not-supported;
  }

  deviation "/ios:native/ios:ip/ios:cef-v2/ios-cef:distributed-boolean-v2" {
    deviate not-supported;
  }

  deviation "/ios:native/ios:ipv6/ios:cef-v2/ios-cef:distributed-boolean-v2" {
    deviate not-supported;
  }
}
