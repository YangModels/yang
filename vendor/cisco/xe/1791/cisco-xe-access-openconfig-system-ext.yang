module cisco-xe-access-openconfig-system-ext{

  yang-version "1";

  // namespace
  namespace "http://cisco.com/ns/yang/cisco-xe-access-openconfig-system-ext";

  prefix "oc-system-cisco";

  import openconfig-system { prefix oc-sys; }


  // import some basic types
  import openconfig-extensions { prefix oc-ext; }


  // meta
  organization "Cisco";

  contact
    "www.cisco.com";

  description
    "Cisco augmentation to oc-system model.";

  oc-ext:openconfig-version "1.0.2";

  revision "2020-05-13" {
    description
      "Initial-revision";
  }

  augment "/oc-sys:system/oc-sys:state" {
    container license {
      leaf eula {
        type string;
        description
          "The end user license agreement text";
      }
    }
  }
}
