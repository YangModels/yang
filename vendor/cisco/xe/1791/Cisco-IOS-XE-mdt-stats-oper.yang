module Cisco-IOS-XE-mdt-stats-oper {
  yang-version 1;
  namespace "http://cisco.com/ns/yang/Cisco-IOS-XE-mdt-stats-oper";
  prefix mdt-stats;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for MDT statistics.
     Copyright (c) 2022 by Cisco Systems, Inc.
     All rights reserved.";

  revision 2022-03-01 {
    description
      "Initial revision";
    reference
      "1.0.0";
    cisco-semver:module-version "1.0.0";
  }

  grouping mdt-core-stats {
    description
      "Statistics that are used for subscriptions,
          connections, per subscription on each connection
        and so on.";
    leaf update-notifs-sent {
      type uint64;
      description
        "The number of update notifications that were sent";
    }
    leaf update-notif-bytes-sent {
      type uint64;
      description
        "Number of bytes used by the update notifications
         that were sent. This will generally not include
         all of the protocol specific overhead.";
    }
    leaf update-notifs-dropped {
      type uint64;
      description
        "The number of update notifications that were
         dropped due to some error.
         Does not include dropped counts for specific
         reasons if/when they are introduced.";
    }
  }

  grouping mdt-sub-stats-data {
    description
      "Subscription statistics record.";
    leaf id {
      type uint32;
      description
        "Subscription identifier.";
    }
    container stats {
      description
        "The statistics for the subscription.";
      uses mdt-stats:mdt-core-stats;
    }
  }

  grouping mdt-con-stats-data {
    description
      "Connection statistics record.";
    leaf index {
      type uint16;
      description
        "Index of the connection entry.";
    }
    container stats {
      description
        "The statistics for the connection.
         Is the lifetime aggregate usage of the connection
         by all subscriptions.";
      uses mdt-stats:mdt-core-stats;
    }
    list sub-con-stats {
      key "sub-id";
      description
        "The statistics for a specific subscription on this
         connection.";
      uses mdt-stats:mdt-sub-con-stats-data;
    }
  }

  grouping mdt-sub-con-stats-data {
    description
      "The statistics record for a specific subscription
       on this connection.";
    leaf sub-id {
      type uint32;
      description
        "Identifier of the subscription using the
         connection.";
    }
    container stats {
      description
        "Statistics for the subscription on the
         connection.";
      uses mdt-stats:mdt-core-stats;
    }
  }

  container mdt-stats-oper-data {
    config false;
    description
      "Telemetry statistics data";
    list sub-stats {
      key "id";
      description
        "Statistics for a telemetry subscription.";
      uses mdt-stats:mdt-sub-stats-data;
    }
    list con-stats {
      key "index";
      description
        "Statistics for a connection used by telemetry";
      uses mdt-stats:mdt-con-stats-data;
    }
  }
}
