submodule Cisco-IOS-XE-arp-rpc {
  belongs-to Cisco-IOS-XE-rpc {
    prefix ios-xe-rpc;
  }

  import cisco-semver {
    prefix cisco-semver;
  }
  import ietf-inet-types {
    prefix inet;
  }

  organization
    "Cisco Systems";
  contact
    "<mailto:cs-yang@cisco.com>";
  description
    "NED ARP RPC YANG module for IOS
     Copyright (c) 2016-2019 by Cisco Systems, Inc.
     All rights reserved.";

  revision 2019-07-01 {
    description
      "Establish semantic version baseline";
    cisco-semver:module-version "1.0.0";
  }
  revision 2018-12-06 {
    description
      "created for NED RPC modularisation";
  }

  grouping clear-choice-arp-cache-case-grouping {
    container arp-cache {
      description
        "Clear the entire ARP cache";
      presence "true";
      leaf vrf {
        description
          "Clear entries for a VPN Routing/Forwarding instance";
        type string;
      }
      leaf interface {
        description
          "Clear the entire ARP cache on the interface";
        type string {
          pattern '[A-Za-z]([\w/.-]+)';
        }
      }
      leaf ip-drop-node-name {
        description
          "IP address";
        type inet:ipv4-address;
      }
    }
  }
}
