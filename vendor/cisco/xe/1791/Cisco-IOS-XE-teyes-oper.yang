module Cisco-IOS-XE-teyes-oper {
  yang-version 1;
  namespace "http://cisco.com/ns/yang/Cisco-IOS-XE-teyes-oper";
  prefix teyes-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for ThousandEyes (TE) operational data.
     Copyright (c) 2021 by Cisco Systems, Inc.
     All rights reserved.";

  revision 2021-07-01 {
    description
      "Initial revision";
    reference
      "1.0.0";
    cisco-semver:module-version "1.0.0";
  }

  grouping teyes-status {
    description
      "ThousandEyes (TE) status";
    leaf supported-regex {
      type string;
      description
        "ThousandEyes (TE) regular expression - support versions 4.0.0 and onwards";
    }
    leaf installed-version {
      type string;
      description
        "ThousandEyes (TE) version currently installed";
    }
    leaf version-supported {
      type boolean;
      description
        "ThousandEyes (TE) version supported flag - indicates installed TE version compatibility with IOS-XE version";
    }
  }

  container teyes-oper-data {
    config false;
    description
      "ThousandEyes (TE) operational data";
    container teyes-status {
      presence "teyes-status";
      description
        "ThousandEyes (TE) status";
      uses teyes-xe-oper:teyes-status;
    }
  }
}
