module Cisco-IOS-XE-wireless-mesh-rpc {
  yang-version 1;
  namespace "http://cisco.com/ns/yang/Cisco-IOS-XE-wireless-mesh-rpc";
  prefix wireless-mesh-rpc;

  import Cisco-IOS-XE-wireless-enum-types {
    prefix wireless-enum-types;
  }
  import Cisco-IOS-XE-wireless-types {
    prefix wireless-types;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of definitions for
     Wireless Mesh Remote Procedure Calls.
     Copyright (c) 2021-2022 by Cisco Systems, Inc.
     All rights reserved.";

  revision 2022-07-01 {
    description
      "- Added mesh backhaul RRM DCA trigger RPC.";
    reference
      "2.0.0";
    cisco-semver:module-version "2.0.0";
  }
  revision 2021-07-01 {
    description
      "Initial revision";
    reference
      "1.0.0";
    cisco-semver:module-version "1.0.0";
  }

  typedef ap-identifier-type {
    type enumeration {
      enum ap-identifier-name {
        value 0;
        description
          "AP name";
      }
      enum ap-identifier-mac-address {
        value 1;
        description
          "AP MAC address";
      }
    }
    description
      "Access point identification type";
  }

  grouping rrm-80211a-channel-update-mesh-bgn {
    description
      "Trigger RRM DCA run for Mesh backhaul for all RAP in bridge group on 5GHz band";
    leaf bgn-name {
      type string;
      mandatory true;
      description
        "Bridge Group name";
    }
  }

  grouping rrm-80211b-channel-update-mesh-bgn {
    description
      "Trigger RRM DCA run for Mesh backhaul for all RAP in bridge group on 2.4GHz band";
    leaf bgn-name {
      type string;
      mandatory true;
      description
        "Bridge Group name";
    }
  }

  grouping exec-linktest-ap {
    description
      "Execute a link test between 2 bridge mode APs";
    leaf dst-ap-mac {
      type yang:mac-address;
      mandatory true;
      description
        "Radio MAC address of the destination AP";
    }
    leaf pkt-per-sec {
      type uint32 {
        range "1..25000";
      }
      units "pps";
      mandatory true;
      description
        "Packet rate";
    }
    leaf pkt-size {
      type uint32 {
        range "1..1500";
      }
      units "bytes";
      mandatory true;
      description
        "Size of packets for link test";
    }
    leaf duration {
      type uint32 {
        range "10..300";
      }
      units "seconds";
      mandatory true;
      description
        "Total link test duration";
    }
    leaf data-rate-idx {
      type wireless-types:mesh-linktest-rate-idx;
      mandatory true;
      description
        "Dot11a/b/g data rate index";
    }
    choice alternative-choice {
      mandatory true;
      description
        "Identify Source AP by AP name or radio MAC";
      case ap-identifier-name {
        leaf ap-name {
          type string;
          mandatory true;
          description
            "Source AP name";
        }
      }
      case ap-identifier-mac-address {
        leaf mac-addr {
          type yang:mac-address;
          mandatory true;
          description
            "Source AP radio MAC address";
        }
      }
    }
  }

  grouping set-rad-mesh-security-psk-provisioning-delete {
    description
      "Delete the provisioned PSK key on a bridge mode AP";
    choice alternative-choice {
      mandatory true;
      description
        "Identify AP by AP name or radio MAC address";
      case ap-identifier-name {
        leaf ap-name {
          type string;
          mandatory true;
          description
            "AP name";
        }
      }
      case ap-identifier-mac-address {
        leaf mac-addr {
          type yang:mac-address;
          mandatory true;
          description
            "AP Radio MAC address";
        }
      }
    }
  }

  grouping set-rad-mesh-preferred-parent-ap {
    description
      "Configure the preferred parent of a bridge mode AP";
    leaf mac-address {
      type yang:mac-address;
      mandatory true;
      description
        "Radio MAC address of the preferred parent";
    }
    leaf enable {
      type boolean;
      mandatory true;
      description
        "Provision/un-provision the preferred parent";
    }
    choice alternative-choice {
      mandatory true;
      description
        "Identify the Mesh AP using AP name or radio MAC address";
      case ap-identifier-name {
        leaf ap-name {
          type string;
          mandatory true;
          description
            "Mesh AP name";
        }
      }
      case ap-identifier-mac-address {
        leaf mac-addr {
          type yang:mac-address;
          mandatory true;
          description
            "Mesh AP radio MAC address";
        }
      }
    }
  }

  grouping set-rad-mesh-daisy-chain-mode {
    description
      "Configure daisy chain mode on a bridge mode AP";
    leaf daisy-chain-mode {
      type boolean;
      mandatory true;
      description
        "Enable/disable daisy chaining";
    }
    choice alternative-choice {
      mandatory true;
      description
        "Identify Mesh AP by AP name or radio MAC address";
      case ap-identifier-name {
        leaf ap-name {
          type string;
          mandatory true;
          description
            "Mesh AP name";
        }
      }
      case ap-identifier-mac-address {
        leaf mac-addr {
          type yang:mac-address;
          mandatory true;
          description
            "Mesh AP radio MAC address";
        }
      }
    }
  }

  grouping set-rad-mesh-daisy-chain-strict-rap {
    description
      "Configure strict daisy chain mode on a bridge mode AP";
    leaf daisy-chain-strict-rap {
      type boolean;
      mandatory true;
      description
        "Provision/un-provision strict daisy chain mode";
    }
    choice alternative-choice {
      mandatory true;
      description
        "Identify Mesh AP by AP name or radio MAC address";
      case ap-identifier-name {
        leaf ap-name {
          type string;
          mandatory true;
          description
            "Mesh AP name";
        }
      }
      case ap-identifier-mac-address {
        leaf mac-addr {
          type yang:mac-address;
          mandatory true;
          description
            "Mesh AP radio MAC address";
        }
      }
    }
  }

  grouping set-rad-mesh-block-child {
    description
      "Configure block child mode on a bridge mode AP";
    leaf block-child-state {
      type boolean;
      mandatory true;
      description
        "Enable/Disable block child mode";
    }
    choice alternative-choice {
      mandatory true;
      description
        "Identify AP by name or radio MAC address";
      case ap-identifier-name {
        leaf ap-name {
          type string;
          mandatory true;
          description
            "AP name";
        }
      }
      case ap-identifier-mac-address {
        leaf mac-addr {
          type yang:mac-address;
          mandatory true;
          description
            "AP radio MAC address";
        }
      }
    }
  }

  grouping set-rad-mesh-bhaul-radio {
    description
      "Configure backhaul radio slot of a bridge mode AP. This is only applicable to root access points connected over ethernet";
    leaf bhaul-slot-id {
      type uint32 {
        range "0..3";
      }
      mandatory true;
      description
        "Backhaul radio slot ID";
    }
    leaf bhaul-radio-band {
      type wireless-enum-types:enm-radio-band;
      must "(current() = 'band-2-dot-4-ghz') or (current() = 'band-5-ghz')" {
        error-message "Invalid radio band selected";
        error-app-tag "must-violation";
      }
      mandatory true;
      description
        "Backhaul radio band";
    }
    choice alternative-choice {
      mandatory true;
      description
        "Identify AP by name or radio MAC address";
      case ap-identifier-name {
        leaf ap-name {
          type string;
          mandatory true;
          description
            "AP name";
        }
      }
      case ap-identifier-mac-address {
        leaf mac-addr {
          type yang:mac-address;
          mandatory true;
          description
            "AP radio MAC address";
        }
      }
    }
  }

  grouping set-rad-mesh-bhaul-tx-rate {
    description
      "Configure backhaul transmission rate parameters for bridge mode AP";
    leaf bhaul-rate-mcs-index {
      when "(../data-rate = 'mesh-bhaul-rate-type-dot11n') or (../data-rate = 'mesh-bhaul-rate-type-dot11ac') or (../data-rate = 'mesh-bhaul-rate-type-dot11ax')";
      type uint32 {
        range "0..31";
      }
      must "((current() >= 0) and (current() <= 9) and (../data-rate = 'mesh-bhaul-rate-type-dot11ac')) or ((current() >= 0) and (current() <= 11) and (../data-rate = 'mesh-bhaul-rate-type-dot11ax')) or (../data-rate = 'mesh-bhaul-rate-type-dot11n')" {
        error-message "MCS index value is invalid for selected data rate type";
        error-app-tag "must-violation";
      }
      mandatory true;
      description
        "Backhaul transmission MCS rate index";
    }
    leaf spatial-stream {
      when "(../data-rate = 'mesh-bhaul-rate-type-dot11ac') or (../data-rate = 'mesh-bhaul-rate-type-dot11ax')";
      type uint32 {
        range "1..8";
      }
      must "((current() >= 1) and (current() <= 4) and (../data-rate = 'mesh-bhaul-rate-type-dot11ac')) or (../data-rate = 'mesh-bhaul-rate-type-dot11ax')" {
        error-message "Spatial stream value is invalid for selected data rate type";
        error-app-tag "must-violation";
      }
      mandatory true;
      description
        "Mesh backhaul 802.11ac spatial stream";
    }
    leaf data-rate {
      type wireless-types:mesh-bhaul-data-rate-type;
      mandatory true;
      description
        "802.11 data rate. Set to auto or manually select 802.11abg/n/ac";
    }
    leaf bhaul-tx-rate-type {
      when "../data-rate = 'mesh-bhaul-rate-type-dot11abg'";
      type wireless-types:mesh-dot11abg-data-rate;
      mandatory true;
      description
        "Valid 802.11a/b/g data rate";
    }
    choice alternative-choice {
      mandatory true;
      description
        "Identify AP by name or radio MAC address";
      case ap-identifier-name {
        leaf ap-name {
          type string;
          mandatory true;
          description
            "AP name";
        }
      }
      case ap-identifier-mac-address {
        leaf mac-addr {
          type yang:mac-address;
          mandatory true;
          description
            "AP radio MAC address";
        }
      }
    }
  }

  grouping rrm-80211b-ap-rrm-channel-update-mesh {
    description
      "Trigger RRM DCA run for Mesh backhaul for RAP on 2.4GHz band";
    choice alternative-choice {
      mandatory true;
      description
        "Identify the Mesh AP using AP name or radio MAC address";
      case ap-identifier-name {
        leaf ap-name {
          type string;
          mandatory true;
          description
            "Mesh AP name";
        }
      }
      case ap-identifier-mac-address {
        leaf mac-addr {
          type yang:mac-address;
          mandatory true;
          description
            "Mesh AP radio MAC address";
        }
      }
    }
  }

  grouping rrm-80211a-ap-rrm-channel-update-mesh {
    description
      "Trigger RRM DCA run for Mesh backhaul for RAP on 5GHz band";
    choice alternative-choice {
      mandatory true;
      description
        "Identify the Mesh AP using AP name or radio MAC address";
      case ap-identifier-name {
        leaf ap-name {
          type string;
          mandatory true;
          description
            "Mesh AP name";
        }
      }
      case ap-identifier-mac-address {
        leaf mac-addr {
          type yang:mac-address;
          mandatory true;
          description
            "Mesh AP radio MAC address";
        }
      }
    }
  }

  grouping set-rad-mesh-trunking-vlan {
    description
      "Configure the trunk native VLAN for primary port of a wired bridge mode AP";
    leaf vlan-id {
      type uint16 {
        range "1..4094";
      }
      mandatory true;
      description
        "VLAN ID to be configured on primary port";
    }
    choice alternative-choice {
      mandatory true;
      description
        "Identify AP by name or radio MAC address";
      case ap-identifier-name {
        leaf ap-name {
          type string;
          mandatory true;
          description
            "AP name";
        }
      }
      case ap-identifier-mac-address {
        leaf mac-addr {
          type yang:mac-address;
          mandatory true;
          description
            "AP radio MAC address";
        }
      }
    }
  }

  grouping set-rad-mesh-trunking {
    description
      "Enable the default trunk native VLAN or reset native VLAN for primary port on a wired bridge mode AP";
    leaf flag {
      type boolean;
      mandatory true;
      description
        "Enable/Disable VLAN trunking";
    }
    choice alternative-choice {
      mandatory true;
      description
        "Identify AP by name or radio MAC address";
      case ap-identifier-name {
        leaf ap-name {
          type string;
          mandatory true;
          description
            "AP name";
        }
      }
      case ap-identifier-mac-address {
        leaf mac-addr {
          type yang:mac-address;
          mandatory true;
          description
            "AP radio MAC address";
        }
      }
    }
  }

  grouping set-rad-mesh-ethernet-access-vlan {
    description
      "Configure access VLAN mode and ID on a bridge mode AP";
    leaf flag {
      type boolean;
      mandatory true;
      description
        "Enable/Disable access mode for an ethernet port";
    }
    leaf port-num {
      type uint32 {
        range "0..3";
      }
      mandatory true;
      description
        "Ethernet port number to be configured";
    }
    leaf vlan-id {
      type uint16 {
        range "0..4094";
      }
      mandatory true;
      description
        "Set VLAN ID of access port. 0 is the default VLAN";
    }
    choice alternative-choice {
      mandatory true;
      description
        "Identify AP by name or radio MAC address";
      case ap-identifier-name {
        leaf ap-name {
          type string;
          mandatory true;
          description
            "AP name";
        }
      }
      case ap-identifier-mac-address {
        leaf mac-addr {
          type yang:mac-address;
          mandatory true;
          description
            "AP radio MAC address";
        }
      }
    }
  }

  grouping set-rad-mesh-ethernet-trunk-native-vlan {
    description
      "Configure trunk mode and native VLAN ID for a bridge mode AP";
    leaf flag {
      type boolean;
      mandatory true;
      description
        "Enable/Disable trunk mode for an ethernet port";
    }
    leaf port-num {
      type uint32 {
        range "0..3";
      }
      mandatory true;
      description
        "Ethernet port number to be configured";
    }
    leaf vlan-id {
      type uint16 {
        range "1..4094";
      }
      mandatory true;
      description
        "Set native VLAN ID of trunking port";
    }
    choice alternative-choice {
      mandatory true;
      description
        "Identify AP by name or radio MAC address";
      case ap-identifier-name {
        leaf ap-name {
          type string;
          mandatory true;
          description
            "AP name";
        }
      }
      case ap-identifier-mac-address {
        leaf mac-addr {
          type yang:mac-address;
          mandatory true;
          description
            "AP radio MAC address";
        }
      }
    }
  }

  grouping set-rad-mesh-ethernet-trunk-allowed-vlan {
    description
      "Configure allowed vlan on trunk port of a bridge mode AP";
    leaf flag {
      type boolean;
      mandatory true;
      description
        "Add/remove allowed VLAN to/from trunk port";
    }
    leaf port-num {
      type uint32 {
        range "0..3";
      }
      mandatory true;
      description
        "Ethernet port number of trunk port";
    }
    leaf vlan-id {
      type uint16 {
        range "0..4094";
      }
      mandatory true;
      description
        "Set allowed VLAN ID of trunk port. 0 is the default VLAN";
    }
    choice alternative-choice {
      mandatory true;
      description
        "Identify AP by name or radio MAC address";
      case ap-identifier-name {
        leaf ap-name {
          type string;
          mandatory true;
          description
            "AP name";
        }
      }
      case ap-identifier-mac-address {
        leaf mac-addr {
          type yang:mac-address;
          mandatory true;
          description
            "AP radio MAC address";
        }
      }
    }
  }

  rpc rrm-80211a-channel-update-mesh {
    description
      "Trigger RRM DCA run for Mesh backhaul for all RAP on 5GHz band";
  }

  rpc rrm-80211b-channel-update-mesh {
    description
      "Trigger RRM DCA run for Mesh backhaul for all RAP on 2.4GHz band";
  }

  rpc rrm-80211a-channel-update-mesh-bgn {
    description
      "Trigger RRM DCA run for Mesh backhaul for all RAP in bridge group on 5GHz band";
    input {
      uses wireless-mesh-rpc:rrm-80211a-channel-update-mesh-bgn;
    }
  }

  rpc rrm-80211b-channel-update-mesh-bgn {
    description
      "Trigger RRM DCA run for Mesh backhaul for all RAP in bridge group on 2.4GHz band";
    input {
      uses wireless-mesh-rpc:rrm-80211b-channel-update-mesh-bgn;
    }
  }

  rpc exec-linktest-ap {
    description
      "Perform link test between 2 bridge mode APs";
    input {
      uses wireless-mesh-rpc:exec-linktest-ap;
    }
  }

  rpc set-rad-mesh-security-psk-provisioning-delete {
    description
      "Delete the provisioned PSK key on a bridge mode AP";
    input {
      uses wireless-mesh-rpc:set-rad-mesh-security-psk-provisioning-delete;
    }
  }

  rpc set-rad-mesh-preferred-parent-ap {
    description
      "Configure the preferred parent of a mesh AP";
    input {
      uses wireless-mesh-rpc:set-rad-mesh-preferred-parent-ap;
    }
  }

  rpc set-rad-mesh-daisy-chain-mode {
    description
      "Configure daisy chain mode on a mesh AP";
    input {
      uses wireless-mesh-rpc:set-rad-mesh-daisy-chain-mode;
    }
  }

  rpc set-rad-mesh-daisy-chain-strict-rap {
    description
      "Configure strict daisy chain on a mesh AP";
    input {
      uses wireless-mesh-rpc:set-rad-mesh-daisy-chain-strict-rap;
    }
  }

  rpc set-rad-mesh-block-child {
    description
      "Configure block child mode on a bridge mode AP";
    input {
      uses wireless-mesh-rpc:set-rad-mesh-block-child;
    }
  }

  rpc set-rad-mesh-bhaul-radio {
    description
      "Configure the backhaul radio of a bridge mode AP";
    input {
      uses wireless-mesh-rpc:set-rad-mesh-bhaul-radio;
    }
  }

  rpc set-rad-mesh-bhaul-tx-rate {
    description
      "Configure the backhaul transmission parameters of a bridge mode AP";
    input {
      uses wireless-mesh-rpc:set-rad-mesh-bhaul-tx-rate;
    }
  }

  rpc rrm-80211b-ap-rrm-channel-update-mesh {
    description
      "Trigger RRM DCA run for Mesh backhaul for RAP on 2.4GHz band";
    input {
      uses wireless-mesh-rpc:rrm-80211b-ap-rrm-channel-update-mesh;
    }
  }

  rpc rrm-80211a-ap-rrm-channel-update-mesh {
    description
      "Trigger RRM DCA run for Mesh backhaul for RAP on 5GHz band";
    input {
      uses wireless-mesh-rpc:rrm-80211a-ap-rrm-channel-update-mesh;
    }
  }

  rpc set-rad-mesh-trunking-vlan {
    description
      "Configure the trunk VLAN port on a bridge mode AP";
    input {
      uses wireless-mesh-rpc:set-rad-mesh-trunking-vlan;
    }
  }

  rpc set-rad-mesh-trunking {
    description
      "Configure VLAN trunking on a bridge mode AP";
    input {
      uses wireless-mesh-rpc:set-rad-mesh-trunking;
    }
  }

  rpc set-rad-mesh-ethernet-access-vlan {
    description
      "Configure access VLAN on a bridge mode AP ethernet port";
    input {
      uses wireless-mesh-rpc:set-rad-mesh-ethernet-access-vlan;
    }
  }

  rpc set-rad-mesh-ethernet-trunk-native-vlan {
    description
      "Configure native VLAN for a trunk ethernet port on a bridge mode AP";
    input {
      uses wireless-mesh-rpc:set-rad-mesh-ethernet-trunk-native-vlan;
    }
  }

  rpc set-rad-mesh-ethernet-trunk-allowed-vlan {
    description
      "Configure allowed VLAN for a trunk ethernet port on a bridge mode AP";
    input {
      uses wireless-mesh-rpc:set-rad-mesh-ethernet-trunk-allowed-vlan;
    }
  }
}
