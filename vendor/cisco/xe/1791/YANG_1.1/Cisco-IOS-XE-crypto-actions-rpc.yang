module Cisco-IOS-XE-crypto-actions-rpc {
  yang-version 1.1;
  namespace "http://cisco.com/ns/yang/Cisco-IOS-XE-crypto-actions-rpc";
  prefix crypto-actions-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     Crypto RPC.
     Copyright (c) 2020-2022 by Cisco Systems, Inc.
     All rights reserved.";

  revision 2022-07-01 {
    description
      "- Added support for different clear crypto SSL RPC. These are
         crypto-clear-ssl-static, crypto-clear-ssl-user and
         crypto-clear-ssl-profile";
    reference
      "1.1.0";
    cisco-semver:module-version "1.1.0";
  }
  revision 2021-03-01 {
    description
      "Initial revision";
    reference
      "1.0.0";
    cisco-semver:module-version "1.0.0";
  }

  typedef crypto-clear-enum {
    type enumeration {
      enum crypto-clear-pki-counters {
        value 0;
        description
          "Clear PKI counters";
      }
    }
    description
      "Clear crypto type";
  }

  typedef crypto-clear-ssl-static-enum {
    type enumeration {
      enum crypto-clear-ssl-diagnose-error {
        value 0;
        description
          "Clear SSL VPN diagnostic errors";
      }
      enum crypto-clear-ssl-session-counters {
        value 1;
        description
          "Clear SSL VPN session counters";
      }
      enum crypto-clear-ssl-stats-tunnel {
        value 2;
        description
          "Clear SSL VPN tunnel statistics";
      }
      enum crypto-clear-ssl-stats {
        value 3;
        description
          "Clear SSL VPN all statistics";
      }
    }
    description
      "Different types of SSL VPN data which are global. These are not related to
       any specific SSL profile name or user name. These data may be cleared using
       crypto-clear-ssl-static RPC";
  }

  typedef crypto-clear-ssl-user-enum {
    type enumeration {
      enum crypto-clear-ssl-session-user {
        value 0;
        description
          "Clear SSL VPN session counters related to particular user name";
      }
    }
    description
      "Different types of data associated with crypto SSL VPN
       user name that may be cleared with crypto-clear-ssl-user RPC";
  }

  typedef crypto-clear-ssl-profile-enum {
    type enumeration {
      enum crypto-clear-ssl-session-profile {
        value 0;
        description
          "Clear SSL VPN session counters related to a particular SSL profile name";
      }
      enum crypto-clear-ssl-stats-profile {
        value 1;
        description
          "Clear SSL VPN statistics related to a particular SSL profile name";
      }
      enum crypto-clear-ssl-tunnel-profile {
        value 2;
        description
          "Clear SSL VPN tunnel statistics related to particular SSL profile name";
      }
    }
    description
      "Different types of data associated with crypto SSL
       profile that may be cleared with crypto-clear-ssl-profile RPC";
  }

  grouping crypto-clear-type {
    description
      "Top level global crypto clear command";
    leaf clear-type {
      type crypto-actions-rpc:crypto-clear-enum;
      mandatory true;
      description
        "crypto clear sub command";
    }
  }

  grouping clear-ssl-static-statistics {
    description
      "Clear crypto SSL static statistics related grouping";
    leaf clear-static-type {
      type crypto-actions-rpc:crypto-clear-ssl-static-enum;
      mandatory true;
      description
        "Selection of SSL static statistics related action";
    }
  }

  grouping clear-ssl-user {
    description
      "Clear crypto SSL user related grouping";
    leaf clear-user-type {
      type crypto-actions-rpc:crypto-clear-ssl-user-enum;
      mandatory true;
      description
        "Selection of SSL user related action";
    }
    leaf user-name {
      type string {
        length "1..64";
      }
      mandatory true;
      description
        "User name to be given (Maximum length is 64 characters)";
    }
  }

  grouping clear-ssl-profile {
    description
      "Clear crypto SSL profile related grouping";
    leaf clear-profile-type {
      type crypto-actions-rpc:crypto-clear-ssl-profile-enum;
      mandatory true;
      description
        "Selection of SSL profile related action";
    }
    leaf profile-name {
      type string {
        length "1..127";
      }
      mandatory true;
      description
        "SSL profile name to be given (Maximum length is 127 characters)";
    }
  }

  rpc crypto-clear {
    description
      "Crypto action RPC";
    input {
      uses crypto-actions-rpc:crypto-clear-type;
    }
  }

  rpc crypto-clear-ssl-static {
    description
      "Clear crypto SSL VPN data. Refer enum crypto-clear-ssl-static-enum
       for supported data to be cleared";
    input {
      uses crypto-actions-rpc:clear-ssl-static-statistics;
    }
  }

  rpc crypto-clear-ssl-user {
    description
      "Clear crypto SSL VPN data related to user name. Refer enum
       crypto-clear-ssl-user-enum for supported data to be cleared";
    input {
      uses crypto-actions-rpc:clear-ssl-user;
    }
  }

  rpc crypto-clear-ssl-profile {
    description
      "Clear crypto SSL VPN data related to SSL profile name. Refer enum
       crypto-clear-ssl-profile-enum for supported data to be cleared";
    input {
      uses crypto-actions-rpc:clear-ssl-profile;
    }
  }
}
