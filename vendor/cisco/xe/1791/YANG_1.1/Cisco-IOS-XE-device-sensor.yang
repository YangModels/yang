module Cisco-IOS-XE-device-sensor {
  yang-version 1.1;
  namespace "http://cisco.com/ns/yang/Cisco-IOS-XE-device-sensor";
  prefix ios-ds;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Device Sensor Yang model.
     Copyright (c) 2016 by Cisco Systems, Inc.
     All rights reserved.";

  revision 2021-11-01 {
    description
      "- Adding device sensor configuration commands
       - Add internal semantic version";
    cisco-semver:module-version "1.1.0";
  }
  revision 2019-07-01 {
    description
      "Establish semantic version baseline";
    cisco-semver:module-version "1.0.0";
  }
  revision 2017-02-07 {
    description
      "Initial revision";
  }

  grouping cdp-filter-list-grouping {
    container tlv {
      description
        "tlv types list";
      container name {
        description
          "tlv names";
        leaf address-type {
          description
            "Address Type";
          type empty;
        }
        leaf capabilities-type {
          description
            "Capabilities Type";
          type empty;
        }
        leaf cos-type {
          description
            "COS Type";
          type empty;
        }
        leaf device-name {
          description
            "Device Name";
          type empty;
        }
        leaf duplex-type {
          description
            "Duplex Type";
          type empty;
        }
        leaf external-port-id-type {
          description
            "External Port Id Type";
          type empty;
        }
        leaf ipprefix-type {
          description
            "IP Prefix Type";
          type empty;
        }
        leaf mgmt-address-type {
          description
            "Management Address Type";
          type empty;
        }
        leaf mtu-type {
          description
            "MTU Type";
          type empty;
        }
        leaf native-vlan-type {
          description
            "Native VLAN Type";
          type empty;
        }
        leaf platform-type {
          description
            "Platform Type";
          type empty;
        }
        leaf port-id-type {
          description
            "Port Id type";
          type empty;
        }
        leaf power-available-type {
          description
            "Power Available Type";
          type empty;
        }
        leaf power-request-type {
          description
            "External Port Id Type";
          type empty;
        }
        leaf power-type {
          description
            "Power Type";
          type empty;
        }
        leaf protocol-hello-type {
          description
            "Protocol Hello Type";
          type empty;
        }
        leaf trigger-type {
          description
            "Trigger Type";
          type empty;
        }
        leaf trust-type {
          description
            "Trust Type";
          type empty;
        }
        leaf twoway-connectivity-type {
          description
            "Twoway Connectivity Type";
          type empty;
        }
        leaf unidirectional-mode-type {
          description
            "Unidirectional Mode Type";
          type empty;
        }
        leaf version-type {
          description
            "Version Type";
          type empty;
        }
        leaf vtp-mgmt-domain-type {
          description
            "VTP Management Domain Type";
          type empty;
        }
        leaf vvid-type {
          description
            "VVID Type";
          type empty;
        }
      }
      container number {
        description
          "tlv type numbers";
        list tlv-number {
          key "tlv-number";
          leaf tlv-number {
            description
              "TLV Type Number";
            type uint16 {
              range "1..65535";
            }
          }
        }
      }
    }
  }

  grouping lldp-filter-list-grouping {
    container tlv {
      description
        "tlv types list";
      container name {
        description
          "tlv names";
        leaf chassis-id {
          description
            "Chassis Id";
          type empty;
        }
        leaf end-of-lldpdu {
          description
            "End Of LLDP";
          type empty;
        }
        leaf management-address {
          description
            "Management Address";
          type empty;
        }
        leaf port-description {
          description
            "Port Description";
          type empty;
        }
        leaf port-id {
          description
            "Port Id";
          type empty;
        }
        leaf system-capabilities {
          description
            "System Capabilities";
          type empty;
        }
        leaf system-description {
          description
            "System Description";
          type empty;
        }
        leaf system-name {
          description
            "System Name";
          type empty;
        }
        leaf time-to-live {
          description
            "Time To Live";
          type empty;
        }
      }
      container number {
        description
          "tlv type numbers";
        list tlv-nnumber {
          key "tlv-number";
          leaf tlv-number {
            description
              "LLDP Type Number";
            type uint8 {
              range "0..127";
            }
          }
        }
      }
    }
  }

  grouping dhcp-filter-list-grouping {
    container option {
      description
        "option types list";
      container name {
        description
          "option names";
        leaf all-subnets-local {
          description
            "All Subnets Local";
          type empty;
        }
        leaf arp-cache-timeout {
          description
            "ARP Cache Timeout";
          type empty;
        }
        leaf authentication {
          description
            "Authentication";
          type empty;
        }
        leaf auto-configure {
          description
            "Autoconfiguration";
          type empty;
        }
        leaf bcmcs-servers-a {
          description
            "BCMCS Controller IPv4 address list";
          type empty;
        }
        leaf bcmcs-servers-d {
          description
            "BCMCS Controller Domain Name list";
          type empty;
        }
        leaf boot-file {
          description
            "Boot File Name";
          type empty;
        }
        leaf boot-size {
          description
            "Boot Size";
          type empty;
        }
        leaf broadcast-address {
          description
            "Broadcast Address";
          type empty;
        }
        leaf cablelabs-client-configuration {
          description
            "Cable labs Client Configuration";
          type empty;
        }
        leaf cisco-auto-configure {
          description
            "Cisco Autoconfiguration";
          type empty;
        }
        leaf cisco-client-last-transaction-time {
          description
            "Cisco Client Last Transaction Time";
          type empty;
        }
        leaf cisco-client-requested-host-name {
          description
            "Cisco Client Requested Host Name";
          type empty;
        }
        leaf cisco-leased-ip {
          description
            "Cisco Leased IP";
          type empty;
        }
        leaf cisco-vpn-id {
          description
            "Cisco VPN Identifier";
          type empty;
        }
        leaf class-identifier {
          description
            "Class Identifier";
          type empty;
        }
        leaf classless-static-route {
          description
            "Classless Static Route";
          type empty;
        }
        leaf client-fqdn {
          description
            "Client FQDN";
          type empty;
        }
        leaf client-identifier {
          description
            "Client Identifier";
          type empty;
        }
        leaf cookie-servers {
          description
            "Cookie Servers";
          type empty;
        }
        leaf default-ip-ttl {
          description
            "Default IP Time To Live";
          type empty;
        }
        leaf default-tcp-ttl {
          description
            "Default TCP Time To Live";
          type empty;
        }
        leaf domain-name {
          description
            "Domain Name";
          type empty;
        }
        leaf domain-name-servers {
          description
            "Domain Name Servers";
          type empty;
        }
        leaf domain-search {
          description
            "Domain Search";
          type empty;
        }
        leaf ethernet-encapsulation {
          description
            "IEEE 802.3 Encapsulation";
          type empty;
        }
        leaf extensions-path {
          description
            "Extensions Path";
          type empty;
        }
        leaf finger-servers {
          description
            "Finger Server";
          type empty;
        }
        leaf font-servers {
          description
            "X Window Font";
          type empty;
        }
        leaf geo-conf {
          description
            "Geo Conf Option";
          type empty;
        }
        leaf geo-conf-civic {
          description
            "Geo conf Civic";
          type empty;
        }
        leaf host-name {
          description
            "Host Name";
          type empty;
        }
        leaf i-sns {
          description
            "Internet Storage Name Service";
          type empty;
        }
        leaf impress-servers {
          description
            "Impress Servers";
          type empty;
        }
        leaf initial-url {
          description
            "Initial URL";
          type empty;
        }
        leaf interface-mtu {
          description
            "Interface MTU";
          type empty;
        }
        leaf ip-forwarding {
          description
            "IP Forwarding";
          type empty;
        }
        leaf irc-servers {
          description
            "IRC Server";
          type empty;
        }
        leaf ldap-url {
          description
            "LDAP URL";
          type empty;
        }
        leaf lease-time {
          description
            "Address Time";
          type empty;
        }
        leaf log-servers {
          description
            "Log Servers";
          type empty;
        }
        leaf lpr-servers {
          description
            "LPR Servers";
          type empty;
        }
        leaf lq-associated-ip {
          description
            "Lease Query Associated IPs";
          type empty;
        }
        leaf lq-client-last-transaction-time {
          description
            "Lease Query Client last transaction time";
          type empty;
        }
        leaf mask-supplier {
          description
            "Mask Supplier";
          type empty;
        }
        leaf max-dgram-reassembly {
          description
            "Maximum Datagram Reassembly";
          type empty;
        }
        leaf max-message-size {
          description
            "Maximum Message Size";
          type empty;
        }
        leaf mcns-security-server {
          description
            "MCNS Security Server";
          type empty;
        }
        leaf merit-dump {
          description
            "Merit Dump";
          type empty;
        }
        leaf message {
          description
            "Message";
          type empty;
        }
        leaf mobile-ip-home-agents {
          description
            "Mobile IP Home Agent";
          type empty;
        }
        leaf name-servers {
          description
            "Name Servers";
          type empty;
        }
        leaf name-service-search {
          description
            "Name Service Search";
          type empty;
        }
        leaf nds-context {
          description
            "NDS Context";
          type empty;
        }
        leaf nds-servers {
          description
            "NDS Servers";
          type empty;
        }
        leaf nds-tree {
          description
            "NDS Tree Name";
          type empty;
        }
        leaf netbios-dd-servers {
          description
            "NetBIOS Distribution Servers";
          type empty;
        }
        leaf netbios-name-servers {
          description
            "NetBIOS Name Servers";
          type empty;
        }
        leaf netbios-node-type {
          description
            "NetBIOS Node Type";
          type empty;
        }
        leaf netbios-scope {
          description
            "NetBIOS Scope";
          type empty;
        }
        leaf netinfo-parent-server-address {
          description
            "Netinfo Parent Server Address";
          type empty;
        }
        leaf netinfo-parent-server-tag {
          description
            "Netinfo Parent Server Tag";
          type empty;
        }
        leaf netware-ip-domain {
          description
            "Netware/IP Domain";
          type empty;
        }
        leaf netware-ip-information {
          description
            "Netware/IP Option";
          type empty;
        }
        leaf nis-domain {
          description
            "NIS Domain";
          type empty;
        }
        leaf nis-plus-domain {
          description
            "NIS Domain Name";
          type empty;
        }
        leaf nis-plus-servers {
          description
            "NIS Server Address";
          type empty;
        }
        leaf nis-servers {
          description
            "NIS Servers";
          type empty;
        }
        leaf nntp-servers {
          description
            "NNTP Server";
          type empty;
        }
        leaf non-local-source-routing {
          description
            "Non Local Source Routing";
          type empty;
        }
        leaf ntp-servers {
          description
            "NTP Servers";
          type empty;
        }
        leaf option-overload {
          description
            "Options Overload";
          type empty;
        }
        leaf parameter-request-list {
          description
            "Parameter List";
          type empty;
        }
        leaf path-mtu-aging-timeout {
          description
            "Path MTU Aging Timeout";
          type empty;
        }
        leaf path-mtu-plateau-tables {
          description
            "Path MTU Plateau Tables";
          type empty;
        }
        leaf perform-mask-discovery {
          description
            "Perform Mask Discovery";
          type empty;
        }
        leaf policy-filters {
          description
            "Policy Filters";
          type empty;
        }
        leaf pop3-servers {
          description
            "POP3 Server";
          type empty;
        }
        leaf pxe-client-arch {
          description
            "PXE Client Architecture";
          type empty;
        }
        leaf pxe-client-machine-id {
          description
            "PXE Client Machine ID";
          type empty;
        }
        leaf pxe-client-network-id {
          description
            "PXE Client Network ID";
          type empty;
        }
        leaf rapid-commit {
          description
            "Rapid Commit";
          type empty;
        }
        leaf rebinding-time {
          description
            "Rebinding Time";
          type empty;
        }
        leaf relay-agent-info {
          description
            "Relay Agent information";
          type empty;
        }
        leaf renewal-time {
          description
            "Renewing Time";
          type empty;
        }
        leaf requested-address {
          description
            "Address Request";
          type empty;
        }
        leaf resource-location-servers {
          description
            "Resource Location Servers";
          type empty;
        }
        leaf root-path {
          description
            "Root Path";
          type empty;
        }
        leaf router-discovery {
          description
            "Router Discovery";
          type empty;
        }
        leaf router-solicitation-address {
          description
            "Router Solicitation Address";
          type empty;
        }
        leaf routers {
          description
            "Routers";
          type empty;
        }
        leaf server-identifier {
          description
            "Server ID";
          type empty;
        }
        leaf sip-servers {
          description
            "SIP Servers";
          type empty;
        }
        leaf slp-directory-agent {
          description
            "Service Location Protocol Directory Agent";
          type empty;
        }
        leaf slp-service-scope {
          description
            "SLP Service Scope";
          type empty;
        }
        leaf smtp-servers {
          description
            "SMTP Server";
          type empty;
        }
        leaf static-routes {
          description
            "Static Routes";
          type empty;
        }
        leaf streettalk-directory-assistance-servers {
          description
            "STDA Server";
          type empty;
        }
        leaf streettalk-servers {
          description
            "StreetTalk Server";
          type empty;
        }
        leaf subnet-alloc {
          description
            "Subnet Allocation";
          type empty;
        }
        leaf subnet-mask {
          description
            "Subnet Mask";
          type empty;
        }
        leaf subnet-selection {
          description
            "Subnet Selection";
          type empty;
        }
        leaf swap-server {
          description
            "Swap Server";
          type empty;
        }
        leaf tcp-keepalive-garbage {
          description
            "TCP Keepalive Garbage";
          type empty;
        }
        leaf tcp-keepalive-interval {
          description
            "TCP Keepalive Interval";
          type empty;
        }
        leaf tftp-server {
          description
            "TFTP Server Name";
          type empty;
        }
        leaf time-offset {
          description
            "Time Offset";
          type empty;
        }
        leaf time-servers {
          description
            "Time Servers";
          type empty;
        }
        leaf trailer-encapsulation {
          description
            "Trailer Encapsulation";
          type empty;
        }
        leaf user-auth {
          description
            "User Authentication";
          type empty;
        }
        leaf user-class-id {
          description
            "User Class ID";
          type empty;
        }
        leaf v-i-vendor-class {
          description
            "Vendor Identifying Vendor Class";
          type empty;
        }
        leaf v-i-vendor-opts {
          description
            "Vendor Identifying Vendor-Specific Options";
          type empty;
        }
        leaf vendor-encapsulated-options {
          description
            "Vendor Encapsulated Options";
          type empty;
        }
        leaf vpn-id {
          description
            "VPN Identifier";
          type empty;
        }
        leaf www-servers {
          description
            "WWW Server";
          type empty;
        }
        leaf x-display-managers {
          description
            "X Window Managers";
          type empty;
        }
      }
      container number {
        description
          "option type numbers";
        list option-number {
          key "option-number";
          leaf option-number {
            description
              "DHCP Option Type number";
            type uint8 {
              range "1..255";
            }
          }
        }
      }
    }
  }

  grouping config-device-sensor-grouping {
    container device-sensor {
      description
        "IOS Sensor Commands";
      leaf accounting {
        description
          "Trigger accounting updates with sensor TLVs/Options";
        type empty;
      }
      container notify {
        description
          "Options for when to trigger identity update events";
        leaf all-changes {
          description
            "Trigger identity update when TLVs are added/modified/removed";
          type empty;
        }
      }
      container filter-list {
        description
          "Sensor Protocol Filter List Configuration";
        container dhcp {
          description
            "DHCP Filter List";
          list list {
            description
              "Protocol Filter List";
            key "name";
            leaf name {
              type string;
            }
            uses dhcp-filter-list-grouping;
          }
        }
        container lldp {
          description
            "LLDP Filter List";
          list list {
            description
              "Protocol Filter List";
            key "name";
            leaf name {
              type string;
            }
            uses lldp-filter-list-grouping;
          }
        }
        container cdp {
          description
            "CDP Filter List";
          list list {
            description
              "Protocol Filter List";
            key "name";
            leaf name {
              type string;
            }
            uses cdp-filter-list-grouping;
          }
        }
      }
      container filter-spec {
        description
          "Sensor Protocol Filter Spec Configuration";
        container cdp {
          description
            "CDP Filter Spec";
          container exclude {
            description
              "Exclude Filter";
            list list {
              description
                "Protocol Filter Spec list";
              key "name";
              leaf name {
                type string;
              }
            }
            leaf all {
              description
                "All";
              type empty;
            }
          }
          container include {
            description
              "Include Filter";
            list list {
              description
                "Protocol Filter Spec list";
              key "name";
              leaf name {
                type string;
              }
            }
          }
        }
        container lldp {
          description
            "LLDP Filter Spec";
          container exclude {
            description
              "Exclude Filter";
            list list {
              description
                "Protocol Filter Spec list";
              key "name";
              leaf name {
                type string;
              }
            }
            leaf all {
              description
                "All";
              type empty;
            }
          }
          container include {
            description
              "Include Filter";
            list list {
              description
                "Protocol Filter Spec list";
              key "name";
              leaf name {
                type string;
              }
            }
          }
        }
        container dhcp {
          description
            "DHCP Filter Spec";
          container exclude {
            description
              "Exclude Filter";
            list list {
              description
                "Protocol Filter Spec list";
              key "name";
              leaf name {
                type string;
              }
            }
            leaf all {
              description
                "All";
              type empty;
            }
          }
          container include {
            description
              "Include Filter";
            list list {
              description
                "Protocol Filter Spec list";
              key "name";
              leaf name {
                type string;
              }
            }
          }
        }
        container dhcpv6 {
          description
            "DHCPV6 Filter Spec";
          container exclude {
            description
              "Exclude Filter";
            list list {
              description
                "Protocol Filter Spec list";
              key "name";
              leaf name {
                type string;
              }
            }
            leaf all {
              description
                "All";
              type empty;
            }
          }
          container include {
            description
              "Include Filter";
            list list {
              description
                "Protocol Filter Spec list";
              key "name";
              leaf name {
                type string;
              }
            }
          }
        }
      }
      container tlv {
        description
          "Device-sensor protocol tlvs";
        leaf limit {
          description
            "Protocol Tlv Limit (Default: 128)";
          type uint16 {
            range "1..1024";
          }
        }
      }
    }
  }

  augment "/ios:native" {
    uses config-device-sensor-grouping;
  }
}
