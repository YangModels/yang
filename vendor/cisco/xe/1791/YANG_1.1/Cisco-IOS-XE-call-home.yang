module Cisco-IOS-XE-call-home {
  yang-version 1.1;
  namespace "http://cisco.com/ns/yang/Cisco-IOS-XE-call-home";
  prefix ios-ch;

  import cisco-semver {
    prefix cisco-semver;
  }
  import Cisco-IOS-XE-native {
    prefix ios;
  }
  import Cisco-IOS-XE-types {
    prefix ios-types;
  }
  import Cisco-IOS-XE-interface-common {
    prefix ios-ifc;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Call Home Yang Model.
     Copyright (c) 2016, 2018-2019 by Cisco Systems, Inc.
     All rights reserved.";

  revision 2020-07-01 {
    description
      "- Add mail server TLS config";
    cisco-semver:module-version "2.1.0";
  }
  revision 2020-03-01 {
    description
      "- Obsolete 'profile' node and its sub-nodes; use tac-profile and
         user-profile instead.
       - Add http dns-resolve preference: ipv4-first or not.
       - Make http-proxy contain at-most one proxy";
    cisco-semver:module-version "2.0.0";
  }
  revision 2019-07-01 {
    description
      "- Establish semantic version baseline
       - Add contract-id, customer-id, mail-server, phone-number,
         rate-limit, site-id, street-address
       - Add support for reporting smart-call-home-data and smart-licensing-data
       - Add support for data-privacy";
    cisco-semver:module-version "1.0.0";
  }
  revision 2018-10-11 {
    description
      "add anonymous-reporting-only and server-identity-check";
  }
  revision 2017-02-07 {
    description
      "Initial revision";
  }

  typedef hhmm-type {
    type string {
      pattern '([1]?[0-9]|2[0-3]):([0-5][0-9])';
    }
  }

  typedef weekday-type {
    type enumeration {
      enum Monday;
      enum Tuesday;
      enum Wednesday;
      enum Thursday;
      enum Friday;
      enum Saturday;
      enum Sunday;
    }
  }

  typedef ipv4-address-with-auth {
    description
      "It consists of SMTP authentication parameters and ipv4-address";
    type string {
      length "1..64";
      pattern '(([^@]*)?@)?((25[0-5]|2[0-4][0-9]|[01]?[0-9]?[0-9])\.){3}(25[0-5]|2[0-4][0-9]|[01]?[0-9]?[0-9])(%[\p{N}\p{L}]+)?';
    }
  }

  typedef ipv6-address-with-auth {
    description
      "It consists of SMTP authentication parameters and ipv6-address";
    type string {
      length "1..64";
      pattern '(([^@]*)?@)?((:|[0-9a-fA-F]{0,4}):)([0-9a-fA-F]{0,4}:){0,5}((([0-9a-fA-F]{0,4}:)?(:|[0-9a-fA-F]{0,4}))|(((25[0-5]|2[0-4][0-9]|[01]?[0-9]?[0-9])\.){3}(25[0-5]|2[0-4][0-9]|[01]?[0-9]?[0-9])))(%[\p{N}\p{L}]+)?';
      pattern '(([^@]*)?@)?(([^:]+:){6}(([^:]+:[^:]+)|(.*\..*)))|((([^:]+:)*[^:]+)?::(([^:]+:)*[^:]+)?)(%.+)?';
    }
  }

  typedef host-with-auth {
    description
      "It consists of SMTP authentication parameters and hostname.";
    type string {
      length "1..64";
      pattern '(([^@]*)?@)?(([a-zA-Z0-9]([a-zA-Z0-9-]){0,61})?[a-zA-Z0-9]\.)*([a-zA-Z0-9]([a-zA-Z0-9-]){0,61})?[a-zA-Z0-9]\.?';
    }
  }

  grouping begin-time-grouping {
    leaf begin-time {
      type hhmm-type;
    }
  }

  grouping profile-periodic-grouping {
    container periodic {
      description
        "Periodic call-home message";
      choice periodic-choice {
        description
          "The choice of the periodic message";
        container daily {
          uses begin-time-grouping;
        }
        container monthly {
          must '(./date and ./begin-time) or (not (./date) and not (./begin-time))' {
            error-message "Must configure both date and begin-time, or neither of them.";
          }
          leaf date {
            type uint8 {
              range "1..31";
            }
          }
          uses begin-time-grouping;
        }
        container weekly {
          must '(./day and ./begin-time) or (not (./day) and not (./begin-time))' {
            error-message "Must configure both day and begin-time, or neither of them.";
          }
          leaf day {
            type weekday-type;
          }
          uses begin-time-grouping;
        }
      }
    }
  }

  grouping call-home-profile-periodic-grouping {
    status obsolete;
    container periodic {
      status obsolete;
      choice periodic-choice {
        status obsolete;
        description
          "Periodic call-home message";
        container daily {
          status obsolete;
          description
            "Daily call-home message";
          leaf begin-time {
            status obsolete;
            description
              "Begin time";
            type ios-types:hhmm-type;
          }
        }
        container monthly {
          status obsolete;
          description
            "Monthly call-home message";
          leaf date {
            status obsolete;
            description
              "Day of month";
            type uint8 {
              range "1..31";
            }
          }
          leaf begin-time {
            status obsolete;
            description
              "Begin time";
            type ios-types:hhmm-type;
          }
        }
        container weekly {
          status obsolete;
          description
            "Weekly call-home message";
          leaf day {
            status obsolete;
            description
              "Day of the week";
            type ios-types:weekday-type;
          }
          leaf begin-time {
            status obsolete;
            description
              "Begin time";
            type ios-types:hhmm-type;
          }
        }
      }
    }
  }

  grouping profile-name-grouping {
    leaf profile-name {
      must 'not(translate(current()/text(),"CISCOTAC","ciscotac") = "ciscotac-1")' {
        error-message "user defined profile name cannot be similar to CiscoTAC-1";
      }
      must 'count(../../profile[translate(profile-name/text(),"ABCDEFGHIJKLMNOPQRSTUVWXYZ","abcdefghijklmnopqrstuvwxyz")=translate(current()/text(),"ABCDEFGHIJKLMNOPQRSTUVWXYZ","abcdefghijklmnopqrstuvwxyz")]) <= 1' {
        error-message "profile names cannot have same spelling with different cases";
      }
      type string {
        pattern '([^aA].*)|([aA]([^lL].*)?)|([aA][lL]([^lL].*)?)|([aA][lL][lL].+)' {
          error-message "the profile name cannot be \"all\"(case-insensitive)";
        }
        length "1..31";
      }
    }
  }

  grouping profile-active-grouping {
    leaf active {
      description
        "Activate the current profile";
      type boolean;
    }
  }

  grouping profile-anonymous-reporting-only-grouping {
    leaf anonymous-reporting-only {
      description
        "Enable call-home anonymous reporting only";
      type empty;
    }
  }

  grouping profile-tac-reporting-data-grouping {
    container reporting {
      description
        "Choose what data to report";
      leaf smart-call-home-data {
        description
          "Report Smart Call Home data";
        type boolean;
        default "true";
      }
      leaf smart-licensing-data {
        description
          "Report Smart Licensing data";
        type boolean;
        default "true";
      }
    }
  }

  grouping profile-user-reporting-data-grouping {
    container reporting {
      description
        "Choose what data to report";
      leaf smart-call-home-data {
        description
          "Report Smart Call Home data";
        type boolean;
        default "true";
      }
      leaf smart-licensing-data {
        description
          "Report Smart Licensing data";
        type empty;
      }
    }
  }

  grouping profile-tac-destination-grouping {
    container destination {
      description
        "Message destination related configuration";
      leaf transport-method {
        description
          "To specify transport method for this profile";
        type enumeration {
          enum http;
          enum email;
        }
      }
      container address {
        description
          "To add destination address to this profile";
        container http {
          description
            "To add http address to this profile, there must be only one in use";
          leaf http-address {
            description
              "To add user-defined http address";
            must 'not (substring(., 1, 5) = "https" and substring(., 6) = "://tools.cisco.com/its/service/oddce/services/DDCEService")' {
              error-message "the leaf http-address cannot use default address";
            }
            type string {
              length "8..200";
              pattern '[hH][tT][tT][pP][sS]?://.*';
            }
          }
          leaf default-address {
            description
              "enable or disable default http address";
            must 'not( . = "true" and boolean(../http-address))' {
              error-message "Must not have both default address and non-default one";
            }
            type boolean;
            default "true";
          }
        }
        container email {
          description
            "To add email address to this profile";
          list email-address {
            description
              "configure user-added email address";
            key "addr";
            leaf addr {
              must 'count(../../email-address[translate(addr/text(),"ABCDEFGHIJKLMNOPQRSTUVWXYZ","abcdefghijklmnopqrstuvwxyz")=translate(current()/text(),"ABCDEFGHIJKLMNOPQRSTUVWXYZ","abcdefghijklmnopqrstuvwxyz")]) <= 1' {
                error-message "email address cannot have same spelling with different cases";
              }
              must 'translate(current()/text(),"CALLHOMECISCO","callhomecisco") != "callhome@cisco.com"' {
                error-message "email address cannot be similar to callhome@cisco.com";
              }
              type string {
                length "5..200";
                pattern '.*@.*';
              }
            }
          }
          leaf default-address {
            description
              "enable or disable default email address";
            type boolean;
            default "true";
          }
        }
      }
    }
  }

  grouping profile-user-destination-grouping {
    container destination {
      description
        "Message destination related configuration";
      container transport-method {
        description
          "To specify transport method for this profile";
        must 'boolean(./http) or ./email = "true"' {
          error-message "there must be at least one transport method";
        }
        leaf http {
          description
            "Enable http as transport method";
          type empty;
        }
        leaf email {
          description
            "Enable email as transport method";
          type boolean;
          default "true";
        }
      }
      container address {
        description
          "To add destination address to this profile";
        leaf http {
          description
            "To add http address to this profile";
          type string {
            length "8..200";
            pattern '[hH][tT][tT][pP][sS]?://.*';
          }
        }
        container email {
          description
            "To add email address to this profile";
          list email-address {
            key "addr";
            leaf addr {
              must 'count(../../email-address[translate(addr/text(),"ABCDEFGHIJKLMNOPQRSTUVWXYZ","abcdefghijklmnopqrstuvwxyz")=translate(current()/text(),"ABCDEFGHIJKLMNOPQRSTUVWXYZ","abcdefghijklmnopqrstuvwxyz")]) <= 1' {
                error-message "email address cannot have same spelling with different cases";
              }
              type string {
                length "5..200";
                pattern '.*@.*';
              }
            }
          }
        }
      }
    }
  }

  grouping alert-group-severity-grouping {
    leaf severity {
      description
        "Severity";
      type enumeration {
        enum catastrophic;
        enum critical;
        enum debugging;
        enum disaster;
        enum fatal;
        enum major;
        enum minor;
        enum normal;
        enum notification;
        enum warning;
      }
    }
  }

  grouping profile-alert-group-grouping {
    container subscribe-to-alert-group {
      description
        "Subscribe to alert-group";
      container diagnostic {
        description
          "diagnostic info";
        presence "true";
        uses alert-group-severity-grouping {
          refine "severity" {
            default "debugging";
          }
        }
      }
      container environment {
        description
          "enviroment info";
        presence "true";
        uses alert-group-severity-grouping {
          refine "severity" {
            default "debugging";
          }
        }
      }
      container inventory {
        description
          "inventory info";
        leaf inventory {
          description
            "inventory info";
          type empty;
        }
      }
      container inventory-periodically {
        description
          "inventory info: report inventory info periodically";
        container inventory {
          description
            "inventory info";
          uses profile-periodic-grouping;
        }
      }
      list syslog {
        description
          "syslog info";
        key "pattern";
        leaf pattern {
          description
            "Syslog message pattern";
          type string {
            length "1..80";
          }
        }
        uses alert-group-severity-grouping {
          refine "severity" {
            mandatory true;
          }
        }
      }
      container configuration {
        description
          "configuration info";
        leaf configuration {
          description
            "configuration info";
          type empty;
        }
      }
      container configuration-periodically {
        description
          "configuration info: report configuration info periodically";
        container configuration {
          description
            "configuration info";
          uses profile-periodic-grouping;
        }
      }
    }
  }

  grouping cfg-call-home-profile-grouping {
    status obsolete;
    leaf active {
      status obsolete;
      description
        "Activate the current profile";
      type boolean;
    }
    leaf anonymous-reporting-only {
      status obsolete;
      description
        "Enable call-home anonymous reporting only";
      type empty;
    }
    container reporting {
      status obsolete;
      description
        "Choose what data to report";
      leaf smart-call-home-data {
        status obsolete;
        description
          "Report Smart Call Home data";
        type boolean;
        default "true";
      }
      leaf tac-sl-data {
        status obsolete;
        description
          "Report Smart Licensing data for TAC profile";
        when 'translate(current()/../../profile-name,"CISOTA","cisota") = "ciscotac-1"';
        type boolean;
        default "true";
      }
      leaf user-sl-data {
        status obsolete;
        description
          "Report Smart Licensing data for user defined profile";
        when 'translate(current()/../../profile-name,"CISOTA","cisota") != "ciscotac-1"';
        type boolean;
        default "false";
      }
    }
    container destination {
      status obsolete;
      description
        "Message destination related configuration";
      leaf transport-method {
        status obsolete;
        description
          "To specify transport method for this profile";
        type enumeration {
          enum http;
          enum email;
        }
      }
      container address {
        status obsolete;
        description
          "To add destination address to this profile";
        leaf email {
          status obsolete;
          description
            "Use email address";
          type string;
        }
        leaf http {
          status obsolete;
          description
            "To add http address to this profile";
          type string;
        }
      }
    }
    container subscribe-to-alert-group {
      status obsolete;
      description
        "Subscribe to alert-group";
      container diagnostic {
        status obsolete;
        description
          "diagnostic info";
        presence "true";
        leaf severity {
          status obsolete;
          description
            "Severity";
          type enumeration {
            enum catastrophic;
            enum critical;
            enum debugging;
            enum disaster;
            enum fatal;
            enum major;
            enum minor;
            enum normal;
            enum notification;
            enum warning;
          }
        }
      }
      container environment {
        status obsolete;
        description
          "environmental info";
        presence "true";
        leaf severity {
          status obsolete;
          description
            "Severity";
          type enumeration {
            enum catastrophic;
            enum critical;
            enum debugging;
            enum disaster;
            enum fatal;
            enum major;
            enum minor;
            enum normal;
            enum notification;
            enum warning;
          }
        }
      }
      container inventory {
        status obsolete;
        description
          "inventory info";
        presence "true";
        uses call-home-profile-periodic-grouping {
          status obsolete;
        }
      }
      container syslog {
        status obsolete;
        description
          "syslog info";
        presence "true";
        list severity {
          status obsolete;
          description
            "severity";
          key "value";
          leaf value {
            status obsolete;
            type enumeration {
              enum catastrophic;
              enum critical;
              enum debugging;
              enum disaster;
              enum fatal;
              enum major;
              enum minor;
              enum normal;
              enum notification;
              enum warning;
            }
          }
          leaf pattern {
            status obsolete;
            description
              "Syslog message pattern";
            type string;
          }
        }
      }
      container configuration {
        status obsolete;
        description
          "configuration info";
        presence "true";
        uses call-home-profile-periodic-grouping {
          status obsolete;
        }
      }
    }
  }

  grouping config-call-home-grouping {
    leaf contact-email-addr {
      description
        "Use email address";
      type string;
    }
    leaf contract-id {
      description
        "Contract identification for Cisco Smart Call Home.
         It cannot contain quote or special characters or only spaces.";
      type string {
        length "1..64";
        pattern '[^"]*[^ "]+[^"]*';
        pattern '[ -~]+';
      }
    }
    leaf customer-id {
      description
        "customer identification for Cisco Smart Call Home.
         It cannot contain quote or special characters or only spaces.";
      type string {
        length "1..64";
        pattern '[^"]*[^ "]+[^"]*';
        pattern '[ -~]+';
      }
    }
    container mail-server {
      description
        "call-home mail server";
      list server {
        description
          "used as a structure to contain other data";
        max-elements 5;
        key "server-name";
        leaf server-name {
          description
            "the server-name has the following format

               user:password@host
               host

             the user and password is used for SMTP authentication.
             They can be any valid printable ascii code except '@'.
             They also can be empty -- depending on mail servers.

             host is the hostname or ip address. hostname consists of labels.
             Each label:
               contains letters, digits, hyphen; cannot start/end with hyphen;
               separated by dot; Refer to RFC 1123, RFC 1034 for detail.";
          type union {
            type ipv4-address-with-auth;
            type ipv6-address-with-auth;
            type host-with-auth;
          }
        }
        leaf priority {
          description
            "Mail server priority order";
          mandatory true;
          type uint8 {
            range "1..100";
          }
        }
        leaf secure {
          description
            "Specify secure settings for mail server";
          type enumeration {
            enum none;
            enum tls;
          }
          default "none";
        }
      }
    }
    leaf phone-number {
      description
        "Phone number of the contact person. The phone number must
         start with '+', and only space, - and numbers are allowed.
         Total length is between 12 to 17 characters.";
      type string {
        length "12..17";
        pattern '\+[0123456789 -]*';
      }
    }
    leaf rate-limit {
      description
        "call-home message rate-limit threshold per minute";
      type uint8 {
        range "1..60";
      }
      default "20";
    }
    leaf site-id {
      description
        "Site identification for Cisco Smart Call Home.
         It cannot contain quote or special characters or only spaces.";
      type string {
        length "1..200";
        pattern '[^"]*[^ "]+[^"]*';
        pattern '[ -~]+';
      }
    }
    leaf street-address {
      description
        "Customer's address for equipment shipments:
           street address, city, state, and zip code.
         It cannot contain quote or special characters or only spaces.";
      type string {
        length "1..200";
        pattern '[^"]*[^ "]+[^"]*';
        pattern '[ -~]+';
      }
    }
    container source-interface {
      description
        "Source interface name to send call-home messages using email";
      uses ios-ifc:interface-grouping;
    }
    container data-privacy {
      description
        "Set call-home data-privacy";
      leaf hostname {
        description
          "Level hostname";
        type empty;
      }
      leaf level {
        description
          "Set call-home data-privacy level";
        type enumeration {
          enum high;
          enum normal;
        }
        default "normal";
      }
    }
    container http {
      description
        "Set parameters for http transport method";
      container resolve-hostname {
        description
          "Specify the IP version to resolve server hostname";
        leaf ipv4-first {
          description
            "ipv4 first";
          type empty;
        }
      }
      container secure {
        description
          "Specify secure settings for http transport method";
        leaf server-identity-check {
          description
            "check server identity";
          type boolean;
          default "true";
        }
      }
    }
    container http-proxy {
      description
        "Specify proxy server for http request";
      list proxy-servers {
        key "proxy-server";
        max-elements 1;
        leaf proxy-server {
          description
            "Http proxy server";
          type string;
        }
        leaf port {
          description
            "http proxy server port number";
          mandatory true;
          type uint16 {
            range "1..65535";
          }
        }
      }
    }
    container tac-profile {
      description
        "Default profile";
      container profile {
        description
          "Enter call-home profile configuration mode.";
        container CiscoTAC-1 {
          uses profile-active-grouping;
          uses profile-anonymous-reporting-only-grouping;
          uses profile-tac-reporting-data-grouping;
          uses profile-tac-destination-grouping;
        }
      }
    }
    container user-profile {
      description
        "User defined profiles";
      must "not(count(profile[active = \"true\"]/reporting/smart-licensing-data) >= 2 or
                            (count(profile[active = \"true\"]/reporting/smart-licensing-data) >= 1 and
                             ../tac-profile/profile/CiscoTAC-1/active = \"true\" and
                             ../tac-profile/profile/CiscoTAC-1/reporting/smart-licensing-data = \"true\"))" {
        error-message "Only one active profile is allowed to report Smart Licensing data";
      }
      list profile {
        description
          "Enter call-home profile configuration mode.";
        key "profile-name";
        uses profile-name-grouping;
        uses profile-active-grouping {
          refine "active" {
            default "true";
          }
        }
        uses profile-anonymous-reporting-only-grouping;
        uses profile-user-reporting-data-grouping;
        uses profile-user-destination-grouping;
        uses profile-alert-group-grouping;
      }
    }
    list profile {
      status obsolete;
      description
        "Enter call-home profile configuration mode.
         (Obsolete. Please use tac-profile or user-profile instead)";
      key "profile-name";
      leaf profile-name {
        status obsolete;
        type string;
      }
      uses cfg-call-home-profile-grouping {
        status obsolete;
      }
    }
  }

  augment "/ios:native/ios:call-home" {
    uses config-call-home-grouping;
  }
}
