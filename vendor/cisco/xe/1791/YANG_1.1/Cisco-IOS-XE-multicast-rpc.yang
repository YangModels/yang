submodule Cisco-IOS-XE-multicast-rpc {
  yang-version 1.1;
  belongs-to Cisco-IOS-XE-rpc {
    prefix ios-xe-rpc;
  }

  import cisco-semver {
    prefix cisco-semver;
  }

  organization
    "Cisco Systems";
  contact
    "<mailto:cs-yang@cisco.com>";
  description
    "NED Multicast RPC YANG module for IOS
     Copyright (c) 2020 by Cisco Systems, Inc.
     All rights reserved.";

  revision 2020-07-01 {
    description
      "created for Multicast RPC YANG";
    cisco-semver:module-version "1.0.0";
  }

  grouping debug-multicast-level-grouping {
    container level {
      description
        "debug level information";
      choice level-choice {
        case error-case {
          leaf error {
            description
              "Enable error debug";
            type empty;
          }
        }
        case info-case {
          leaf info {
            description
              "Enable info debug";
            type empty;
          }
        }
        case verbose-case {
          leaf verbose {
            description
              "Enable verbose debug";
            type empty;
          }
        }
        case warning-case {
          leaf warning {
            description
              "Enable warning debug";
            type empty;
          }
        }
      }
      leaf no {
        description
          "for no debug platform condition feature multicast ...";
        type empty;
      }
    }
  }

  grouping debug-multicast-submode-grouping {
    container submode {
      description
        "submode information";
      choice submode-choice {
        case all-case {
          leaf all {
            description
              "all information";
            type empty;
          }
        }
        case boundary-case {
          leaf boundary {
            description
              "boundary information";
            type empty;
          }
        }
        case config-case {
          leaf config {
            description
              "config information";
            type empty;
          }
        }
        case error-case {
          leaf error {
            description
              "error information";
            type empty;
          }
        }
        case packet-case {
          leaf packet {
            description
              "packet information";
            type empty;
          }
        }
        case sr-case {
          leaf sr {
            description
              "sr information";
            type empty;
          }
        }
        case state-case {
          leaf state {
            description
              "state information";
            type empty;
          }
        }
      }
      leaf no {
        description
          "for no debug platform condition feature multicast ...";
        type empty;
      }
    }
  }

  grouping debug-platform-condition-feature-multicast-grouping {
    container multicast {
      description
        "MULTICAST feature";
      choice multicast-choice {
        case controlplane-case {
          container controlplane {
            description
              "control plane information";
            uses debug-multicast-level-grouping;
          }
        }
        case dataplane-case {
          container dataplane {
            description
              "packet/flow information";
            choice dataplane-debug-choice {
              case v4mcast-case {
                container v4mcast {
                  description
                    "ipv4 mcast feature";
                  uses debug-multicast-submode-grouping;
                }
              }
              case v6mcast-case {
                container v6mcast {
                  description
                    "ipv6 mcast feature";
                  uses debug-multicast-submode-grouping;
                }
              }
            }
          }
        }
      }
    }
  }
}
