module Cisco-IOS-XE-mrp {
  yang-version 1.1;
  namespace "http://cisco.com/ns/yang/Cisco-IOS-XE-mrp";
  prefix mrp;

  import cisco-semver {
    prefix cisco-semver;
  }
  import Cisco-IOS-XE-native {
    prefix ios;
  }

  organization
    "Cisco Systems, Inc.";
  contact
    "Cisco Systems, Inc.
     Customer Service
     Postal: 170 W Tasman Drive
     San Jose, CA 95134
     Tel: +1 1800 553-NETS
     E-mail: cs-yang@cisco.com";
  description
    "Cisco XE MRP (Media Redundancy Protocol) model";

  revision 2022-07-01 {
    description
      "Initially created";
    cisco-semver:module-version "1.0.0";
  }

  grouping config-profinet-grouping {
    container profinet {
      description
        "configure profinet on device";
      leaf mrp {
        description
          "configure profinet mrp on device";
        type boolean;
        default "true";
      }
    }
  }

  grouping config-mrp-grouping {
    container mrp {
      list ring {
        description
          "configure mrp ring node";
        must "/ios:native/mrp:profinet/mrp = 'false'" {
          error-message "Profinet must be disabled first";
        }
        key "id";
        leaf id {
          description
            "denotes mrp ring number";
          type uint8 {
            range "1..3";
          }
        }
        container mode {
          description
            "enable and configure mrp mode";
          container auto-manager {
            description
              "enable manager mode and configure mrp auto-mrp-manager mode parameters";
            presence "true";
            leaf vlan-id {
              description
                "vlan-id of manager";
              type uint16 {
                range "1..4094";
              }
              default "1";
            }
            leaf domain-id {
              description
                "MRP domain-id";
              type string {
                pattern '[0-9a-fA-F]{8}\-[0-9a-fA-F]{4}\-[0-9a-fA-F]{4}\-[0-9a-fA-F]{4}\-[0-9a-fA-F]{12}';
              }
            }
            leaf domain-name {
              description
                "logical name of the configured MRP domain-ID";
              type string {
                length "1..32";
              }
            }
            leaf priority {
              description
                "set the manager priority for multiple MRM";
              type uint16 {
                range "36864..61441 | 65534..65535";
              }
              default "40960";
            }
            leaf profile {
              description
                "standard profile";
              type uint16 {
                range "30 | 200 | 500";
              }
              default "200";
            }
            leaf interval {
              description
                "test frame interval in ms";
              type uint16 {
                range "3..10 | 20 | 50";
              }
              default "20";
            }
          }
        }
      }
    }
  }

  augment "/ios:native" {
    uses config-profinet-grouping;
    uses config-mrp-grouping;
  }
}
