module Cisco-IOS-XE-qfp-appqoe-dp-oper {
  yang-version 1.1;
  namespace "http://cisco.com/ns/yang/Cisco-IOS-XE-qfp-appqoe-dp-oper";
  prefix qfp-appqoe-dp-ios-xe-oper;

  import Cisco-IOS-XE-common-types {
    prefix common-types-ios-xe;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for APPQOE datapath operational data.
     Copyright (c) 2021-2022 by Cisco Systems, Inc.
     All rights reserved.";

  revision 2022-07-01 {
    description
      "Initial revision";
    reference
      "1.0.0";
    cisco-semver:module-version "1.0.0";
  }

  typedef appnav-snstat {
    type enumeration {
      enum appnav-sn-is-down {
        value 0;
        description
          "Service node is down";
      }
      enum appnav-sn-is-up-with-green {
        value 1;
        description
          "Service node is up services are available";
      }
      enum appnav-sn-is-up-with-yellow {
        value 2;
        description
          "Service node is up No now session are accepted";
      }
      enum appnav-sn-is-up-with-red {
        value 3;
        description
          "Service node is up Frames to sessions are dropped";
      }
    }
    description
      "AppNav service node status";
  }

  typedef sn-service-type {
    type enumeration {
      enum service-type-waas {
        value 0;
        description
          "Service type is WAAS";
      }
      enum service-type-utd {
        value 1;
        description
          "Service type is UTD";
      }
      enum service-type-dpss {
        value 2;
        description
          "Service type is DPSS";
      }
      enum service-type-appqoe {
        value 3;
        description
          "Service type is AppQoE";
      }
      enum service-type-unknown {
        value 4;
        description
          "Service type is not known";
      }
    }
    description
      "AppQoE service type";
  }

  typedef appqoe-hash-status {
    type enumeration {
      enum appqoe-hash-ok {
        value 0;
        description
          "Hash status is okay";
      }
      enum appqoe-hash-count-mismatch {
        value 1;
        description
          "Hash status error due to count mismatch of service node";
      }
      enum appqoe-hash-mem-corrupt {
        value 2;
        description
          "Hash status error due to table memory corruption";
      }
      enum appqoe-hash-sn-mismatch {
        value 3;
        description
          "Hash status error due to service node identifier incorrect at expected index";
      }
    }
    description
      "AppQoE Hash table status";
  }

  grouping sdvt-global-stats {
    description
      "SDVT datapath global statistics";
    leaf channel-id {
      type uint8;
      description
        "SDVT channel id";
    }
    leaf sdvt-divert-flow-pers-mark {
      type uint64;
      description
        "Remarking persistent for diverted flows";
    }
    leaf sdvt-htx-inj-flow-mark {
      type uint64;
      description
        "Remarking persistent for htx injected flows";
    }
    leaf sdvt-init-vfr-reg-failed {
      type uint64;
      description
        "Failed VFR callback registration";
    }
    leaf sdvt-init-vfr-unreg-failed {
      type uint64;
      description
        "Failed VFR callback deregistration";
    }
    leaf sdvt-init-cft-get-failed {
      type uint64;
      description
        "Failed connection-table instance init";
    }
    leaf sdvt-init-del-cb-reg-fail {
      type uint64;
      description
        "Failed connection-delete callback registration";
    }
    leaf sdvt-cft-del-dereg-fail {
      type uint64;
      description
        "Could not deregister CFT delete callback";
    }
    leaf sdvt-cft-dump-reg-fail {
      type uint64;
      description
        "Failed CFT feature object dump callback registration";
    }
    leaf sdvt-cft-dump-dereg-fail {
      type uint64;
      description
        "Could not deregister CFT dump callback";
    }
    leaf sdvt-cft-unreg-fl-cr-fail {
      type uint64;
      description
        "Could not deregister CFT create callback";
    }
    leaf sdvt-appnav-reg-fail {
      type uint64;
      description
        "AppNav registration failed";
    }
    leaf sdvt-appnav-reg {
      type uint64;
      description
        "AppNav registration";
    }
    leaf sdvt-appnav-dereg {
      type uint64;
      description
        "AppNav deregister";
    }
    leaf sdvt-appnav-dereg-fail {
      type uint64;
      description
        "AppNav deregistration failed";
    }
    leaf sdvt-cft-pers-reg-fail {
      type uint64;
      description
        "Failed CFT persist callback registration";
    }
    leaf sdvt-cft-pers-cb-fail {
      type uint64;
      description
        "Failed in CFT persist callback";
    }
    leaf sdvt-cft-pers-dereg-fail {
      type uint64;
      description
        "Could not deregister CFT persistent callback";
    }
    leaf sdvt-ingress-ip-frag-cnt {
      type uint64;
      description
        "Ingress: bypass previously reassembled packet";
    }
    leaf sdvt-ingress-ip-vfr-cnt {
      type uint64;
      description
        "Ingress: bypass fragmented packet";
    }
    leaf sdvt-egress-ip-frag-cnt {
      type uint64;
      description
        "Egress: drop fragmented packet";
    }
    leaf sdvt-egress-ip-vfr-cnt {
      type uint64;
      description
        "Egress: drop previously reassembled packet";
    }
    leaf sdvt-appnav-decap-no-flow {
      type uint64;
      description
        "Control decap: could not find flow from tuple";
    }
    leaf sdvt-appnav-decap-no-tuple {
      type uint64;
      description
        "Control decap: could not find tuple in packet";
    }
    leaf sdvt-appnav-decap-no-fo {
      type uint64;
      description
        "Control decap: could not find sdvt CFT feature object";
    }
    leaf sdvt-appnav-no-cft-hdl {
      type uint64;
      description
        "Control decap: could not find tuple in packet";
    }
    leaf sdvt-syn-policer-drop {
      type uint64;
      description
        "Exceeded SDVT syn policer limit";
    }
    leaf sdvt-syn-policer-allow {
      type uint64;
      description
        "Within SDVT syn policer limit";
    }
    leaf sdvt-alarm-rate-limited {
      type uint64;
      description
        "Alarm not send as rate limited";
    }
    leaf sdvt-nat-api-ret-err {
      type uint64;
      description
        "NAT api returned error";
    }
  }

  grouping appqoe-global-stats-entry {
    description
      "AppQoE datapath global statistics counters";
    leaf appqoe-ip-non-tcp {
      type uint64;
      description
        "AppQoE policy matched on non TCP packets";
    }
    leaf appqoe-not-enabled {
      type uint64;
      description
        "AppQoE policy matched but feature not enabled";
    }
    leaf appqoe-cft-handle-pkt {
      type uint64;
      description
        "AppQoE failed to get FID while handling packet";
    }
    leaf appqoe-sdvt-div-req-fail {
      type uint64;
      description
        "AppQoE failed the divert the request";
    }
    leaf appqoe-sn-data-pkts {
      type uint64;
      description
        "AppQoE Data packets processed by service node";
    }
    leaf appqoe-alloc-empty-entry {
      type uint64;
      description
        "AppQoE allotted hash table entry has no entries";
    }
    leaf appqoe-cvla-alloc-fail {
      type uint64;
      description
        "CVLA memory allocation failures for AppQoE structures";
    }
    leaf appqoe-bulk-upd-bm-no-sng {
      type uint64;
      description
        "Bulk update has member service node bit mask for service node group but it is not present";
    }
    leaf appqoe-srv-chain-trans-dre {
      type uint64;
      description
        "AppQoE service chaining with DRE bypass condition";
    }
    leaf appqoe-srv-sn-unhealthy {
      type uint64;
      description
        "AppQoE service chaining with service node unhealthy condition";
    }
    leaf appqoe-srv-tcp-mid-flow {
      type uint64;
      description
        "AppQoE service chaining with TCP mid flow bypass condition";
    }
    leaf appqoe-srv-chain-non-tcp {
      type uint64;
      description
        "AppQoE service chaining with non TCP bypass condition";
    }
    leaf appqoe-srv-chain-frag {
      type uint64;
      description
        "AppQoE service chaining with fragments bypass condition";
    }
    leaf appqoe-lb-without-dre {
      type uint64;
      description
        "AppQoE load balancing with DRE service cleared";
    }
    leaf appqoe-svc-on-vpn-drop {
      type uint64;
      description
        "AppQoE service configured on AppQoE VPN";
    }
    leaf appqoe-sng-not-config {
      type uint64;
      description
        "AppQoE AOS requested for un-configured service node group";
    }
    leaf appqoe-unknown-tlv-type {
      type uint64;
      description
        "AppQoE Unknown TLV type during DECAP";
    }
    leaf appqoe-sn-data-pkts-drop {
      type uint64;
      description
        "AppQoE non supported data packets dropped by service node";
    }
    leaf appqoe-appnav-fo-reset {
      type uint64;
      description
        "AppQoE reset AppNav feature object data";
    }
  }

  grouping sdvt-sub-chnl-hlth {
    description
      "SDVT sub service channel health";
    leaf sdvt-sp-chnl-srv-tcp {
      type qfp-appqoe-dp-ios-xe-oper:appnav-snstat;
      description
        "TCP sub service health status";
    }
    leaf sdvt-sp-chnl-srv-ssl {
      type qfp-appqoe-dp-ios-xe-oper:appnav-snstat;
      description
        "SSL sub service health status";
    }
    leaf sdvt-sp-chnl-srv-dre {
      type qfp-appqoe-dp-ios-xe-oper:appnav-snstat;
      description
        "DRE sub service health status";
    }
    leaf sdvt-sp-chnl-srv-cache {
      type qfp-appqoe-dp-ios-xe-oper:appnav-snstat;
      description
        "Caching sub service health status";
    }
    leaf sdvt-sp-chnl-srv-utd {
      type qfp-appqoe-dp-ios-xe-oper:appnav-snstat;
      description
        "AppQoE UTD channel health status";
    }
  }

  grouping appqoe-global-info {
    description
      "Service controller generic information";
    leaf syn-policer-rate {
      type uint32;
      description
        "Maximum connection requests per second configured";
    }
    leaf external-cluster {
      type uint8;
      description
        "Service controller mode is external cluster";
    }
    leaf sc-vrf-id {
      type uint16;
      description
        "Service controller VRF identifier";
    }
    leaf sdvt-sp-chnl-hlth {
      type qfp-appqoe-dp-ios-xe-oper:appnav-snstat;
      description
        "AppQoE service health status";
    }
    container sp-chan-sub-srv-hlth {
      description
        "AppQoE sub services health status";
      uses qfp-appqoe-dp-ios-xe-oper:sdvt-sub-chnl-hlth;
    }
  }

  grouping appqoe-global-stats {
    description
      "AppQoE global feature data";
    container counter {
      description
        "AppQoE global statistics";
      uses qfp-appqoe-dp-ios-xe-oper:appqoe-global-stats-entry;
    }
    container intern-info {
      description
        "Service controller generic info with channel health details";
      uses qfp-appqoe-dp-ios-xe-oper:appqoe-global-info;
    }
    list channel {
      description
        "SDVT per channel counters";
      uses qfp-appqoe-dp-ios-xe-oper:sdvt-global-stats;
    }
  }

  grouping sdvt-cnt-stats-entry {
    description
      "SDVT count statistics entry";
    leaf sdvt-active-conn {
      type uint64;
      description
        "Active connections";
    }
    leaf sdvt-appnav-decaps {
      type uint64;
      description
        "Decapsulation counter";
    }
    leaf sdvt-appnav-encaps {
      type uint64;
      description
        "Encapsulation counter";
    }
    leaf sdvt-apv-decaps-proc-icmp {
      type uint64;
      description
        "Decapsulation: processed ICMP error packet from service node";
    }
    leaf sdvt-pkt-no-ingress-mark {
      type uint64;
      description
        "Packets unclassified by ingress policy";
    }
    leaf sdvt-expired-conn {
      type uint64;
      description
        "Expired connections";
    }
    leaf sdvt-override-conn {
      type uint64;
      description
        "Overridden connections";
    }
    leaf sdvt-non-syn-divert-reqs {
      type uint64;
      description
        "Non-SYN divert requests";
    }
    leaf sdvt-timedout-pers-conn {
      type uint64;
      description
        "Idle timed-out persistent connections";
    }
    leaf sdvt-appnav-ctrl-decap {
      type uint64;
      description
        "Decapsulation: processed control messages from service node";
    }
    leaf sdvt-appnav-decap-del-req {
      type uint64;
      description
        "Decapsulation: delete requests received total";
    }
    leaf sdvt-appnav-decap-del-term {
      type uint64;
      description
        "Decapsulation: delete - protocol decision";
    }
    leaf sdvt-decap-del-add-flow {
      type uint64;
      description
        "Decapsulation: delete and add new flow";
    }
    leaf sdvt-apv-decap-del-unknown {
      type uint64;
      description
        "Decapsulation: delete - unknown reason";
    }
    leaf sdvt-ctrl-msgs-drop {
      type uint64;
      description
        "Control messages from service node dropped";
    }
    leaf sdvt-pass-intermed-node {
      type uint64;
      description
        "Connections passed-through as intermediate node";
    }
    leaf sdvt-passthrough-alg-flow {
      type uint64;
      description
        "Connections passed-through as ALG flow";
    }
    leaf sdvt-cleared-dreopt {
      type uint64;
      description
        "Connections DREOPT service is cleared";
    }
    leaf sdvt-gw-transit-flow {
      type uint64;
      description
        "Transit flows";
    }
  }

  grouping sdvt-pkt-stats-entry {
    description
      "SDVT packet statistics entry";
    leaf sdvt-bypass-cnt-pkts {
      type uint64;
      description
        "Bypassed frames without optimisation packets";
    }
    leaf sdvt-bypass-cnt-octets {
      type uint64;
      description
        "Bypassed frames without optimisation octets";
    }
    leaf sdvt-divert-cnt-pkts {
      type uint64;
      description
        "Diverted frames to service node packets";
    }
    leaf sdvt-divert-cnt-octets {
      type uint64;
      description
        "Diverted frames to service node octets";
    }
    leaf sdvt-reinject-cnt-pkts {
      type uint64;
      description
        "Reinject frames from service node packets";
    }
    leaf sdvt-reinject-cnt-octets {
      type uint64;
      description
        "Reinject frames from service node octets";
    }
    leaf sdvt-pkts-drop-pkts {
      type uint64;
      description
        "Service divert packets dropped packets";
    }
    leaf sdvt-pkts-drop-octets {
      type uint64;
      description
        "Service divert packets dropped octets";
    }
    leaf sdvt-no-action-cnt-pkts {
      type uint64;
      description
        "Service divert no action packets";
    }
    leaf sdvt-no-action-cnt-octets {
      type uint64;
      description
        "Service divert no action packets in octets";
    }
    leaf sdvt-unknown-act-cnt-pkts {
      type uint64;
      description
        "Unknown action packet counters";
    }
    leaf sdvt-unknown-act-cnt-oct {
      type uint64;
      description
        "Unknown action packet counters in octets";
    }
    leaf sdvt-divert-icmp-cnt-pkts {
      type uint64;
      description
        "Diverted ICMP frames to service node packets";
    }
    leaf sdvt-divert-icmp-cnt-oct {
      type uint64;
      description
        "Diverted ICMP frames to service node octets";
    }
  }

  grouping sdvt-drop-cause-entry {
    description
      "SDVT drop cause entry";
    leaf sdvt-drop-msg-loged {
      type uint64;
      description
        "Invalid drop cause";
    }
    leaf sdvt-drop-appnav-divert {
      type uint64;
      description
        "APPNAV failed divert";
    }
    leaf sdvt-drop-decap-conn-est {
      type uint64;
      description
        "Decapsulation: VPATH connection establishment error";
    }
    leaf sdvt-decap-no-flow-tuple {
      type uint64;
      description
        "Decapsulation: VPATH could not find flow, no tuple";
    }
    leaf sdvt-drop-decaps-pass-err {
      type uint64;
      description
        "Decapsulation: VPATH notification event error";
    }
    leaf sdvt-drop-sn-req {
      type uint64;
      description
        "Service node flagged flow for dropping";
    }
    leaf sdvt-drop-appnav-decap-del {
      type uint64;
      description
        "Decapsulation: could not delete flow";
    }
    leaf sdvt-decap-class-event-err {
      type uint64;
      description
        "Decapsulation: VPATH connection classification error";
    }
    leaf sdvt-drop-cft-no-fo {
      type uint64;
      description
        "No feature object";
    }
    leaf sdvt-appnav-unhealthy {
      type uint64;
      description
        "Packets dropped as service node unhealthy";
    }
    leaf sdvt-drop-reinject {
      type uint64;
      description
        "Re-inject error";
    }
    leaf sdvt-drop-encap-serv-add {
      type uint64;
      description
        "Encapsulation: VPATH could not add TLV";
    }
    leaf sdvt-drop-apv-encap-no-mem {
      type uint64;
      description
        "Encapsulation: VPATH no memory for meta-data";
    }
    leaf sdvt-drop-encap-not-enuf {
      type uint64;
      description
        "Encapsulation: VPATH could not fit TLV into memory";
    }
    leaf sdvt-drop-unwant-icmp-err {
      type uint64;
      description
        "ICMP Error: unwanted error messages";
    }
    leaf sdvt-drop-srv-sn-unhealthy {
      type uint64;
      description
        "Service chain bypass drop as service node unhealthy";
    }
    leaf sdvt-drop-srv-appnav-fail {
      type uint64;
      description
        "Service chain bypass drop as divert failed";
    }
  }

  grouping sdvt-errors-entry {
    description
      "SDVT errors entry";
    leaf sdvt-pkt-fail-divert {
      type uint64;
      description
        "Packets failed divert";
    }
    leaf sdvt-divert-chng-err {
      type uint64;
      description
        "Error changing flow state";
    }
    leaf sdvt-div-chng-no-cb {
      type uint64;
      description
        "Error: missing divert flow change callback";
    }
    leaf fo-del-fail {
      type uint64;
      description
        "Error: feature object delete failed";
    }
    leaf sdvt-encap-debug-err {
      type uint64;
      description
        "Encapsulation: could not create debug meta-data:";
    }
    leaf sdvt-decap-not-icmp-v6 {
      type uint64;
      description
        "Decapsulation: expected ICMP v6 packet";
    }
    leaf sdvt-not-icmp-v6-err {
      type uint64;
      description
        "Decapsulation: expected ICMP v6 error packet";
    }
    leaf sdvt-icmp-no-payload-err {
      type uint64;
      description
        "Decapsulation: No ICMP payload";
    }
    leaf sdvt-skip-unsupp-protocol {
      type uint64;
      description
        "Unsupported protocol";
    }
    leaf sdvt-decap-ipv6-parse-err {
      type uint64;
      description
        "Decapsulation: could not parse ipv6 packet";
    }
    leaf sdvt-ip-unsupport-ver {
      type uint64;
      description
        "Decapsulation: IP error: unsupported version";
    }
    leaf sdvt-decap-no-flow {
      type uint64;
      description
        "Decapsulation: could not locate flow";
    }
    leaf sdvt-bypass-drop {
      type uint64;
      description
        "Service Node requested flow bypass drop";
    }
    leaf sdvt-sn-drop {
      type uint64;
      description
        " Service Node requested packet drop";
    }
    leaf sdvt-flow-notify-offload {
      type uint64;
      description
        "SN offloaded flow";
    }
    leaf sdvt-appnav-decap-del-req {
      type uint64;
      description
        "Decapsulation: delete requests received total";
    }
    leaf sdvt-appnav-decap-del-idle {
      type uint64;
      description
        "Decapsulation: delete - flow idle";
    }
    leaf sdvt-appnav-decap-del-term {
      type uint64;
      description
        "Decapsulation: delete - protocol decision";
    }
    leaf sdvt-decap-del-resource {
      type uint64;
      description
        "Decapsulation: delete - no resources";
    }
    leaf sdvt-decap-del-unknown {
      type uint64;
      description
        "Decapsulation: delete - unknown reason";
    }
    leaf sdvt-icmpv6-no-payload-err {
      type uint64;
      description
        "Decapsulation: no ICMP V6 payload";
    }
    leaf sdvt-decap-icmp-v6-tcp-err {
      type uint64;
      description
        "Decapsulation: ICMP V6 error: could not find TCP header";
    }
    leaf sdvt-decap-icmp-v6-udp-err {
      type uint64;
      description
        "Decapsulation: ICMP V6 error: could not find UDP header";
    }
    leaf sdvt-icmpv6-unsup-protocol {
      type uint64;
      description
        "Decapsulation: ICMP V6 error: unsupported protocol";
    }
    leaf sdvt-appnav-decap-not-icmp {
      type uint64;
      description
        "Decapsulation: expected ICMP packet";
    }
    leaf sdvt-decap-not-icmp-err {
      type uint64;
      description
        "Decapsulation: expected ICMP error packet";
    }
    leaf sdvt-decap-icmp-tcp-err {
      type uint64;
      description
        "Decapsulation: ICMP error: could not find TCP header";
    }
    leaf sdvt-decap-icmp-udp-err {
      type uint64;
      description
        "Decapsulation: ICMP error: could not find UDP header";
    }
    leaf sdvt-icmp-unsup-protocol {
      type uint64;
      description
        "Decapsulation: ICMP error: unsupported protocol";
    }
    leaf sdvt-icmp-no-inner-flow {
      type uint64;
      description
        "Decapsulation: IP error: ICMP not found";
    }
    leaf sdvt-icmp-no-inner-fo {
      type uint64;
      description
        "Decapsulation: IP error: ICMP feature object not found";
    }
    leaf sdvt-decap-no-fo {
      type uint64;
      description
        "Decapsulation: No feature object";
    }
    leaf sdvt-appnav-err-unhealthy {
      type uint64;
      description
        "Flows Bypassed as service node unhealthy";
    }
    leaf sdvt-cft-fo-alloc-fail {
      type uint64;
      description
        "Could not allocate feature object";
    }
    leaf sdvt-cft-attach-fo-fail {
      type uint64;
      description
        "Could not attach feature object";
    }
    leaf sdvt-set-lb-idx-fail {
      type uint64;
      description
        "Set load-balancing index failed";
    }
    leaf sdvt-set-cft-ager-fail {
      type uint64;
      description
        "CFT set ager failed";
    }
    leaf sdvt-incorrect-channel {
      type uint64;
      description
        "Divert request on incorrect channel";
    }
    leaf sdvt-cft-fo-print-fail {
      type uint64;
      description
        "CFT feature object print failed";
    }
    leaf sdvt-cft-set-pers-fail {
      type uint64;
      description
        "Failed to mark CFT flow persistent";
    }
    leaf sdvt-cft-set-unpers-fail {
      type uint64;
      description
        "Failed to unmark CFT flow persistent";
    }
    leaf sdvt-ctrl-decap-no-notif {
      type uint64;
      description
        "Control Decapsulation: message has no notification";
    }
    leaf sdvt-err-natted-in2out {
      type uint64;
      description
        "Failed to create reverse flow database entry";
    }
    leaf sdvt-cft-no-config {
      type uint64;
      description
        "CFT not configured";
    }
    leaf sdvt-unknown-health-status {
      type uint64;
      description
        "Health update has unknown health status";
    }
  }

  grouping appqoe-sdvt-stats {
    description
      "AppQoE datapath per service node SDVT statistics";
    container cntstat {
      description
        "AppQoE per service node SDVT count statistics";
      uses qfp-appqoe-dp-ios-xe-oper:sdvt-cnt-stats-entry;
    }
    container pktstat {
      description
        "AppQoE per service node SDVT packets statistics";
      uses qfp-appqoe-dp-ios-xe-oper:sdvt-pkt-stats-entry;
    }
    container dropcause {
      description
        "AppQoE per service node SDVT drop cause";
      uses qfp-appqoe-dp-ios-xe-oper:sdvt-drop-cause-entry;
    }
    container error {
      description
        "AppQoE per service node SDVT errors";
      uses qfp-appqoe-dp-ios-xe-oper:sdvt-errors-entry;
    }
  }

  grouping sc-dp-key-infra-sn {
    description
      "Service controller datapath key information";
    leaf sn-id {
      type uint8;
      description
        "Service node identifier";
    }
    leaf sn-idx {
      type uint8;
      description
        "Service node index";
    }
    leaf service-type {
      type qfp-appqoe-dp-ios-xe-oper:sn-service-type;
      description
        "Service controller service type";
    }
    leaf sng-id {
      type uint8;
      description
        "Service node group identifier";
    }
    leaf del {
      type uint8;
      description
        "Service node delete state";
    }
    leaf infra-sn-version {
      type uint8;
      description
        "Service node version";
    }
    leaf infra-oce-obj-id {
      type uint64;
      description
        "Service node OCE adj pointer";
    }
    leaf infra-ip-addr {
      type inet:ip-address;
      description
        "Service node IP address";
    }
    leaf status {
      type qfp-appqoe-dp-ios-xe-oper:appnav-snstat;
      description
        "Service node status";
    }
  }

  grouping appnav-snstats {
    description
      "APPNAV service node statistics";
    leaf mismatch {
      type uint8;
      description
        "AppNav service node IP address mismatch";
    }
    leaf type {
      type qfp-appqoe-dp-ios-xe-oper:sn-service-type;
      description
        "AppNav service node type";
    }
    leaf sng-id {
      type uint16;
      description
        "AppNav Service node group";
    }
    leaf stats-to-sn-pkts {
      type uint64;
      description
        "AppNav packets sent to service node";
    }
    leaf stats-to-sn-octets {
      type uint64;
      description
        "AppNav stats in octets sent to service node";
    }
    leaf stats-from-sn-pkts {
      type uint64;
      description
        "AppNav packets received from service node";
    }
    leaf stats-from-sn-octets {
      type uint64;
      description
        "AppNav stats in octets received from service node";
    }
    leaf no-fo-drop-pkts {
      type uint64;
      description
        "AppNav fo drop packets";
    }
    leaf no-fo-drop-octets {
      type uint64;
      description
        "AppNav fo drop stats in octets";
    }
  }

  grouping appnav-sn-info {
    description
      "AppNav service node related information";
    container sn {
      description
        "Datapath infra per service node key information";
      uses qfp-appqoe-dp-ios-xe-oper:sc-dp-key-infra-sn;
    }
    container appnav-stats {
      description
        "AppNav per service node statistics";
      uses qfp-appqoe-dp-ios-xe-oper:appnav-snstats;
    }
  }

  grouping appqoe-sn-info {
    description
      "Per service node information";
    leaf sn-id {
      type uint32;
      description
        "Service node identifier";
    }
    container sn-stats {
      description
        "Per service node statistics";
      uses qfp-appqoe-dp-ios-xe-oper:appqoe-sdvt-stats;
    }
    container appnav-sn {
      description
        "Per service node AppNav statistics";
      uses qfp-appqoe-dp-ios-xe-oper:appnav-sn-info;
    }
  }

  grouping appqoe-hash-tbl-entry {
    description
      "Service node group hash table status";
    leaf aos-enabled {
      type uint8;
      description
        "Application optimisation enabled for this table";
    }
    leaf allotted-entries {
      type uint8;
      description
        "Number of entries in the table";
    }
    leaf-list slot {
      type uint8;
      ordered-by user;
      description
        "Number of slots allocated per service node";
    }
    leaf-list sn {
      type uint8;
      ordered-by user;
      description
        "Service nodes active for an service node group";
    }
    leaf status {
      type qfp-appqoe-dp-ios-xe-oper:appqoe-hash-status;
      description
        "Status of the hash table";
    }
  }

  grouping appqoe-per-sn-entry {
    description
      "Service node table entry details";
    leaf idx {
      type uint8;
      description
        "Which index service node info is stored in the table";
    }
    leaf sn-id {
      type uint8;
      description
        "Service node Identifier";
    }
    leaf hdl {
      type uint8;
      description
        "AppQoE Service handle";
    }
    leaf ver {
      type uint8;
      description
        "Service infra version";
    }
    leaf snstat {
      type qfp-appqoe-dp-ios-xe-oper:appnav-snstat;
      description
        "Service controller service node status";
    }
    leaf snip {
      type inet:ip-address;
      description
        "IP address of the service node";
    }
    leaf dpstat {
      type qfp-appqoe-dp-ios-xe-oper:appnav-snstat;
      description
        "Datapath service node status";
    }
    leaf timestamp {
      type yang:date-and-time;
      description
        "Datapath timestamp when last status update received";
    }
    leaf-list sub-service-hlth {
      type uint8;
      ordered-by user;
      description
        "Service node sub service health status";
    }
  }

  grouping appqoe-sng-info {
    description
      "Per service node group information";
    leaf sng-id {
      type uint32;
      description
        "Service node group identifier";
    }
    leaf mem-bm {
      type uint64;
      description
        "Service node membership bit mask";
    }
    leaf active-sn-bm {
      type uint64;
      description
        "Current active service node for this service node group bit mask";
    }
    list hash-table {
      description
        "Hash table for service node group";
      uses qfp-appqoe-dp-ios-xe-oper:appqoe-hash-tbl-entry;
    }
    list sn-tbl {
      description
        "Service node table for service node group";
      uses qfp-appqoe-dp-ios-xe-oper:appqoe-per-sn-entry;
    }
  }

  grouping appqoe-dp-feature-stats {
    description
      "AppQoE datapath feature statistics";
    container global {
      description
        "AppQoE global statistics";
      uses qfp-appqoe-dp-ios-xe-oper:appqoe-global-stats;
    }
    list appqoe-sn-info {
      key "sn-id";
      description
        "AppQoE per service node instance information";
      uses qfp-appqoe-dp-ios-xe-oper:appqoe-sn-info;
    }
    list appqoe-sng-intern-info {
      key "sng-id";
      description
        "AppQoE per service node group instance internal information";
      uses qfp-appqoe-dp-ios-xe-oper:appqoe-sng-info;
    }
  }

  container qfp-appqoe-dp-oper-data {
    config false;
    description
      "AppQoE datapath operational data";
    list location {
      key "fru slot bay chassis node";
      description
        "A list of data provider locations";
      uses common-types-ios-xe:extended-location;
      container appqoe-dp-feature-stats {
        presence "appqoe-dp-feature-stats";
        description
          "AppQoE datapath feature statistics";
        uses qfp-appqoe-dp-ios-xe-oper:appqoe-dp-feature-stats;
      }
    }
  }
}
