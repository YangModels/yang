module Cisco-IOS-XE-wireless-rrm-emul-oper {
  yang-version 1.1;
  namespace "http://cisco.com/ns/yang/Cisco-IOS-XE-wireless-rrm-emul-oper";
  prefix wireless-rrm-emul-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains RFID operational data.
     Copyright (c) 2022 by Cisco Systems, Inc.
     All rights reserved.";

  revision 2022-07-01 {
    description
      "Initial revision";
    reference
      "1.0.0";
    cisco-semver:module-version "1.0.0";
  }

  grouping st-rrm-fra-statistics {
    description
      "RRM flexible radio statistics";
    leaf dual-band-monitor-to-24ghz {
      type uint32;
      description
        "Dual-band radio transition from monitor to 2.4GHz";
    }
    leaf dual-band-monitor-to-5ghz {
      type uint32;
      description
        "Dual-band radio transition from monitor to 5GHz";
    }
    leaf dual-band-24ghz-to-5ghz {
      type uint32;
      description
        "Dual-band radio transition from 2.4GHz to 5GHz";
    }
    leaf dual-band-24ghz-to-monitor {
      type uint32;
      description
        "Dual-band radio transition from 2.4GHz to monitor";
    }
    leaf dual-band-5ghz-to-24ghz {
      type uint32;
      description
        "Dual-band radio transition from 5GHz to 2.4GHz";
    }
    leaf dual-band-5ghz-to-monitor {
      type uint32;
      description
        "Dual-band radio transition from 5GHz to monitor";
    }
    leaf sec-radio-monitor-to-5ghz {
      type uint32;
      description
        "Secondary radio transition from monitor to 5GHz";
    }
    leaf sec-radio-5ghz-to-monitor {
      type uint32;
      description
        "Secondary radio transition from 5GHz to monitor";
    }
    leaf dual-band-6ghz-to-5ghz {
      type uint32;
      description
        "Dual-band radio transition from 6GHz to 5GHz";
    }
    leaf dual-band-5ghz-to-6ghz {
      type uint32;
      description
        "Dual-band radio transition from 5GHz to 6GHz";
    }
  }

  container rrm-emul-oper-data {
    config false;
    description
      "RRM operational data";
    container rrm-fra-stats {
      presence "rrm-fra-stats";
      description
        "RRM flexible radio statistics";
      uses wireless-rrm-emul-oper:st-rrm-fra-statistics;
    }
  }
}
