module Cisco-IOS-XE-netconf-diag-oper {
  yang-version 1.1;
  namespace "http://cisco.com/ns/yang/Cisco-IOS-XE-netconf-diag-oper";
  prefix ios-xe-netconf-diag-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for NETCONF Message Diagnostics operational data,
     which includes current diagnostic level, total log size
     and a list of transactions having been recorded.
     Copyright (c) 2020-2021 by Cisco Systems, Inc.
     All rights reserved.";

  revision 2022-03-01 {
    description
      "- Add transaction status
       - Remove log size
       - Update description of diag-basic level";
    reference
      "2.0.0";
    cisco-semver:module-version "2.0.0";
  }
  revision 2021-03-01 {
    description
      "Initial revision";
    reference
      "1.0.0";
    cisco-semver:module-version "1.0.0";
  }

  typedef diagnostic-level {
    type enumeration {
      enum diag-disabled {
        value 0;
        description
          "No diagnostic data collection (default).";
      }
      enum diag-basic {
        value 1;
        description
          "Include debugging logs.";
      }
      enum diag-maximum {
        value 2;
        description
          "Include the basic diagnostics plus before and after
           running-config snapshots.";
      }
    }
    description
      "Levels of diagnostic reporting.";
  }

  typedef transaction-status {
    type enumeration {
      enum trans-status-unknown {
        value 0;
        description
          "Transaction status is unknown.";
      }
      enum trans-status-success {
        value 1;
        description
          "Transaction is successful.";
      }
      enum trans-status-failed {
        value 2;
        description
          "Transaction is failed.";
      }
    }
    description
      "Transaction status.";
  }

  grouping diag-transaction {
    description
      "A transaction having been recorded for diagnostics.";
    leaf message {
      type uint32;
      description
        "Message number assigned for identifying this transaction.
         It can be used to find the transaction in the diagnostic logs.";
    }
    leaf username {
      type string;
      description
        "Username of this NETCONF session.";
    }
    leaf session-id {
      type int32;
      description
        "NETCONF session-id of this transaction.";
    }
    leaf trans-id {
      type int32;
      description
        "Transaction-id of this transaction.";
    }
    leaf start-time {
      type yang:date-and-time;
      description
        "Starting time of recording the transaction.";
    }
    leaf end-time {
      type yang:date-and-time;
      description
        "Ending time of recording the transaction.";
    }
    leaf status {
      type ios-xe-netconf-diag-oper:transaction-status;
      description
        "Transaction status.";
    }
  }

  grouping diag-summary {
    description
      "Summary of current status of NETCONF Message diagnostics,
       which includes current diagnostic level, total log size
       and number of transactions having been recorded.";
    leaf level {
      type ios-xe-netconf-diag-oper:diagnostic-level;
      description
        "Diagnostic level enabled.";
    }
    leaf trans-count {
      type uint16;
      description
        "Number of transactions having been recorded.";
    }
  }

  container netconf-diag-oper-data {
    config false;
    description
      "Operational data of NETCONF Message Diagnostics,
       which includes current diagnostic level, total log size
       and a list of transactions having been recorded.";
    container diag-summary {
      presence "diag-summary";
      description
        "Summary of current status of NETCONF Message diagnostics,
         which includes current diagnostic level, total log size
         and number of transactions having been recorded.";
      uses ios-xe-netconf-diag-oper:diag-summary;
    }
    list diag-trans {
      key "message";
      description
        "A list of transactions having been recorded.";
      uses ios-xe-netconf-diag-oper:diag-transaction;
    }
  }
}
