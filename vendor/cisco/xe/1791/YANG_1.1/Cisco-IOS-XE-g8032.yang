module Cisco-IOS-XE-g8032 {
  yang-version 1.1;
  namespace "http://cisco.com/ns/yang/Cisco-IOS-XE-g8032";
  prefix ios-g8032;

  import cisco-semver {
    prefix cisco-semver;
  }
  import Cisco-IOS-XE-native {
    prefix ios;
  }
  import Cisco-IOS-XE-interface-common {
    prefix ios-ifc;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Ethernet Ring protection (G8032) Yang model.
     Copyright (c) 2019 by Cisco Systems, Inc.
     All rights reserved.";

  revision 2019-07-01 {
    description
      "Establish semantic version baseline";
    cisco-semver:module-version "1.0.0";
  }
  revision 2019-01-01 {
    description
      "Initial revision";
  }

  grouping config-ethernet-grouping {
    container ring {
      description
        "Ring Protection G8032";
      container g8032 {
        description
          "Specify the g.8032 ethernet ring";
        list ring-name {
          key "name";
          leaf name {
            description
              "Name of the ethernet ring";
            type string {
              length "1..32";
            }
          }
          container exclusion-list {
            description
              "Specify exclusion list not protected by ERP";
            leaf vlan-ids {
              description
                "List of VLAN IDs in the form a-b,c,d,e-f,g";
              type string;
            }
          }
          leaf open-ring {
            description
              "Specify the g.8032 ring as open ring";
            type empty;
          }
          container port0 {
            description
              "Port0 of the local node connected to G.8032 ring";
            container interface {
              description
                "Assign port interface";
              uses ios-ifc:interface-grouping;
            }
            container monitor {
              description
                "Assign the Ethernet Service Instance to monitor g.8032 ring port";
              container service {
                description
                  "Specify an Ethernet Service Instance";
                leaf instance {
                  description
                    "Specify an Ethernet Service Instance";
                  type uint16 {
                    range "1..8184";
                  }
                }
              }
            }
          }
          container port1 {
            description
              "Port1 of the local node connected to G.8032 ring";
            leaf none {
              description
                "Assign port1 as none to enable g.8032 open-ring";
              type empty;
            }
            container interface {
              description
                "Assign port interface";
              uses ios-ifc:interface-grouping;
            }
            container monitor {
              description
                "Assign the Ethernet Service Instance to monitor g.8032 ring port";
              container service {
                description
                  "Specify an Ethernet Service Instance";
                leaf instance {
                  description
                    "Specify an Ethernet Service Instance";
                  type uint16 {
                    range "1..8184";
                  }
                }
              }
            }
          }
          list instance {
            description
              "Configure the g.8032 ethernet ring instance";
            key "number";
            leaf number {
              description
                "Instance number";
              type uint8 {
                range "1..2";
              }
            }
            container aps-channel {
              description
                "Configure g.8032 instance aps-channel";
              presence "true";
              leaf level {
                description
                  "Specify the APS message level";
                type uint8 {
                  range "0..7";
                }
              }
              container port0 {
                description
                  "Configure g.8032 aps-channel info associated to port0";
                container service {
                  description
                    "Specify an Ethernet Service Instance";
                  leaf instance {
                    description
                      "Specify an Ethernet Service Instance";
                    type uint16 {
                      range "1..8184";
                    }
                  }
                }
              }
              container port1 {
                description
                  "Configure g.8032 aps-channel info associated to port1";
                choice service-instance {
                  case none-case {
                    leaf none {
                      description
                        "Specify port1 APS channel as none";
                      type empty;
                    }
                  }
                  case service-instance-case {
                    container service {
                      description
                        "Specify an Ethernet Service Instance";
                      leaf instance {
                        description
                          "Specify an Ethernet Service Instance";
                        type uint16 {
                          range "1..8184";
                        }
                      }
                    }
                  }
                }
              }
            }
            leaf description {
              description
                "Description for the instance";
              type string;
            }
            container inclusion-list {
              description
                "Specify inclusion list protected by ERP";
              leaf vlan-ids {
                description
                  "Associates a set of VLAN IDs with the current instance";
                type string;
              }
            }
            leaf profile {
              description
                "Ethernet ring profile name";
              type string;
            }
            container rpl {
              description
                "Specify RPL owner, neighbor or next-neighbor";
              choice port {
                case port0 {
                  leaf port0 {
                    description
                      "Assign port0 as RPL owner, neighbor or next-neighbor";
                    type enumeration {
                      enum neighbor;
                      enum next-neighbor;
                      enum owner;
                    }
                  }
                }
                case port1 {
                  leaf port1 {
                    description
                      "Assign port1 as RPL owner, neighbor or next-neighbor";
                    type enumeration {
                      enum neighbor;
                      enum next-neighbor;
                      enum owner;
                    }
                  }
                }
              }
            }
          }
        }
        list profile {
          description
            "g.8032 ring profile configuration";
          key "name";
          leaf name {
            description
              "ERP profile name string";
            type string {
              length "1..32";
            }
          }
          container timer {
            description
              "g.8032 timer";
            leaf guard {
              description
                "Guard timer";
              type uint32 {
                range "10..2000";
              }
              default "500";
            }
            leaf hold-off {
              description
                "Hold off timer";
              type uint32 {
                range "0..10";
              }
              default "0";
            }
            leaf wtr {
              description
                "Wait-to-Restore timer";
              type uint32 {
                range "1..12";
              }
              default "5";
            }
          }
          leaf non-revertive {
            description
              "Non-revertive ring instance";
            type empty;
          }
        }
      }
    }
    container tcn-propagation {
      description
        "Enable TCN propagation";
      container g8032 {
        description
          "g.8032 ethernet ring";
        container to {
          description
            "propagate TCN to";
          leaf g8032 {
            description
              "g.8032 ethernet ring";
            type empty;
          }
          leaf rep {
            description
              "resilient ethernet protocol";
            type empty;
          }
        }
      }
    }
  }

  augment "/ios:native/ios:ethernet" {
    uses config-ethernet-grouping;
  }
}
