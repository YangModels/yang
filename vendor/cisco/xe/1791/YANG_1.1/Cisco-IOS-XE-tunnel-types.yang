module Cisco-IOS-XE-tunnel-types {
  yang-version 1.1;
  namespace "http://cisco.com/ns/yang/Cisco-IOS-XE-tunnel-types";
  prefix tunnel-types;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for tunnel types.
     Copyright (c) 2018-2019 by Cisco Systems, Inc.
     All rights reserved.";

  revision 2021-07-01 {
    description
      "IPSEC IPV4 Dual Overlay";
    reference
      "1.2.0";
    cisco-semver:module-version "1.2.0";
  }
  revision 2019-05-01 {
    description
      "Added semantic version";
    reference
      "1.1.0";
    cisco-semver:module-version "1.1.0";
  }
  revision 2018-11-01 {
    description
      "Initial revision";
    reference
      "1.0.0";
    cisco-semver:module-version "1.0.0";
  }

  typedef tunnel-domain-mode {
    type enumeration {
      enum uninitialized-tunnel-domain-mode {
        value 0;
        description
          "Uninitialized tunnel domain mode";
      }
      enum tunnel-domain-mode-eogre {
        value 1;
        description
          "GRE over point to point IPV4/IPV6 domain";
      }
      enum tunnel-domain-mode-pmipv6 {
        value 2;
        description
          "Proxy Mobile IPV6 domain";
      }
      enum tunnel-domain-mode-gtpv2 {
        value 3;
        description
          "GPRS Tunneling Protocol Version 2 domain";
      }
    }
    description
      "Represents the tunnel domain mode";
  }

  typedef tunnel-intf-mode {
    type enumeration {
      enum uninitialized-tunnel-mode {
        value 0;
        description
          "Uninitialized tunnel mode";
      }
      enum tunnel-mode-gre-ip {
        value 1;
        description
          "GRE over point to point IPV4 tunnel mode";
      }
      enum tunnel-mode-mgre-ip {
        value 2;
        description
          "GRE over multipoint IPv4 tunnel mode";
      }
      enum tunnel-mode-mgre-ipv6 {
        value 3;
        description
          "GRE over multipoint IPv6 tunnel mode";
      }
      enum tunnel-mode-nos-ip {
        value 4;
        description
          "NOS over IPv4 tunnel mode";
      }
      enum tunnel-mode-ip-ip {
        value 5;
        description
          "IP over point to point IPv4 tunnel mode";
      }
      enum tunnel-mode-dvmrp-ip {
        value 6;
        description
          "DVMRP over IPv4 tunnel mode";
      }
      enum tunnel-mode-eon-ip {
        value 7;
        description
          "EON over IPv4 tunnel mode";
      }
      enum tunnel-mode-cayman-udp {
        value 8;
        description
          "CAYMAN over UDP over IPv4 tunnel mode";
      }
      enum tunnel-mode-aurp-udp {
        value 9;
        description
          "AURP over UDP over IPv4 tunnel mode";
      }
      enum tunnel-mode-iptalk-udp {
        value 10;
        description
          "IPTALK over UDP over multipoint IPv4 tunnel mode";
      }
      enum tunnel-mode-tagswitching {
        value 11;
        description
          "mpls transport tunnel mode";
      }
      enum tunnel-mode-ip-ip-dcap-any {
        value 12;
        description
          "IPv4 over point to point IPv4 tunnel mode (receive only)";
      }
      enum tunnel-mode-gre-ipmcast {
        value 13;
        description
          "GRE over IPv4 multicast tunnel mode (deprecated)";
      }
      enum tunnel-mode-cdma {
        value 14;
        description
          "GRE over IPV4 tunnel mode used by the CDMA client";
      }
      enum tunnel-mode-ipv6-ip {
        value 15;
        description
          "IPv6 over point to point IPv4 tunnel mode";
      }
      enum tunnel-mode-ipv6-auto-tunnel {
        value 16;
        description
          "IPv6 over multipoint IPv4 tunnel mode";
      }
      enum tunnel-mode-ipv6-6to4 {
        value 17;
        description
          "IPv6 over multipoint IPv4 tunnel mode";
      }
      enum tunnel-mode-ipv6-6rd {
        value 18;
        description
          "IPv6 over multipoint IPv4 tunnel mode";
      }
      enum tunnel-mode-ipv6-isatap {
        value 19;
        description
          "IPv6 over multipoint IPv4 tunnel mode";
      }
      enum tunnel-mode-ipv6 {
        value 20;
        description
          "IPv6 over point to point IPv6 tunnel mode";
      }
      enum tunnel-mode-gre-ipv6 {
        value 21;
        description
          "GRE over point to point IPv6 tunnel mode";
      }
      enum tunnel-mode-pim-embd-enc-ipv6 {
        value 22;
        description
          "PIM register encapsulation over multipoint IPv6 tunnel mode";
      }
      enum tunnel-mode-pim-enc-ipv6 {
        value 23;
        description
          "PIM register encapsulation over point to point IPv6 tunnel mode";
      }
      enum tunnnel-mode-pim-dec-ipv6 {
        value 24;
        description
          "PIM register decapsulation over point to point IPv6 tunnel mode";
      }
      enum tunnel-mode-pim-enc-ipv4 {
        value 25;
        description
          "PIM register encapsulation over point to point IPv4 tunnel mode";
      }
      enum tunnel-mode-pim-dec-ipv4 {
        value 26;
        description
          "PIM register decapsulation over point to point IPv4 tunnel mode";
      }
      enum tunnel-mode-rbscp-ip {
        value 27;
        description
          "RBSCP over point to point IPv4 tunnel mode";
      }
      enum tunnel-mode-mip-udp {
        value 28;
        description
          "UDP over point to point IPV4 tunnel mode used by ip mobile client";
      }
      enum tunnel-mode-ipsec-ip {
        value 29;
        description
          "Encapsulating Security Protocol (ESP) over point 2 point IPv4 used by the ipsec client";
      }
      enum tunnel-mode-ipsec-ipv6 {
        value 30;
        description
          "Encapsulating Security Protocol (ESP) over point 2 point IPv6 used by the ipsec client";
      }
      enum tunnel-mode-gtp-ipv4 {
        value 31;
        description
          "GPRS Tunnelling Protocol (GTP) IPV4 used by the GTP module";
      }
      enum tunnel-mode-ether-gre-ipv4 {
        value 32;
        description
          "Ethernet Over GRE IPV4";
      }
      enum tunnel-mode-ether-gre-ipv6 {
        value 33;
        description
          "Ethernet Over GRE IPV6";
      }
      enum tunnel-mode-udp-ip {
        value 34;
        description
          "UDP Over IPV4";
      }
      enum tunnel-mode-udp-ipv6 {
        value 35;
        description
          "UDP Over IPV6";
      }
      enum tunnel-mode-mudp-ip {
        value 36;
        description
          "UDP Over multipoint IPV4";
      }
      enum tunnel-mode-mudp-ipv6 {
        value 37;
        description
          "UDP Over multipoint IPV6";
      }
      enum tunnel-mode-vxlan-gpe-ip {
        value 38;
        description
          "VXLAN_GPE Over IPV4";
      }
      enum tunnel-mode-mvxlan-gpe-ip {
        value 39;
        description
          "MVXLAN-GPE Over IPV4";
      }
      enum tunnel-mode-vxlan-gpe-ipv6 {
        value 40;
        description
          "VXLAN_GPE Over IPV6";
      }
      enum tunnel-mode-mvxlan-gpe-ipv6 {
        value 41;
        description
          "MVXLAN-GPE Over IPV6";
      }
      enum tunnel-mode-vxlan-mac-ip {
        value 42;
        description
          "VXLAN_Over IPV4";
      }
      enum tunnel-mode-vxlan-mac-ipv6 {
        value 43;
        description
          "VXLAN_Over IPV6";
      }
      enum tunnel-mode-ether-l2tpv3-ipv6 {
        value 44;
        description
          "L2TPv3 over point to point IPv6 tunnel mode";
      }
      enum tunnel-mode-sdwan {
        value 45;
        description
          "SDWAN Overlay tunnel mode";
      }
      enum tunnel-mode-mvxlan-mac-ip {
        value 46;
        description
          "VXLAN Over IPV4 tunnel mode";
      }
      enum tunnel-mode-mvxlan-mac-ipv6 {
        value 47;
        description
          "VXLAN Over IPV6 tunnel mode";
      }
      enum tunnel-mode-p2p-ethernet-gre-ip {
        value 48;
        description
          "Ethernet Over GRE IPV4 tunnel mode";
      }
      enum tunnel-mode-p2p-ethernet-gre-ipv6 {
        value 49;
        description
          "Ethernet Over GRE IPV6 tunnel mode";
      }
      enum tunnel-mode-ipsec-ipv4-dualoverlay {
        value 50;
        description
          "IPSEC IPV4 Dual Overlay";
      }
    }
    description
      "Represents the tunnel interface mode";
  }

  typedef tunnel-redundancy-model {
    type enumeration {
      enum tunnel-nonrevertive-redundancy {
        value 0;
        description
          "Nonrevertive redundancy";
      }
      enum tunnel-revertive-redundancy {
        value 1;
        description
          "Revertive redundancy";
      }
    }
    description
      "Represents the tunnel redundancy models";
  }

  typedef tunnel-intf-status {
    type enumeration {
      enum tunnel-down {
        value 0;
        description
          "Tunnel not operative";
      }
      enum tunnel-up {
        value 1;
        description
          "Tunnel operative";
      }
    }
    description
      "Represents the tunnel status";
  }

  grouping tunnel-domain-index {
    description
      "Tunnel domain database entry key";
    leaf name {
      type string;
      description
        "Domain Name";
    }
    leaf type {
      type tunnel-types:tunnel-domain-mode;
      description
        "Tunnel Type";
    }
  }

  grouping tunnel-stats {
    description
      "Tunnel Statistics";
    leaf flap-count {
      type uint32;
      description
        "Tunnel flap (up/down) count";
    }
    leaf total-rx-bytes {
      type uint64;
      description
        "Total received bytes";
    }
    leaf total-tx-bytes {
      type uint64;
      description
        "Total transmitted bytes";
    }
    leaf total-rx-pkts {
      type uint64;
      description
        "Total received packets";
    }
    leaf total-tx-pkts {
      type uint64;
      description
        "Total transmitted packets";
    }
    leaf client-count {
      type uint32;
      description
        "Number of clients in this tunnel";
    }
    leaf up-time {
      type uint32;
      description
        "How long this tunnel has been up";
    }
    leaf keepalive-tx {
      type uint64;
      description
        "Number of transmitted keepalives in last window";
    }
    leaf keepalive-rx {
      type uint64;
      description
        "Number of received keepalives in last window";
    }
    leaf keepalive-windows {
      type uint32;
      description
        "Keepalive windows";
    }
    leaf keepalive-dropped {
      type uint32;
      description
        "Number of dropped keepalives in last window";
    }
    leaf total-keepalive-tx {
      type uint64;
      description
        "Number of transmitted keepalives";
    }
    leaf total-keepalive-rx {
      type uint64;
      description
        "Number of received keepalives";
    }
  }

  grouping tunnel-domain-common {
    description
      "Tunnel domain common data";
    leaf primary-tunnel-name {
      type string;
      description
        "Primary tunnel";
    }
    leaf secondary-tunnel-name {
      type string;
      description
        "Secondary tunnel";
    }
    leaf redundancy-model {
      type tunnel-types:tunnel-redundancy-model;
      description
        "Redundancy model";
    }
    leaf enable {
      type boolean;
      description
        "Whether it is enabled";
    }
  }
}
