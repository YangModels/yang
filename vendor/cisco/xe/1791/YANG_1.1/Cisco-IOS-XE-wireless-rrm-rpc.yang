module Cisco-IOS-XE-wireless-rrm-rpc {
  yang-version 1.1;
  namespace "http://cisco.com/ns/yang/Cisco-IOS-XE-wireless-rrm-rpc";
  prefix rrm-rpc;

  import Cisco-IOS-XE-wireless-enum-types {
    prefix wireless-enum-types;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     Wireless Radio Resource Manager Remote Control Procedures.
     Copyright (c) 2020-2022 by Cisco Systems, Inc.
     All rights reserved.";

  revision 2022-07-01 {
    description
      "- Added RPC for RRM grouping and RRM DCA restart configuration
       - Added optional enable 6ghz flag to Remote Leader set and Reset Open RRM RPC";
    reference
      "1.1.0";
    cisco-semver:module-version "1.1.0";
  }
  revision 2020-11-01 {
    description
      "Initial revision";
    reference
      "1.0.0";
    cisco-semver:module-version "1.0.0";
  }

  grouping rrm-80211-dca-restart {
    description
      "DCA restart";
    leaf band {
      type wireless-enum-types:radio-type;
      mandatory true;
      description
        "RRM DCA algorithm restart";
    }
  }

  grouping rrm-80211-grouping-restart {
    description
      "Grouping restart";
    leaf band {
      type wireless-enum-types:radio-type;
      mandatory true;
      description
        "RRM grouping algorithm restart";
    }
  }

  grouping rrm-rldr-reset {
    description
      "Remote Leader Reset";
    leaf reason {
      type wireless-enum-types:enm-reset-reason;
      mandatory true;
      description
        "Remote Leader disconnect reason";
    }
    leaf enable-6ghz {
      type boolean;
      default "false";
      description
        "Flag to set remote leader for 6ghz";
    }
  }

  grouping rrm-rldr-heartbeat {
    description
      "Remote Leader heartbeat";
    leaf timer {
      type uint32 {
        range "1..86400";
      }
      units "seconds";
      mandatory true;
      description
        "Remote Leader heartbeat timer";
    }
  }

  grouping rrm-rldr-set {
    description
      "Remote Leader Set";
    leaf ip-addr {
      type inet:ip-address;
      mandatory true;
      description
        "Remote Leader IP Address";
    }
    leaf leader-name {
      type string {
        length "1..32";
        pattern '[!-~]([ -~]*[!-~])?';
      }
      mandatory true;
      description
        "Remote Leader Name";
    }
    leaf rf-network-name {
      type string {
        length "1..20";
        pattern '[!-~]([ -~]*[!-~])?';
      }
      mandatory true;
      description
        "RF Network Name";
    }
    leaf enable-6ghz {
      type boolean;
      default "false";
      description
        "Flag to set remote leader for 6ghz";
    }
  }

  rpc rrm-80211-dca-restart {
    description
      "RRM DCA algorithm restart";
    input {
      uses rrm-rpc:rrm-80211-dca-restart;
    }
  }

  rpc rrm-80211-grouping-restart {
    description
      "RRM grouping algorithm restart";
    input {
      uses rrm-rpc:rrm-80211-grouping-restart;
    }
  }

  rpc rrm-rldr-reset {
    description
      "Remote Leader Reset Remote Control Procedure resets the rrm group state from remote-member-state to its pre remote-member-state immediately, as opposed to the heartbeat timer which resets after the timer expires.";
    input {
      uses rrm-rpc:rrm-rldr-reset;
    }
  }

  rpc rrm-rldr-heartbeat {
    description
      "Remote Leader Heart Beat Remote Control Procedure sets the heart beat timer to the device. Until this timer expires the device will continue in remote member state. Any new timer value will replace the old timer. If there is no new heartbeat timer value before this timer expires, device will reset to original pre rrm-remote-group state.";
    input {
      uses rrm-rpc:rrm-rldr-heartbeat;
    }
  }

  rpc rrm-rldr-set {
    description
      "Remote Leader Set Remote Control Procedure";
    input {
      uses rrm-rpc:rrm-rldr-set;
    }
  }
}
