module Cisco-IOS-XE-qfp-stats {
  yang-version 1.1;
  namespace "http://cisco.com/ns/yang/Cisco-IOS-XE-qfp-stats";
  prefix ios-xe-qfp-stats;

  import cisco-semver {
    prefix cisco-semver;
  }
  import ietf-yang-types {
    prefix yang;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for data plane statistics.
     Copyright (c) 2018-2021 by Cisco Systems, Inc.
     All rights reserved.";

  revision 2022-07-01 {
    description
      "- Add new drop cause for Unicast Service Reflection.";
    cisco-semver:module-version "1.7.0";
  }
  revision 2022-03-01 {
    description
      "- Add new drop cause for Cable ARP Automatic Reply.";
    cisco-semver:module-version "1.6.0";
  }
  revision 2021-11-01 {
    description
      "- Add new drop cause for Memory Interface and No Interface Resource.
       - Add new drop cause for Dynamic Link Exchange Protocol feature.";
    cisco-semver:module-version "1.5.0";
  }
  revision 2021-07-01 {
    description
      "- Add new drop cause for Cable Recycle Queue.
       - Add new drop causes for
         Packet Core Gateway platform.
       - Add Flow Based Distribution Error Counters.
       - Add new virtual TCP drop causes.";
    cisco-semver:module-version "1.4.0";
  }
  revision 2020-11-01 {
    description
      "- Add new drop cause for sisf ctrl packet.";
    cisco-semver:module-version "1.3.0";
  }
  revision 2020-07-01 {
    description
      "- Add new drop cause for Cable.
       - Add new drop cause for Cable DHCP.";
    cisco-semver:module-version "1.2.0";
  }
  revision 2020-03-01 {
    description
      "- Add new drop cause for Service Divert, VxLAN tunnel policer.
       - Add new drop cause for fragment invalid pkt.
       - Add new drop cause for crypto offload output drop counter.";
    cisco-semver:module-version "1.1.0";
  }
  revision 2019-07-01 {
    description
      "Establish semantic version baseline";
    cisco-semver:module-version "1.0.0";
  }
  revision 2018-12-03 {
    description
      "Add new drop cause for ePBR";
  }
  revision 2018-09-19 {
    description
      "Initial revision";
    reference
      "1.0.0";
  }

  container global-drop-statistics {
    config false;
    leaf uidb-not-cfgd-pkts {
      type yang:counter64;
    }
    leaf uidb-not-cfgd-octets {
      type yang:counter64;
    }
    leaf bad-uidb-idx-pkts {
      type yang:counter64;
    }
    leaf bad-uidb-idx-octets {
      type yang:counter64;
    }
    leaf bad-uidb-sub-idx-pkts {
      type yang:counter64;
    }
    leaf bad-uidb-sub-idx-octets {
      type yang:counter64;
    }
    leaf unknown-encap-pkts {
      type yang:counter64;
    }
    leaf unknown-encap-octets {
      type yang:counter64;
    }
    leaf inv-l2-hdr-pkts {
      type yang:counter64;
    }
    leaf inv-l2-hdr-octets {
      type yang:counter64;
    }
    leaf bad-len-pkts {
      type yang:counter64;
    }
    leaf bad-len-octets {
      type yang:counter64;
    }
    leaf tcp-badfrag-pkts {
      type yang:counter64;
    }
    leaf tcp-badfrag-octets {
      type yang:counter64;
    }
    leaf ipv4-acl-pkts {
      type yang:counter64;
    }
    leaf ipv4-acl-octets {
      type yang:counter64;
    }
    leaf ipv4-acl-lookup-miss-pkts {
      type yang:counter64;
    }
    leaf ipv4-acl-lookup-miss-octets {
      type yang:counter64;
    }
    leaf bad-ip-checksum-pkts {
      type yang:counter64;
    }
    leaf bad-ip-checksum-octets {
      type yang:counter64;
    }
    leaf ip-format-err-pkts {
      type yang:counter64;
    }
    leaf ip-format-err-octets {
      type yang:counter64;
    }
    leaf ip-bad-options-pkts {
      type yang:counter64;
    }
    leaf ip-bad-options-octets {
      type yang:counter64;
    }
    leaf ipv4-martian-pkts {
      type yang:counter64;
    }
    leaf ipv4-martian-octets {
      type yang:counter64;
    }
    leaf mpass-err-pkts {
      type yang:counter64;
    }
    leaf mpass-err-octets {
      type yang:counter64;
    }
    leaf ipv4-pbr-pkts {
      type yang:counter64;
    }
    leaf ipv4-pbr-octets {
      type yang:counter64;
    }
    leaf inv-hdr-err-pkts {
      type yang:counter64;
    }
    leaf inv-hdr-err-octets {
      type yang:counter64;
    }
    leaf punt-err-pkts {
      type yang:counter64;
    }
    leaf punt-err-octets {
      type yang:counter64;
    }
    leaf inject-err-pkts {
      type yang:counter64;
    }
    leaf inject-err-octets {
      type yang:counter64;
    }
    leaf ipv4-no-route-pkts {
      type yang:counter64;
    }
    leaf ipv4-no-route-octets {
      type yang:counter64;
    }
    leaf qos-policing-pkts {
      type yang:counter64;
    }
    leaf qos-policing-octets {
      type yang:counter64;
    }
    leaf qos-actions-pkts {
      type yang:counter64;
    }
    leaf qos-actions-octets {
      type yang:counter64;
    }
    leaf null-jib-hdr-tbl-pkts {
      type yang:counter64;
    }
    leaf null-jib-hdr-tbl-octets {
      type yang:counter64;
    }
    leaf tail-drop-pkts {
      type yang:counter64;
    }
    leaf tail-drop-octets {
      type yang:counter64;
    }
    leaf wred-pkts {
      type yang:counter64;
    }
    leaf wred-octets {
      type yang:counter64;
    }
    leaf invalid-queue-pkts {
      type yang:counter64;
    }
    leaf invalid-queue-octets {
      type yang:counter64;
    }
    leaf invalid-wred-pkts {
      type yang:counter64;
    }
    leaf invalid-wred-octets {
      type yang:counter64;
    }
    leaf mpls-pkts {
      type yang:counter64;
    }
    leaf mpls-octets {
      type yang:counter64;
    }
    leaf ipv6-truncatedpkts-pkts {
      type yang:counter64;
    }
    leaf ipv6-truncatedpkts-octets {
      type yang:counter64;
    }
    leaf ipv6-formaterr-pkts {
      type yang:counter64;
    }
    leaf ipv6-formaterr-octets {
      type yang:counter64;
    }
    leaf ipv6-badsource-pkts {
      type yang:counter64;
    }
    leaf ipv6-badsource-octets {
      type yang:counter64;
    }
    leaf ipv6-badhop-pkts {
      type yang:counter64;
    }
    leaf ipv6-badhop-octets {
      type yang:counter64;
    }
    leaf ipv6-toobigpacket-pkts {
      type yang:counter64;
    }
    leaf ipv6-toobigpacket-octets {
      type yang:counter64;
    }
    leaf ipv6-no-route-pkts {
      type yang:counter64;
    }
    leaf ipv6-no-route-octets {
      type yang:counter64;
    }
    leaf ipv6-acl-lookup-miss-pkts {
      type yang:counter64;
    }
    leaf ipv6-acl-lookup-miss-octets {
      type yang:counter64;
    }
    leaf ipv6-acl-pkts {
      type yang:counter64;
    }
    leaf ipv6-acl-octets {
      type yang:counter64;
    }
    leaf ip-acl-err-pkts {
      type yang:counter64;
    }
    leaf ip-acl-err-octets {
      type yang:counter64;
    }
    leaf mac-acl-pkts {
      type yang:counter64;
    }
    leaf mac-acl-octets {
      type yang:counter64;
    }
    leaf mac-acl-lookup-miss-pkts {
      type yang:counter64;
    }
    leaf mac-acl-lookup-miss-octets {
      type yang:counter64;
    }
    leaf ipv4mc-no-route-pkts {
      type yang:counter64;
    }
    leaf ipv4mc-no-route-octets {
      type yang:counter64;
    }
    leaf unknown-ext-header-pkts {
      type yang:counter64;
    }
    leaf unknown-ext-header-octets {
      type yang:counter64;
    }
    leaf ipv4mc-rpf-failed-pkts {
      type yang:counter64;
    }
    leaf ipv4mc-rpf-failed-octets {
      type yang:counter64;
    }
    leaf ipv4mc-invalid-replica-record-pkts {
      type yang:counter64;
    }
    leaf ipv4mc-invalid-replica-record-octets {
      type yang:counter64;
    }
    leaf ipv4mc-ttl-threshold-chk-failed-pkts {
      type yang:counter64;
    }
    leaf ipv4mc-ttl-threshold-chk-failed-octets {
      type yang:counter64;
    }
    leaf ipv4mc-extra-replicae-pkts {
      type yang:counter64;
    }
    leaf ipv4mc-extra-replicae-octets {
      type yang:counter64;
    }
    leaf ipv4-mtr-pkts {
      type yang:counter64;
    }
    leaf ipv4-mtr-octets {
      type yang:counter64;
    }
    leaf internal-ctl-pkts {
      type yang:counter64;
    }
    leaf internal-ctl-octets {
      type yang:counter64;
    }
    leaf bad-dist-fifo-pkts {
      type yang:counter64;
    }
    leaf bad-dist-fifo-octets {
      type yang:counter64;
    }
    leaf frfab-wred-drop-pkts {
      type yang:counter64;
    }
    leaf frfab-wred-drop-octets {
      type yang:counter64;
    }
    leaf firewall-nonsession-pkts {
      type yang:counter64;
    }
    leaf firewall-nonsession-octets {
      type yang:counter64;
    }
    leaf firewall-invalid-zone-pkts {
      type yang:counter64;
    }
    leaf firewall-invalid-zone-octets {
      type yang:counter64;
    }
    leaf firewall-backpressure-pkts {
      type yang:counter64;
    }
    leaf firewall-backpressure-octets {
      type yang:counter64;
    }
    leaf firewall-l4-insp-pkts {
      type yang:counter64;
    }
    leaf firewall-l4-insp-octets {
      type yang:counter64;
    }
    leaf ip-frag-err-pkts {
      type yang:counter64;
    }
    leaf ip-frag-err-octets {
      type yang:counter64;
    }
    leaf no-gpm-memory-err-pkts {
      type yang:counter64;
    }
    leaf no-gpm-memory-err-octets {
      type yang:counter64;
    }
    leaf for-us-pkts {
      type yang:counter64;
    }
    leaf for-us-octets {
      type yang:counter64;
    }
    leaf ipsec-input-pkts {
      type yang:counter64;
    }
    leaf ipsec-input-octets {
      type yang:counter64;
    }
    leaf ipsec-ike-indicate-pkts {
      type yang:counter64;
    }
    leaf ipsec-ike-indicate-octets {
      type yang:counter64;
    }
    leaf ipsec-invalid-sa-pkts {
      type yang:counter64;
    }
    leaf ipsec-invalid-sa-octets {
      type yang:counter64;
    }
    leaf ipsec-tail-drop-pkts {
      type yang:counter64;
    }
    leaf ipsec-tail-drop-octets {
      type yang:counter64;
    }
    leaf layer2-no-route-pkts {
      type yang:counter64;
    }
    leaf layer2-no-route-octets {
      type yang:counter64;
    }
    leaf icmp-pkts {
      type yang:counter64;
    }
    leaf icmp-octets {
      type yang:counter64;
    }
    leaf ip-ttl-exceeded-pkts {
      type yang:counter64;
    }
    leaf ip-ttl-exceeded-octets {
      type yang:counter64;
    }
    leaf tunnel-bad-gre-checksum-pkts {
      type yang:counter64;
    }
    leaf tunnel-bad-gre-checksum-octets {
      type yang:counter64;
    }
    leaf tunnel-misconfiguration-pkts {
      type yang:counter64;
    }
    leaf tunnel-misconfiguration-octets {
      type yang:counter64;
    }
    leaf gre-bad-options-pkts {
      type yang:counter64;
    }
    leaf gre-bad-options-octets {
      type yang:counter64;
    }
    leaf frag-tail-drop-pkts {
      type yang:counter64;
    }
    leaf frag-tail-drop-octets {
      type yang:counter64;
    }
    leaf unconfigured-fia-pkts {
      type yang:counter64;
    }
    leaf unconfigured-fia-octets {
      type yang:counter64;
    }
    leaf ipv4-fpm-pkts {
      type yang:counter64;
    }
    leaf ipv4-fpm-octets {
      type yang:counter64;
    }
    leaf nat-in2out-pkts {
      type yang:counter64;
    }
    leaf nat-in2out-octets {
      type yang:counter64;
    }
    leaf nat-out2in-pkts {
      type yang:counter64;
    }
    leaf nat-out2in-octets {
      type yang:counter64;
    }
    leaf pa-walk-err-pkts {
      type yang:counter64;
    }
    leaf pa-walk-err-octets {
      type yang:counter64;
    }
    leaf ipv4-routing-err-pkts {
      type yang:counter64;
    }
    leaf ipv4-routing-err-octets {
      type yang:counter64;
    }
    leaf ipv6-routing-err-pkts {
      type yang:counter64;
    }
    leaf ipv6-routing-err-octets {
      type yang:counter64;
    }
    leaf mpass-invalid-fs-vector-pkts {
      type yang:counter64;
    }
    leaf mpass-invalid-fs-vector-octets {
      type yang:counter64;
    }
    leaf reass-drop-pkts {
      type yang:counter64;
    }
    leaf reass-drop-octets {
      type yang:counter64;
    }
    leaf reass-frag-too-big-pkts {
      type yang:counter64;
    }
    leaf reass-frag-too-big-octets {
      type yang:counter64;
    }
    leaf reass-no-frag-info-pkts {
      type yang:counter64;
    }
    leaf reass-no-frag-info-octets {
      type yang:counter64;
    }
    leaf reass-no-frag-info-low-pkts {
      type yang:counter64;
    }
    leaf reass-no-frag-info-low-octets {
      type yang:counter64;
    }
    leaf reass-bad-len-pkts {
      type yang:counter64;
    }
    leaf reass-bad-len-octets {
      type yang:counter64;
    }
    leaf reass-too-many-frags-pkts {
      type yang:counter64;
    }
    leaf reass-too-many-frags-octets {
      type yang:counter64;
    }
    leaf reass-no-frags-left-pkts {
      type yang:counter64;
    }
    leaf reass-no-frags-left-octets {
      type yang:counter64;
    }
    leaf reass-overlap-pkts {
      type yang:counter64;
    }
    leaf reass-overlap-octets {
      type yang:counter64;
    }
    leaf reass-timeout-pkts {
      type yang:counter64;
    }
    leaf reass-timeout-octets {
      type yang:counter64;
    }
    leaf no-mem-pkts {
      type yang:counter64;
    }
    leaf no-mem-octets {
      type yang:counter64;
    }
    leaf vfr-err-pkts {
      type yang:counter64;
    }
    leaf vfr-err-octets {
      type yang:counter64;
    }
    leaf vfr-tail-drop-pkts {
      type yang:counter64;
    }
    leaf vfr-tail-drop-octets {
      type yang:counter64;
    }
    leaf iphc-pkts {
      type yang:counter64;
    }
    leaf iphc-octets {
      type yang:counter64;
    }
    leaf multilink-cfg-pkts {
      type yang:counter64;
    }
    leaf multilink-cfg-octets {
      type yang:counter64;
    }
    leaf mlp-pkts {
      type yang:counter64;
    }
    leaf mlp-octets {
      type yang:counter64;
    }
    leaf min-tu-pkts {
      type yang:counter64;
    }
    leaf min-tu-octets {
      type yang:counter64;
    }
    leaf max-tu-pkts {
      type yang:counter64;
    }
    leaf max-tu-octets {
      type yang:counter64;
    }
    leaf ipv4-unclassified-pkts {
      type yang:counter64;
    }
    leaf ipv4-unclassified-octets {
      type yang:counter64;
    }
    leaf ipv6-unclassified-pkts {
      type yang:counter64;
    }
    leaf ipv6-unclassified-octets {
      type yang:counter64;
    }
    leaf ipv4-no-adj-pkts {
      type yang:counter64;
    }
    leaf ipv4-no-adj-octets {
      type yang:counter64;
    }
    leaf ipv4-null0-pkts {
      type yang:counter64;
    }
    leaf ipv4-null0-octets {
      type yang:counter64;
    }
    leaf ipv6-null0-pkts {
      type yang:counter64;
    }
    leaf ipv6-null0-octets {
      type yang:counter64;
    }
    leaf mpls-mismatch-linktype-pkts {
      type yang:counter64;
    }
    leaf mpls-mismatch-linktype-octets {
      type yang:counter64;
    }
    leaf mpls-frag-req-pkts {
      type yang:counter64;
    }
    leaf mpls-frag-req-octets {
      type yang:counter64;
    }
    leaf choice-oce-pkts {
      type yang:counter64;
    }
    leaf choice-oce-octets {
      type yang:counter64;
    }
    leaf unsupported-oce-pkts {
      type yang:counter64;
    }
    leaf unsupported-oce-octets {
      type yang:counter64;
    }
    leaf attn-invalid-spid-pkts {
      type yang:counter64;
    }
    leaf attn-invalid-spid-octets {
      type yang:counter64;
    }
    leaf inv-common-preamble-pkts {
      type yang:counter64;
    }
    leaf inv-common-preamble-octets {
      type yang:counter64;
    }
    leaf ext-drop-path-pkts {
      type yang:counter64;
    }
    leaf ext-drop-path-octets {
      type yang:counter64;
    }
    leaf frr-oce-no-backup-pkts {
      type yang:counter64;
    }
    leaf frr-oce-no-backup-octets {
      type yang:counter64;
    }
    leaf frr-oce-invalid-state-pkts {
      type yang:counter64;
    }
    leaf frr-oce-invalid-state-octets {
      type yang:counter64;
    }
    leaf bqs-oor-pkts {
      type yang:counter64;
    }
    leaf bqs-oor-octets {
      type yang:counter64;
    }
    leaf ess-bad-sess-uidb-pkts {
      type yang:counter64;
    }
    leaf ess-bad-sess-uidb-octets {
      type yang:counter64;
    }
    leaf ess-pktsb-missed-pkts {
      type yang:counter64;
    }
    leaf ess-pktsb-missed-octets {
      type yang:counter64;
    }
    leaf ess-unsup-pkt-type-pkts {
      type yang:counter64;
    }
    leaf ess-unsup-pkt-type-octets {
      type yang:counter64;
    }
    leaf ess-no-encap-info-pkts {
      type yang:counter64;
    }
    leaf ess-no-encap-info-octets {
      type yang:counter64;
    }
    leaf ess-inv-switch-mode-pkts {
      type yang:counter64;
    }
    leaf ess-inv-switch-mode-octets {
      type yang:counter64;
    }
    leaf inv-ppp-cp-pkt-pkts {
      type yang:counter64;
    }
    leaf inv-ppp-cp-pkt-octets {
      type yang:counter64;
    }
    leaf ppp-cxt-missed-pkts {
      type yang:counter64;
    }
    leaf ppp-cxt-missed-octets {
      type yang:counter64;
    }
    leaf ess-unbound-session-pkts {
      type yang:counter64;
    }
    leaf ess-unbound-session-octets {
      type yang:counter64;
    }
    leaf ess-pi-inv-subtype-pkts {
      type yang:counter64;
    }
    leaf ess-pi-inv-subtype-octets {
      type yang:counter64;
    }
    leaf ess-pi-state-err-pkts {
      type yang:counter64;
    }
    leaf ess-pi-state-err-octets {
      type yang:counter64;
    }
    leaf ess-inject-bad-hdr-pkts {
      type yang:counter64;
    }
    leaf ess-inject-bad-hdr-octets {
      type yang:counter64;
    }
    leaf ess-l2-hdr-too-big-pkts {
      type yang:counter64;
    }
    leaf ess-l2-hdr-too-big-octets {
      type yang:counter64;
    }
    leaf pppox-unconfigured-pkts {
      type yang:counter64;
    }
    leaf pppox-unconfigured-octets {
      type yang:counter64;
    }
    leaf pppoe-pkt-inv-hdr-pkts {
      type yang:counter64;
    }
    leaf pppoe-pkt-inv-hdr-octets {
      type yang:counter64;
    }
    leaf pppoe-pkt-bad-len-pkts {
      type yang:counter64;
    }
    leaf pppoe-pkt-bad-len-octets {
      type yang:counter64;
    }
    leaf pppoe-no-session-pkts {
      type yang:counter64;
    }
    leaf pppoe-no-session-octets {
      type yang:counter64;
    }
    leaf pppoe-inv-encap-info-pkts {
      type yang:counter64;
    }
    leaf pppoe-inv-encap-info-octets {
      type yang:counter64;
    }
    leaf ess-cac-pkts {
      type yang:counter64;
    }
    leaf ess-cac-octets {
      type yang:counter64;
    }
    leaf l2tp-unconfigured-pkts {
      type yang:counter64;
    }
    leaf l2tp-unconfigured-octets {
      type yang:counter64;
    }
    leaf l2tp-pkt-inv-hdr-pkts {
      type yang:counter64;
    }
    leaf l2tp-pkt-inv-hdr-octets {
      type yang:counter64;
    }
    leaf l2tp-pkt-bad-len-pkts {
      type yang:counter64;
    }
    leaf l2tp-pkt-bad-len-octets {
      type yang:counter64;
    }
    leaf l2tp-no-session-pkts {
      type yang:counter64;
    }
    leaf l2tp-no-session-octets {
      type yang:counter64;
    }
    leaf l2tp-pktsb-missed-pkts {
      type yang:counter64;
    }
    leaf l2tp-pktsb-missed-octets {
      type yang:counter64;
    }
    leaf l2tp-security-check-pkts {
      type yang:counter64;
    }
    leaf l2tp-security-check-octets {
      type yang:counter64;
    }
    leaf l2tp-bad-udp-chksum-pkts {
      type yang:counter64;
    }
    leaf l2tp-bad-udp-chksum-octets {
      type yang:counter64;
    }
    leaf l2tp-ooo-rx-pkt-pkts {
      type yang:counter64;
    }
    leaf l2tp-ooo-rx-pkt-octets {
      type yang:counter64;
    }
    leaf l2tp-exceed-tx-mtu-pkts {
      type yang:counter64;
    }
    leaf l2tp-exceed-tx-mtu-octets {
      type yang:counter64;
    }
    leaf ipsec-output-pkts {
      type yang:counter64;
    }
    leaf ipsec-output-octets {
      type yang:counter64;
    }
    leaf ipsec-ted-indicate-pkts {
      type yang:counter64;
    }
    leaf ipsec-ted-indicate-octets {
      type yang:counter64;
    }
    leaf ipsec-deny-drop-pkts {
      type yang:counter64;
    }
    leaf ipsec-deny-drop-octets {
      type yang:counter64;
    }
    leaf l2tp-cxt-missed-pkts {
      type yang:counter64;
    }
    leaf l2tp-cxt-missed-octets {
      type yang:counter64;
    }
    leaf l2tp-tx-seq-missed-pkts {
      type yang:counter64;
    }
    leaf l2tp-tx-seq-missed-octets {
      type yang:counter64;
    }
    leaf disabled-pkts {
      type yang:counter64;
    }
    leaf disabled-octets {
      type yang:counter64;
    }
    leaf ipv6-no-adj-pkts {
      type yang:counter64;
    }
    leaf ipv6-no-adj-octets {
      type yang:counter64;
    }
    leaf not-enabled-pkts {
      type yang:counter64;
    }
    leaf not-enabled-octets {
      type yang:counter64;
    }
    leaf special-multicast-obj-pkts {
      type yang:counter64;
    }
    leaf special-multicast-obj-octets {
      type yang:counter64;
    }
    leaf illegal-obj-pkts {
      type yang:counter64;
    }
    leaf illegal-obj-octets {
      type yang:counter64;
    }
    leaf unresolved-pkts {
      type yang:counter64;
    }
    leaf unresolved-octets {
      type yang:counter64;
    }
    leaf discard-pkts {
      type yang:counter64;
    }
    leaf discard-octets {
      type yang:counter64;
    }
    leaf ipv6mc-no-route-pkts {
      type yang:counter64;
    }
    leaf ipv6mc-no-route-octets {
      type yang:counter64;
    }
    leaf ipv6mc-rpf-failed-pkts {
      type yang:counter64;
    }
    leaf ipv6mc-rpf-failed-octets {
      type yang:counter64;
    }
    leaf ipv6mc-invalid-replica-record-pkts {
      type yang:counter64;
    }
    leaf ipv6mc-invalid-replica-record-octets {
      type yang:counter64;
    }
    leaf ipv6mc-ttl-threshold-chk-failed-pkts {
      type yang:counter64;
    }
    leaf ipv6mc-ttl-threshold-chk-failed-octets {
      type yang:counter64;
    }
    leaf ipv6mc-extra-replica-pkts {
      type yang:counter64;
    }
    leaf ipv6mc-extra-replica-octets {
      type yang:counter64;
    }
    leaf layer2-switching-pkts {
      type yang:counter64;
    }
    leaf layer2-switching-octets {
      type yang:counter64;
    }
    leaf internal-intf-err-pkts {
      type yang:counter64;
    }
    leaf internal-intf-err-octets {
      type yang:counter64;
    }
    leaf sbc-police-punt-pkts {
      type yang:counter64;
    }
    leaf sbc-police-punt-octets {
      type yang:counter64;
    }
    leaf sbc-uidb-pkts {
      type yang:counter64;
    }
    leaf sbc-uidb-octets {
      type yang:counter64;
    }
    leaf sbc-sess-pkts {
      type yang:counter64;
    }
    leaf sbc-sess-octets {
      type yang:counter64;
    }
    leaf sbc-mmoh-invalid-replica-record-pkts {
      type yang:counter64;
    }
    leaf sbc-mmoh-invalid-replica-record-octets {
      type yang:counter64;
    }
    leaf mpls-ipv6-frag-req-pkts {
      type yang:counter64;
    }
    leaf mpls-ipv6-frag-req-octets {
      type yang:counter64;
    }
    leaf sw-mac-filter-pkts {
      type yang:counter64;
    }
    leaf sw-mac-filter-octets {
      type yang:counter64;
    }
    leaf tunnel-bad-pim-checksum-pkts {
      type yang:counter64;
    }
    leaf tunnel-bad-pim-checksum-octets {
      type yang:counter64;
    }
    leaf tunnel-unsupported-config-pkts {
      type yang:counter64;
    }
    leaf tunnel-unsupported-config-octets {
      type yang:counter64;
    }
    leaf firewall-no-forwarding-pkts {
      type yang:counter64;
    }
    leaf firewall-no-forwarding-octets {
      type yang:counter64;
    }
    leaf erspan-pkts {
      type yang:counter64;
    }
    leaf erspan-octets {
      type yang:counter64;
    }
    leaf ipv4-urpf-null-path-list-pkts {
      type yang:counter64;
    }
    leaf ipv4-urpf-null-path-list-octets {
      type yang:counter64;
    }
    leaf mpls-unclassified-pkts {
      type yang:counter64;
    }
    leaf mpls-unclassified-octets {
      type yang:counter64;
    }
    leaf mpls-eos-invalid-pkts {
      type yang:counter64;
    }
    leaf mpls-eos-invalid-octets {
      type yang:counter64;
    }
    leaf glean-adj-unsupport-linktype-pkts {
      type yang:counter64;
    }
    leaf glean-adj-unsupport-linktype-octets {
      type yang:counter64;
    }
    leaf mpls-label-oce-ptr-null-pkts {
      type yang:counter64;
    }
    leaf mpls-label-oce-ptr-null-octets {
      type yang:counter64;
    }
    leaf mpls-label-oce-invalid-label-pkts {
      type yang:counter64;
    }
    leaf mpls-label-oce-invalid-label-octets {
      type yang:counter64;
    }
    leaf mpls-label-oce-unsupport-linktype-pkts {
      type yang:counter64;
    }
    leaf mpls-label-oce-unsupport-linktype-octets {
      type yang:counter64;
    }
    leaf lookup-oce-should-drop-pkts {
      type yang:counter64;
    }
    leaf lookup-oce-should-drop-octets {
      type yang:counter64;
    }
    leaf lookup-oce-unsupport-linktype-pkts {
      type yang:counter64;
    }
    leaf lookup-oce-unsupport-linktype-octets {
      type yang:counter64;
    }
    leaf unsupport-linktype-no-route-pkts {
      type yang:counter64;
    }
    leaf unsupport-linktype-no-route-octets {
      type yang:counter64;
    }
    leaf unsupport-linktype-null0-pkts {
      type yang:counter64;
    }
    leaf unsupport-linktype-null0-octets {
      type yang:counter64;
    }
    leaf sr-te-remote-error-pkts {
      type yang:counter64;
    }
    leaf sr-te-remote-error-octets {
      type yang:counter64;
    }
    leaf ipv4-pop-pipe-php-ttl-expire-pkts {
      type yang:counter64;
    }
    leaf ipv4-pop-pipe-php-ttl-expire-octets {
      type yang:counter64;
    }
    leaf ipv4-pop-unf-uhp-ttl-expire-pkts {
      type yang:counter64;
    }
    leaf ipv4-pop-unf-uhp-ttl-expire-octets {
      type yang:counter64;
    }
    leaf ipv4-pop-unf-php-ttl-expire-pkts {
      type yang:counter64;
    }
    leaf ipv4-pop-unf-php-ttl-expire-octets {
      type yang:counter64;
    }
    leaf mpls-pop-pipe-ttl-expire-pkts {
      type yang:counter64;
    }
    leaf mpls-pop-pipe-ttl-expire-octets {
      type yang:counter64;
    }
    leaf mpls-pop-unf-uhp-ttl-expire-pkts {
      type yang:counter64;
    }
    leaf mpls-pop-unf-uhp-ttl-expire-octets {
      type yang:counter64;
    }
    leaf mpls-pop-unf-php-ttl-expire-pkts {
      type yang:counter64;
    }
    leaf mpls-pop-unf-php-ttl-expire-octets {
      type yang:counter64;
    }
    leaf label-pop-unsupport-linktype-pkts {
      type yang:counter64;
    }
    leaf label-pop-unsupport-linktype-octets {
      type yang:counter64;
    }
    leaf mpls-no-route-pkts {
      type yang:counter64;
    }
    leaf mpls-no-route-octets {
      type yang:counter64;
    }
    leaf mpls-icmp-invalid-hdr-pkts {
      type yang:counter64;
    }
    leaf mpls-icmp-invalid-hdr-octets {
      type yang:counter64;
    }
    leaf mpls-sanity-echo-req-pkts {
      type yang:counter64;
    }
    leaf mpls-sanity-echo-req-octets {
      type yang:counter64;
    }
    leaf mpls-sanity-drop-pkts {
      type yang:counter64;
    }
    leaf mpls-sanity-drop-octets {
      type yang:counter64;
    }
    leaf ess-unprov-session-pkts {
      type yang:counter64;
    }
    leaf ess-unprov-session-octets {
      type yang:counter64;
    }
    leaf firewall-policy-pkts {
      type yang:counter64;
    }
    leaf firewall-policy-octets {
      type yang:counter64;
    }
    leaf firewall-l4-pkts {
      type yang:counter64;
    }
    leaf firewall-l4-octets {
      type yang:counter64;
    }
    leaf firewall-l7-pkts {
      type yang:counter64;
    }
    leaf firewall-l7-octets {
      type yang:counter64;
    }
    leaf firewall-no-new-sessions-pkts {
      type yang:counter64;
    }
    leaf firewall-no-new-sessions-octets {
      type yang:counter64;
    }
    leaf firewall-not-initiator-pkts {
      type yang:counter64;
    }
    leaf firewall-not-initiator-octets {
      type yang:counter64;
    }
    leaf firewall-not-from-init-pkts {
      type yang:counter64;
    }
    leaf firewall-not-from-init-octets {
      type yang:counter64;
    }
    leaf gen-pkt-replication-pkts {
      type yang:counter64;
    }
    leaf gen-pkt-replication-octets {
      type yang:counter64;
    }
    leaf esf-l4r-bad-config-pkts {
      type yang:counter64;
    }
    leaf esf-l4r-bad-config-octets {
      type yang:counter64;
    }
    leaf esf-l4r-trans-unavail-pkts {
      type yang:counter64;
    }
    leaf esf-l4r-trans-unavail-octets {
      type yang:counter64;
    }
    leaf esf-pbhk-bad-config-pkts {
      type yang:counter64;
    }
    leaf esf-pbhk-bad-config-octets {
      type yang:counter64;
    }
    leaf esf-pbhk-unalloc-pkts {
      type yang:counter64;
    }
    leaf esf-pbhk-unalloc-octets {
      type yang:counter64;
    }
    leaf esf-pbhk-port-unavail-pkts {
      type yang:counter64;
    }
    leaf esf-pbhk-port-unavail-octets {
      type yang:counter64;
    }
    leaf esf-pbhk-port-notfound-pkts {
      type yang:counter64;
    }
    leaf esf-pbhk-port-notfound-octets {
      type yang:counter64;
    }
    leaf esf-pbhk-port-removed-pkts {
      type yang:counter64;
    }
    leaf esf-pbhk-port-removed-octets {
      type yang:counter64;
    }
    leaf mpls-no-adj-pkts {
      type yang:counter64;
    }
    leaf mpls-no-adj-octets {
      type yang:counter64;
    }
    leaf ipv4-adj-drop-pkts {
      type yang:counter64;
    }
    leaf ipv4-adj-drop-octets {
      type yang:counter64;
    }
    leaf ipv6-adj-drop-pkts {
      type yang:counter64;
    }
    leaf ipv6-adj-drop-octets {
      type yang:counter64;
    }
    leaf mpls-adj-drop-pkts {
      type yang:counter64;
    }
    leaf mpls-adj-drop-octets {
      type yang:counter64;
    }
    leaf bad-adj-pkts {
      type yang:counter64;
    }
    leaf bad-adj-octets {
      type yang:counter64;
    }
    leaf punt-policer-drop-pkts {
      type yang:counter64;
    }
    leaf punt-policer-drop-octets {
      type yang:counter64;
    }
    leaf punt-global-policer-drop-pkts {
      type yang:counter64;
    }
    leaf punt-global-policer-drop-octets {
      type yang:counter64;
    }
    leaf esf-tc-drop-pkts {
      type yang:counter64;
    }
    leaf esf-tc-drop-octets {
      type yang:counter64;
    }
    leaf esf-drl-drop-pkts {
      type yang:counter64;
    }
    leaf esf-drl-drop-octets {
      type yang:counter64;
    }
    leaf ess-ipsub-drop-pkts {
      type yang:counter64;
    }
    leaf ess-ipsub-drop-octets {
      type yang:counter64;
    }
    leaf ess-ipsub-fsol-drop-pkts {
      type yang:counter64;
    }
    leaf ess-ipsub-fsol-drop-octets {
      type yang:counter64;
    }
    leaf ess-ipsub-classifier-drop-pkts {
      type yang:counter64;
    }
    leaf ess-ipsub-classifier-drop-octets {
      type yang:counter64;
    }
    leaf ess-ipsub-ka-drop-pkts {
      type yang:counter64;
    }
    leaf ess-ipsub-ka-drop-octets {
      type yang:counter64;
    }
    leaf oam-loopback-pkts {
      type yang:counter64;
    }
    leaf oam-loopback-octets {
      type yang:counter64;
    }
    leaf unconfigured-ipv4-fia-pkts {
      type yang:counter64;
    }
    leaf unconfigured-ipv4-fia-octets {
      type yang:counter64;
    }
    leaf unconfigured-ipv6-fia-pkts {
      type yang:counter64;
    }
    leaf unconfigured-ipv6-fia-octets {
      type yang:counter64;
    }
    leaf unconfigured-mpls-fia-pkts {
      type yang:counter64;
    }
    leaf unconfigured-mpls-fia-octets {
      type yang:counter64;
    }
    leaf smi-disabled-pkts {
      type yang:counter64;
    }
    leaf smi-disabled-octets {
      type yang:counter64;
    }
    leaf oce-drop-adj-pkts {
      type yang:counter64;
    }
    leaf oce-drop-adj-octets {
      type yang:counter64;
    }
    leaf internal-pkts {
      type yang:counter64;
    }
    leaf internal-octets {
      type yang:counter64;
    }
    leaf inv-spa-hdr-pkts {
      type yang:counter64;
    }
    leaf inv-spa-hdr-octets {
      type yang:counter64;
    }
    leaf ppe-exception-pkts {
      type yang:counter64;
    }
    leaf ppe-exception-octets {
      type yang:counter64;
    }
    leaf internal-replication-pkts {
      type yang:counter64;
    }
    leaf internal-replication-octets {
      type yang:counter64;
    }
    leaf internal-recycle-tail-pkts {
      type yang:counter64;
    }
    leaf internal-recycle-tail-octets {
      type yang:counter64;
    }
    leaf internal-no-gpm-pkts {
      type yang:counter64;
    }
    leaf internal-no-gpm-octets {
      type yang:counter64;
    }
    leaf internal-no-channel-mem-pkts {
      type yang:counter64;
    }
    leaf internal-no-channel-mem-octets {
      type yang:counter64;
    }
    leaf ip-sia-hdr-err-pkts {
      type yang:counter64;
    }
    leaf ip-sia-hdr-err-octets {
      type yang:counter64;
    }
    leaf ip-sia-hop-limit-exceeded-pkts {
      type yang:counter64;
    }
    leaf ip-sia-hop-limit-exceeded-octets {
      type yang:counter64;
    }
    leaf ip-sia-processing-err-pkts {
      type yang:counter64;
    }
    leaf ip-sia-processing-err-octets {
      type yang:counter64;
    }
    leaf sslvpn-svi-invalid-h-pkts {
      type yang:counter64;
    }
    leaf sslvpn-svi-invalid-h-octets {
      type yang:counter64;
    }
    leaf esf-acct-exceed-drop-pkts {
      type yang:counter64;
    }
    leaf esf-acct-exceed-drop-octets {
      type yang:counter64;
    }
    leaf tcp-pkts {
      type yang:counter64;
    }
    leaf tcp-octets {
      type yang:counter64;
    }
    leaf invalid-encap-pkts {
      type yang:counter64;
    }
    leaf invalid-encap-octets {
      type yang:counter64;
    }
    leaf dsp-pkts {
      type yang:counter64;
    }
    leaf dsp-octets {
      type yang:counter64;
    }
    leaf mpls-csc-drop-pkts {
      type yang:counter64;
    }
    leaf mpls-csc-drop-octets {
      type yang:counter64;
    }
    leaf cstp-cdtp-inv-frame-pkts {
      type yang:counter64;
    }
    leaf cstp-cdtp-inv-frame-octets {
      type yang:counter64;
    }
    leaf cstp-cdtp-no-tunnel-pkts {
      type yang:counter64;
    }
    leaf cstp-cdtp-no-tunnel-octets {
      type yang:counter64;
    }
    leaf cstp-cdtp-unsup-frame-pkts {
      type yang:counter64;
    }
    leaf cstp-cdtp-unsup-frame-octets {
      type yang:counter64;
    }
    leaf esf-l4r-trans-sess-limit-pkts {
      type yang:counter64;
    }
    leaf esf-l4r-trans-sess-limit-octets {
      type yang:counter64;
    }
    leaf lisp-elig-oce-pkts {
      type yang:counter64;
    }
    leaf lisp-elig-oce-octets {
      type yang:counter64;
    }
    leaf lisp-misconfiguration-pkts {
      type yang:counter64;
    }
    leaf lisp-misconfiguration-octets {
      type yang:counter64;
    }
    leaf lisp-disabled-pkts {
      type yang:counter64;
    }
    leaf lisp-disabled-octets {
      type yang:counter64;
    }
    leaf lisp-decap-failed-pkts {
      type yang:counter64;
    }
    leaf lisp-decap-failed-octets {
      type yang:counter64;
    }
    leaf lisp-hash-lkup-failed-pkts {
      type yang:counter64;
    }
    leaf lisp-hash-lkup-failed-octets {
      type yang:counter64;
    }
    leaf lisp-failed-to-punt-lsb-mismatch-pkts {
      type yang:counter64;
    }
    leaf lisp-failed-to-punt-lsb-mismatch-octets {
      type yang:counter64;
    }
    leaf nat64-v6tov4-pkts {
      type yang:counter64;
    }
    leaf nat64-v6tov4-octets {
      type yang:counter64;
    }
    leaf nat64-v4tov6-pkts {
      type yang:counter64;
    }
    leaf nat64-v4tov6-octets {
      type yang:counter64;
    }
    leaf tunnel-sec-chk-fail-pkts {
      type yang:counter64;
    }
    leaf tunnel-sec-chk-fail-octets {
      type yang:counter64;
    }
    leaf servicewire-hdr-err-pkts {
      type yang:counter64;
    }
    leaf servicewire-hdr-err-octets {
      type yang:counter64;
    }
    leaf servicewire-hop-limit-exceeded-pkts {
      type yang:counter64;
    }
    leaf servicewire-hop-limit-exceeded-octets {
      type yang:counter64;
    }
    leaf servicewire-processing-err-pkts {
      type yang:counter64;
    }
    leaf servicewire-processing-err-octets {
      type yang:counter64;
    }
    leaf l2bd-pkts {
      type yang:counter64;
    }
    leaf l2bd-octets {
      type yang:counter64;
    }
    leaf tcp-bp-sslvpn-pkts {
      type yang:counter64;
    }
    leaf tcp-bp-sslvpn-octets {
      type yang:counter64;
    }
    leaf evc-efp-egress-filter-pkts {
      type yang:counter64;
    }
    leaf evc-efp-egress-filter-octets {
      type yang:counter64;
    }
    leaf sslvpn-svi-if-err-pkts {
      type yang:counter64;
    }
    leaf sslvpn-svi-if-err-octets {
      type yang:counter64;
    }
    leaf sslvpn-ctx-null-pkts {
      type yang:counter64;
    }
    leaf sslvpn-ctx-null-octets {
      type yang:counter64;
    }
    leaf sslvpn-ctx-not-alive-pkts {
      type yang:counter64;
    }
    leaf sslvpn-ctx-not-alive-octets {
      type yang:counter64;
    }
    leaf sslvpn-invalid-pkt-pkts {
      type yang:counter64;
    }
    leaf sslvpn-invalid-pkt-octets {
      type yang:counter64;
    }
    leaf sslvpn-socket-wr-err-pkts {
      type yang:counter64;
    }
    leaf sslvpn-socket-wr-err-octets {
      type yang:counter64;
    }
    leaf sslvpn-pkt-rc-err-pkts {
      type yang:counter64;
    }
    leaf sslvpn-pkt-rc-err-octets {
      type yang:counter64;
    }
    leaf sslvpn-null-rc-pkts {
      type yang:counter64;
    }
    leaf sslvpn-null-rc-octets {
      type yang:counter64;
    }
    leaf sslvpn-wrong-pkt-type-pkts {
      type yang:counter64;
    }
    leaf sslvpn-wrong-pkt-type-octets {
      type yang:counter64;
    }
    leaf sslvpn-not-ssl-record-pkts {
      type yang:counter64;
    }
    leaf sslvpn-not-ssl-record-octets {
      type yang:counter64;
    }
    leaf firewall-syncookie-pkts {
      type yang:counter64;
    }
    leaf firewall-syncookie-octets {
      type yang:counter64;
    }
    leaf l2bd-mac-security-violation-pkts {
      type yang:counter64;
    }
    leaf l2bd-mac-security-violation-octets {
      type yang:counter64;
    }
    leaf l2bd-src-filter-pkts {
      type yang:counter64;
    }
    leaf l2bd-src-filter-octets {
      type yang:counter64;
    }
    leaf l2bd-policy-pkts {
      type yang:counter64;
    }
    leaf l2bd-policy-octets {
      type yang:counter64;
    }
    leaf l2bd-repl-start-pkts {
      type yang:counter64;
    }
    leaf l2bd-repl-start-octets {
      type yang:counter64;
    }
    leaf l2bd-repl-end-pkts {
      type yang:counter64;
    }
    leaf l2bd-repl-end-octets {
      type yang:counter64;
    }
    leaf l2bd-recycle-tail-pkts {
      type yang:counter64;
    }
    leaf l2bd-recycle-tail-octets {
      type yang:counter64;
    }
    leaf l2bd-static-mac-move-pkts {
      type yang:counter64;
    }
    leaf l2bd-static-mac-move-octets {
      type yang:counter64;
    }
    leaf l2bd-bd-disabled-pkts {
      type yang:counter64;
    }
    leaf l2bd-bd-disabled-octets {
      type yang:counter64;
    }
    leaf l2bd-inject-no-sb-pkts {
      type yang:counter64;
    }
    leaf l2bd-inject-no-sb-octets {
      type yang:counter64;
    }
    leaf l2bd-inject-invalid-pkts {
      type yang:counter64;
    }
    leaf l2bd-inject-invalid-octets {
      type yang:counter64;
    }
    leaf l2bd-stp-state-pkts {
      type yang:counter64;
    }
    leaf l2bd-stp-state-octets {
      type yang:counter64;
    }
    leaf l2bd-storm-ctrl-pkts {
      type yang:counter64;
    }
    leaf l2bd-storm-ctrl-octets {
      type yang:counter64;
    }
    leaf sslvpn-coprocessor-err-pkts {
      type yang:counter64;
    }
    leaf sslvpn-coprocessor-err-octets {
      type yang:counter64;
    }
    leaf sslvpn-tail-drop-pkts {
      type yang:counter64;
    }
    leaf sslvpn-tail-drop-octets {
      type yang:counter64;
    }
    leaf ecfm-pkts {
      type yang:counter64;
    }
    leaf ecfm-octets {
      type yang:counter64;
    }
    leaf ipv4mc-oif-rpf-failed-pkts {
      type yang:counter64;
    }
    leaf ipv4mc-oif-rpf-failed-octets {
      type yang:counter64;
    }
    leaf ipv6mc-oif-rpf-failed-pkts {
      type yang:counter64;
    }
    leaf ipv6mc-oif-rpf-failed-octets {
      type yang:counter64;
    }
    leaf ipv6-pbr-pkts {
      type yang:counter64;
    }
    leaf ipv6-pbr-octets {
      type yang:counter64;
    }
    leaf sslvpn-coprocessor-state-not-set-pkts {
      type yang:counter64;
    }
    leaf sslvpn-coprocessor-state-not-set-octets {
      type yang:counter64;
    }
    leaf sslvpn-coprocessor-state-reply-not-set-pkts {
      type yang:counter64;
    }
    leaf sslvpn-coprocessor-state-reply-not-set-octets {
      type yang:counter64;
    }
    leaf sslvpn-neg-ssl-rec-pad-len-pkts {
      type yang:counter64;
    }
    leaf sslvpn-neg-ssl-rec-pad-len-octets {
      type yang:counter64;
    }
    leaf sslvpn-inv-ssl-rec-pkts {
      type yang:counter64;
    }
    leaf sslvpn-inv-ssl-rec-octets {
      type yang:counter64;
    }
    leaf sslvpn-not-ssl-rec-rc-pkts {
      type yang:counter64;
    }
    leaf sslvpn-not-ssl-rec-rc-octets {
      type yang:counter64;
    }
    leaf sslvpn-ssl-rec-not-pkt-pkts {
      type yang:counter64;
    }
    leaf sslvpn-ssl-rec-not-pkt-octets {
      type yang:counter64;
    }
    leaf sslvpn-add-ssl-rec-hdr-err-pkts {
      type yang:counter64;
    }
    leaf sslvpn-add-ssl-rec-hdr-err-octets {
      type yang:counter64;
    }
    leaf sslvpn-null-session-pkts {
      type yang:counter64;
    }
    leaf sslvpn-null-session-octets {
      type yang:counter64;
    }
    leaf sslvpn-invalid-session-pkts {
      type yang:counter64;
    }
    leaf sslvpn-invalid-session-octets {
      type yang:counter64;
    }
    leaf sslvpn-empty-pkt-pkts {
      type yang:counter64;
    }
    leaf sslvpn-empty-pkt-octets {
      type yang:counter64;
    }
    leaf ipv4-reass-tail-drop-pkts {
      type yang:counter64;
    }
    leaf ipv4-reass-tail-drop-octets {
      type yang:counter64;
    }
    leaf ipv6-reass-tail-drop-pkts {
      type yang:counter64;
    }
    leaf ipv6-reass-tail-drop-octets {
      type yang:counter64;
    }
    leaf ipv4mc-nat-in2out-pkts {
      type yang:counter64;
    }
    leaf ipv4mc-nat-in2out-octets {
      type yang:counter64;
    }
    leaf ipv4mc-nat-out2in-pkts {
      type yang:counter64;
    }
    leaf ipv4mc-nat-out2in-octets {
      type yang:counter64;
    }
    leaf fia-error-pkts {
      type yang:counter64;
    }
    leaf fia-error-octets {
      type yang:counter64;
    }
    leaf firewall-syncookie-max-dst-pkts {
      type yang:counter64;
    }
    leaf firewall-syncookie-max-dst-octets {
      type yang:counter64;
    }
    leaf ipv4-urpf-loose-failed-pkts {
      type yang:counter64;
    }
    leaf ipv4-urpf-loose-failed-octets {
      type yang:counter64;
    }
    leaf ipv4-urpf-strict-failed-pkts {
      type yang:counter64;
    }
    leaf ipv4-urpf-strict-failed-octets {
      type yang:counter64;
    }
    leaf ipv6-urpf-loose-failed-pkts {
      type yang:counter64;
    }
    leaf ipv6-urpf-loose-failed-octets {
      type yang:counter64;
    }
    leaf ipv6-urpf-strict-failed-pkts {
      type yang:counter64;
    }
    leaf ipv6-urpf-strict-failed-octets {
      type yang:counter64;
    }
    leaf ipv6-urpf-null-path-list-pkts {
      type yang:counter64;
    }
    leaf ipv6-urpf-null-path-list-octets {
      type yang:counter64;
    }
    leaf ipv6-urpf-no-fib-pkts {
      type yang:counter64;
    }
    leaf ipv6-urpf-no-fib-octets {
      type yang:counter64;
    }
    leaf unknown-mcast-pkt-type-pkts {
      type yang:counter64;
    }
    leaf unknown-mcast-pkt-type-octets {
      type yang:counter64;
    }
    leaf l2v4mc-invalid-replica-record-pkts {
      type yang:counter64;
    }
    leaf l2v4mc-invalid-replica-record-octets {
      type yang:counter64;
    }
    leaf l2v6mc-invalid-replica-record-pkts {
      type yang:counter64;
    }
    leaf l2v6mc-invalid-replica-record-octets {
      type yang:counter64;
    }
    leaf l2mc-invalid-replica-record-pkts {
      type yang:counter64;
    }
    leaf l2mc-invalid-replica-record-octets {
      type yang:counter64;
    }
    leaf lsm-invalid-replica-record-pkts {
      type yang:counter64;
    }
    leaf lsm-invalid-replica-record-octets {
      type yang:counter64;
    }
    leaf cts-format-pkts {
      type yang:counter64;
    }
    leaf cts-format-octets {
      type yang:counter64;
    }
    leaf cts-not-enable-pkts {
      type yang:counter64;
    }
    leaf cts-not-enable-octets {
      type yang:counter64;
    }
    leaf idle-packet-pkts {
      type yang:counter64;
    }
    leaf idle-packet-octets {
      type yang:counter64;
    }
    leaf mfr-pkts {
      type yang:counter64;
    }
    leaf mfr-octets {
      type yang:counter64;
    }
    leaf ar-tx-pkts {
      type yang:counter64;
    }
    leaf ar-tx-octets {
      type yang:counter64;
    }
    leaf ar-rx-pkts {
      type yang:counter64;
    }
    leaf ar-rx-octets {
      type yang:counter64;
    }
    leaf ar-standby-pkts {
      type yang:counter64;
    }
    leaf ar-standby-octets {
      type yang:counter64;
    }
    leaf ar-fnf-clnup-pkts {
      type yang:counter64;
    }
    leaf ar-fnf-clnup-octets {
      type yang:counter64;
    }
    leaf mac-mcast-ip-nonmcast-pkts {
      type yang:counter64;
    }
    leaf mac-mcast-ip-nonmcast-octets {
      type yang:counter64;
    }
    leaf bfd-pkts {
      type yang:counter64;
    }
    leaf bfd-octets {
      type yang:counter64;
    }
    leaf bundle-oce-pkts {
      type yang:counter64;
    }
    leaf bundle-oce-octets {
      type yang:counter64;
    }
    leaf bqs-oor-pri-pkts {
      type yang:counter64;
    }
    leaf bqs-oor-pri-octets {
      type yang:counter64;
    }
    leaf bqs-oor-pak-pri-pkts {
      type yang:counter64;
    }
    leaf bqs-oor-pak-pri-octets {
      type yang:counter64;
    }
    leaf bqs-oor-vital-pkts {
      type yang:counter64;
    }
    leaf bqs-oor-vital-octets {
      type yang:counter64;
    }
    leaf epc-pkts {
      type yang:counter64;
    }
    leaf epc-octets {
      type yang:counter64;
    }
    leaf lisp-failed-to-punt-dynmaic-eid-config-pkts {
      type yang:counter64;
    }
    leaf lisp-failed-to-punt-dynmaic-eid-config-octets {
      type yang:counter64;
    }
    leaf sv-match-fail-pkts {
      type yang:counter64;
    }
    leaf sv-match-fail-octets {
      type yang:counter64;
    }
    leaf cblbf-null-repllist-pkts {
      type yang:counter64;
    }
    leaf cblbf-null-repllist-octets {
      type yang:counter64;
    }
    leaf cblbf-repl-fail-pkts {
      type yang:counter64;
    }
    leaf cblbf-repl-fail-octets {
      type yang:counter64;
    }
    leaf cblbf-repl-start-pkts {
      type yang:counter64;
    }
    leaf cblbf-repl-start-octets {
      type yang:counter64;
    }
    leaf cblbf-repl-end-pkts {
      type yang:counter64;
    }
    leaf cblbf-repl-end-octets {
      type yang:counter64;
    }
    leaf cblbf-recycle-tail-pkts {
      type yang:counter64;
    }
    leaf cblbf-recycle-tail-octets {
      type yang:counter64;
    }
    leaf cblbf-fwdint-down-pkts {
      type yang:counter64;
    }
    leaf cblbf-fwdint-down-octets {
      type yang:counter64;
    }
    leaf cable-p2pl-oce-ptr-null-pkts {
      type yang:counter64;
    }
    leaf cable-p2pl-oce-ptr-null-octets {
      type yang:counter64;
    }
    leaf cable-mc-invalid-replica-record-pkts {
      type yang:counter64;
    }
    leaf cable-mc-invalid-replica-record-octets {
      type yang:counter64;
    }
    leaf no-def-jib-pkts {
      type yang:counter64;
    }
    leaf no-def-jib-octets {
      type yang:counter64;
    }
    leaf no-inj-jib-pkts {
      type yang:counter64;
    }
    leaf no-inj-jib-octets {
      type yang:counter64;
    }
    leaf onefw-pkts {
      type yang:counter64;
    }
    leaf onefw-octets {
      type yang:counter64;
    }
    leaf ccm-tx-pkts {
      type yang:counter64;
    }
    leaf ccm-tx-octets {
      type yang:counter64;
    }
    leaf appnav-sn-pkt-invalid-pkts {
      type yang:counter64;
    }
    leaf appnav-sn-pkt-invalid-octets {
      type yang:counter64;
    }
    leaf appnav-internal-err-pkts {
      type yang:counter64;
    }
    leaf appnav-internal-err-octets {
      type yang:counter64;
    }
    leaf appnav-badroute-pkts {
      type yang:counter64;
    }
    leaf appnav-badroute-octets {
      type yang:counter64;
    }
    leaf appnav-notunnel-pkts {
      type yang:counter64;
    }
    leaf appnav-notunnel-octets {
      type yang:counter64;
    }
    leaf appnav-nosvcctx-pkts {
      type yang:counter64;
    }
    leaf appnav-nosvcctx-octets {
      type yang:counter64;
    }
    leaf appnav-inv-flow-state-pkts {
      type yang:counter64;
    }
    leaf appnav-inv-flow-state-octets {
      type yang:counter64;
    }
    leaf appnav-unexpected-pkt-pkts {
      type yang:counter64;
    }
    leaf appnav-unexpected-pkt-octets {
      type yang:counter64;
    }
    leaf rl2gp-non-tcb-pkts {
      type yang:counter64;
    }
    leaf rl2gp-non-tcb-octets {
      type yang:counter64;
    }
    leaf tunnel-pkt-sb-missed-pkts {
      type yang:counter64;
    }
    leaf tunnel-pkt-sb-missed-octets {
      type yang:counter64;
    }
    leaf fhs-pkt-invalid-pkts {
      type yang:counter64;
    }
    leaf fhs-pkt-invalid-octets {
      type yang:counter64;
    }
    leaf fhs-pkt-dropped-pkts {
      type yang:counter64;
    }
    leaf fhs-pkt-dropped-octets {
      type yang:counter64;
    }
    leaf tunnel-sgre-virtual-mac-mismatch-pkts {
      type yang:counter64;
    }
    leaf tunnel-sgre-virtual-mac-mismatch-octets {
      type yang:counter64;
    }
    leaf tunnel-sgre-unsupported-proto-pkts {
      type yang:counter64;
    }
    leaf tunnel-sgre-unsupported-proto-octets {
      type yang:counter64;
    }
    leaf mpls-gal-check-non-gal-dropped-pkts {
      type yang:counter64;
    }
    leaf mpls-gal-check-non-gal-dropped-octets {
      type yang:counter64;
    }
    leaf mpls-gal-check-non-eos-dropped-pkts {
      type yang:counter64;
    }
    leaf mpls-gal-check-non-eos-dropped-octets {
      type yang:counter64;
    }
    leaf mpls-gal-check-invalid-pkts {
      type yang:counter64;
    }
    leaf mpls-gal-check-invalid-octets {
      type yang:counter64;
    }
    leaf mpls-gal-exception-non-eos-dropped-pkts {
      type yang:counter64;
    }
    leaf mpls-gal-exception-non-eos-dropped-octets {
      type yang:counter64;
    }
    leaf mpls-gal-exception-non-gach-dropped-pkts {
      type yang:counter64;
    }
    leaf mpls-gal-exception-non-gach-dropped-octets {
      type yang:counter64;
    }
    leaf conf-sw-sess-pkts {
      type yang:counter64;
    }
    leaf conf-sw-sess-octets {
      type yang:counter64;
    }
    leaf tunnel-decap-too-many-times-pkts {
      type yang:counter64;
    }
    leaf tunnel-decap-too-many-times-octets {
      type yang:counter64;
    }
    leaf loadbalance-null0-pkts {
      type yang:counter64;
    }
    leaf loadbalance-null0-octets {
      type yang:counter64;
    }
    leaf gpm-tx-len-exceed-pkts {
      type yang:counter64;
    }
    leaf gpm-tx-len-exceed-octets {
      type yang:counter64;
    }
    leaf esf-ffr-drop-pkts {
      type yang:counter64;
    }
    leaf esf-ffr-drop-octets {
      type yang:counter64;
    }
    leaf ec-bundle-enq-pkts {
      type yang:counter64;
    }
    leaf ec-bundle-enq-octets {
      type yang:counter64;
    }
    leaf ec-link-tx-pkts {
      type yang:counter64;
    }
    leaf ec-link-tx-octets {
      type yang:counter64;
    }
    leaf pfrv3-probe-err-pkts {
      type yang:counter64;
    }
    leaf pfrv3-probe-err-octets {
      type yang:counter64;
    }
    leaf ovl-bad-pkt-pkts {
      type yang:counter64;
    }
    leaf ovl-bad-pkt-octets {
      type yang:counter64;
    }
    leaf ovl-l2-filter-pkts {
      type yang:counter64;
    }
    leaf ovl-l2-filter-octets {
      type yang:counter64;
    }
    leaf dpss-pkts {
      type yang:counter64;
    }
    leaf dpss-octets {
      type yang:counter64;
    }
    leaf tunnel-invalid-protocol-pkts {
      type yang:counter64;
    }
    leaf tunnel-invalid-protocol-octets {
      type yang:counter64;
    }
    leaf pfrv3-at-failure-pkts {
      type yang:counter64;
    }
    leaf pfrv3-at-failure-octets {
      type yang:counter64;
    }
    leaf ipv4-mcast-acl-pkts {
      type yang:counter64;
    }
    leaf ipv4-mcast-acl-octets {
      type yang:counter64;
    }
    leaf ipv6-mcast-acl-pkts {
      type yang:counter64;
    }
    leaf ipv6-mcast-acl-octets {
      type yang:counter64;
    }
    leaf pprl-sbrl-drop-pkts {
      type yang:counter64;
    }
    leaf pprl-sbrl-drop-octets {
      type yang:counter64;
    }
    leaf cbl-req-arl-drop-pkts {
      type yang:counter64;
    }
    leaf cbl-req-arl-drop-octets {
      type yang:counter64;
    }
    leaf cbl-rep-arl-drop-pkts {
      type yang:counter64;
    }
    leaf cbl-rep-arl-drop-octets {
      type yang:counter64;
    }
    leaf appnav-acgreloaddelay-pkts {
      type yang:counter64;
    }
    leaf appnav-acgreloaddelay-octets {
      type yang:counter64;
    }
    leaf ngfw-policy-pkts {
      type yang:counter64;
    }
    leaf ngfw-policy-octets {
      type yang:counter64;
    }
    leaf ngfw-divert-pkts {
      type yang:counter64;
    }
    leaf ngfw-divert-octets {
      type yang:counter64;
    }
    leaf pfrv3-blackhole-pkts {
      type yang:counter64;
    }
    leaf pfrv3-blackhole-octets {
      type yang:counter64;
    }
    leaf pppoe-fctl-pkts {
      type yang:counter64;
    }
    leaf pppoe-fctl-octets {
      type yang:counter64;
    }
    leaf lisp-sfltr-pkts {
      type yang:counter64;
    }
    leaf lisp-sfltr-octets {
      type yang:counter64;
    }
    leaf flowspec-pkts {
      type yang:counter64;
    }
    leaf flowspec-octets {
      type yang:counter64;
    }
    leaf identity-cft-error-pkts {
      type yang:counter64;
    }
    leaf identity-cft-error-octets {
      type yang:counter64;
    }
    leaf bad-us-jib-hdr-pkts {
      type yang:counter64;
    }
    leaf bad-us-jib-hdr-octets {
      type yang:counter64;
    }
    leaf too-many-mpls-lookup-oce-pkts {
      type yang:counter64;
    }
    leaf too-many-mpls-lookup-oce-octets {
      type yang:counter64;
    }
    leaf cable-prereg-not-cm-pkts {
      type yang:counter64;
    }
    leaf cable-prereg-not-cm-octets {
      type yang:counter64;
    }
    leaf invalid-virtual-id-pkts {
      type yang:counter64;
    }
    leaf invalid-virtual-id-octets {
      type yang:counter64;
    }
    leaf flow-queue-failure-id-pkts {
      type yang:counter64;
    }
    leaf flow-queue-failure-id-octets {
      type yang:counter64;
    }
    leaf l2es-input-invalid-tag-pkts {
      type yang:counter64;
    }
    leaf l2es-input-invalid-tag-octets {
      type yang:counter64;
    }
    leaf l2es-input-invalid-svi-pkts {
      type yang:counter64;
    }
    leaf l2es-input-invalid-svi-octets {
      type yang:counter64;
    }
    leaf svi-output-invalid-l2sb-pkts {
      type yang:counter64;
    }
    leaf svi-output-invalid-l2sb-octets {
      type yang:counter64;
    }
    leaf svi-input-invalid-mac-pkts {
      type yang:counter64;
    }
    leaf svi-input-invalid-mac-octets {
      type yang:counter64;
    }
    leaf svi-output-recycle-tail-pkts {
      type yang:counter64;
    }
    leaf svi-output-recycle-tail-octets {
      type yang:counter64;
    }
    leaf svi-output-repl-pkts {
      type yang:counter64;
    }
    leaf svi-output-repl-octets {
      type yang:counter64;
    }
    leaf svi-repl-end-pkts {
      type yang:counter64;
    }
    leaf svi-repl-end-octets {
      type yang:counter64;
    }
    leaf cws-ctx-id-not-found-mob-pkts {
      type yang:counter64;
    }
    leaf cws-ctx-id-not-found-mob-octets {
      type yang:counter64;
    }
    leaf cws-ctx-id-not-found-conn-pkts {
      type yang:counter64;
    }
    leaf cws-ctx-id-not-found-conn-octets {
      type yang:counter64;
    }
    leaf l2cp-cfg-action-pkts {
      type yang:counter64;
    }
    leaf l2cp-cfg-action-octets {
      type yang:counter64;
    }
    leaf perf-lic-policer-lo-pkts {
      type yang:counter64;
    }
    leaf perf-lic-policer-lo-octets {
      type yang:counter64;
    }
    leaf perf-lic-policer-hi-pkts {
      type yang:counter64;
    }
    leaf perf-lic-policer-hi-octets {
      type yang:counter64;
    }
    leaf hqf-tx-error-pkts {
      type yang:counter64;
    }
    leaf hqf-tx-error-octets {
      type yang:counter64;
    }
    leaf cmd-format-pkts {
      type yang:counter64;
    }
    leaf cmd-format-octets {
      type yang:counter64;
    }
    leaf utd-pkts {
      type yang:counter64;
    }
    leaf utd-octets {
      type yang:counter64;
    }
    leaf nat66-in2out-pkts {
      type yang:counter64;
    }
    leaf nat66-in2out-octets {
      type yang:counter64;
    }
    leaf nat66-out2in-pkts {
      type yang:counter64;
    }
    leaf nat66-out2in-octets {
      type yang:counter64;
    }
    leaf dsa-no-ip-pkts {
      type yang:counter64;
    }
    leaf dsa-no-ip-octets {
      type yang:counter64;
    }
    leaf cws-inter-error-pkts {
      type yang:counter64;
    }
    leaf cws-inter-error-octets {
      type yang:counter64;
    }
    leaf utd-sn-pkts {
      type yang:counter64;
    }
    leaf utd-sn-octets {
      type yang:counter64;
    }
    leaf mpls-el-invalid-tag-pkts {
      type yang:counter64;
    }
    leaf mpls-el-invalid-tag-octets {
      type yang:counter64;
    }
    leaf lisp-failed-to-punt-gsmr-enabled-pkts {
      type yang:counter64;
    }
    leaf lisp-failed-to-punt-gsmr-enabled-octets {
      type yang:counter64;
    }
    leaf schain-flow-action-pkts {
      type yang:counter64;
    }
    leaf schain-flow-action-octets {
      type yang:counter64;
    }
    leaf opendns-pkts {
      type yang:counter64;
    }
    leaf opendns-octets {
      type yang:counter64;
    }
    leaf capwap-err-pkts {
      type yang:counter64;
    }
    leaf capwap-err-octets {
      type yang:counter64;
    }
    leaf capwap-no-uidb-pkts {
      type yang:counter64;
    }
    leaf capwap-no-uidb-octets {
      type yang:counter64;
    }
    leaf dtls-err-pkts {
      type yang:counter64;
    }
    leaf dtls-err-octets {
      type yang:counter64;
    }
    leaf wlclnt-err-pkts {
      type yang:counter64;
    }
    leaf wlclnt-err-octets {
      type yang:counter64;
    }
    leaf wlclnt-fnf-v9-report-pkts {
      type yang:counter64;
    }
    leaf wlclnt-fnf-v9-report-octets {
      type yang:counter64;
    }
    leaf wlclnt-fnf-v9-err-pkts {
      type yang:counter64;
    }
    leaf wlclnt-fnf-v9-err-octets {
      type yang:counter64;
    }
    leaf cgacl-err-pkts {
      type yang:counter64;
    }
    leaf cgacl-err-octets {
      type yang:counter64;
    }
    leaf cgacl-lookup-miss-pkts {
      type yang:counter64;
    }
    leaf cgacl-lookup-miss-octets {
      type yang:counter64;
    }
    leaf cgacl-inv-stats-pkts {
      type yang:counter64;
    }
    leaf cgacl-inv-stats-octets {
      type yang:counter64;
    }
    leaf cgacl-match-pkts {
      type yang:counter64;
    }
    leaf cgacl-match-octets {
      type yang:counter64;
    }
    leaf cgacl-action-pkts {
      type yang:counter64;
    }
    leaf cgacl-action-octets {
      type yang:counter64;
    }
    leaf cgacl-pkt-type-pkts {
      type yang:counter64;
    }
    leaf cgacl-pkt-type-octets {
      type yang:counter64;
    }
    leaf cwfrag-err-pkts {
      type yang:counter64;
    }
    leaf cwfrag-err-octets {
      type yang:counter64;
    }
    leaf pathmgr-measurement-err-pkts {
      type yang:counter64;
    }
    leaf pathmgr-measurement-err-octets {
      type yang:counter64;
    }
    leaf pathmgr-select-err-pkts {
      type yang:counter64;
    }
    leaf pathmgr-select-err-octets {
      type yang:counter64;
    }
    leaf capwap-reass-frag-consm-pkts {
      type yang:counter64;
    }
    leaf capwap-reass-frag-consm-octets {
      type yang:counter64;
    }
    leaf capwap-reass-alloc-err-pkts {
      type yang:counter64;
    }
    leaf capwap-reass-alloc-err-octets {
      type yang:counter64;
    }
    leaf capwap-reass-frag-err-pkts {
      type yang:counter64;
    }
    leaf capwap-reass-frag-err-octets {
      type yang:counter64;
    }
    leaf redistrib-err-bad-dst-pkts {
      type yang:counter64;
    }
    leaf redistrib-err-bad-dst-octets {
      type yang:counter64;
    }
    leaf redistrib-err-sb-trans-fail-pkts {
      type yang:counter64;
    }
    leaf redistrib-err-sb-trans-fail-octets {
      type yang:counter64;
    }
    leaf redistrib-err-ph-alc-fail-pkts {
      type yang:counter64;
    }
    leaf redistrib-err-ph-alc-fail-octets {
      type yang:counter64;
    }
    leaf redistrib-err-not-sup-pkts {
      type yang:counter64;
    }
    leaf redistrib-err-not-sup-octets {
      type yang:counter64;
    }
    leaf redistrib-fifo-tail-drop-pkts {
      type yang:counter64;
    }
    leaf redistrib-fifo-tail-drop-octets {
      type yang:counter64;
    }
    leaf redistrib-no-credits-pkts {
      type yang:counter64;
    }
    leaf redistrib-no-credits-octets {
      type yang:counter64;
    }
    leaf max-indirect-exceeded-pkts {
      type yang:counter64;
    }
    leaf max-indirect-exceeded-octets {
      type yang:counter64;
    }
    leaf punt-intf-drop-pkts {
      type yang:counter64;
    }
    leaf punt-intf-drop-octets {
      type yang:counter64;
    }
    leaf srh-pkt-truncated-in-gpm-pkts {
      type yang:counter64;
    }
    leaf srh-pkt-truncated-in-gpm-octets {
      type yang:counter64;
    }
    leaf srh-invalid-extension-pkts {
      type yang:counter64;
    }
    leaf srh-invalid-extension-octets {
      type yang:counter64;
    }
    leaf swport-pkts {
      type yang:counter64;
    }
    leaf swport-octets {
      type yang:counter64;
    }
    leaf swport-disabled-pkts {
      type yang:counter64;
    }
    leaf swport-disabled-octets {
      type yang:counter64;
    }
    leaf swport-sanity-check-pkts {
      type yang:counter64;
    }
    leaf swport-sanity-check-octets {
      type yang:counter64;
    }
    leaf swport-vp-state-pkts {
      type yang:counter64;
    }
    leaf swport-vp-state-octets {
      type yang:counter64;
    }
    leaf swport-mac-conflict-pkts {
      type yang:counter64;
    }
    leaf swport-mac-conflict-octets {
      type yang:counter64;
    }
    leaf swport-stby-pkts {
      type yang:counter64;
    }
    leaf swport-stby-octets {
      type yang:counter64;
    }
    leaf swport-tx-stby-pkts {
      type yang:counter64;
    }
    leaf swport-tx-stby-octets {
      type yang:counter64;
    }
    leaf switch-l2m-pkts {
      type yang:counter64;
    }
    leaf switch-l2m-octets {
      type yang:counter64;
    }
    leaf switch-l2m-igmp-pkts {
      type yang:counter64;
    }
    leaf switch-l2m-igmp-octets {
      type yang:counter64;
    }
    leaf switch-l2m-mld-pkts {
      type yang:counter64;
    }
    leaf switch-l2m-mld-octets {
      type yang:counter64;
    }
    leaf switch-l2m-lookup-miss-pkts {
      type yang:counter64;
    }
    leaf switch-l2m-lookup-miss-octets {
      type yang:counter64;
    }
    leaf switch-l2m-sanity-check-pkts {
      type yang:counter64;
    }
    leaf switch-l2m-sanity-check-octets {
      type yang:counter64;
    }
    leaf bier-invalid-replica-record-pkts {
      type yang:counter64;
    }
    leaf bier-invalid-replica-record-octets {
      type yang:counter64;
    }
    leaf bier-snaity-pkts {
      type yang:counter64;
    }
    leaf bier-snaity-octets {
      type yang:counter64;
    }
    leaf cable-oob-us-sess-invalid-pkts {
      type yang:counter64;
    }
    leaf cable-oob-us-sess-invalid-octets {
      type yang:counter64;
    }
    leaf cable-oob-us-src-id-invalid-pkts {
      type yang:counter64;
    }
    leaf cable-oob-us-src-id-invalid-octets {
      type yang:counter64;
    }
    leaf cable-oob-us-pkt-invalid-pkts {
      type yang:counter64;
    }
    leaf cable-oob-us-pkt-invalid-octets {
      type yang:counter64;
    }
    leaf cbl-oob-null-repllist-pkts {
      type yang:counter64;
    }
    leaf cbl-oob-null-repllist-octets {
      type yang:counter64;
    }
    leaf cbl-oob-repl-fail-pkts {
      type yang:counter64;
    }
    leaf cbl-oob-repl-fail-octets {
      type yang:counter64;
    }
    leaf cbl-oob-add-hdr-fail-pkts {
      type yang:counter64;
    }
    leaf cbl-oob-add-hdr-fail-octets {
      type yang:counter64;
    }
    leaf cbl-oob-repl-end-pkts {
      type yang:counter64;
    }
    leaf cbl-oob-repl-end-octets {
      type yang:counter64;
    }
    leaf cbl-oob-recycle-tail-pkts {
      type yang:counter64;
    }
    leaf cbl-oob-recycle-tail-octets {
      type yang:counter64;
    }
    leaf cbl-oob-repl-uidb-invalid-pkts {
      type yang:counter64;
    }
    leaf cbl-oob-repl-uidb-invalid-octets {
      type yang:counter64;
    }
    leaf cbl-oob-repl-sess-invalid-pkts {
      type yang:counter64;
    }
    leaf cbl-oob-repl-sess-invalid-octets {
      type yang:counter64;
    }
    leaf cbl-oob-null-repl-info-pkts {
      type yang:counter64;
    }
    leaf cbl-oob-null-repl-info-octets {
      type yang:counter64;
    }
    leaf nid-vlan-mismatch-pkts {
      type yang:counter64;
    }
    leaf nid-vlan-mismatch-octets {
      type yang:counter64;
    }
    leaf pfrv3-loop-pkts {
      type yang:counter64;
    }
    leaf pfrv3-loop-octets {
      type yang:counter64;
    }
    leaf dialer-list-pkts {
      type yang:counter64;
    }
    leaf dialer-list-octets {
      type yang:counter64;
    }
    leaf udp-pkts {
      type yang:counter64;
    }
    leaf udp-octets {
      type yang:counter64;
    }
    leaf tunnel-l2tpv3oipv6-cookie-mismatch-pkts {
      type yang:counter64;
    }
    leaf tunnel-l2tpv3oipv6-cookie-mismatch-octets {
      type yang:counter64;
    }
    leaf tunnel-l2tpv3oipv6-minmtu-error-pkts {
      type yang:counter64;
    }
    leaf tunnel-l2tpv3oipv6-minmtu-error-octets {
      type yang:counter64;
    }
    leaf tunnel-l2tpv3oipv6-cookieflag-error-pkts {
      type yang:counter64;
    }
    leaf tunnel-l2tpv3oipv6-cookieflag-error-octets {
      type yang:counter64;
    }
    leaf tunnel-l2tpv3oipv6-mac-mismatch-pkts {
      type yang:counter64;
    }
    leaf tunnel-l2tpv3oipv6-mac-mismatch-octets {
      type yang:counter64;
    }
    leaf tunnel-l2tpv3oipv6-vlanid-mismatch-pkts {
      type yang:counter64;
    }
    leaf tunnel-l2tpv3oipv6-vlanid-mismatch-octets {
      type yang:counter64;
    }
    leaf tunnel-l2tpv3oipv6-unsupported-proto-pkts {
      type yang:counter64;
    }
    leaf tunnel-l2tpv3oipv6-unsupported-proto-octets {
      type yang:counter64;
    }
    leaf pfrv3-stickiness-pkts {
      type yang:counter64;
    }
    leaf pfrv3-stickiness-octets {
      type yang:counter64;
    }
    leaf cbl-sid-exceed-pkts {
      type yang:counter64;
    }
    leaf cbl-sid-exceed-octets {
      type yang:counter64;
    }
    leaf sdwan-pkts {
      type yang:counter64;
    }
    leaf sdwan-octets {
      type yang:counter64;
    }
    leaf sdwan-generic-pkts {
      type yang:counter64;
    }
    leaf sdwan-generic-octets {
      type yang:counter64;
    }
    leaf sdwan-implicit-acl-pkts {
      type yang:counter64;
    }
    leaf sdwan-implicit-acl-octets {
      type yang:counter64;
    }
    leaf sdwan-acl-pkts {
      type yang:counter64;
    }
    leaf sdwan-acl-octets {
      type yang:counter64;
    }
    leaf sdwan-bfd-pkts {
      type yang:counter64;
    }
    leaf sdwan-bfd-octets {
      type yang:counter64;
    }
    leaf sdwan-app-route-policy-pkts {
      type yang:counter64;
    }
    leaf sdwan-app-route-policy-octets {
      type yang:counter64;
    }
    leaf sdwan-data-policy-pkts {
      type yang:counter64;
    }
    leaf sdwan-data-policy-octets {
      type yang:counter64;
    }
    leaf sdwan-interface-policy-pkts {
      type yang:counter64;
    }
    leaf sdwan-interface-policy-octets {
      type yang:counter64;
    }
    leaf sdwan-tunnel-lkup-pkts {
      type yang:counter64;
    }
    leaf sdwan-tunnel-lkup-octets {
      type yang:counter64;
    }
    leaf sdwan-tloc-ext-pkts {
      type yang:counter64;
    }
    leaf sdwan-tloc-ext-octets {
      type yang:counter64;
    }
    leaf tunnel-vxlan-mismatch-pkts {
      type yang:counter64;
    }
    leaf tunnel-vxlan-mismatch-octets {
      type yang:counter64;
    }
    leaf l2bd-mac-security-move-pkts {
      type yang:counter64;
    }
    leaf l2bd-mac-security-move-octets {
      type yang:counter64;
    }
    leaf l2bd-mac-security-unknown-pkts {
      type yang:counter64;
    }
    leaf l2bd-mac-security-unknown-octets {
      type yang:counter64;
    }
    leaf dapr-noroute-pkts {
      type yang:counter64;
    }
    leaf dapr-noroute-octets {
      type yang:counter64;
    }
    leaf epbr-pkts {
      type yang:counter64;
    }
    leaf epbr-octets {
      type yang:counter64;
    }
    leaf sdvt-sn-pkts {
      type yang:counter64;
    }
    leaf sdvt-sn-octets {
      type yang:counter64;
    }
    leaf sdvt-pkts {
      type yang:counter64;
    }
    leaf sdvt-octets {
      type yang:counter64;
    }
    leaf tunnel-vxlan-policer-pkts {
      type yang:counter64;
    }
    leaf tunnel-vxlan-policer-octets {
      type yang:counter64;
    }
    leaf tunnel-vrf-mux-pkts {
      type yang:counter64;
    }
    leaf tunnel-vrf-mux-octets {
      type yang:counter64;
    }
    leaf tunnel-vrf-demux-pkts {
      type yang:counter64;
    }
    leaf tunnel-vrf-demux-octets {
      type yang:counter64;
    }
    leaf frag-invalid-pkt-pkts {
      type yang:counter64;
    }
    leaf frag-invalid-pkt-octets {
      type yang:counter64;
    }
    leaf frag-invalid-ip6pkt-pkts {
      type yang:counter64;
    }
    leaf frag-invalid-ip6pkt-octets {
      type yang:counter64;
    }
    leaf crypto-offload-output-pkts {
      type yang:counter64;
    }
    leaf crypto-offload-output-octets {
      type yang:counter64;
    }
    leaf cable-prng-expected-drops-pkts {
      type yang:counter64;
    }
    leaf cable-prng-expected-drops-octets {
      type yang:counter64;
    }
    leaf ipv4-egress-intf-enforce-pkts {
      type yang:counter64;
    }
    leaf ipv4-egress-intf-enforce-octets {
      type yang:counter64;
    }
    leaf ipv6-egress-intf-enforce-pkts {
      type yang:counter64;
    }
    leaf ipv6-egress-intf-enforce-octets {
      type yang:counter64;
    }
    leaf cable-dhcp-bad-len-pkts {
      type yang:counter64;
    }
    leaf cable-dhcp-bad-len-octets {
      type yang:counter64;
    }
    leaf l2bd-uuf-suppression-drops-pkts {
      type yang:counter64;
    }
    leaf l2bd-uuf-suppression-drops-octets {
      type yang:counter64;
    }
    leaf wpan-drop-pkts {
      type yang:counter64;
    }
    leaf wpan-drop-octets {
      type yang:counter64;
    }
    leaf l2bd-sisf-ctrl-drops-pkts {
      type yang:counter64;
    }
    leaf l2bd-sisf-ctrl-drops-octets {
      type yang:counter64;
    }
    leaf cable-recycle-queue-pkts {
      type yang:counter64;
    }
    leaf cable-recycle-queue-octets {
      type yang:counter64;
    }
    leaf pcgw-pdu-sess-drops-pkts {
      type yang:counter64;
    }
    leaf pcgw-pdu-sess-drops-octets {
      type yang:counter64;
    }
    leaf pcgw-gtpu-drops-pkts {
      type yang:counter64;
    }
    leaf pcgw-gtpu-drops-octets {
      type yang:counter64;
    }
    leaf pcgw-punt-inject-drops-pkts {
      type yang:counter64;
    }
    leaf pcgw-punt-inject-drops-octets {
      type yang:counter64;
    }
    leaf pcgw-pcacl-drop-pkts {
      type yang:counter64;
    }
    leaf pcgw-pcacl-drop-octets {
      type yang:counter64;
    }
    leaf vtcp-err-drops-pkts {
      type yang:counter64;
    }
    leaf vtcp-err-drops-octets {
      type yang:counter64;
    }
    leaf vtcp-invalid-tx-drops-pkts {
      type yang:counter64;
    }
    leaf vtcp-invalid-tx-drops-octets {
      type yang:counter64;
    }
    leaf vtcp-pa-err-drops-pkts {
      type yang:counter64;
    }
    leaf vtcp-pa-err-drops-octets {
      type yang:counter64;
    }
    leaf vtcp-mem-err-drops-pkts {
      type yang:counter64;
    }
    leaf vtcp-mem-err-drops-octets {
      type yang:counter64;
    }
    leaf vtcp-punt-err-drops-pkts {
      type yang:counter64;
    }
    leaf vtcp-punt-err-drops-octets {
      type yang:counter64;
    }
    leaf fbd-oom-err-pkts {
      type yang:counter64;
    }
    leaf fbd-oom-err-octets {
      type yang:counter64;
    }
    leaf memory-interface-pkts {
      type yang:counter64;
    }
    leaf memory-interface-octets {
      type yang:counter64;
    }
    leaf no-interface-resources-pkts {
      type yang:counter64;
    }
    leaf no-interface-resources-octets {
      type yang:counter64;
    }
    leaf dlep-unconfigured-pkts {
      type yang:counter64;
    }
    leaf dlep-unconfigured-octets {
      type yang:counter64;
    }
    leaf cable-arp-autoreply-pkts {
      type yang:counter64;
    }
    leaf cable-arp-autoreply-octets {
      type yang:counter64;
    }
    leaf unisr-no-match-pkts {
      type yang:counter64;
    }
    leaf unisr-no-match-octets {
      type yang:counter64;
    }
    leaf unisr-src-filtered-pkts {
      type yang:counter64;
    }
    leaf unisr-src-filtered-octets {
      type yang:counter64;
    }
  }
}
