module Cisco-IOS-XE-bbu-oper {
  yang-version 1.1;
  namespace "http://cisco.com/ns/yang/Cisco-IOS-XE-bbu-oper";
  prefix bbu-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for IOS-XE Battery Backup Unit operational data.
     Copyright (c) 2021-2022 by Cisco Systems, Inc.
     All rights reserved.";

  revision 2022-03-01 {
    description
      "Initial revision";
    reference
      "1.0.0";
    cisco-semver:module-version "1.0.0";
  }

  typedef bbu-module-presence-status {
    type enumeration {
      enum bbums-unknown {
        value 0;
        description
          "Module presence status unknown";
      }
      enum bbums-absent {
        value 1;
        description
          "Module presence status absent";
      }
      enum bbums-ready {
        value 2;
        description
          "Module presence status ready";
      }
    }
    description
      "Battery Backup Unit module presence status";
  }

  typedef bbu-battery-state {
    type enumeration {
      enum bs-unknown {
        value 0;
        description
          "Battery state unknown";
      }
      enum bs-error {
        value 1;
        description
          "Battery state error";
      }
      enum bs-bad-cell {
        value 2;
        description
          "Battery state bad cell";
      }
      enum bs-charging {
        value 3;
        description
          "Battery state charging";
      }
      enum bs-discharging {
        value 4;
        description
          "Battery state discharging";
      }
      enum bs-full {
        value 5;
        description
          "Battery state full";
      }
      enum bs-empty {
        value 6;
        description
          "Battery state empty";
      }
      enum bs-idle {
        value 7;
        description
          "Battery state idle";
      }
    }
    description
      "Battery Backup Unit battery state";
  }

  typedef bbu-charge-discharge-status {
    type enumeration {
      enum bbucds-enabled {
        value 0;
        description
          "Charge and discharge status enabled";
      }
      enum bbucds-disabled {
        value 1;
        description
          "Charge and discharge status disabled";
      }
    }
    description
      "Battery Backup Unit charge and discharge status";
  }

  typedef bbu-category {
    type enumeration {
      enum bbuc-li-ion {
        value 0;
        description
          "Battery Backup Unit category Li-ion";
      }
      enum bbuc-unknown {
        value 1;
        description
          "Battery Backup Unit category unknown";
      }
    }
    description
      "Battery Backup Unit category";
  }

  grouping common-sprom-block-info {
    description
      "Battery Backup Unit Serial Programmable Read Only Memory block header";
    leaf oem {
      type string;
      description
        "Original Equipment Manufacturer string";
    }
    leaf product-number {
      type string;
      description
        "Product number";
    }
    leaf serial-number {
      type string;
      description
        "Serial number";
    }
    leaf part-number {
      type string;
      description
        "Part number";
    }
    leaf part-revision {
      type string;
      description
        "Part revision";
    }
    leaf hw-version {
      type string;
      description
        "Hardware version";
    }
  }

  grouping bbu-sprom-block-info {
    description
      "Battery Backup Unit specific Serial Programmable Read Only Memory block header";
    leaf vend-name {
      type string;
      description
        "Vendor name";
    }
    leaf prod-num {
      type string;
      description
        "Product number";
    }
    leaf rev-num {
      type string;
      description
        "Revision number";
    }
    leaf build-date {
      type yang:date-and-time;
      description
        "Buid date";
    }
    leaf build-ver {
      type string;
      description
        "Build version";
    }
    leaf category {
      type bbu-ios-xe-oper:bbu-category;
      description
        "Battery Backup Unit category";
    }
    leaf num-of-cells-in-series {
      type uint16;
      description
        "Number of cells in series";
    }
    leaf num-of-cells-in-parallel {
      type uint16;
      description
        "Number of cells in parallel";
    }
    leaf min-discharge-temp {
      type uint16;
      units "Kelvin";
      description
        "Minimum discharge temperature";
    }
    leaf max-discharge-temp {
      type uint16;
      units "Kelvin";
      description
        "Maximum discharge temperature";
    }
    leaf min-charging-temp {
      type uint16;
      units "Kelvin";
      description
        "Minimum charging temperature";
    }
    leaf max-charging-temp {
      type uint16;
      units "Kelvin";
      description
        "Maximum charging temperature";
    }
    leaf output-curr-max {
      type uint16;
      units "milliAmper";
      description
        "Maximum output current";
    }
    leaf output-voltage-max {
      type uint16;
      units "milliVoltage";
      description
        "Maximum output voltage";
    }
  }

  grouping sprom-bbu-info {
    description
      "Battery Backup Unit Serial Programmable Read Only Memory information";
    leaf bbu-index {
      type uint8;
      description
        "Battery Backup Unit index";
    }
    container common-sprom-block-info {
      description
        "Common Serial Programmable Read Only Memory block information";
      uses bbu-ios-xe-oper:common-sprom-block-info;
    }
    container bbu-sprom-block-info {
      description
        "Battery Backup Unit specific Serial Programmable Read Only Memory block information";
      uses bbu-ios-xe-oper:bbu-sprom-block-info;
    }
  }

  grouping bbu-unit-info {
    description
      "Battery Backup Unit information";
    leaf bbu-index {
      type uint8;
      description
        "Battery Backup Unit index";
    }
    leaf battery-state {
      type bbu-ios-xe-oper:bbu-battery-state;
      description
        "Battery Backup Unit battery state";
    }
    leaf unit-status {
      type bbu-ios-xe-oper:bbu-charge-discharge-status;
      description
        "Battery Backup Unit index unit status";
    }
    leaf charge-level {
      type uint8;
      units "percentage";
      description
        "Battery Backup Unit index charge level";
    }
    leaf tte-time {
      type yang:date-and-time;
      description
        "The estimated time when battery will be empty.";
    }
    leaf cap-remain {
      type uint16;
      units "milliAmperHour";
      description
        "Remaining capacity";
    }
    leaf full-charge-cap {
      type uint16;
      units "milliAmperHour";
      description
        "Full charge capacity";
    }
    leaf voltage {
      type uint16;
      units "milliVoltage";
      description
        "Battery Backup Unit voltage";
    }
    leaf current {
      type uint16;
      units "milliAmper";
      description
        "Battery Backup Unit current";
    }
    leaf temp {
      type uint16;
      units "Degree Celsius";
      description
        "Battery Backup Unit temperature";
    }
    leaf fw-version {
      type uint16;
      description
        "Battery Backup Unit firmware version";
    }
  }

  grouping bbu-hw-pins-info {
    description
      "Battery Backup Unit hardware pins information";
    leaf present-pin {
      type uint8;
      description
        "Battery Backup Unit hardware present pin";
    }
    leaf ready-state-pin {
      type uint8;
      description
        "Battery Backup Unit hardware ready state pin";
    }
    leaf ready-bit-pin {
      type uint8;
      description
        "Battery Backup Unit hardware ready bit pin";
    }
    leaf interrupt-pin {
      type uint8;
      description
        "Battery Backup Unit hardware interrupt pin";
    }
    leaf reset-pin {
      type uint8;
      description
        "Battery Backup Unit hardware reset pin";
    }
    leaf ac-pin {
      type uint8;
      description
        "Battery Backup Unit hardware Alternating Current pin";
    }
  }

  grouping bbu-fw-oper-data {
    description
      "Battery Backup Unit firmware data";
    leaf needs-fw-upgrade {
      type boolean;
      description
        "Battery Backup Unit needs to do firmware upgrade";
    }
    leaf fw-upgrade-failures {
      type int64;
      description
        "Battery Backup Unit the count of failing to do the firmware upgrade";
    }
  }

  grouping bbu-oper-info {
    description
      "Battery Backup Unit Information";
    leaf avg-charge-level {
      type uint8;
      description
        "Battery Backup Unit average charge level";
    }
    leaf avg-low-level {
      type boolean;
      description
        "Battery Backup Unit average low level";
    }
    leaf tran-mode {
      type boolean;
      description
        "Battery Backup Unit in transportation mode";
    }
    container bbu-fw-data {
      description
        "Battery Backup Unit firmware data";
      uses bbu-ios-xe-oper:bbu-fw-oper-data;
    }
    container bbu-hw-pins-info {
      description
        "Battery Backup Unit hardware pins information";
      uses bbu-ios-xe-oper:bbu-hw-pins-info;
    }
    leaf bbu-number {
      type uint8;
      description
        "Total number of Battery Backup Unit";
    }
    list bbu-unit-info {
      max-elements 4;
      description
        "Battery Backup Unit unit information";
      uses bbu-ios-xe-oper:bbu-unit-info;
    }
    list bbu-sprom-info {
      max-elements 4;
      description
        "Battery Backup Unit Serial Programmable Read Only Memory information";
      uses bbu-ios-xe-oper:sprom-bbu-info;
    }
  }

  grouping bbu-data {
    description
      "Battery Backup Unit data";
    leaf status {
      type bbu-ios-xe-oper:bbu-module-presence-status;
      description
        "Battery Backup Unit presence status";
    }
    leaf collect-time {
      type yang:date-and-time;
      description
        "It is the timestamp when Battery Backup Unit data was collected.";
    }
    container bbu-info {
      when "../status = 'bbums-ready'";
      description
        "Battery Backup Unit information";
      uses bbu-ios-xe-oper:bbu-oper-info;
    }
  }

  container bbu-oper-data {
    config false;
    description
      "Battery Backup Unit operational data";
    container bbu-data {
      presence "bbu-data";
      description
        "Battery Backup Unit data";
      uses bbu-ios-xe-oper:bbu-data;
    }
  }
}
