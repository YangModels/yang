module Cisco-IOS-XE-appqoe-http-oper {
  yang-version 1.1;
  namespace "http://cisco.com/ns/yang/Cisco-IOS-XE-appqoe-http-oper";
  prefix appqoe-http-xe-oper;

  import Cisco-IOS-XE-appqoe-types {
    prefix appqoe-types-ios-xe;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for AppQoE Hypertext Transfer Protocol caching operational data.
     Copyright (c) 2022 by Cisco Systems, Inc.
     All rights reserved.";

  revision 2022-07-01 {
    description
      "Initial revision";
    reference
      "1.0.0";
    cisco-semver:module-version "1.0.0";
  }

  grouping appqoe-http-config {
    description
      "AppQoE HTTP caching service configuration details";
    leaf profile {
      type appqoe-types-ios-xe:appqoe-profile-type;
      description
        "Profile type assigned to the HTTP caching service";
    }
    leaf max-cons {
      type uint32;
      description
        "Maximum connections supported based on the profile assigned";
    }
    leaf total-disk {
      type uint16;
      units "gigabytes";
      description
        "Total disk space allocated for the HTTP cache";
    }
    leaf total-memory {
      type uint64;
      units "megabytes";
      description
        "Total memory allocated to the HTTP caching service";
    }
    leaf cpu-cores {
      type uint8;
      description
        "Number of CPU cores allocated to the HTTP caching service";
    }
    leaf disk-encrypt {
      type boolean;
      description
        "HTTP cache disk encryption status ON:enabled, OFF:disabled";
    }
  }

  grouping http-status-data {
    description
      "Operational status information of the AppQoE HTTP caching service";
    leaf http-start-time {
      type yang:date-and-time;
      description
        "HTTP caching service start time";
    }
    leaf hs-change-reason {
      type appqoe-types-ios-xe:appqoe-hs-change-reason;
      description
        "HTTP health status change reason";
    }
    leaf hs-change-time {
      type yang:date-and-time;
      description
        "Time of last HTTP caching service health status change";
    }
    leaf last-hs-update {
      type yang:date-and-time;
      description
        "Time of last health status update received from HTTP caching service";
    }
    leaf disk-cache-usage {
      type uint8;
      units "percentage";
      description
        "Percentage of disk cache used";
    }
    list alarm {
      description
        "Alarms asserted by HTTP caching service";
      uses appqoe-types-ios-xe:active-appqoe-alarms;
    }
    container config {
      description
        "HTTP caching service configuration details";
      uses appqoe-http-xe-oper:appqoe-http-config;
    }
  }

  grouping appqoe-http-status {
    description
      "Operational status information of the AppQoE HTTP caching service";
    leaf health-status {
      type appqoe-types-ios-xe:appqoe-health-status;
      description
        "HTTP health status";
    }
    container data {
      when "(../health-status!='http-status-unavailable' and ../health-status!='http-status-disabled')";
      description
        "HTTP status data";
      uses appqoe-http-xe-oper:http-status-data;
    }
  }

  grouping http-stats-cache {
    description
      "HTTP cache statistics";
    leaf total-cache {
      type uint64;
      units "gigabytes";
      description
        "Size of the HTTP cache";
    }
    leaf total-cache-used {
      type uint64;
      units "bytes";
      description
        "Total number of bytes of HTTP cache currently used";
    }
    leaf cache-used-percent {
      type uint16;
      units "percentage";
      description
        "Percentage of HTTP cache currently used";
    }
    leaf cache-hits {
      type uint64;
      description
        "Total number of cache hits";
    }
    leaf cache-hit-fresh {
      type uint64;
      description
        "Total number of fresh cache hits";
    }
    leaf cache-hit-ims {
      type uint64;
      description
        "Total number of If-Modified-Since (IMS) cache hits";
    }
    leaf cache-hit-mem-fresh {
      type uint64;
      description
        "Total number of memory fresh cache hits";
    }
    leaf cache-hit-reval {
      type uint64;
      description
        "Total number of revalidated cache hits";
    }
    leaf cache-hit-stale {
      type uint64;
      description
        "Total number of cache hits served stale";
    }
    leaf cache-misses {
      type uint64;
      description
        "Total number of cache miss";
    }
    leaf cache-miss-client {
      type uint64;
      description
        "Total number of cache miss when cache not present";
    }
    leaf cache-miss-changed {
      type uint64;
      description
        "Total number of cache miss when cache changed";
    }
    leaf cache-miss-ims {
      type uint64;
      description
        "Total number of cache miss due to IMS";
    }
    leaf cache-miss-other {
      type uint64;
      description
        "Total number of cache miss due to other reasons";
    }
    leaf total-ram-cache {
      type uint64;
      units "megabytes";
      description
        "Total RAM cache available";
    }
    leaf ram-cache-used {
      type uint64;
      units "bytes";
      description
        "Total RAM cache used";
    }
    leaf ram-cache-hit {
      type uint64;
      description
        "Total number of RAM cache hits";
    }
    leaf ram-cache-miss {
      type uint64;
      description
        "Total number of RAM cache misses";
    }
    leaf cache-read {
      type uint64;
      units "kbps";
      description
        "Total cache read per second (KB/s)";
    }
    leaf cache-write {
      type uint64;
      units "kbps";
      description
        "Total cache write per second (KB/s)";
    }
    leaf bk-fill-aborted {
      type uint64;
      description
        "Total background-fill download bytes aborted";
    }
    leaf bk-fill-completed {
      type uint64;
      description
        "Total background-fill download bytes completed";
    }
  }

  grouping http-stats-brief {
    description
      "HTTP operational statistics";
    leaf last-stats-clr-time {
      type yang:date-and-time;
      description
        "Time HTTP cache service related statistics were last cleared";
    }
    leaf total-cons {
      type uint64;
      description
        "Total number of connections";
    }
    leaf max-cons {
      type uint64;
      description
        "Total number of maximum concurrent connections";
    }
    leaf cur-active-cons {
      type uint64;
      description
        "Total number of current active connections";
    }
    leaf active-http-cons {
      type uint64;
      description
        "Total number of active HTTP connections";
    }
    leaf active-http2-cons {
      type uint64;
      description
        "Total number of active HTTP 2 connections";
    }
    leaf conn-resets {
      type uint64;
      description
        "Total number of connection resets";
    }
    leaf http-1-0-conns {
      type uint64;
      description
        "Total number of HTTP-1.0 connections";
    }
    leaf http-2-0-conns {
      type uint64;
      description
        "Total number of HTTP-2.0 connections";
    }
  }

  grouping http-session-stats {
    description
      "HTTP session related statistics";
    leaf allocated {
      type uint64;
      description
        "Total number of sessions allocated";
    }
    leaf freed {
      type uint64;
      description
        "Total number of session freed";
    }
  }

  grouping http-ebp-stats {
    description
      "HTTP EBP related statistics";
    leaf recvd {
      type uint64;
      description
        "Total number of data buffers received";
    }
    leaf freed {
      type uint64;
      description
        "Total number of data buffers freed";
    }
    leaf reused {
      type uint64;
      description
        "Total number of data buffers re-used";
    }
    leaf allocated {
      type uint64;
      description
        "Total number of data buffers allocated";
    }
    leaf sent {
      type uint64;
      description
        "Total number of data buffers sent";
    }
    leaf send-failed {
      type uint64;
      description
        "Total number of data buffers failed to send";
    }
    leaf no-flow-ctx {
      type uint64;
      description
        "Total number of data buffers dropped due to no flow context";
    }
    leaf more-than-max-size {
      type uint64;
      description
        "Total number of times requested data block size was greater than max block size";
    }
    leaf less-than-req-size {
      type uint64;
      description
        "Total number of times allocated data block size was less than requested block size";
    }
    leaf ctrl-recvd {
      type uint64;
      description
        "Total number of control buffers received";
    }
    leaf ctrl-freed {
      type uint64;
      description
        "Total number of control buffers freed";
    }
    leaf ctrl-reused {
      type uint64;
      description
        "Total number of control buffers reused";
    }
    leaf ctrl-alloc {
      type uint64;
      description
        "Total number of control buffers allocated";
    }
    leaf ctrl-sent {
      type uint64;
      description
        "Total number of control buffers sent";
    }
    leaf ctrl-send-fail {
      type uint64;
      description
        "Total number of control buffers failed to send";
    }
    leaf ctrl-no-flow-ctx {
      type uint64;
      description
        "Total number of control buffers dropped due to no flow context";
    }
    leaf ctrl-req-more {
      type uint64;
      description
        "Total number of times requested control block size was greater than max block size";
    }
    leaf ctrl-ret-less {
      type uint64;
      description
        "Total number of times allocated control block size was less than requested block size";
    }
  }

  grouping appqoe-http-stats-detail {
    description
      "Detailed set of statistics for the AppQoE HTTP caching service";
    leaf status {
      type appqoe-types-ios-xe:appqoe-health-status;
      description
        "HTTP caching health status";
    }
    container stats-data {
      description
        "HTTP caching service connection statistics";
      uses appqoe-http-xe-oper:http-stats-brief;
    }
    container cache-data {
      description
        "Cache statistics of HTTP caching service";
      uses appqoe-http-xe-oper:http-stats-cache;
    }
    leaf accept-failed {
      type uint64;
      description
        "Total number of server intercept accept failed";
    }
    leaf vio-wcapi-wr-failed {
      type uint64;
      description
        "Total number of VIO to WCAPI write failed";
    }
    leaf wcapi-vio-wr-failed {
      type uint64;
      description
        "Total number of WCAPI to VIO write failed";
    }
    leaf send-flow-ctrl {
      type uint64;
      description
        "Total number of flow control message send failed";
    }
    leaf reset-recv {
      type uint64;
      description
        "Total number of service reset received";
    }
    container sess-data {
      description
        "Session statistics of HTTP caching service";
      uses appqoe-http-xe-oper:http-session-stats;
    }
    container ebp-stats {
      description
        "HTTP extensible buffer pool (EBP) statistics";
      uses appqoe-http-xe-oper:http-ebp-stats;
    }
  }

  grouping appqoe-http-stats {
    description
      "Brief set of statistics for the AppQoE HTTP caching service";
    leaf status {
      type appqoe-types-ios-xe:appqoe-health-status;
      description
        "HTTP health status";
    }
    container stats-data {
      description
        "HTTP caching service connection statistics";
      uses appqoe-http-xe-oper:http-stats-brief;
    }
    container cache-data {
      description
        "HTTP cache statistics";
      uses appqoe-http-xe-oper:http-stats-cache;
    }
  }

  container appqoe-http-oper-data {
    config false;
    description
      "AppQoE HTTP caching operational data";
    container appqoe-http-status {
      presence "appqoe-http-status";
      description
        "Operational status information of the AppQoE HTTP caching service";
      uses appqoe-http-xe-oper:appqoe-http-status;
    }
    container appqoe-http-stats-detail {
      presence "appqoe-http-stats-detail";
      description
        "Detailed set of statistics for the AppQoE HTTP caching service";
      uses appqoe-http-xe-oper:appqoe-http-stats-detail;
    }
    container appqoe-http-stats {
      presence "appqoe-http-stats";
      description
        "Brief set of statistics for the AppQoE HTTP caching service";
      uses appqoe-http-xe-oper:appqoe-http-stats;
    }
  }
}
