module Cisco-IOS-XE-wireless-sdavc-oper {
  yang-version 1.1;
  namespace "http://cisco.com/ns/yang/Cisco-IOS-XE-wireless-sdavc-oper";
  prefix wireless-oper-sdavc;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Software Defined-Application Visibility Control (SD-AVC)
     operational data.
     Copyright (c) 2021 by Cisco Systems, Inc.
     All rights reserved.";

  revision 2021-11-01 {
    description
      "Initial revision";
    reference
      "1.0.0";
    cisco-semver:module-version "1.0.0";
  }

  typedef sdavc-file-dwld-status {
    type enumeration {
      enum sdavc-dwld-not-initiated {
        value 0;
        description
          "File download not initiated";
      }
      enum sdavc-dwld-file-success {
        value 1;
        description
          "File download successful";
      }
      enum sdavc-dwld-file-failure {
        value 2;
        description
          "File download failed";
      }
    }
    description
      "Enum for SD-AVC File download status.";
  }

  grouping st-sdavc-ap-dwld-status {
    description
      "SD-AVC per AP latest file download status";
    leaf ap-mac {
      type yang:mac-address;
      description
        "AP MAC address";
    }
    leaf dwld-status {
      type wireless-oper-sdavc:sdavc-file-dwld-status;
      description
        "File download status";
    }
    leaf filename {
      type string;
      description
        "Name of downloaded file";
    }
  }

  container sdavc-oper-data {
    config false;
    description
      "SD-AVC operational data";
    list sdavc-ap-dwld-status {
      key "ap-mac";
      description
        "Per AP SD-AVC File download status";
      uses wireless-oper-sdavc:st-sdavc-ap-dwld-status;
    }
  }
}
