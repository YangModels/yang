module Cisco-IOS-XE-cts-rpc {
  yang-version 1.1;
  namespace "http://cisco.com/ns/yang/Cisco-IOS-XE-cts-rpc";
  prefix ios-xe-cts-rpc;

  import cisco-semver {
    prefix cisco-semver;
  }
  import ietf-inet-types {
    prefix inet;
  }
  import Cisco-IOS-XE-rpc {
    prefix ios-xe-rpc;
  }

  organization
    "Cisco Systems";
  contact
    "<mailto:cs-yang@cisco.com>";
  description
    "NED CTS RPC YANG module for IOS
     Copyright (c) 2016-2019 by Cisco Systems, Inc.
     All rights reserved.";

  revision 2019-07-01 {
    description
      "Establish semantic version baseline";
    cisco-semver:module-version "1.0.0";
  }
  revision 2018-12-06 {
    description
      "created for NED RPC modularisation";
  }

  grouping clear-cts-counters-ip-grouping {
    choice ip-choice {
      case ipv6-case {
        leaf ipv6 {
          description
            "Protocol Version - IPv4";
          type empty;
        }
      }
      case ipv4-case {
        leaf ipv4 {
          description
            "Protocol Version - IPv6";
          type empty;
        }
      }
    }
  }

  grouping clear-cts-source-destination-grouping {
    choice from-to-choice {
      case security-tag-case {
        leaf security-tag {
          description
            "Security Group Tag";
          type uint16 {
            range "0..65519";
          }
        }
        choice ip-choice {
          case ipv6-case {
            leaf ipv6 {
              description
                "Protocol Version - IPv6";
              when '../security-tag';
              type empty;
            }
          }
          case ipv4-case {
            leaf ipv4 {
              description
                "Protocol Version - IPv4";
              when '../security-tag';
              type empty;
            }
          }
        }
      }
      case unknown-case {
        container unknown {
          description
            " Unknown Destination Group";
          presence "true";
          uses clear-cts-counters-ip-grouping;
        }
      }
    }
  }

  rpc cts {
    description
      "Cisco Trusted Security Exec Commands";
    input {
      container credentials {
        description
          "Insert CTS device ID and password into the keystore";
        leaf id {
          description
            "Specify the CTS device ID for this switch or router(upto 32 char)";
          type string {
            length "1..24";
          }
        }
        leaf password {
          description
            "specify this device's CTS password(upto 24 char)";
          when '../id';
          type string;
        }
      }
    }
    output {
      uses ios-xe-rpc:cisco-xe-rpc-output;
    }
  }

  augment "/ios-xe-rpc:clear/ios-xe-rpc:input/ios-xe-rpc:clear-choice" {
    case cts-case {
      container cts {
        description
          "Cisco Trusted Security commands";
        choice cts-choice {
          case counter-case {
            container counter {
              description
                "Clear a CTS interface's counters or all counters";
              presence "true";
              leaf interface {
                description
                  "GigabitEthernet IEEE 802.3z";
                type string;
              }
            }
          }
          case credentials-case {
            leaf credentials {
              description
                "Clear all CTS credentials, including all PACs";
              type empty;
            }
          }
          case environment-data-case {
            leaf environment-data {
              description
                "Clear CTS Environment Data";
              type empty;
            }
          }
          case pac-case {
            container pac {
              description
                "Clear a PAC or all PACs from the keystore";
              choice pac-choice {
                case A-ID-case {
                  leaf A-ID {
                    description
                      "Specify A-ID of a PAC to be removed from the key store";
                    type string;
                  }
                }
                case all-case {
                  leaf all {
                    description
                      "Clear all PACs on the device";
                    type empty;
                  }
                }
              }
            }
          }
          case role-based-case {
            container role-based {
              description
                "Role-based Access Control information";
              container counters {
                description
                  "Display role-based access control statistics per <SGT, DGT> cell";
                presence "true";
                choice counters-choice {
                  case default-case {
                    container default {
                      description
                        "Default policy counters";
                      presence "true";
                      uses clear-cts-counters-ip-grouping;
                    }
                  }
                  case ipv4-case {
                    leaf ipv4 {
                      description
                        "Protocol Version - IPv4";
                      type empty;
                    }
                  }
                  case ipv6-case {
                    leaf ipv6 {
                      description
                        "Protocol Version - IPv4";
                      type empty;
                    }
                  }
                  case from-case {
                    container from {
                      description
                        "Source Group";
                      uses clear-cts-source-destination-grouping;
                    }
                    container to {
                      description
                        "Destination Group";
                      uses clear-cts-source-destination-grouping;
                    }
                  }
                }
              }
            }
          }
          case server-case {
            leaf server {
              description
                " Remove the specified authentication server";
              type inet:ipv4-address;
            }
          }
          case sxp-case {
            container sxp {
              description
                "Clear the SXP counters";
              leaf filter-counters {
                type empty;
              }
            }
          }
        }
      }
    }
  }
}
