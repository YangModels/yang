module Cisco-IOS-XE-app-hosting {
  yang-version 1.1;
  namespace "http://cisco.com/ns/yang/Cisco-IOS-XE-app-hosting";
  prefix ios-app-hosting;

  import cisco-semver {
    prefix cisco-semver;
  }
  import ietf-inet-types {
    prefix inet;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE App-Hosting Yang model.
     Copyright (c) 2018-2021 by Cisco Systems, Inc.
     All rights reserved.";

  revision 2021-07-01 {
    description
      "- Added docker run-time option
       - Added persist-disk";
  }
  revision 2021-03-01 {
    description
      "- Replaced cli-diff-dependency";
  }
  revision 2020-11-01 {
    description
      "- Added CPU percent that allows user to enter the percentage of
         IOX cpu resource, instead of entering unit. If cpu-percent is used,
         cpu will be ignored";
  }
  revision 2019-07-01 {
    description
      "Establish semantic version baseline";
    cisco-semver:module-version "1.0.0";
  }
  revision 2018-08-16 {
    description
      "Add add diff-dependency on iox config";
  }
  revision 2018-08-02 {
    description
      "Add custom profile options";
  }
  revision 2018-07-26 {
    description
      "Add app-hosting to native model";
  }

  typedef app-hosting-ip-address {
    type union {
      type inet:ipv4-address;
      type inet:ipv6-address;
    }
  }

  grouping config-app-hosting-grouping {
    container app-hosting {
      description
        "Application hosting configuration mode";
      list appid {
        description
          "Enter Application Name up to 40 alphanumeric characters";
        key "name";
        leaf name {
          type string {
            length "1..40";
          }
        }
        container app-default-gateway {
          description
            "Application default-gateway";
          leaf ip-address {
            description
              "Ip Address";
            type app-hosting-ip-address;
          }
          leaf guest-interface {
            description
              "Application Network Interface #(0..3)";
            type uint8 {
              range "0..3";
            }
          }
        }
        container app-resource {
          description
            "Application resources";
          leaf package-profile {
            description
              "Application package-profile name";
            type string;
          }
          container profile {
            description
              "Application profile name";
            choice profile-choice {
              case standard-profile {
                leaf profile-name {
                  type enumeration {
                    enum tiny;
                    enum small;
                    enum large;
                    enum huge;
                  }
                }
              }
              case custom-profile {
                container custom {
                  presence "true";
                  leaf cpu {
                    description
                      "Application CPU units/share quota (will be ignored if cpu-percent is provided)";
                    type uint16 {
                      range "0..20000";
                    }
                  }
                  leaf cpu-percent {
                    description
                      "Application CPU percent";
                    type uint8 {
                      range "0..100";
                    }
                  }
                  leaf memory {
                    description
                      "Memory reservation MB units";
                    type uint16 {
                      range "0..4096";
                    }
                  }
                  leaf vcpu {
                    description
                      "Application vcpu count";
                    type uint16;
                  }
                  leaf persist-disk {
                    description
                      "IOX Application persistent data disk reservation MB units";
                    type uint16;
                  }
                }
              }
            }
          }
          container docker {
            description
              "Application docker options";
            presence "true";
            leaf prepend-pkg-opts {
              description
                "Prepend docker package runtime options";
              type empty;
            }
            list run-opts {
              description
                "Multi-line docker run-time options with line index and string";
              key "run-opts";
              leaf run-opts {
                type uint8 {
                  range "1..30";
                }
              }
              leaf run-options {
                type string {
                  length "1..235";
                }
              }
            }
          }
        }
        list app-vnic {
          description
            "Virtual Network Interface";
          key "gateway";
          unique "virtualportgroup";
          unique "guest-interface";
          leaf gateway {
            type enumeration {
              enum gateway0;
              enum gateway1;
              enum gateway2;
              enum gateway3;
              enum l2port;
              enum management;
            }
          }
          leaf virtualportgroup {
            when "../gateway != 'l2port' and ../gateway != 'management'";
            type uint8 {
              range "0..31";
            }
          }
          leaf guest-interface {
            type uint8 {
              range "0..3";
            }
          }
          container guest-ipaddress {
            description
              "Guest IP address";
            leaf ip-address {
              type app-hosting-ip-address;
            }
            leaf netmask {
              type app-hosting-ip-address;
            }
          }
        }
        leaf name-server0 {
          description
            "Name server Ip Address";
          type app-hosting-ip-address;
        }
        leaf name-server1 {
          description
            "Name server Ip Address";
          type app-hosting-ip-address;
        }
        leaf name-server2 {
          description
            "Name server Ip Address";
          type app-hosting-ip-address;
        }
        leaf name-server3 {
          description
            "Name server Ip Address";
          type app-hosting-ip-address;
        }
        leaf name-server4 {
          description
            "Name server Ip Address";
          type app-hosting-ip-address;
        }
        leaf name-server5 {
          status obsolete;
          description
            "Name server Ip Address";
          type app-hosting-ip-address;
        }
        leaf start {
          description
            "Start configured app";
          type empty;
        }
      }
    }
  }

  augment "/ios:native" {
    uses config-app-hosting-grouping;
  }
}
