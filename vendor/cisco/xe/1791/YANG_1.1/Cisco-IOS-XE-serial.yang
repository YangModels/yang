module Cisco-IOS-XE-serial {
  yang-version 1.1;
  namespace "http://cisco.com/ns/yang/Cisco-IOS-XE-serial";
  prefix ios-serial;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE serial Interfaces.
     Copyright (c) 2018 by Cisco Systems, Inc.
     All rights reserved.";

  revision 2019-07-01 {
    description
      "Establish semantic version baseline";
    cisco-semver:module-version "1.0.0";
  }
  revision 2018-10-17 {
    description
      "Add encapsulation hdlc for serial interface";
  }
  revision 2018-06-11 {
    description
      "Initial revision";
  }

  grouping config-interface-serial-grouping {
    leaf nrzi-encoding {
      description
        "Enable use of NRZI encoding";
      type empty;
    }
    leaf transmitter-delay {
      description
        "Set dead-time after transmitting a datagram";
      type uint8 {
        range "0..15";
      }
    }
    container pulse-time {
      description
        "Force DTR low during resets";
      choice pulse-time-choice {
        leaf seconds {
          description
            "DTR low time in seconds";
          type uint8 {
            range "1..60";
          }
        }
        leaf msec {
          description
            "DTR low time in milliseconds";
          type uint16 {
            range "1..59999";
          }
        }
      }
    }
    leaf loopback {
      description
        "Configure internal loopback on an interface";
      type empty;
    }
    container carrier-delay {
      description
        "Specify delay for interface transitions";
      choice carrier-delay-choice {
        leaf seconds {
          description
            "Carrier Transitions delay seconds";
          type uint8 {
            range "1..60";
          }
        }
        leaf msec {
          description
            "delay specified in milliseconds";
          type uint16 {
            range "1..59999";
          }
        }
      }
    }
    leaf idle-character {
      description
        "Set idle character type";
      type enumeration {
        enum flag;
        enum marks;
      }
      default "flag";
    }
    container serial {
      description
        "serial interface commands";
      leaf restart-delay {
        description
          "Configure serial interface restart-delay";
        type uint16 {
          range "0..900";
        }
      }
    }
    choice serial-mode {
      case DCE-mode {
        container DCE-mode-config {
          description
            "special config when synchronous serial interface is in DCE mode";
          leaf dce-terminal-timing-enable {
            description
              "Enable DCE terminal timing";
            type empty;
          }
          container clock {
            description
              "Configure serial interface clock";
            leaf rate {
              description
                "Configure serial interface clock speed";
              type enumeration {
                enum 1200;
                enum 2400;
                enum 4800;
                enum 9600;
                enum 14400;
                enum 19200;
                enum 28800;
                enum 32000;
                enum 38400;
                enum 48000;
                enum 56000;
                enum 57600;
                enum 64000;
                enum 72000;
                enum 115200;
                enum 125000;
                enum 148000;
                enum 192000;
                enum 250000;
                enum 256000;
                enum 384000;
                enum 500000;
                enum 512000;
                enum 768000;
                enum 800000;
                enum 1000000;
                enum 2000000;
                enum 4000000;
                enum 5300000;
                enum 8000000;
              }
            }
          }
          container ignore {
            description
              "ignore signals";
            leaf dtr {
              description
                "DCE ignore dtr";
              type empty;
            }
            leaf rts {
              description
                "DCE ignore rts";
              type empty;
            }
          }
        }
      }
      case DTE-mode {
        container DTE-mode-config {
          description
            "special config when synchronous serial interface is in DTE mode";
          container invert {
            description
              "Serial invert modes";
            leaf txclock {
              description
                "Invert transmit clock";
              type empty;
            }
          }
          container clock {
            description
              "Configure serial interface clock";
            container rate {
              description
                "Configure serial interface clock speed";
              leaf threshold {
                description
                  "Configure the threshold clockrate limit for DTE interfaces";
                type uint32 {
                  range "246..8064000";
                }
              }
            }
          }
          container ignore {
            description
              "ignore signals";
            leaf dcd {
              description
                "DTE ignore dcd";
              type empty;
            }
            leaf cts {
              description
                "DTE ignore cts";
              type empty;
            }
            leaf dsr {
              description
                "DTE ignore dst";
              type empty;
            }
          }
        }
      }
    }
  }

  augment "/ios:native/ios:interface/ios:Serial/ios:encapsulation/ios:encap-choice" {
    leaf hdlc {
      description
        "Serial HDLC synchronous";
      type boolean;
      default "true";
    }
  }

  augment "/ios:native/ios:interface/ios:Serial" {
    uses config-interface-serial-grouping;
  }
}
