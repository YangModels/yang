module Cisco-IOS-XE-verify-events {
  yang-version 1.1;
  namespace "http://cisco.com/ns/yang/Cisco-IOS-XE-verify-events";
  prefix verify-ios-xe-events;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains collection of YANG definitions
     for checksum verification and computation status event
     notifications.
     Copyright (c) 2020-2021 by Cisco Systems, Inc.
     All rights reserved.";

  revision 2021-07-01 {
    description
      "Initial revision";
    reference
      "1.0.0";
    cisco-semver:module-version "1.0.0";
  }

  typedef verify-status {
    type enumeration {
      enum verify-success {
        value 0;
        description
          "Checksum verification success";
      }
      enum verify-failed {
        value 1;
        description
          "Checksum verification failed";
      }
    }
    description
      "Checksum verification and computation status ";
  }

  typedef verify-err-type {
    type enumeration {
      enum verify-event-err-no-mem {
        value 0;
        description
          "No Memory at back end";
      }
      enum verify-event-err-invalid-file-input {
        value 1;
        description
          "Invalid File Input";
      }
      enum verify-event-err-invalid-filesystem {
        value 2;
        description
          "Invalid Filesystem";
      }
      enum verify-event-err-not-computible {
        value 3;
        description
          "Hash can't be computed for given file";
      }
      enum verify-event-err-hash-mismatch {
        value 4;
        description
          "Calculated hash do not match expected hash";
      }
      enum verify-event-no-err {
        value 5;
        description
          "No Error";
      }
    }
    description
      "Checksum verification and computation status ";
  }

  grouping verify-notif-header {
    description
      "Checksum verification notification header";
    leaf err-type {
      type verify-ios-xe-events:verify-err-type;
      description
        "The Error type for rpc request";
    }
    leaf uuid {
      type string;
      description
        "The UUID (universally unique identifier) is a string and it
         is mapped with the UUID of input rpc request";
    }
  }

  grouping verify-event-fields {
    description
      "Checksum verification event fields";
    leaf status {
      type verify-ios-xe-events:verify-status;
      description
        "Checksum verification status";
    }
    leaf computed-hash {
      type string;
      description
        "Computed hash value, it can based on MD5 or SHA512";
    }
  }

  notification verify-event {
    description
      "Checksum verification and computation notification";
    uses verify-ios-xe-events:verify-notif-header;
    uses verify-ios-xe-events:verify-event-fields;
  }
}
