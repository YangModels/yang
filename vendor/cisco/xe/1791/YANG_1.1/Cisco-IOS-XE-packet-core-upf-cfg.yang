module Cisco-IOS-XE-packet-core-upf-cfg {
  yang-version 1.1;
  namespace "http://cisco.com/ns/yang/Cisco-IOS-XE-packet-core-upf-cfg";
  prefix packet-core-upf-cfg;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Packet-Core UPF configuration.
     Copyright (c) 2021 by Cisco Systems, Inc.
     All rights reserved.";

  revision 2021-11-01 {
    description
      "Initial revision";
    reference
      "1.0.0";
    cisco-semver:module-version "1.0.0";
  }

  grouping upf {
    description
      "Packet-Core UPF related configuration";
    leaf status {
      type boolean;
      default "false";
      description
        "Administrative status of UPF";
    }
    leaf gtpu-profile-name {
      type string {
        length "1..32";
      }
      description
        "GTPU profile name";
    }
    leaf timer-profile-name {
      type string {
        length "1..32";
      }
      description
        "Timer profile name";
    }
  }

  container packet-core-upf-cfg-data {
    description
      "Packet-Core UPF configuration data model";
    container packet-core-upf {
      presence "packet-core-upf";
      description
        "UPF configuration data";
      uses packet-core-upf-cfg:upf;
    }
  }
}
