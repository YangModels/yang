module Cisco-IOS-XE-appqoe-types {
  yang-version 1.1;
  namespace "http://cisco.com/ns/yang/Cisco-IOS-XE-appqoe-types";
  prefix appqoe-types-ios-xe;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for service-insertion operational data.
     Copyright (c) 2020-2022 by Cisco Systems, Inc.
     All rights reserved.";

  revision 2022-07-01 {
    description
      "- Added AppQoE specific status, alarm, profile
         and status change reason enumerations";
    reference
      "1.2.0";
    cisco-semver:module-version "1.2.0";
  }
  revision 2021-07-01 {
    description
      "- Added support for AppQoE sub service status
       - Added new hybrid device mode";
    reference
      "1.1.0";
    cisco-semver:module-version "1.1.0";
  }
  revision 2020-11-01 {
    description
      "Initial revision";
    reference
      "1.0.0";
    cisco-semver:module-version "1.0.0";
  }

  typedef appqoe-sn-status {
    type enumeration {
      enum sn-status-down {
        value 0;
        description
          "Service node status is down";
      }
      enum sn-status-green {
        value 1;
        description
          "Service node status is green";
      }
      enum sn-status-yellow {
        value 2;
        description
          "Service node status is yellow";
      }
      enum sn-status-red {
        value 3;
        description
          "Service node status is red";
      }
    }
    description
      "Service node status";
  }

  typedef appqoe-device-mode {
    type enumeration {
      enum device-mode-cedge-sdwan {
        value 0;
        description
          "Device mode is not configured";
      }
      enum device-mode-service-node {
        value 1;
        description
          "Device mode is service node";
      }
      enum device-mode-integrated-service-node {
        value 2;
        description
          "Device mode is integrated service node";
      }
      enum device-mode-service-controller {
        value 3;
        description
          "Device mode is service controller";
      }
      enum device-mode-hybrid {
        value 4;
        description
          "Device mode is hybrid";
      }
    }
    description
      "Device mode state";
  }

  typedef appqoe-service-id {
    type enumeration {
      enum appqoe-service-unknown {
        value 0;
        description
          "AppQoE service unknown";
      }
      enum appqoe-service-tcpopt {
        value 1;
        description
          "AppQoE service Transmission Control Protocol (TCP) optimization";
      }
      enum appqoe-service-ssl {
        value 2;
        description
          "AppQoE service Secure Sockets Layer (SSL)";
      }
      enum appqoe-service-dreopt {
        value 3;
        description
          "AppQoE service Data Redundancy Elimination (DRE)";
      }
    }
    description
      "Sub services offered under AppQoE";
  }

  typedef appqoe-service-status {
    type enumeration {
      enum appqoe-service-status-unknown {
        value 0;
        description
          "AppQoE sub service status unknown";
      }
      enum appqoe-service-status-green {
        value 1;
        description
          "AppQoE sub service status green";
      }
      enum appqoe-service-status-yellow {
        value 2;
        description
          "AppQoE sub service status yellow";
      }
      enum appqoe-service-status-red {
        value 3;
        description
          "AppQoE sub service status red";
      }
    }
    description
      "AppQoE sub service status";
  }

  typedef appqoe-health-status {
    type enumeration {
      enum appqoe-health-status-unknown {
        value 0;
        description
          "APPQOE health status is unknown";
      }
      enum appqoe-health-status-green {
        value 1;
        description
          "APPQOE health status is green";
      }
      enum appqoe-health-status-yellow {
        value 2;
        description
          "APPQOE health status is yellow";
      }
      enum appqoe-health-status-red {
        value 3;
        description
          "APPQOE health status is red";
      }
      enum appqoe-health-status-unavailable {
        value 4;
        description
          "APPQOE health status is unavailable";
      }
      enum appqoe-health-status-disabled {
        value 5;
        description
          "APPQOE health status is disabled";
      }
    }
    description
      "APPQOE health status";
  }

  typedef appqoe-hs-change-reason {
    type enumeration {
      enum appqoe-hs-reason-none {
        value 0;
        description
          "Health status change reason - none";
      }
      enum appqoe-hs-reason-init-failed {
        value 1;
        description
          "Health status reason - init failed";
      }
      enum appqoe-hs-reason-srv-not-responding {
        value 2;
        description
          "Health status reason - no response";
      }
      enum appqoe-hs-reason-cache-corrupted {
        value 3;
        description
          "Health status reason - cache corrupted";
      }
      enum appqoe-hs-reason-disk-overload {
        value 4;
        description
          "Health status change reason - disk overload";
      }
      enum appqoe-hs-reason-disk-full {
        value 5;
        description
          "Health status change reason - disk full";
      }
      enum appqoe-hs-reason-cpu-threshold {
        value 6;
        description
          "Health status change reason - CPU threshold exceeded";
      }
      enum appqoe-hs-reason-maxconn-threshold {
        value 7;
        description
          "Health status change  - maximum connections threshold exceeded";
      }
      enum appqoe-hs-reason-over-fanout {
        value 8;
        description
          "Health status change - over fanout";
      }
    }
    description
      "APPQOE health status change reason";
  }

  typedef appqoe-service-alarms {
    type enumeration {
      enum appqoe-almid-none {
        value 0;
        description
          "Alarm ID none";
      }
      enum appqoe-almid-disk-full {
        value 1;
        description
          "Disk full alarm";
      }
      enum appqoe-almid-cache-corrupted {
        value 2;
        description
          "Cache corrupted alarm";
      }
      enum appqoe-almid-over-fanout {
        value 3;
        description
          "Over fanout alarm";
      }
      enum appqoe-almid-disk-overload {
        value 4;
        description
          "Disk overload alarm";
      }
      enum appqoe-almid-maxconn-threshold {
        value 5;
        description
          "Maximum connections threshold exceeded alarm";
      }
      enum appqoe-almid-cpu-threshold {
        value 6;
        description
          "CPU threshold exceeded alarm";
      }
      enum appqoe-almid-init-failed {
        value 7;
        description
          "Init failed alarm";
      }
      enum appqoe-almid-init-success {
        value 8;
        description
          "Init success alarm";
      }
    }
    description
      "HTTP alarms";
  }

  typedef appqoe-profile-type {
    type enumeration {
      enum http-profile-unknown {
        value 0;
        description
          "HTTP profile type unknown";
      }
      enum http-profile-small {
        value 1;
        description
          "HTTP profile type small";
      }
      enum http-profile-medium {
        value 2;
        description
          "HTTP profile type medium";
      }
      enum http-profile-large {
        value 3;
        description
          "HTTP profile type large";
      }
      enum http-profile-extra-large {
        value 4;
        description
          "HTTP profile type extra large";
      }
      enum http-profile-extra-extra-large {
        value 5;
        description
          "HTTP profile type extra extra Large";
      }
    }
    description
      "HTTP profile type";
  }

  grouping appqoe-service {
    description
      "List of AppQoE sub service with status";
    leaf service {
      type appqoe-types-ios-xe:appqoe-service-id;
      description
        "Service offered by AppQoE";
    }
    leaf load-status {
      type appqoe-types-ios-xe:appqoe-service-status;
      description
        "AppQoE service status";
    }
    leaf load-percentage {
      when "(../load-status = 'appqoe-service-status-green')";
      type uint8;
      units "percentage";
      description
        "AppQoE service load percentage";
    }
  }

  grouping active-appqoe-alarms {
    description
      "Active alarms";
    leaf alarms-list {
      type appqoe-types-ios-xe:appqoe-service-alarms;
      description
        "List of alarms";
    }
  }
}
