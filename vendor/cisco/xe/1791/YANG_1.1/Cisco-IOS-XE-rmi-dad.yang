module Cisco-IOS-XE-rmi-dad {
  yang-version 1.1;
  namespace "http://cisco.com/ns/yang/Cisco-IOS-XE-rmi-dad";
  prefix ios-rmi-dad;

  import cisco-semver {
    prefix cisco-semver;
  }
  import ietf-inet-types {
    prefix inet;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native RMI-DAD, configure RMI, DAD Yang Model.
     Copyright (c) 2019-2020, 2022 by Cisco Systems, Inc.
     All rights reserved.";

  revision 2022-07-01 {
    description
      "fast switchover notification addition
       Configuring Gratuitous ARP retransmission during switch over";
    cisco-semver:module-version "1.3.0";
  }
  revision 2021-07-01 {
    description
      "hostname override command addition";
    cisco-semver:module-version "1.2.0";
  }
  revision 2020-07-02 {
    description
      "Interval addition for gateway-failover";
    cisco-semver:module-version "1.1.1";
  }
  revision 2019-07-01 {
    description
      "Initial revision";
    cisco-semver:module-version "1.0.0";
  }

  grouping config-redun-management-grouping {
    leaf fast-switchover {
      description
        "Configure fast switchover notification";
      type boolean;
      default "true";
    }
    container garp-retransmit {
      description
        "Gratuitous ARP retransmit configuration";
      list burst {
        description
          "Number of packets in each Gratuitous ARP burst";
        key "burst-size";
        leaf burst-size {
          type uint32 {
            range "0..1000";
          }
        }
        list interval {
          description
            "Time interval between each Gratuitous ARP burst";
          key "burst-interval";
          leaf burst-interval {
            type uint8 {
              range "0..5";
            }
          }
        }
      }
      leaf initial {
        description
          "Enable initial Gratuitous ARP burst";
        type boolean;
        default "true";
      }
    }
    container hostname {
      description
        "Override the hostname configuration";
      list chassis {
        description
          "chassis configuration";
        key "chassis";
        leaf chassis {
          description
            "Chassis Number range";
          type uint8 {
            range "1..16";
          }
        }
        list name {
          description
            "This system's network name";
          key "hostname";
          leaf hostname {
            type string;
          }
          list chassis {
            description
              "chassis configuration";
            key "chassis";
            leaf chassis {
              description
                "Chassis Number range";
              type uint8 {
                range "1..16";
              }
            }
            list name {
              description
                "This system's network name";
              key "hostname";
              leaf hostname {
                type string;
              }
            }
          }
        }
      }
    }
    list interface {
      description
        "management interface to configure";
      key "interface";
      leaf interface {
        type string;
      }
      list chassis {
        description
          "<1-16> chassis configuration";
        key "chassis";
        leaf chassis {
          type uint8 {
            range "1..16";
          }
        }
        list address {
          description
            "chassis ip address";
          key "address";
          leaf address {
            type union {
              type inet:ipv4-address;
              type inet:ipv6-address;
            }
          }
          list chassis {
            description
              "<1-16> chassis configuration";
            key "chassis";
            leaf chassis {
              type uint8 {
                range "1..16";
              }
            }
            list address {
              description
                "chassis ip address";
              key "address";
              leaf address {
                type union {
                  type inet:ipv4-address;
                  type inet:ipv6-address;
                }
              }
            }
          }
        }
      }
    }
  }

  grouping config-management-grouping {
    container gateway-failover {
      description
        "Gateway failover";
      leaf enable {
        description
          "Enable Gateway monitoring";
        type boolean;
        default "true";
      }
      leaf interval {
        description
          "Gateway monitoring interval";
        type uint8 {
          range "6..12";
        }
        default "8";
      }
    }
  }

  augment "/ios:native/ios:redun-management" {
    uses config-redun-management-grouping;
  }

  augment "/ios:native/ios:management" {
    uses config-management-grouping;
  }
}
