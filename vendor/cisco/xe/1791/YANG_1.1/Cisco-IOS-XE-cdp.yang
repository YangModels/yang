module Cisco-IOS-XE-cdp {
  yang-version 1.1;
  namespace "http://cisco.com/ns/yang/Cisco-IOS-XE-cdp";
  prefix ios-cdp;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Cisco Discovery Protocol (CDP) Yang Model.
     Copyright (c) 2016-2017, 2019-2020 by Cisco Systems, Inc.
     All rights reserved.";

  revision 2021-11-01 {
    description
      "-added cdp tlv app changes";
    cisco-semver:module-version "3.2.0";
  }
  revision 2021-03-01 {
    description
      "- Added the support of cdp tlv-list and filter-tlv-list
       - Added cdp enable support under dialer interface
       - Added interface Serial to use CDP grouping";
    cisco-semver:module-version "3.1.0";
  }
  revision 2020-07-01 {
    description
      "Reverting the revision 2020-03-01 ";
    cisco-semver:module-version "3.0.0";
  }
  revision 2020-03-01 {
    description
      "- Obsolete the node cdp run and cdp tlv under interface";
    cisco-semver:module-version "2.1.0";
  }
  revision 2019-11-01 {
    description
      "- Added new must statement";
    cisco-semver:module-version "2.0.0";
  }
  revision 2019-07-01 {
    description
      "- Establish semantic version baseline
       - Corrected behavior of cdp tlv under interface
       - Added support for BDI interface";
    cisco-semver:module-version "1.0.0";
  }
  revision 2019-01-22 {
    description
      "Added leaf for App-hosting Gigabit Ethernet interface";
  }
  revision 2017-11-27 {
    description
      "Added Change 25GE name";
  }
  revision 2017-11-14 {
    description
      "This revision has changes for new 40 and 100GE interface addition";
  }
  revision 2017-09-14 {
    description
      "This revision has changes for new 2gig interface addition";
  }
  revision 2017-08-16 {
    description
      "This revision has changes for new 5gig and 25gig interfaces addition";
  }
  revision 2017-02-07 {
    description
      "Initial revision";
  }

  grouping config-interface-cdp-tlv-grouping {
    container tlv {
      description
        "Enable exchange of specific tlv information";
      when "../enable = 'true'";
      choice app-option {
        default "default-case";
        case default-case {
          container default-wrp {
            leaf app {
              type boolean;
              default "true";
            }
          }
        }
        case regular-case {
          container regular-wrp {
            container app {
              description
                "Enable/Configure Application TLV";
              leaf tlvtype {
                description
                  "Configure APP TLV";
                type uint16 {
                  range "1001..65535";
                }
              }
              leaf value {
                description
                  "Configure App TLV Value information";
                type string;
              }
            }
          }
        }
      }
      container app-config {
        status deprecated;
        description
          "Enable/Configure Application TLV";
        leaf app {
          status deprecated;
          description
            "Enable CDP location server on interface";
          type boolean;
          default "true";
        }
        leaf tlvtype {
          status deprecated;
          description
            "Configure APP TLV";
          type uint16 {
            range "1001..65535";
          }
        }
        leaf value {
          status deprecated;
          description
            "Configure App TLV Value information";
          type string;
        }
      }
      leaf server-location-config {
        description
          "Enable CDP location server on interface";
        type boolean;
        default "true";
      }
      leaf location-config {
        description
          "Exchange location information";
        type boolean;
        default "true";
      }
      container app {
        status deprecated;
        description
          "Enable/Configure Application TLV";
        presence "true";
        leaf tlvtype {
          status deprecated;
          description
            "Configure APP TLV";
          type uint16 {
            range "1001..65535";
          }
        }
        leaf value {
          status deprecated;
          description
            "Configure App TLV Value information";
          type string;
        }
      }
      leaf server-location {
        status deprecated;
        description
          "Enable CDP location server on interface";
        type empty;
      }
      leaf location {
        status deprecated;
        description
          "Exchange location information";
        type empty;
      }
    }
  }

  grouping config-interface-cdp-default-enable-grouping {
    container cdp {
      description
        "CDP interface subcommands";
      leaf enable {
        description
          "Enable CDP on interface";
        type boolean;
        default "true";
      }
      uses config-interface-cdp-tlv-grouping;
    }
  }

  grouping config-interface-cdp-default-disable-grouping {
    container cdp {
      description
        "CDP interface subcommands";
      leaf enable {
        description
          "Enable CDP on interface";
        type boolean;
        default "false";
      }
      uses config-interface-cdp-tlv-grouping;
    }
  }

  grouping config-cdp-grouping {
    leaf holdtime {
      description
        "Specify the holdtime (in sec) to be sent in packets";
      type uint8 {
        range "10..255";
      }
    }
    leaf timer {
      description
        "Specify the rate at which CDP packets are sent (in sec)";
      type uint8 {
        range "5..254";
      }
    }
    leaf run-enable {
      description
        "Enable CDP";
      type boolean;
      default "true";
    }
    leaf run {
      status deprecated;
      description
        "Enable CDP, deprecated and replaced by run-enable";
      type empty;
    }
    list tlv-list {
      description
        "Configure tlv-list";
      key "name";
      leaf name {
        description
          "Tlv-list";
        type string {
          length "1..40" {
            error-message "Tlv-list name should not exceed 40 character";
          }
        }
      }
      leaf version {
        description
          "Select version TLV";
        type empty;
      }
      leaf vtp-mgmt-domain {
        description
          "Select vtp mgmt domain TLV";
        type empty;
      }
      leaf cos {
        description
          "Select cos TLV";
        type empty;
      }
      leaf duplex {
        description
          "Select duplex TLV";
        type empty;
      }
      leaf trust {
        description
          "Select trust TLV";
        type empty;
      }
    }
    leaf filter-tlv-list {
      description
        "Apply tlv-list globally";
      must '/ios:native/ios:cdp/ios-cdp:tlv-list[ios-cdp:name=current()]' {
        error-message "tlv-list must be created first";
      }
      must "/ios:native/ios:cdp/ios-cdp:run-enable = 'true'" {
        error-message "Cannot enable CDP filter ,since CDP is not running";
      }
      type string {
        length "1..40" {
          error-message "Tlv-list name should not exceed 40 character";
        }
      }
    }
  }

  augment "/ios:native/ios:cdp" {
    uses config-cdp-grouping;
  }

  augment "/ios:native/ios:interface/ios:BDI" {
    uses config-interface-cdp-default-enable-grouping;
  }

  augment "/ios:native/ios:interface/ios:FastEthernet" {
    uses config-interface-cdp-default-enable-grouping;
  }

  augment "/ios:native/ios:interface/ios:GigabitEthernet" {
    uses config-interface-cdp-default-enable-grouping;
  }

  augment "/ios:native/ios:interface/ios:TenGigabitEthernet" {
    uses config-interface-cdp-default-enable-grouping;
  }

  augment "/ios:native/ios:interface/ios:FiveGigabitEthernet" {
    uses config-interface-cdp-default-enable-grouping;
  }

  augment "/ios:native/ios:interface/ios:AppGigabitEthernet" {
    uses config-interface-cdp-default-enable-grouping;
  }

  augment "/ios:native/ios:interface/ios:TwentyFiveGigE" {
    uses config-interface-cdp-default-enable-grouping;
  }

  augment "/ios:native/ios:interface/ios:TwoGigabitEthernet" {
    uses config-interface-cdp-default-enable-grouping;
  }

  augment "/ios:native/ios:interface/ios:FortyGigabitEthernet" {
    uses config-interface-cdp-default-enable-grouping;
  }

  augment "/ios:native/ios:interface/ios:HundredGigE" {
    uses config-interface-cdp-default-enable-grouping;
  }

  augment "/ios:native/ios:interface/ios:Tunnel" {
    uses config-interface-cdp-default-disable-grouping;
  }

  augment "/ios:native/ios:interface/ios:Virtual-Template" {
    uses config-interface-cdp-default-enable-grouping;
  }

  augment "/ios:native/ios:interface/ios:Dialer" {
    uses config-interface-cdp-default-enable-grouping;
  }

  augment "/ios:native/ios:interface/ios:Serial" {
    uses config-interface-cdp-default-enable-grouping;
  }
}
