module Cisco-IOS-XE-mpls-te-oper {
  yang-version 1.1;
  namespace "http://cisco.com/ns/yang/Cisco-IOS-XE-mpls-te-oper";
  prefix mpls-te-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for MPLS traffic engineering operational data.
     Copyright (c) 2018-2021 by Cisco Systems, Inc.
     All rights reserved.";

  revision 2021-07-01 {
    description
      "Initial revision";
    reference
      "1.0.0";
    cisco-semver:module-version "1.0.0";
  }

  typedef te-slsp-role {
    type enumeration {
      enum te-slsp-role-head {
        value 0;
        description
          "Traffic engineering sub LSP role head";
      }
      enum te-slsp-role-mid {
        value 1;
        description
          "Traffic engineering sub LSP role mid";
      }
      enum te-slsp-role-tail {
        value 2;
        description
          "Traffic engineering sub LSP role tail";
      }
    }
    description
      "TE sub LSP role";
  }

  typedef te-slsp-state {
    type enumeration {
      enum te-slsp-state-discon {
        value 0;
        description
          "TE sub LSP state disconnected";
      }
      enum te-slsp-state-con {
        value 1;
        description
          "TE sub LSP role connected";
      }
    }
    description
      "Traffic engineering sub LSP state";
  }

  typedef te-slsp-frr-state {
    type enumeration {
      enum te-slsp-frr-state-none {
        value 0;
        description
          "TE sub LSP FRR state none";
      }
      enum te-slsp-frr-state-enabled {
        value 1;
        description
          "TE sub LSP FRR state enabled";
      }
      enum te-slsp-frr-state-ready {
        value 2;
        description
          "TE sub LSP FRR state ready";
      }
      enum te-slsp-frr-state-active {
        value 3;
        description
          "TE sub LSP FRR state active";
      }
    }
    description
      "TE sub LSP FRR state";
  }

  typedef te-slsp-ero-type {
    type enumeration {
      enum te-slsp-ero-type-strict {
        value 0;
        description
          "Sub LSP explicit route object type strict";
      }
      enum te-slsp-ero-type-loose {
        value 1;
        description
          "Sub LSP explicit route object type state loose";
      }
    }
    description
      "TE sub LSP explicit route object type";
  }

  typedef te-he-lsp-mode {
    type enumeration {
      enum te-he-lsp-mode-working {
        value 0;
        description
          "TE HE LSP mode working";
      }
      enum te-he-lsp-mode-working-reopt {
        value 1;
        description
          "TE HE LSP mode working re-optimization";
      }
      enum te-he-lsp-mode-working-clean {
        value 2;
        description
          "TE HE LSP mode working clean";
      }
      enum te-he-lsp-mode-protect {
        value 3;
        description
          "TE HE LSP mode protect";
      }
      enum te-he-lsp-mode-protect-reopt {
        value 4;
        description
          "TE HE LSP mode protect re-optimization";
      }
      enum te-he-lsp-mode-protect-clean {
        value 5;
        description
          "TE HE LSP mode protect clean";
      }
    }
    description
      "Traffic engineering head-end mode";
  }

  typedef te-he-lsp-fail-reason {
    type enumeration {
      enum te-he-lsp-fail-none {
        value 0;
        description
          "TE HE LSP fail reason none";
      }
      enum te-he-lsp-fail-generic {
        value 1;
        description
          "TE HE LSP fail reason generic";
      }
      enum te-he-lsp-fail-misconfig {
        value 2;
        description
          "TE HE LSP fail reason mis-config";
      }
      enum te-he-lsp-fail-already {
        value 3;
        description
          "TE HE LSP fail already";
      }
      enum te-he-lsp-fail-reopt {
        value 4;
        description
          "TE HE LSP fail re-optimization";
      }
      enum te-he-lsp-fail-abort-install {
        value 5;
        description
          "TE HE LSP fail reason abort install";
      }
      enum te-he-lsp-fail-all-shut {
        value 6;
        description
          "TE HE LSP fail all shut";
      }
      enum te-he-lsp-fail-vif-shut {
        value 7;
        description
          "TE HE LSP fail virtual interface shut";
      }
      enum te-he-lsp-fail-popt-decfg {
        value 8;
        description
          "TE HE LSP fail path opt de-cfg";
      }
      enum te-he-lsp-fail-popt-recfg {
        value 9;
        description
          "TE HE LSP fail reason path opt re-cfg";
      }
      enum te-he-lsp-fail-vif-src-chg {
        value 10;
        description
          "TE LSP fail reason virtual interface src change";
      }
      enum te-he-lsp-fail-no-path {
        value 11;
        description
          "TE HE LSP fail reason no path";
      }
      enum te-he-lsp-fail-verify {
        value 12;
        description
          "TE HE LSP fail verify";
      }
      enum te-he-lsp-fail-frr-verify {
        value 13;
        description
          "TE HE LSP fail reason FRR verify";
      }
      enum te-he-lsp-fail-max-metric {
        value 14;
        description
          "TE HE LSP fail reason max metric";
      }
      enum te-he-lsp-fail-timeout {
        value 15;
        description
          "TE HE LSP fail reason timeout";
      }
      enum te-he-lsp-fail-patherr {
        value 16;
        description
          "TE HE LSP fail reason path error";
      }
      enum te-he-lsp-fail-remerge-patherr {
        value 17;
        description
          "TE HE LSP fail reason re-merge path error";
      }
      enum te-he-lsp-fail-frr-patherr {
        value 18;
        description
          "TE HE LSP fail reason FRR path error";
      }
      enum te-he-lsp-fail-param-adj {
        value 19;
        description
          "TE HE LSP fail reason parameter adj";
      }
      enum te-he-lsp-fail-param-cfg {
        value 20;
        description
          "TE HE LSP fail reason parameter cfg";
      }
      enum te-he-lsp-fail-pathtear {
        value 21;
        description
          "TE HE LSP fail reason path tear";
      }
      enum te-he-lsp-fail-sso-failure {
        value 22;
        description
          "TE HE LSP fail reason SSO failure";
      }
      enum te-he-lsp-fail-frr-active {
        value 23;
        description
          "TE HE LSP fail reason FRR active";
      }
      enum te-he-lsp-fail-preempt {
        value 24;
        description
          "TE HE LSP fail reason preempt";
      }
      enum te-he-lsp-fail-resv-del {
        value 25;
        description
          "TE HE LSP fail reason del";
      }
      enum te-he-lsp-fail-path-out {
        value 26;
        description
          "TE HE LSP fail reason path out";
      }
      enum te-he-lsp-fail-path-del {
        value 27;
        description
          "TE HE LSP fail reason path del";
      }
      enum te-he-lsp-fail-dest-list-disassoc {
        value 28;
        description
          "TE fail reason destination list disassociated";
      }
      enum te-he-lsp-fail-popt-not-ready {
        value 29;
        description
          "TE HE LSP fail reason path-opt not ready";
      }
      enum te-he-lsp-fail-p2mp-reopt-graft {
        value 30;
        description
          "TE fail reason point-2-multi-point re-opt graft";
      }
    }
    description
      "Traffic engineering head-end LSP fail reason";
  }

  typedef te-he-lsp-elect-reason {
    type enumeration {
      enum te-he-lsp-elect-none {
        value 0;
        description
          "TE HE LSP elect reason none";
      }
      enum te-he-lsp-elect-new-cur {
        value 1;
        description
          "TE HE LSP elect new current";
      }
      enum te-he-lsp-elect-reopt {
        value 2;
        description
          "TE HE LSP elect re-optimization";
      }
      enum te-he-lsp-elect-sso-recover {
        value 3;
        description
          "TE HE LSP elect SSO recover";
      }
      enum te-he-lsp-elect-backup {
        value 4;
        description
          "TE HE LSP elect backup";
      }
      enum te-he-lsp-elect-multilsp {
        value 5;
        description
          "TE HE LSP elect multi LSP";
      }
      enum te-he-lsp-elect-restore {
        value 6;
        description
          "TE HE LSP elect restore";
      }
      enum te-he-lsp-elect-lockout {
        value 7;
        description
          "TE HE LSP elect lockout";
      }
      enum te-he-lsp-elect-non-revert {
        value 8;
        description
          "TE HE LSP elect reason non revert";
      }
    }
    description
      "Traffic engineering head-end LSP elect reason";
  }

  typedef te-he-lsp-state {
    type enumeration {
      enum te-he-lsp-state-down {
        value 0;
        description
          "TE HE LSP state down";
      }
      enum te-he-lsp-state-sig-proceeding {
        value 1;
        description
          "TE HE LSP state signalling proceeding";
      }
      enum te-he-lsp-state-bfd-proceeding {
        value 2;
        description
          "TE HE LSP state BFD proceeding";
      }
      enum te-he-lsp-state-con {
        value 3;
        description
          "TE HE LSP state connected";
      }
      enum te-he-lsp-state-active {
        value 4;
        description
          "TE HE LSP state active";
      }
    }
    description
      "Traffic engineering head-end LSP state";
  }

  typedef te-he-tunnel-state {
    type enumeration {
      enum tun-state-admin-down {
        value 0;
        description
          "TE HE tunnel state admin down";
      }
      enum tun-state-down {
        value 1;
        description
          "TE HE tunnel state down";
      }
      enum tun-state-up {
        value 2;
        description
          "TE HE tunnel state up";
      }
      enum tun-state-fa-hold-up {
        value 3;
        description
          "TE HE tunnel state FA hold up";
      }
    }
    description
      "Traffic engineering head-end tunnel state";
  }

  typedef te-he-tunnel-fail-reason {
    type enumeration {
      enum fail-reason-unapplicable {
        value 0;
        description
          "TE HE tunnel fail reason un-applicable";
      }
      enum fail-reason-shutdown {
        value 1;
        description
          "TE HE tunnel fail reason shutdown";
      }
      enum fail-reason-no-dest {
        value 2;
        description
          "TE HE tunnel fail reason no destination";
      }
      enum fail-reason-no-pathoption {
        value 3;
        description
          "TE HE tunnel fail reason no path option";
      }
      enum fail-reason-no-source {
        value 4;
        description
          "TE HE tunnel fail reason no source";
      }
      enum fail-reason-collaborator-disc {
        value 5;
        description
          "TE HE tunnel fail reason collaborator disc";
      }
      enum fail-reason-unmatch-ctype-priority {
        value 6;
        description
          "TE HE fail reason unmatched class-type priority";
      }
      enum fail-reason-invalid-bidir-cfg {
        value 7;
        description
          "TE HE fail reason invalid bidirectional cfg";
      }
      enum fail-reason-po-switchover {
        value 8;
        description
          "TE HE tunnel fail reason PO switch over";
      }
      enum fail-reason-no-te-he-tun-id {
        value 9;
        description
          "TE HE tunnel fail reason no HE tunnel ID";
      }
      enum fail-reason-no-link {
        value 10;
        description
          "TE HE tunnel fail reason no link";
      }
      enum fail-reason-link-shutdown {
        value 11;
        description
          "TE HE tunnel fail reason link shutdown";
      }
      enum fail-reason-link-lmp-down {
        value 12;
        description
          "TE HE tunnel fail reason link down";
      }
      enum fail-reason-src-dest-same {
        value 13;
        description
          "TE HE tunnel fail reason destination same";
      }
      enum fail-reason-otn-no-odu-level {
        value 14;
        description
          "TE HE tunnel fail reason OTN no level";
      }
      enum fail-reason-bidir-associd-missing {
        value 15;
        description
          "TE HE tunnel fail reason bidir assoc ID missing";
      }
      enum fail-reason-bfd-gal-on-unidir {
        value 16;
        description
          "TE HE fail reason BFD GAL on unidirectional";
      }
      enum fail-reason-bidir-assoc-working-err {
        value 17;
        description
          "BI direction working error";
      }
      enum fail-reason-bidir-assoc-working-dn {
        value 18;
        description
          "BI direction Working down";
      }
      enum fail-reason-bidir-assoc-standby-err {
        value 19;
        description
          "Standby error";
      }
      enum fail-reason-bidir-assoc-standby-dn {
        value 20;
        description
          "Standby down";
      }
    }
    description
      "Traffic engineering head-end tunnel fail reason";
  }

  typedef te-he-tunnel-type {
    type enumeration {
      enum te-he-tunnel-static-cfg {
        value 0;
        description
          "TE HE tunnel static config";
      }
      enum te-he-tunnel-static-cfg-master {
        value 1;
        description
          "TE HE tunnel static config master";
      }
      enum te-he-tunnel-static-cfg-member {
        value 2;
        description
          "TE HE tunnel static config member";
      }
      enum te-he-tunnel-auto-backup {
        value 3;
        description
          "TE HE tunnel auto backup";
      }
      enum te-he-tunnel-auto-onehop {
        value 4;
        description
          "TE HE tunnel auto one-hop";
      }
      enum te-he-tunnel-auto-mesh {
        value 5;
        description
          "TE HE tunnel auto mesh";
      }
      enum te-he-tunnel-auto-api {
        value 6;
        description
          "TE HE tunnel auto API";
      }
    }
    description
      "Traffic engineering head-end tunnel type";
  }

  typedef te-he-tunnel-mode-type {
    type enumeration {
      enum te-he-tunnel-type-p2p {
        value 0;
        description
          "TE HE tunnel type P2P";
      }
      enum te-he-tunnel-type-p2mp {
        value 1;
        description
          "TE HE tunnel type point 2 multi point";
      }
      enum te-he-tunnel-type-multilsp {
        value 2;
        description
          "TE HE tunnel type multi LSP";
      }
    }
    description
      "TE HE tunnel mode type";
  }

  typedef te-he-tunnel-hop-type {
    type enumeration {
      enum tun-hop-type-ip-strict {
        value 0;
        description
          "TE HE tunnel hop type IP strict";
      }
      enum tun-hop-type-ip-loose {
        value 1;
        description
          "TE HE tunnel hop type IP loose";
      }
      enum tun-hop-type-sr-label {
        value 2;
        description
          "TE HE tunnel hop type SR label";
      }
      enum tun-hop-type-sr-link {
        value 3;
        description
          "TE HE tunnel hop type SR link";
      }
      enum tun-hop-type-sr-node {
        value 4;
        description
          "TE HE tunnel hop type SR node";
      }
    }
    description
      "Traffic engineering head-end tunnel hop type";
  }

  typedef te-he-tunnel-metric-type {
    type enumeration {
      enum te-he-tunnel-metric-igp {
        value 0;
        description
          "TE HE tunnel metric IGP";
      }
      enum te-he-tunnel-metric-te {
        value 1;
        description
          "TE HE tunnel metric TE";
      }
    }
    description
      "Traffic engineering head-end tunnel metric type";
  }

  typedef te-he-pcalc-tiebreaker-type {
    type enumeration {
      enum tun-tiebreaker-not-set {
        value 0;
        description
          "TE HE tunnel tie-breaker not set";
      }
      enum tun-tiebreaker-min-fill {
        value 1;
        description
          "TE HE tunnel tie-breaker min fill";
      }
      enum tun-tiebreaker-max-fill {
        value 2;
        description
          "TE HE tunnel tie-breaker max fill";
      }
      enum tun-tiebreaker-random {
        value 3;
        description
          "TE HE tunnel tie-breaker random";
      }
    }
    description
      "Traffic engineering head-end tunnel tie-breaker type";
  }

  typedef te-he-path-inval-action {
    type enumeration {
      enum tun-path-inval-action-not-set {
        value 0;
        description
          "TE head-end path in-val action not set";
      }
      enum tun-path-inval-action-tear {
        value 1;
        description
          "TE head-end path in-val action tear";
      }
      enum tun-path-inval-action-drop {
        value 2;
        description
          "TE head-end path in-val action drop";
      }
    }
    description
      "Traffic engineering head-end path in-val action";
  }

  typedef te-he-sr-path-selection {
    type enumeration {
      enum sr-path-sel-not-set {
        value 0;
        description
          "Path selection not set";
      }
      enum sr-path-sel-adj-unprotected {
        value 1;
        description
          "SR path selection adj un-protected";
      }
      enum sr-path-sel-adj-protected {
        value 2;
        description
          "SR path selection adj protected";
      }
    }
    description
      "TE head-end segment routing path selection";
  }

  typedef te-tunnel-admin-state {
    type enumeration {
      enum tun-admin-state-down {
        value 0;
        description
          "TE tunnel admin state down";
      }
      enum tun-admin-state-up {
        value 1;
        description
          "TE tunnel admin state up";
      }
      enum tun-admin-state-unknown {
        value 2;
        description
          "TE tunnel admin state unknown";
      }
    }
    description
      "TE tunnel admin state";
  }

  typedef te-tunnel-oper-state {
    type enumeration {
      enum tun-oper-down {
        value 0;
        description
          "TE tunnel oper state down";
      }
      enum tun-oper-up {
        value 1;
        description
          "TE tunnel oper state up";
      }
    }
    description
      "TE tunnel oper state";
  }

  typedef te-tunnel-path {
    type enumeration {
      enum tun-path-not-valid {
        value 0;
        description
          "TE tunnel path not valid";
      }
      enum tun-path-valid {
        value 1;
        description
          "TE tunnel path valid";
      }
      enum tun-path-pending {
        value 2;
        description
          "TE tunnel path pending";
      }
    }
    description
      "TE tunnel path info";
  }

  typedef te-tunnel-signalling {
    type enumeration {
      enum tun-sig-down {
        value 0;
        description
          "Tunnel signalling down";
      }
      enum tun-sig-connected {
        value 1;
        description
          "Tunnel signalling connected";
      }
      enum tun-sig-waiting-for-bfd {
        value 2;
        description
          "Tunnel waiting for BFD";
      }
      enum tun-sig-waiting-for-bidir {
        value 3;
        description
          "Tunnel waiting for bidir";
      }
      enum tun-sig-disabled {
        value 4;
        description
          "Tunnel signalling disabled";
      }
      enum tun-sig-reroute-pending {
        value 5;
        description
          "Tunnel reroute pending";
      }
      enum tun-sig-pce-req-pending {
        value 6;
        description
          "Tunnel PCE request pending";
      }
      enum tun-sig-pce-reply-pending {
        value 7;
        description
          "Tunnel PCE reply pending";
      }
      enum tun-sig-rsvp-proceeding {
        value 8;
        description
          "Tunnel RSVP signal proceeding";
      }
      enum tun-sig-none {
        value 9;
        description
          "Tunnel signal none";
      }
    }
    description
      "TE tunnel signalling info";
  }

  typedef te-lm-link-agent-type {
    type enumeration {
      enum te-link-agent-none {
        value 0;
        description
          "TE LM link agent none";
      }
      enum te-link-agent-rsvp {
        value 1;
        description
          "TE LM link agent RSVP";
      }
      enum te-link-agent-static-tp {
        value 2;
        description
          "TE LM link agent static TP";
      }
    }
    description
      "TE LM link agent type";
  }

  typedef te-lm-link-igp-subnet-type {
    type enumeration {
      enum link-igp-subnet-type-unknown {
        value 0;
        description
          "TE LM link IGP subnet type unknown";
      }
      enum link-igp-subnet-type-p2-p {
        value 1;
        description
          "TE LM link IGP subnet type P2P";
      }
      enum link-igp-subnet-type-broadcast {
        value 2;
        description
          "TE LM link IGP subnet type broadcast";
      }
      enum link-igp-subnet-type-nbma {
        value 3;
        description
          "TE LM link IGP subnet type NBMA";
      }
      enum link-igp-subnet-type-p2mp {
        value 4;
        description
          "TE LM link IGP subnet type point 2 multi point";
      }
    }
    description
      "TE LM link IGP subnet type";
  }

  typedef te-lm-link-admit-method {
    type enumeration {
      enum link-admit-method-none {
        value 0;
        description
          "TE link admit method none";
      }
      enum link-admit-method-yes {
        value 1;
        description
          "TE link admit method yes";
      }
      enum link-admit-method-check-bw {
        value 2;
        description
          "TE link admit method check BW";
      }
      enum link-admit-method-alloc-bw {
        value 3;
        description
          "TE link admit method allocate BW";
      }
    }
    description
      "TE LM link admit method";
  }

  typedef te-lm-link-bcid-type {
    type enumeration {
      enum lm-link-type-mam {
        value 0;
        description
          "Link type Maximum allocation model";
      }
      enum lm-link-type-rdm {
        value 1;
        description
          "Link type R-D-M";
      }
    }
    description
      "TE link management type";
  }

  grouping te-slsp-ero-hop {
    description
      "TE sub LSP explicit route object hop";
    leaf ero-type {
      type mpls-te-ios-xe-oper:te-slsp-ero-type;
      description
        "Explicit route object type";
    }
    leaf ero-address {
      type inet:ip-address;
      description
        "Explicit route object address";
    }
  }

  grouping te-slsp-hop {
    description
      "TE sub LSP hop";
    leaf slsp-hop-interface {
      type string;
      description
        "TE sub LSP hop interface";
    }
    leaf slsp-hop-interface-id {
      type uint32;
      description
        "TE sub LSP hop interface ID";
    }
    leaf slsp-hop-label {
      type uint32;
      description
        "TE sub LSP hop label";
    }
  }

  grouping te-sub-lsp-key {
    description
      "TE sub LSP key";
    leaf slsp-source-address {
      type inet:ip-address;
      description
        "TE sub LSP source address";
    }
    leaf slsp-destination-address {
      type inet:ip-address;
      description
        "TE sub LSP destination address";
    }
    leaf slsp-tunnel-id {
      type uint16;
      description
        "TE sub LSP tunnel ID";
    }
    leaf slsp-lsp-id {
      type uint16;
      description
        "TE sub LSP ID";
    }
    leaf slsp-extended-ip-address {
      type inet:ip-address;
      description
        "TE sub LSP extended IP address";
    }
    leaf slsp-p2mp-id {
      type uint32;
      description
        "TE sub LSP point 2 multi-point ID";
    }
    leaf slsp-p2mp-grp-id {
      type uint32;
      description
        "TE sub LSP point to multi-point group ID";
    }
    leaf slsp-p2mp-grp-origin {
      type uint32;
      description
        "TE sub LSP point 2 multi-point group origin";
    }
  }

  grouping te-sub-lsp {
    description
      "TE sub LSP";
    leaf slsp-role {
      type mpls-te-ios-xe-oper:te-slsp-role;
      description
        "TE sub LSP role";
    }
    leaf slsp-state {
      type mpls-te-ios-xe-oper:te-slsp-state;
      description
        "TE sub LSP state";
    }
    container slsp-ingress-hop {
      description
        "TE sub LSP ingress hop";
      uses mpls-te-ios-xe-oper:te-slsp-hop;
    }
    container slsp-egress-hop {
      description
        "TE sub LSP egress hop";
      uses mpls-te-ios-xe-oper:te-slsp-hop;
    }
    leaf slsp-frr-state {
      type mpls-te-ios-xe-oper:te-slsp-frr-state;
      description
        "TE sub LSP FRR state";
    }
    leaf slsp-frr-backup-tunnel-id {
      type uint16;
      description
        "TE sub LSP FRR backup tunnel ID";
    }
    leaf slsp-frr-backup-label {
      type uint32;
      description
        "TE sub LSP FRR backup label";
    }
    leaf slsp-frr-mergepoint-label {
      type uint32;
      description
        "TE sub LSP FRR merge point label";
    }
    leaf slsp-bandwidth-kbps {
      type uint32;
      units "kbps";
      description
        "TE sub LSP bandwidth";
    }
    list ero-hop {
      description
        "Explicit route object hop";
      uses mpls-te-ios-xe-oper:te-slsp-ero-hop;
    }
  }

  grouping te-he-tunnel-counters {
    description
      "TE head-end tunnel counters";
    leaf path-err-no-route {
      type uint32;
      description
        "TE path error no route";
    }
    leaf path-err-bad-label {
      type uint32;
      description
        "TE path error bad label";
    }
    leaf path-err-adminstrative {
      type uint32;
      description
        "TE path error administrative";
    }
    leaf path-err-no-bandwidth {
      type uint32;
      description
        "TE path error no bandwidth";
    }
    leaf path-err-bad-strict-node {
      type uint32;
      description
        "TE path error bad strict node";
    }
    leaf path-err-bad-loose-node {
      type uint32;
      description
        "TE path error bad loose node";
    }
    leaf path-err-rro-loop {
      type uint32;
      description
        "TE path error loop";
    }
    leaf path-err-bad-ero {
      type uint32;
      description
        "TE path error bad explicit route object";
    }
    leaf path-change {
      type uint32;
      description
        "TE path change";
    }
    leaf state-change {
      type uint32;
      description
        "TE state change";
    }
    leaf admin-down {
      type uint32;
      description
        "TE admin down";
    }
    leaf oper-down {
      type uint32;
      description
        "TE oper down";
    }
    leaf missing-explicit-path {
      type uint32;
      description
        "TE missing explicit path";
    }
    leaf no-path {
      type uint32;
      description
        "TE no path";
    }
    leaf path-lookups {
      type uint32;
      description
        "TE path lookups";
    }
    leaf invalid-path {
      type uint32;
      description
        "TE invalid path";
    }
    leaf protect-path-opt-cfg-err {
      type uint32;
      description
        "Protection path option config error";
    }
    leaf protection-path-opt-error {
      type uint32;
      description
        "Protection path option error";
    }
    leaf sig-timeout {
      type uint32;
      description
        "Signal timeout";
    }
    leaf sig-bad-path {
      type uint32;
      description
        "Signal bad path";
    }
    leaf sig-abort {
      type uint32;
      description
        "Signal abort";
    }
    leaf sig-ok {
      type uint32;
      description
        "Signal OK";
    }
    leaf frr-activated {
      type uint32;
      description
        "Fast re-route activated";
    }
    leaf wrap-activated {
      type uint32;
      description
        "Wrap activated";
    }
    leaf loose-path-reopt {
      type uint32;
      description
        "Loose path re-opt";
    }
    leaf p2mp-remerge {
      type uint32;
      description
        "Point to multi-point re-merge";
    }
    leaf other {
      type uint32;
      description
        "Other";
    }
    leaf autobw-adjustment {
      type uint32;
      description
        "Auto bandwidth adjustment";
    }
    leaf autobw-overflow {
      type uint32;
      description
        "Auto bandwidth overflow";
    }
    leaf sso-recover-attempts {
      type uint32;
      description
        "SSO recover attempts";
    }
    leaf sso-recover-success {
      type uint32;
      description
        "SSO recover success";
    }
    leaf sso-recover-failures {
      type uint32;
      description
        "SSO recover failures";
    }
  }

  grouping te-he-tunnel-history {
    description
      "TE head-end tunnel history";
    leaf prev-lsp-instance {
      type int32;
      description
        "Previous LSP instance";
    }
    leaf prev-lsp-remove-reason {
      type mpls-te-ios-xe-oper:te-he-lsp-fail-reason;
      description
        "Previous LSP remove reason";
    }
    leaf elect-reason {
      type mpls-te-ios-xe-oper:te-he-lsp-elect-reason;
      description
        "Elect reason";
    }
  }

  grouping te-he-tunnel-bundle {
    description
      "TE head-end tunnel bundle";
    leaf bundle-name {
      type string;
      description
        "TE tunnel bundle name";
    }
    leaf exp-bits {
      type uint16;
      description
        "TE bundle exp bits";
    }
    leaf nonexp-bits {
      type uint16;
      description
        "TE bundle non-exp bits";
    }
    leaf-list member-id {
      type uint16;
      ordered-by user;
      description
        "TE bundle member tunnel ID";
    }
  }

  grouping te-he-tunnel-hop {
    description
      "TE head-end tunnel hop";
    leaf hop-type {
      type mpls-te-ios-xe-oper:te-he-tunnel-hop-type;
      description
        "TE tunnel hop type";
    }
    leaf next-ip {
      type inet:ip-address;
      description
        "TE tunnel next hop IP address";
    }
    leaf local-ip {
      type inet:ip-address;
      description
        "TE tunnel hop local IP address";
    }
    leaf label {
      type uint32;
      description
        "TE tunnel hop label";
    }
  }

  grouping te-he-tunnel-slsp {
    description
      "TE head-end tunnel sub LSP";
    container slsp-key {
      description
        "TE tunnel sub LSP key";
      uses mpls-te-ios-xe-oper:te-sub-lsp-key;
    }
    leaf up-timestamp {
      type yang:date-and-time;
      description
        "TE tunnel sub LSP up-time";
    }
    leaf path-option-idx {
      type uint32;
      description
        "TE tunnel sub LSP path option";
    }
    list hop {
      description
        "TE tunnel sub LSP hops";
      uses mpls-te-ios-xe-oper:te-he-tunnel-hop;
    }
  }

  grouping te-he-tunnel-lsp {
    description
      "TE head-end tunnel LSP";
    leaf tunnel-lsp-state {
      type mpls-te-ios-xe-oper:te-he-lsp-state;
      description
        "TE tunnel LSP state";
    }
    leaf tunnel-lsp-mode {
      type mpls-te-ios-xe-oper:te-he-lsp-mode;
      description
        "TE tunnel LSP mode";
    }
    leaf tunnel-lsp-fail-reason {
      type mpls-te-ios-xe-oper:te-he-lsp-fail-reason;
      description
        "TE tunnel LSP fail reason";
    }
    leaf tunnel-lsp-uptime {
      type yang:date-and-time;
      description
        "TE tunnel LSP up-time";
    }
    list tunnel-lsp-slsps {
      description
        "TE tunnel LSP sub-LSP";
      uses mpls-te-ios-xe-oper:te-he-tunnel-slsp;
    }
  }

  grouping te-he-tunnel-auto-bw-info {
    description
      "TE head-end tunnel auto bandwidth information";
    leaf auto-bw-kbps-last {
      type uint32;
      description
        "TE auto bandwidth KBPS last";
    }
    leaf auto-bw-kbps-highest {
      type uint32;
      description
        "TE auto bandwidth KBPS highest";
    }
    leaf auto-bw-overflow-cnt {
      type uint32;
      description
        "TE auto bandwidth overflow count";
    }
  }

  grouping te-he-tunnel {
    description
      "TE head-end tunnel";
    leaf tunnel-id {
      type uint16;
      description
        "TE head-end tunnel ID";
    }
    leaf tunnel-name {
      type string;
      description
        "TE head-end tunnel name";
    }
    leaf tunnel-type {
      type mpls-te-ios-xe-oper:te-he-tunnel-type;
      description
        "TE tunnel type";
    }
    leaf tunnel-mode-type {
      type mpls-te-ios-xe-oper:te-he-tunnel-mode-type;
      description
        "TE tunnel mode type";
    }
    leaf dest-ip {
      type inet:ip-address;
      description
        "TE tunnel destination IP";
    }
    leaf admin-state {
      type mpls-te-ios-xe-oper:te-tunnel-admin-state;
      description
        "TE tunnel admin status";
    }
    leaf oper-state {
      type mpls-te-ios-xe-oper:te-tunnel-oper-state;
      description
        "TE tunnel oper status";
    }
    leaf path {
      type mpls-te-ios-xe-oper:te-tunnel-path;
      description
        "TE tunnel oper path value";
    }
    leaf signalling {
      type mpls-te-ios-xe-oper:te-tunnel-signalling;
      description
        "TE tunnel signalling details";
    }
    leaf tunnel-inst {
      type uint32;
      description
        "Number of TE tunnel instances";
    }
    container tunnel-bundle {
      description
        "TE tunnel bundle";
      uses mpls-te-ios-xe-oper:te-he-tunnel-bundle;
    }
    leaf create-time {
      type yang:date-and-time;
      description
        "TE tunnel create time";
    }
    leaf path-chg-time {
      type yang:date-and-time;
      description
        "TE tunnel path change time";
    }
    leaf tunnel-state {
      type mpls-te-ios-xe-oper:te-he-tunnel-state;
      description
        "TE tunnel state";
    }
    container tunnel-counters {
      description
        "TE tunnel counters";
      uses mpls-te-ios-xe-oper:te-he-tunnel-counters;
    }
    leaf last-fail-reason {
      type mpls-te-ios-xe-oper:te-he-tunnel-fail-reason;
      description
        "TE tunnel last fail reason";
    }
    leaf last-deactivate-reason {
      type mpls-te-ios-xe-oper:te-he-lsp-fail-reason;
      description
        "TE tunnel last de-activate reason";
    }
    container tunnel-history {
      description
        "TE tunnel history";
      uses mpls-te-ios-xe-oper:te-he-tunnel-history;
    }
    list tun-lsp {
      description
        "TE tunnel LSP";
      uses mpls-te-ios-xe-oper:te-he-tunnel-lsp;
    }
    leaf cfg-bw-kbps {
      type uint32;
      units "kbps";
      description
        "TE tunnel config bandwidth KBPS";
    }
    leaf request-bw-kbps {
      type uint32;
      units "kbps";
      description
        "TE tunnel request bandwidth KBPS";
    }
    leaf bw-sub-pool {
      type boolean;
      description
        "TE tunnel bandwidth sub pool";
    }
    container auto-bw-inf {
      description
        "TE tunnel auto bandwidth";
      uses mpls-te-ios-xe-oper:te-he-tunnel-auto-bw-info;
    }
    leaf auto-bw-enabled {
      type boolean;
      description
        "TE tunnel auto bandwidth enabled";
    }
    leaf auto-bw-minimum {
      type uint32;
      description
        "TE tunnel auto bandwidth minimum";
    }
    leaf auto-bw-maximum {
      type uint32;
      description
        "TE tunnel auto bandwidth maximum";
    }
    leaf bw-adjmnt-threshold {
      type uint32;
      description
        "Tunnel auto bandwidth threshold";
    }
    leaf bw-adjmnt-interval {
      type uint32;
      description
        "Tunnel auto bandwidth adjustment interval";
    }
    leaf bw-ovrflow-enabled {
      type boolean;
      description
        "Tunnel auto bandwidth overflow enabled";
    }
    leaf bw-ovrflow-threshold {
      type uint32;
      description
        "Tunnel auto bandwidth overflow threshold";
    }
    leaf bw-ovrflow-trigr-cnt {
      type uint32;
      description
        "Tunnel auto bandwidth overflow trigger count";
    }
    leaf setup-priority {
      type uint8;
      description
        "TE tunnel setup priority";
    }
    leaf hold-priority {
      type uint8;
      description
        "TE tunnel hold priority";
    }
    leaf affinity-val {
      type uint32;
      description
        "TE tunnel affinity value";
    }
    leaf affinity-mask {
      type uint32;
      description
        "TE tunnel affinity mask";
    }
    leaf tunnel-metric-type {
      type mpls-te-ios-xe-oper:te-he-tunnel-metric-type;
      description
        "TE tunnel metric type";
    }
    leaf metric-value {
      type uint32;
      description
        "TE tunnel metric value";
    }
    leaf tunnel-loadshare {
      type uint32;
      description
        "TE tunnel load-share";
    }
    leaf autoroute-announce-en {
      type boolean;
      description
        "Tunnel autoroute announce enabled";
    }
    leaf autoroute-announce {
      type boolean;
      description
        "Tunnel auto route announce";
    }
    leaf announce-fwdng-adj-en {
      type boolean;
      description
        "Tunnel announce forwarding adjacency enabled";
    }
    leaf announce-fwdng-adj {
      type boolean;
      description
        "Tunnel announce forwarding adjacency";
    }
    leaf announce-dest-en {
      type boolean;
      description
        "Tunnel announce destination enabled";
    }
    leaf announce-dest {
      type boolean;
      description
        "Tunnel announce destination";
    }
    leaf frr-enabled {
      type boolean;
      description
        "TE fast re-route enabled";
    }
    leaf frr-bw-protect {
      type boolean;
      description
        "TE fast re-route bandwidth protect";
    }
    leaf frr-node-protect {
      type boolean;
      description
        "TE fast re-route node protect";
    }
    leaf tunnel-rro {
      type boolean;
      description
        "TE tunnel record route object";
    }
    leaf pcalc-tiebreaker {
      type mpls-te-ios-xe-oper:te-he-pcalc-tiebreaker-type;
      description
        "TE tunnel path calculate tie-breaker";
    }
    leaf pcalc-hop-limit {
      type uint8;
      description
        "TE path calculate hop limit";
    }
    leaf pcalc-cost-limit {
      type uint32;
      description
        "TE path calculate cost limit";
    }
    leaf down-delay-secs {
      type uint32;
      description
        "TE tunnel down delay seconds";
    }
    leaf fa-hold-secs {
      type uint32;
      description
        "TE tunnel hold seconds";
    }
    leaf inval-action {
      type mpls-te-ios-xe-oper:te-he-path-inval-action;
      description
        "TE tunnel action";
    }
    leaf sr-binding-sid {
      type uint32;
      description
        "TE tunnel segment routing binding ID";
    }
    leaf sr-path-type {
      type mpls-te-ios-xe-oper:te-he-sr-path-selection;
      description
        "TE tunnel segment routing path type";
    }
  }

  grouping te-lm-sub-lsp {
    description
      "TE link management sub LSP";
    leaf te-lm-slsp-not-used {
      type uint16;
      description
        "TE link management sub LSP not used";
    }
  }

  grouping te-lm-link-bw-thresholds {
    description
      "TE link management bandwidth threshold";
    leaf-list link-bw-up-thresholds {
      type uint8;
      ordered-by user;
      description
        "TE link bandwidth up threshold";
    }
    leaf-list link-bw-down-thresholds {
      type uint8;
      ordered-by user;
      description
        "TE link bandwidth down threshold";
    }
  }

  grouping te-lm-bw-pool-value {
    description
      "TE link management bandwidth pool value";
    leaf pool-bw-held {
      type uint64;
      description
        "TE pool bandwidth held";
    }
    leaf pool-bw-total-held {
      type uint64;
      description
        "TE pool bandwidth total held";
    }
    leaf pool-bw-locked {
      type uint64;
      description
        "TE pool bandwidth locked";
    }
    leaf pool-bw-total-locked {
      type uint64;
      description
        "TE pool bandwidth total locked";
    }
  }

  grouping te-lm-bw-pool {
    description
      "TE link management bandwidth pool";
    leaf bw-pool-priority {
      type uint16;
      description
        "TE bandwidth pool priority";
    }
    container bw-pool-global {
      description
        "TE bandwidth pool global";
      uses mpls-te-ios-xe-oper:te-lm-bw-pool-value;
    }
    container bw-pool-sub-pool {
      description
        "TE bandwidth pool sub pool";
      uses mpls-te-ios-xe-oper:te-lm-bw-pool-value;
    }
  }

  grouping te-lm-link {
    description
      "TE link management link";
    leaf link-handle {
      type uint32;
      description
        "TE link handle";
    }
    leaf link-name {
      type string;
      description
        "TE link name";
    }
    leaf link-ipaddress {
      type inet:ip-address;
      description
        "TE link IP-address";
    }
    leaf link-local-if-id {
      type uint32;
      description
        "TE link local interface ID";
    }
    leaf link-user-flags {
      type uint32;
      description
        "TE link user flags";
    }
    leaf link-user-admin-weight {
      type uint64;
      description
        "TE link user admin weight";
    }
    leaf link-is-lockout {
      type boolean;
      description
        "TE link is lock-out";
    }
    leaf link-lockout-on-time {
      type yang:date-and-time;
      description
        "TE link lock-out on time";
    }
    leaf link-lockout-off-time {
      type yang:date-and-time;
      description
        "TE link lock-out off time";
    }
    leaf link-agent-type {
      type mpls-te-ios-xe-oper:te-lm-link-agent-type;
      description
        "TE link agent type";
    }
    leaf link-bcid-type {
      type mpls-te-ios-xe-oper:te-lm-link-bcid-type;
      description
        "TE link B-C-I-D type";
    }
    leaf link-physical-bw {
      type uint64;
      description
        "TE link physical bandwidth";
    }
    leaf link-max-res-bw {
      type uint64;
      description
        "TE link maximum result bandwidth";
    }
    leaf link-max-res-glbl-pool-bw {
      type uint64;
      description
        "TE link maximum global pool bandwidth";
    }
    leaf link-max-res-sub-pool-bw {
      type uint64;
      description
        "TE Link maximum sub pool bandwidth";
    }
    container link-bw-thresholds {
      description
        "TE link bandwidth threshold";
      uses mpls-te-ios-xe-oper:te-lm-link-bw-thresholds;
    }
    leaf link-flow-bw-min {
      type uint64;
      description
        "TE link flow bandwidth minimum";
    }
    leaf link-flow-bw-max {
      type uint64;
      description
        "TE link flow bandwidth maximum";
    }
    leaf link-mtu {
      type uint16;
      description
        "TE link MTU";
    }
    leaf link-uplink-admit-method {
      type mpls-te-ios-xe-oper:te-lm-link-admit-method;
      description
        "TE up-link admit method";
    }
    leaf link-downlink-admit-method {
      type mpls-te-ios-xe-oper:te-lm-link-admit-method;
      description
        "TE down-link admit method";
    }
    leaf link-igp-admin-weight {
      type uint32;
      description
        "TE link IGP admin weight";
    }
    leaf link-igp-nbrs-flooded {
      type uint16;
      description
        "TE link IGP neighbors flooded";
    }
    leaf link-igp-nbr-count {
      type uint16;
      description
        "TE link IGP neighbor count";
    }
    leaf link-igp-subnet-type {
      type mpls-te-ios-xe-oper:te-lm-link-igp-subnet-type;
      description
        "TE link IGP subnet type";
    }
    list mpls-te-link-bw-pool {
      key "bw-pool-priority";
      description
        "TE link bandwidth pool";
      uses mpls-te-ios-xe-oper:te-lm-bw-pool;
    }
    list mpls-te-link-ingress-slsp {
      key "slsp-source-address slsp-destination-address slsp-tunnel-id slsp-lsp-id slsp-extended-ip-address slsp-p2mp-id slsp-p2mp-grp-id slsp-p2mp-grp-origin";
      description
        "TE link ingress sub-LSP";
      uses mpls-te-ios-xe-oper:te-sub-lsp-key;
      uses mpls-te-ios-xe-oper:te-lm-sub-lsp;
    }
    list mpls-te-link-egress-slsp {
      key "slsp-source-address slsp-destination-address slsp-tunnel-id slsp-lsp-id slsp-extended-ip-address slsp-p2mp-id slsp-p2mp-grp-id slsp-p2mp-grp-origin";
      description
        "TE link egress sub-LSP";
      uses mpls-te-ios-xe-oper:te-sub-lsp-key;
      uses mpls-te-ios-xe-oper:te-lm-sub-lsp;
    }
  }

  container mpls-te-oper-data {
    config false;
    description
      "MPLS TE operational data";
    list mpls-te-sub-lsp {
      key "slsp-source-address slsp-destination-address slsp-tunnel-id slsp-lsp-id slsp-extended-ip-address slsp-p2mp-id slsp-p2mp-grp-id slsp-p2mp-grp-origin";
      description
        "MPLS TE sub LSP data";
      uses mpls-te-ios-xe-oper:te-sub-lsp-key;
      uses mpls-te-ios-xe-oper:te-sub-lsp;
    }
    list mpls-te-tunnel {
      key "tunnel-id";
      description
        "MPLS traffic engineering tunnel information";
      uses mpls-te-ios-xe-oper:te-he-tunnel;
    }
    list mpls-te-link {
      key "link-handle";
      description
        "MPLS traffic engineering link information";
      uses mpls-te-ios-xe-oper:te-lm-link;
    }
  }
}
