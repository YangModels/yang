module Cisco-IOS-XE-service-insertion-oper {
  yang-version 1.1;
  namespace "http://cisco.com/ns/yang/Cisco-IOS-XE-service-insertion-oper";
  prefix si-ios-xe-oper;

  import Cisco-IOS-XE-appqoe-types {
    prefix appqoe-types-ios-xe;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for service-insertion operational data.
     Copyright (c) 2020-2021 by Cisco Systems, Inc.
     All rights reserved.";

  revision 2021-07-01 {
    description
      "- Added support for AppQoE sub service status";
    reference
      "1.1.0";
    cisco-semver:module-version "1.1.0";
  }
  revision 2020-11-01 {
    description
      "Initial revision";
    reference
      "1.0.0";
    cisco-semver:module-version "1.0.0";
  }

  grouping si-sn-type {
    description
      "Service node details";
    leaf lan-ip {
      type inet:ip-address;
      description
        "LAN IP address of service node";
    }
    leaf system-ip {
      type inet:ip-address;
      description
        "System IP address of service node";
    }
    leaf site-id {
      type uint32;
      description
        "Site ID of service node";
    }
    leaf status {
      type appqoe-types-ios-xe:appqoe-sn-status;
      description
        "Service node status";
    }
    leaf error-message {
      when "(../status!='sn-status-green')";
      type string;
      description
        "Error message from service node";
    }
    leaf sng-name {
      type string;
      description
        "Service node group name";
    }
    list appqoe-service {
      key "service";
      description
        "AppQoE services and status on the service node";
      uses appqoe-types-ios-xe:appqoe-service;
    }
  }

  grouping si-appqoe-cluster {
    description
      "Service insertion AppQoE";
    leaf device-mode {
      type appqoe-types-ios-xe:appqoe-device-mode;
      description
        "Device mode";
    }
    list si-sn-type {
      key "lan-ip";
      description
        "List of service nodes";
      uses si-ios-xe-oper:si-sn-type;
    }
  }

  container service-insertion-oper-data {
    config false;
    description
      "service-insertion operational data";
    container si-appqoe-cluster {
      presence "si-appqoe-cluster";
      description
        "service-insertion type appqoe";
      uses si-ios-xe-oper:si-appqoe-cluster;
    }
  }
}
