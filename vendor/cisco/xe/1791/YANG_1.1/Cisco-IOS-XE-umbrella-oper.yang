module Cisco-IOS-XE-umbrella-oper {
  yang-version 1.1;
  namespace "http://cisco.com/ns/yang/Cisco-IOS-XE-umbrella-oper";
  prefix umbrella-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains collection of YANG
     definitions for Umbrella operational data.
     Copyright (c) 2018-2019 by Cisco Systems, Inc.
     All rights reserved.";

  revision 2019-05-01 {
    description
      "Added semantic version";
    reference
      "1.1.0";
    cisco-semver:module-version "1.1.0";
  }
  revision 2018-04-19 {
    description
      "Initial revision";
    reference
      "1.0.0";
    cisco-semver:module-version "1.0.0";
  }

  grouping umbrella-dev-reg-data {
    description
      "Umbrella Device Registration Data";
    leaf name {
      type string;
      description
        "Name of the device";
    }
    leaf status {
      type string;
      description
        "Registration status";
    }
    leaf tag {
      type string;
      description
        "Device Tag";
    }
    leaf device-id {
      type string;
      description
        "Device Identifier";
    }
    leaf description {
      type string;
      description
        "Device Registration Description";
    }
  }

  grouping umbrella-overview {
    description
      "Overview of Umbrella";
    leaf registrations-completed {
      type uint16;
      description
        "Number of registrations completed";
    }
    leaf registrations-requested {
      type uint16;
      description
        "Number of registrations requested";
    }
    leaf dnscrypt {
      type boolean;
      description
        "State of DNSCrypt";
    }
    leaf last-success-attempt {
      type yang:date-and-time;
      description
        "Last successful attempt for DNSCrypt";
    }
  }

  container umbrella-ios-oper-data {
    config false;
    description
      "Operational data of Umbrella";
    list umbrella-dev-reg-data {
      key "name";
      description
        "Umbrella Device Registration Data";
      uses umbrella-ios-xe-oper:umbrella-dev-reg-data;
    }
    container umbrella-overview {
      presence "umbrella-overview";
      description
        "Overview of Umbrella";
      uses umbrella-ios-xe-oper:umbrella-overview;
    }
  }
}
