submodule Cisco-IOS-XE-ospf-rpc {
  yang-version 1.1;
  belongs-to Cisco-IOS-XE-rpc {
    prefix ios-xe-rpc;
  }

  import cisco-semver {
    prefix cisco-semver;
  }

  organization
    "Cisco Systems";
  contact
    "<mailto:cs-yang@cisco.com>";
  description
    "NED OSPF RPC YANG module for IOS
     Copyright (c) 2016-2019 by Cisco Systems, Inc.
     All rights reserved.";

  revision 2019-07-01 {
    description
      "Establish semantic version baseline";
    cisco-semver:module-version "1.0.0";
  }
  revision 2018-12-06 {
    description
      "created for NED RPC modularisation";
  }

  grouping clear-choice-ip-case-ip-protocol-ospf-case-grouping {
    container ospf {
      leaf id-drop-node-name {
        description
          "Process ID number";
        type uint16;
      }
      leaf process {
        description
          "Reset OSPF process";
        type empty;
      }
    }
  }
}
