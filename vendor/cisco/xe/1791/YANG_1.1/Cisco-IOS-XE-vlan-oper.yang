module Cisco-IOS-XE-vlan-oper {
  yang-version 1.1;
  namespace "http://cisco.com/ns/yang/Cisco-IOS-XE-vlan-oper";
  prefix vlan-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     monitoring vlans in a Network Element.
     Copyright (c) 2016-2017, 2019 by Cisco Systems, Inc.
     All rights reserved.";

  revision 2019-05-01 {
    description
      "Added semantic version";
    reference
      "2.2.0";
    cisco-semver:module-version "2.2.0";
  }
  revision 2018-10-29 {
    description
      "Cleaned up spelling errors in descriptions.";
    reference
      "2.1.0";
    cisco-semver:module-version "2.1.0";
  }
  revision 2018-04-09 {
    description
      "vlan interfaces container added under vlan members";
    reference
      "2.0.0";
    cisco-semver:module-version "2.0.0";
  }
  revision 2017-05-05 {
    description
      "Initial revision";
    reference
      "1.0.0";
    cisco-semver:module-version "1.0.0";
  }

  typedef vlan-status-type {
    type enumeration {
      enum active {
        value 0;
      }
      enum suspend {
        value 1;
      }
    }
    description
      "Operational state of the VLAN";
  }

  grouping vlan-members-interface {
    description
      "Assigned ports to the given  VLAN";
    leaf interface {
      type string;
      description
        "Assigned interface to the vlan";
    }
    leaf subinterface {
      type uint32;
      description
        "Assigned subinterface to the vlan";
    }
  }

  grouping interfaces {
    description
      "Assigned ports to this VLAN";
    leaf interface {
      type string;
      description
        "Assigned interface";
    }
    leaf subinterface {
      type uint32;
      description
        "Assigned subinterface";
    }
  }

  grouping vlan-members {
    description
      "List of VLAN information";
    leaf id {
      type uint16;
      description
        "VLAN id";
    }
    leaf name {
      type string;
      description
        "VLAN name";
    }
    leaf status {
      type vlan-ios-xe-oper:vlan-status-type;
      description
        "VLAN status";
    }
    list ports {
      description
        "Assigned ports";
      uses vlan-ios-xe-oper:interfaces;
    }
    list vlan-interfaces {
      key "interface";
      description
        "List of interfaces for a given VLAN";
      uses vlan-ios-xe-oper:vlan-members-interface;
    }
  }

  container vlans {
    config false;
    description
      "Information about VLANs";
    list vlan {
      key "id";
      description
        "List of VLANs, keyed by id";
      uses vlan-ios-xe-oper:vlan-members;
    }
  }
}
