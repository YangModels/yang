module Cisco-IOS-XE-banner-internal {
  yang-version 1.1;
  namespace "http://cisco.com/ns/yang/Cisco-IOS-XE-banner-internal";
  prefix ios-banner-internal;

  import Cisco-IOS-XE-native {
    prefix ios;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "NED YANG module for IOS-XE.
     Copyright (c) 2019-2020 by Cisco Systems, Inc.
     All rights reserved.";

  revision 2020-07-01 {
    description
      "Initial revision";
    cisco-semver:module-version "1.0.0";
  }

  grouping config-internal-banner-grouping {
    leaf internal-banner {
      description
        "Banner message";
      type string;
    }
  }

  augment "/ios:native/ios:banner/ios:exec" {
    uses config-internal-banner-grouping;
  }

  augment "/ios:native/ios:banner/ios:login" {
    uses config-internal-banner-grouping;
  }

  augment "/ios:native/ios:banner/ios:prompt-timeout" {
    uses config-internal-banner-grouping;
  }

  augment "/ios:native/ios:banner/ios:motd" {
    uses config-internal-banner-grouping;
  }
}
