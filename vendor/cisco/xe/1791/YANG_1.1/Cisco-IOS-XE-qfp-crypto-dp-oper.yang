module Cisco-IOS-XE-qfp-crypto-dp-oper {
  yang-version 1.1;
  namespace "http://cisco.com/ns/yang/Cisco-IOS-XE-qfp-crypto-dp-oper";
  prefix crypto-dp-oper-ios-xe;

  import Cisco-IOS-XE-common-types {
    prefix common-types-ios-xe;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for crypto datapath operational data.
     Copyright (c) 2020-2021 by Cisco Systems, Inc.
     All rights reserved.";

  revision 2022-03-01 {
    description
      "Initial revision";
    reference
      "1.0.0";
    cisco-semver:module-version "1.0.0";
  }

  typedef crypto-dp-ipsec-state-msg-type {
    type enumeration {
      enum ipsec-state-msg-init-msg {
        value 0;
        description
          "Crypto datapath IPSEC state init message";
      }
      enum ipsec-state-msg-spd-create {
        value 1;
        description
          "Crypto datapath IPSEC state SPD create";
      }
      enum ipsec-state-msg-spd-delete {
        value 2;
        description
          "Crypto datapath IPSEC state SPD delete";
      }
      enum ipsec-state-msg-spd-if-bind {
        value 3;
        description
          "Crypto datapath IPSEC state SPD interface bind";
      }
      enum ipsec-state-msg-spd-cm-bind {
        value 4;
        description
          "Crypto datapath IPSEC state SPD cm bind";
      }
      enum ipsec-state-msg-spd-if-unbind {
        value 5;
        description
          "Crypto datapath IPSEC state SPD interface unbind";
      }
      enum ipsec-state-msg-spd-cm-unbind {
        value 6;
        description
          "Crypto datapath IPSEC state SPD  unbind";
      }
      enum ipsec-state-msg-spd-unbind {
        value 7;
        description
          "Crypto datapath IPSEC state SPD unbind";
      }
      enum ipsec-state-msg-sp-create {
        value 8;
        description
          "Crypto datapath IPSEC state SP create";
      }
      enum ipsec-state-msg-sp-remove {
        value 9;
        description
          "Crypto datapath IPSEC state SP remove";
      }
      enum ipsec-state-msg-cac-create {
        value 10;
        description
          "Crypto datapath IPSEC state CAC create";
      }
      enum ipsec-state-msg-cac-remove {
        value 11;
        description
          "Crypto datapath IPSEC state CAC remove";
      }
      enum ipsec-state-msg-sa-bind {
        value 12;
        description
          "Crypto datapath IPSEC state SA bind";
      }
      enum ipsec-state-msg-sa-unbind {
        value 13;
        description
          "Crypto datapath IPSEC state SA unbind";
      }
      enum ipsec-state-msg-deny-obj-add {
        value 14;
        description
          "Crypto datapath IPSEC state deny object add";
      }
      enum ipsec-state-msg-deny-obj-remove {
        value 15;
        description
          "Crypto datapath IPSEC state deny object remove";
      }
      enum ipsec-state-msg-denyjump-obj-add {
        value 16;
        description
          "Crypto datapath IPSEC state deny jump object add";
      }
      enum ipsec-state-msg-denyjump-obj-remove {
        value 17;
        description
          "Crypto datapath IPSEC state deny jump object remove";
      }
      enum ipsec-state-msg-out-sa-add {
        value 18;
        description
          "Crypto datapath IPSEC state out SA add";
      }
      enum ipsec-state-msg-out-sa-remove {
        value 19;
        description
          "Crypto datapath IPSEC state out SA remove";
      }
      enum ipsec-state-msg-in-sa-add {
        value 20;
        description
          "Crypto datapath IPSEC state in SA add";
      }
      enum ipsec-state-msg-in-sa-remove {
        value 21;
        description
          "Crypto datapath IPSEC state in SA remove";
      }
      enum ipsec-state-msg-sa-nest {
        value 22;
        description
          "Crypto datapath IPSEC state SA nest";
      }
      enum ipsec-state-msg-sa-unnest {
        value 23;
        description
          "Crypto datapath IPSEC state SA un-nest";
      }
      enum ipsec-state-msg-sa-inout-bind {
        value 24;
        description
          "Crypto datapath IPSEC state SA in out bind";
      }
      enum ipsec-state-msg-sa-resolve {
        value 25;
        description
          "Crypto datapath IPSEC state SA resolve";
      }
      enum ipsec-state-msg-sa-unresolve {
        value 26;
        description
          "Crypto datapath IPSEC state SA unresolve";
      }
      enum ipsec-state-msg-intf-enable {
        value 27;
        description
          "Crypto datapath IPSEC state interface enable";
      }
      enum ipsec-state-msg-intf-disable {
        value 28;
        description
          "Crypto datapath IPSEC state interface disable";
      }
      enum ipsec-state-msg-intf-update {
        value 29;
        description
          "Crypto datapath IPSEC state interface update";
      }
      enum ipsec-state-msg-sa-info-get {
        value 30;
        description
          "Crypto datapath IPSEC state sa information get";
      }
      enum ipsec-state-msg-sa-stats-get {
        value 31;
        description
          "Crypto datapath IPSEC state SA stats get";
      }
      enum ipsec-state-msg-intf-stats-get {
        value 32;
        description
          "Crypto datapath IPSEC state interface stats get";
      }
      enum ipsec-state-msg-cli-get {
        value 33;
        description
          "Crypto datapath IPSEC state CLI get";
      }
      enum ipsec-state-msg-sa-update {
        value 34;
        description
          "Crypto datapath IPSEC state SA update";
      }
      enum ipsec-state-msg-uninit-msg {
        value 35;
        description
          "Crypto datapath IPSEC state uninitialized";
      }
      enum ipsec-state-msg-ike-msg {
        value 36;
        description
          "Crypto datapath IPSEC state IKE message";
      }
      enum ipsec-state-msg-ted-initiate-msg {
        value 37;
        description
          "Crypto datapath IPSEC state TED initiate";
      }
      enum ipsec-state-msg-ted-catcher-msg {
        value 38;
        description
          "Crypto datapath IPSEC state TED catcher";
      }
      enum ipsec-state-msg-sa-timer-expiry-msg {
        value 39;
        description
          "Crypto datapath IPSEC state SA timer expiry";
      }
      enum ipsec-state-msg-sa-traffic-expiry {
        value 40;
        description
          "Crypto datapath IPSEC state SA traffic expiry";
      }
      enum ipsec-state-msg-restart-msg {
        value 41;
        description
          "Crypto datapath IPSEC state restart";
      }
      enum ipsec-state-msg-sa-remove-done-msg {
        value 42;
        description
          "Crypto datapath IPSEC state SA remove done";
      }
      enum ipsec-state-msg-bulk-sa-stats {
        value 43;
        description
          "Crypto datapath IPSEC state bulk SA stats";
      }
      enum ipsec-state-msg-bind2crypto {
        value 44;
        description
          "Crypto datapath IPSEC state bind to crypto";
      }
      enum ipsec-state-msg-unbind2crypto {
        value 45;
        description
          "Crypto datapath IPSEC state unbind to crypto";
      }
      enum ipsec-state-msg-llq-qos-enable {
        value 46;
        description
          "Crypto datapath IPSEC state LLQ QOS enable";
      }
      enum ipsec-state-msg-llq-qos-disable {
        value 47;
        description
          "Crypto datapath IPSEC state LLQ QOS disable";
      }
      enum ipsec-state-msg-cgm-begin-batch {
        value 48;
        description
          "Crypto datapath IPSEC state CGM begin batch";
      }
      enum ipsec-state-msg-cgm-end-batch {
        value 49;
        description
          "Crypto datapath IPSEC state CGM end batch";
      }
      enum ipsec-state-msg-tunnel-protect {
        value 50;
        description
          "Crypto datapath IPSEC state tunnel protect";
      }
      enum ipsec-state-msg-invalid-spi-enable {
        value 51;
        description
          "Crypto datapath IPSEC state invalid SPI enable";
      }
      enum ipsec-state-msg-invalid-spi-disable {
        value 52;
        description
          "Crypto datapath IPSEC state invalid SPI disable";
      }
      enum ipsec-state-msg-invalid-spi-notif {
        value 53;
        description
          "Crypto datapath IPSEC state invalid SPI notification";
      }
      enum ipsec-state-msg-seqno-overflow {
        value 54;
        description
          "Crypto datapath IPSEC state sequence number overflow";
      }
      enum ipsec-state-msg-out-sa-add-bind {
        value 55;
        description
          "Crypto datapath IPSEC state out SA add bind";
      }
      enum ipsec-state-msg-out-sa-unbind-del {
        value 56;
        description
          "Crypto datapath IPSEC state out SA unbind delete";
      }
      enum ipsec-state-msg-bulk-sa-update {
        value 57;
        description
          "Crypto datapath IPSEC state bulk SA update";
      }
      enum ipsec-state-msg-gdoi-mcast-set {
        value 58;
        description
          "Crypto datapath IPSEC state GDOI multicast set";
      }
      enum ipsec-state-msg-fips-bypass-err {
        value 59;
        description
          "Crypto datapath IPSEC state FIPS bypass error notification";
      }
      enum ipsec-state-msg-llq-qos-grp {
        value 60;
        description
          "Crypto datapath IPSEC state LLQ QOS Group";
      }
      enum ipsec-state-msg-reass-msg {
        value 61;
        description
          "Crypto datapath IPSEC state reassign";
      }
      enum ipsec-state-msg-crypto-device-event {
        value 62;
        description
          "Crypto datapath IPSEC state crypto device event";
      }
      enum ipsec-state-msg-gdoi-legacy-msg {
        value 63;
        description
          "Crypto datapath IPSEC state GDOI legacy";
      }
      enum ipsec-state-msg-supress-arlog-msg {
        value 64;
        description
          "Crypto datapath IPSEC state suppress ARLOG";
      }
      enum ipsec-state-msg-pwk-invalid-spi-msg {
        value 65;
        description
          "Crypto datapath IPSEC state pair wise invalid SPI";
      }
      enum ipsec-state-msg-pwk-first-spi-msg {
        value 66;
        description
          "Crypto datapath IPSEC pair wise first SPI";
      }
    }
    description
      "Crypto datapath IPSEC state message type";
  }

  grouping crypto-dp-ipsec-state-data {
    description
      "Crypto datapath IPSEC state data";
    leaf msg-type {
      type crypto-dp-oper-ios-xe:crypto-dp-ipsec-state-msg-type;
      description
        "Message type";
    }
    leaf rx-cnt {
      type uint64;
      description
        "RX packet count";
    }
    leaf tx-eok-cnt {
      type uint64;
      description
        "TX good packet count";
    }
    leaf tx-error-cnt {
      type uint64;
      description
        "TX error packet count";
    }
  }

  grouping crypto-dp-ipsec-state {
    description
      "Crypto datapath IPSEC state";
    list ipsec-state {
      description
        "IPSEC state";
      uses crypto-dp-oper-ios-xe:crypto-dp-ipsec-state-data;
    }
  }

  container qfp-crypto-dp-oper-data {
    config false;
    description
      "Crypto datapath operational data";
    list location {
      key "fru slot bay chassis node";
      description
        "A list of data provider locations";
      uses common-types-ios-xe:extended-location;
      container crypto-dp-ipsec-state {
        presence "crypto-dp-ipsec-state";
        description
          "Crypto datapath IPSEC state";
        uses crypto-dp-oper-ios-xe:crypto-dp-ipsec-state;
      }
    }
  }
}
