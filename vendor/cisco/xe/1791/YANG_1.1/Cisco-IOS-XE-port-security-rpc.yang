module Cisco-IOS-XE-port-security-rpc {
  yang-version 1.1;
  namespace "http://cisco.com/ns/yang/Cisco-IOS-XE-port-security-rpc";
  prefix port-security-ios-actions-rpc;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for clear port security action data.
     Copyright (c) 2021 by Cisco Systems, Inc.
     All rights reserved.";

  revision 2022-03-01 {
    description
      "Initial revision";
    reference
      "1.0.0";
    cisco-semver:module-version "1.0.0";
  }

  typedef ps-mode {
    type enumeration {
      enum md-all {
        value 0;
        description
          "All secure MAC addresses.";
      }
      enum md-configured {
        value 1;
        description
          "Configured secure MAC addresses.";
      }
      enum md-sticky {
        value 2;
        description
          "Secure MAC address either auto-learned or configured.";
      }
      enum md-dynamic {
        value 3;
        description
          "Secure MAC address auto-learned by hardware.";
      }
    }
    description
      "Clear port security mode options.";
  }

  typedef ps-if-type {
    type enumeration {
      enum if-fast-eth {
        value 0;
        description
          "Fast ethernet.";
      }
      enum if-gb-eth {
        value 1;
        description
          "Gigabit ethernet.";
      }
      enum if-2gb-eth {
        value 2;
        description
          "Two gigabit ethernet.";
      }
      enum if-5gb-eth {
        value 3;
        description
          "Five gigabit ethernet.";
      }
      enum if-appgb-eth {
        value 4;
        description
          "App gigabit ethernet.";
      }
      enum if-10gb-eth {
        value 5;
        description
          "Ten gigabit ethernet.";
      }
      enum if-25gb-eth {
        value 6;
        description
          "Twenty five gigabit ethernet.";
      }
      enum if-40gb-eth {
        value 7;
        description
          "Forty gigabit ethernet.";
      }
      enum if-100gb-eth {
        value 8;
        description
          "Hundred gigabit ethernet.";
      }
      enum if-port-channel {
        value 9;
        description
          "Port channel";
      }
    }
    description
      "Clear port security interface type options.";
  }

  typedef ps-if-addr-choice-type {
    type enumeration {
      enum ps-if {
        value 0;
        description
          "Choice to clear interface ports.";
      }
      enum ps-if-vlan-access {
        value 1;
        description
          "Choice to clear interface ports with access.";
      }
      enum ps-if-vlan-voice {
        value 2;
        description
          "Choice to clear interface ports with voice.";
      }
      enum ps-if-vlan-trunk {
        value 3;
        description
          "Choice to clear interface ports with VLAN trunk.";
      }
      enum ps-mac-address {
        value 4;
        description
          "Choice to clear MAC address.";
      }
      enum ps-none {
        value 5;
        description
          "Default, if none of interface and address is selected";
      }
    }
    description
      "Clear port choice between interface and address.";
  }

  grouping ps-if-name-type {
    description
      "Parameter to select interface type and enter the name of interface.";
    leaf if-type {
      type port-security-ios-actions-rpc:ps-if-type;
      mandatory true;
      description
        "Option for selecting one of the interface types.";
    }
    leaf if-name {
      type string {
        length "1..256";
      }
      mandatory true;
      description
        "Interface number or name.";
    }
  }

  grouping ps-vlan-spec {
    description
      "List for VLAN id or VLAN range for clearing port security.";
    leaf start-id {
      type uint16;
      default "0";
      description
        "Start of range or a single VLAN ID or left at zero/empty to ignore.";
    }
    leaf end-id {
      type uint16;
      default "0";
      description
        "END of range or left at zero if an individual VLAN ID is specified.";
    }
  }

  grouping ps-if {
    description
      "Parameter to select interface.";
    container if-name-type {
      description
        "Parameter used to select interface (name,type).";
      uses port-security-ios-actions-rpc:ps-if-name-type;
    }
  }

  grouping ps-if-vlan-access {
    description
      "Parameter to select interface with vlan access.";
    container if-with-access {
      description
        "Parameter for selecting interface (name,type) with access.";
      uses port-security-ios-actions-rpc:ps-if-name-type;
    }
    leaf access {
      type boolean;
      default "true";
      description
        "To select access, default is true.";
    }
  }

  grouping ps-if-vlan-voice {
    description
      "Parameter used to select interface and vlan voice.";
    container if-with-voice {
      description
        "Parameter for selecting interface (name,type) with voice.";
      uses port-security-ios-actions-rpc:ps-if-name-type;
    }
    leaf voice {
      type boolean;
      default "true";
      description
        "To select voice,default is true.";
    }
  }

  grouping ps-if-vlan-trunk {
    description
      "Parameter used to select an interface port with VLAN trunk enabled.";
    container if-with-trunk {
      description
        "Parameter for selecting interface (name,type) with VLAN trunk enabled.";
      uses port-security-ios-actions-rpc:ps-if-name-type;
    }
    list vlan-trunk {
      description
        "VLAN id or VLAN range with VLAN trunk enabled. Left empty for clearing port security from all VLAN.";
      uses port-security-ios-actions-rpc:ps-vlan-spec;
    }
  }

  grouping ps-mac-addr {
    description
      "Parameter used to enter MAC address and VLAN id or VLAN range.";
    leaf mac-address {
      type yang:mac-address;
      mandatory true;
      description
        "Parameter for entering MAC address.";
    }
    list vlan {
      description
        "VLAN id or VLAN range with VLAN trunk enabled. Left empty for clearing port security from all VLAN.";
      uses port-security-ios-actions-rpc:ps-vlan-spec;
    }
  }

  grouping clear-port-security {
    description
      "Parameters to select various options for clearing port security from interfaces or MAC address.";
    leaf mode {
      type port-security-ios-actions-rpc:ps-mode;
      mandatory true;
      description
        "Selecting mode for port security clear operation, all/configured/dynamic/sticky.";
    }
    choice if-addr-choice {
      default "ps-none";
      description
        "Choice to select interface with various options or MAC address.";
      case ps-if {
        container intf {
          description
            "Clear port security from an interface using interface name and type.";
          uses port-security-ios-actions-rpc:ps-if;
        }
      }
      case ps-if-vlan-access {
        container vlan-access {
          description
            "Clear port security from an interface port, that has access enabled.";
          uses port-security-ios-actions-rpc:ps-if-vlan-access;
        }
      }
      case ps-if-vlan-voice {
        container vlan-voice {
          description
            "Clear port security from an interface port, that has voice enabled.";
          uses port-security-ios-actions-rpc:ps-if-vlan-voice;
        }
      }
      case ps-if-vlan-trunk {
        container if-vlan-trunk {
          description
            "Clear port security from an interface port, that has trunk enabled.";
          uses port-security-ios-actions-rpc:ps-if-vlan-trunk;
        }
      }
      case ps-mac-address {
        container mac-addr {
          description
            "Clear port security from an MAC address.";
          uses port-security-ios-actions-rpc:ps-mac-addr;
        }
      }
      case ps-none {
        leaf ps-none {
          type boolean;
          default "true";
          description
            " Default when none of interface and MAC address is selected, default value is true.";
        }
      }
    }
  }

  rpc clear-port-security {
    description
      "To clear, port security applied at the interfaces or VLAN, for the following modes.
       all: all secure MAC addresses
       configured: configured secure MAC address
       dynamic: secure MAC address auto-learned by hardware
       sticky: secure MAC address either auto-learned or configured";
    input {
      uses port-security-ios-actions-rpc:clear-port-security;
    }
  }
}
