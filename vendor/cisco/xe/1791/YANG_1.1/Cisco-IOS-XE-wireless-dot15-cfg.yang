module Cisco-IOS-XE-wireless-dot15-cfg {
  yang-version 1.1;
  namespace "http://cisco.com/ns/yang/Cisco-IOS-XE-wireless-dot15-cfg";
  prefix wireless-dot15-cfg;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Model for managing 802.15 global configurations
     Copyright (c) 2019-2020 by Cisco Systems, Inc.
     All rights reserved.";

  revision 2020-07-01 {
    description
      "Initial revision";
    reference
      "1.0.0";
    cisco-semver:module-version "1.0.0";
  }

  grouping dot15-global-config {
    description
      "Global 802.15 radio configuration";
    leaf global-radio-shut {
      type boolean;
      default "true";
      description
        "Global 802.15 radio switch";
    }
  }

  container dot15-cfg-data {
    description
      "yang model for 802.15 config";
    container dot15-global-config {
      presence "dot15-global-config";
      description
        "802.15 global configuration";
      uses wireless-dot15-cfg:dot15-global-config;
    }
  }
}
