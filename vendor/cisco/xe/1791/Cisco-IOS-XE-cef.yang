module Cisco-IOS-XE-cef {
  namespace "http://cisco.com/ns/yang/Cisco-IOS-XE-cef";
  prefix ios-cef;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Cisco Express Forwarding (CEF) Yang model.
     Copyright (c) 2016-2017, 2019 by Cisco Systems, Inc.
     All rights reserved.";

  revision 2022-07-01 {
    description
      "- Migrate to new ip/ipv6 cef model to address various config issues
       - Deprecated old ip/ipv6 cef model
       - Restore and obsolete key-control container in old ip/ipv6 cef model";
    cisco-semver:module-version "3.0.0";
  }
  revision 2022-03-01 {
    description
      "- Added CEF source only load balancing hashing algorithm type.
       - Changed handling of ip[v6] cef distributed command";
    cisco-semver:module-version "2.1.0";
  }
  revision 2019-11-01 {
    description
      "- Added obsolete/deprecated status for child node when parent was
         already obsolete/deprecated";
    cisco-semver:module-version "2.0.0";
  }
  revision 2019-07-01 {
    description
      "Establish semantic version baseline";
    cisco-semver:module-version "1.0.0";
  }
  revision 2018-11-07 {
    description
      "Cleanup spelling errors in description statements";
  }
  revision 2017-05-19 {
    description
      "fix ip cef ip cef load-sharing algorithm include-ports configurations";
  }
  revision 2017-03-01 {
    description
      "Completion of cef table and ip cef configurations";
  }
  revision 2017-02-07 {
    description
      "Initial revision";
  }

  typedef fixed-id {
    description
      "<1-FFFFFFFF>  Fixed ID";
    type string {
      pattern '[0-9a-fA-F]{1,8}';
    }
  }

  grouping config-af-cef-ldshr-alg-incl-ports-grouping {
    container include-ports-v2 {
      description
        "Algorithm that includes layer 4 ports";
      leaf source {
        type empty;
      }
      leaf destination {
        type empty;
      }
      leaf gtp {
        when '../source and ../destination';
        must '../source and ../destination' {
          error-message "Must have source and destination enabled for GTP";
        }
        type empty;
      }
      leaf fixed-id {
        when '../source or ../destination or ../gtp';
        type fixed-id;
      }
    }
  }

  grouping config-af-cef-ldshr-alg-tun-grouping {
    container tunnel-v2 {
      description
        "Algorithm for use in tunnel only environments";
      leaf tunnel {
        type empty;
      }
      leaf fixed-id {
        type fixed-id;
      }
    }
  }

  grouping config-af-cef-ldshr-alg-uni-grouping {
    container universal-v2 {
      description
        "Algorithm for use in most environments";
      leaf universal {
        type empty;
      }
      leaf fixed-id {
        type fixed-id;
      }
    }
  }

  grouping config-af-cef-ldshr-alg-src-only-grouping {
    container src-only-v2 {
      description
        "Algorithm that uses Src Addr Only";
      leaf src-only {
        type empty;
      }
      leaf fixed-id {
        type fixed-id;
      }
    }
  }

  grouping config-af-cef-ldshr-alg-orig-grouping {
    container original-v2 {
      description
        "Original algorithm";
      leaf original {
        type empty;
      }
    }
  }

  grouping config-v4-cef-load-sharing-grouping {
    container load-sharing-v2 {
      description
        "Load sharing";
      container algorithm-v2 {
        choice alg-type {
          case universal {
            uses config-af-cef-ldshr-alg-uni-grouping;
          }
          case tunnel {
            uses config-af-cef-ldshr-alg-tun-grouping;
          }
          case original {
            uses config-af-cef-ldshr-alg-orig-grouping;
          }
          case src-only {
            uses config-af-cef-ldshr-alg-src-only-grouping;
          }
          case include-ports {
            uses config-af-cef-ldshr-alg-incl-ports-grouping;
          }
        }
      }
    }
  }

  grouping config-v6-cef-load-sharing-grouping {
    container load-sharing-v2 {
      description
        "Load sharing";
      container algorithm-v2 {
        choice alg-type {
          case universal {
            uses config-af-cef-ldshr-alg-uni-grouping;
          }
          case original {
            uses config-af-cef-ldshr-alg-orig-grouping;
          }
          case src-only {
            uses config-af-cef-ldshr-alg-src-only-grouping;
          }
          case include-ports {
            uses config-af-cef-ldshr-alg-incl-ports-grouping;
          }
        }
      }
    }
  }

  grouping config-v4-cef-trfc-stats-grouping {
    container traffic-statistics-v2 {
      description
        "Enable collection of ipv4 traffic statistics";
      leaf load-interval-v2 {
        description
          "Specify interval for load calculation";
        type uint16 {
          range "30..600";
        }
      }
      leaf update-rate-v2 {
        description
          "Specify update rate for non-recursive prefix stats";
        type uint16 {
          range "0..65535";
        }
      }
    }
  }

  grouping config-v6-cef-trfc-stats-grouping {
    container traffic-statistics-v2 {
      description
        "Enable collection of ipv6 traffic statistics";
      leaf load-interval-v2 {
        description
          "Specify interval for load calculation";
        type uint16 {
          range "30..600";
        }
      }
      leaf update-rate-v2 {
        description
          "Specify update rate for non-recursive prefix stats";
        type uint16 {
          range "0..65535";
        }
      }
    }
  }

  grouping config-af-cef-acnt-opt-grouping {
    container accounting-v2 {
      description
        "Enable CEF accounting";
      leaf per-prefix-v2 {
        description
          "Enable per prefix accounting";
        type empty;
      }
      leaf non-recursive-v2 {
        description
          "Enable accounting for traffic through non-recursive prefixes";
        type empty;
      }
      leaf prefix-length-v2 {
        description
          "Enable prefix length accounting";
        type empty;
      }
      leaf load-balance-hash-v2 {
        description
          "Enable load balance hash accounting";
        type empty;
      }
    }
  }

  grouping config-af-cef-optimization-opt-grouping {
    container optimize-v2 {
      description
        "Optimizations";
      container neighbor-v2 {
        description
          "Optimizations for directly connected neighbors";
        leaf resolution-v2 {
          description
            "Trigger layer 2 address resolution directly from CEF";
          type boolean;
          default "true";
        }
      }
    }
  }

  grouping config-af-cef-dist-grouping {
    leaf distributed-boolean-v2 {
      description
        "Distributed Cisco Express Forwarding";
      type boolean;
      default "true";
    }
  }

  grouping config-af-cef-grouping {
    uses config-af-cef-acnt-opt-grouping;
    uses config-af-cef-dist-grouping;
    uses config-af-cef-optimization-opt-grouping;
  }

  grouping config-ip-cef-grouping {
    description
      "Cisco Express Forwarding for IPv4";
    uses config-af-cef-grouping;
    uses config-v4-cef-trfc-stats-grouping;
    uses config-v4-cef-load-sharing-grouping;
  }

  grouping config-ipv6-cef-grouping {
    description
      "Cisco Express Forwarding for IPv6";
    uses config-af-cef-grouping;
    uses config-v6-cef-trfc-stats-grouping;
    uses config-v6-cef-load-sharing-grouping;
  }

  grouping config-cef-tbl-cnst-chk-opt-types-scan-opt-grouping {
    container scan-opt {
      leaf count {
        description
          "Maximum number of prefixes to check per scan";
        type uint16 {
          range "2..10000";
        }
      }
      leaf period {
        description
          "Period between scans";
        type uint16 {
          range "30..3600";
        }
      }
    }
  }

  grouping config-cef-tbl-cnst-chk-opt-v4-types-grouping {
    container scan-ios-rib {
      description
        "Passive scan that checks RP tables against RIB";
      uses config-cef-tbl-cnst-chk-opt-types-scan-opt-grouping;
    }
    container scan-rib-ios {
      description
        "Passive scan that checks RIB against RP tables";
      uses config-cef-tbl-cnst-chk-opt-types-scan-opt-grouping;
    }
    container scan-lc-rp {
      description
        "Passive scan that checks LC tables against RP tables";
      uses config-cef-tbl-cnst-chk-opt-types-scan-opt-grouping;
    }
    container scan-rp-lc {
      description
        "Passive scan that checks RP tables against LC tables";
      uses config-cef-tbl-cnst-chk-opt-types-scan-opt-grouping;
    }
    leaf lc-detect {
      description
        "Linecard detects missing prefix. Confirmed by RP";
      type empty;
    }
  }

  grouping config-cef-tbl-cnst-chk-opt-v6-types-grouping {
    container scan-ios-rib {
      description
        "Passive scan that checks RP tables against RIB";
      uses config-cef-tbl-cnst-chk-opt-types-scan-opt-grouping;
    }
    container scan-lc-rp {
      description
        "Passive scan that checks LC tables against RP tables";
      uses config-cef-tbl-cnst-chk-opt-types-scan-opt-grouping;
    }
    container scan-rp-lc {
      description
        "Passive scan that checks RP tables against LC tables";
      uses config-cef-tbl-cnst-chk-opt-types-scan-opt-grouping;
    }
    leaf lc-detect {
      description
        "Linecard detects missing prefix. Confirmed by RP";
      type empty;
    }
  }

  grouping config-cef-tbl-cnst-chk-opt-v4-common-grouping {
    container auto-repair {
      description
        "Control auto-repair function";
      leaf delay {
        description
          "Delay in seconds";
        type uint16 {
          range "10..300";
        }
      }
      leaf holddown {
        description
          "Delay in seconds";
        type uint16 {
          range "300..3000";
        }
      }
    }
    container type {
      description
        "Type of consistency check to configure";
      uses config-cef-tbl-cnst-chk-opt-v4-types-grouping;
    }
    leaf data-checking {
      description
        "Perform data consistency check";
      type empty;
    }
    leaf error-message {
      description
        "Generate error message on inconsistency detection";
      type empty;
    }
  }

  grouping config-cef-tbl-cnst-chk-opt-v6-common-grouping {
    container auto-repair {
      description
        "Control auto-repair function";
      leaf delay {
        description
          "Delay in seconds";
        type uint16 {
          range "10..300";
        }
      }
      leaf holddown {
        description
          "Delay in seconds";
        type uint16 {
          range "300..3000";
        }
      }
    }
    container type {
      description
        "Type of consistency check to configure";
      uses config-cef-tbl-cnst-chk-opt-v6-types-grouping;
    }
    leaf data-checking {
      description
        "Perform data consistency check";
      type empty;
    }
    leaf error-message {
      description
        "Generate error message on inconsistency detection";
      type empty;
    }
  }

  grouping config-cef-tbl-dl-rt-type-pri-grouping {
    container priority {
      leaf priority1 {
        description
          "1st priority";
        type empty;
      }
      leaf priority2 {
        description
          "2nd priority";
        type empty;
      }
      leaf priority3 {
        description
          "3rd priority";
        type empty;
      }
      leaf priority4 {
        description
          "4th priority";
        type empty;
      }
    }
  }

  grouping config-cef-tbl-dl-rt-type-grouping {
    container catch-all {
      description
        "Any other route not matched (default P4)";
      uses config-cef-tbl-dl-rt-type-pri-grouping;
    }
    container connected-route {
      description
        "Directly connected route (default P2)";
      uses config-cef-tbl-dl-rt-type-pri-grouping;
    }
    container default-route {
      description
        "Default route, 0.0.0.0/0 or ::/0 (default P1)";
      uses config-cef-tbl-dl-rt-type-pri-grouping;
    }
    container receive-route {
      description
        "Receive route, local address on router (default P2)";
      uses config-cef-tbl-dl-rt-type-pri-grouping;
    }
    container recursive-dependents {
      description
        "Route with recursive dependents, matches next-hop
              of other recursive routes (default P1)";
      uses config-cef-tbl-dl-rt-type-pri-grouping;
    }
    container route-in-vrf {
      description
        "Route is in a VRF (default P3)";
      uses config-cef-tbl-dl-rt-type-pri-grouping;
    }
  }

  grouping config-cef-grouping {
    container cef {
      description
        "Cisco Express Forwarding";
      container table {
        description
          "Set CEF forwarding table characteristics";
        container output-chain {
          description
            "Set table output chain characteristics";
          container build {
            description
              "Set table output chain building characteristics";
            container favor {
              choice favor-choice {
                status deprecated;
                description
                  "Set which table output chain building characteristics to favor";
                leaf convergence-speed {
                  description
                    "Favor faster convergence";
                  type empty;
                }
                leaf memory-utilization {
                  description
                    "Favor smaller memory utilization";
                  type empty;
                }
              }
            }
            container indirection {
              description
                "Customize table output chain building indirection characteristics";
              leaf ipv4-to-mpls {
                description
                  "shared indirection object for IPv4 labeled prefixes";
                type empty;
              }
              leaf ipv6-to-mpls {
                description
                  "shared indirection object for IPv6 labeled prefixes";
                type empty;
              }
              leaf mpls-end-of-stack {
                description
                  "shared indirection object for MPLS disposition";
                type empty;
              }
              leaf mpls-non-end-of-stack {
                description
                  "shared indirection object for MPLS label switch";
                type empty;
              }
              leaf non-recursive-prefix {
                description
                  "non-recursive-prefix";
                type empty;
              }
              leaf recursive-prefix {
                description
                  "recursive-prefix";
                type empty;
              }
            }
            container inplace-modify {
              description
                "Customize table output chain building inplace modification characteristics";
              leaf load-sharing {
                description
                  "load sharing structures";
                type empty;
              }
              leaf push-counter {
                description
                  "push counter structures";
                type empty;
              }
            }
          }
        }
        container consistency-check {
          container ipv4 {
            description
              "IPv4 address family";
            uses config-cef-tbl-cnst-chk-opt-v4-common-grouping;
          }
          container ipv6 {
            description
              "IPv6 address family";
            uses config-cef-tbl-cnst-chk-opt-v6-common-grouping;
          }
        }
        container download {
          uses config-cef-tbl-dl-rt-type-grouping;
        }
        leaf rate-monitor-period {
          description
            "Period in minutes";
          type uint8 {
            range "1..60";
          }
        }
      }
    }
  }

  grouping config-cef-get-fixed-id-grouping-deprecated {
    leaf fixed-id {
      status deprecated;
      description
        "Fixed ID (DEPRECATED)";
      type fixed-id;
    }
  }

  grouping config-af-cef-ldshr-alg-incl-ports-grouping-deprecated {
    container include-ports {
      status deprecated;
      description
        "Algorithm that includes layer 4 ports (DEPRECATED)";
      presence "true";
      container destination {
        status deprecated;
        presence "true";
        description
          "Use destination port in hash function (DEPRECATED)";
        uses config-cef-get-fixed-id-grouping-deprecated;
      }
      container source {
        status deprecated;
        description
          "Use source port in hash function (DEPRECATED)";
        presence "true";
        container destination {
          status deprecated;
          description
            "Use source and destination ports in hash function (DEPRECATED)";
          presence "true";
          container gtp {
            status deprecated;
            presence "true";
            description
              "Use GTP te-id as source and destination ports in hash function (DEPRECATED)";
            uses config-cef-get-fixed-id-grouping-deprecated;
          }
          uses config-cef-get-fixed-id-grouping-deprecated;
        }
        uses config-cef-get-fixed-id-grouping-deprecated;
      }
    }
  }

  grouping config-af-cef-ldshr-alg-tun-grouping-deprecated {
    container tunnel {
      status deprecated;
      description
        "Algorithm for use in tunnel only environments";
      leaf tunnel {
        status deprecated;
        type empty;
      }
      uses config-cef-get-fixed-id-grouping-deprecated;
    }
  }

  grouping config-af-cef-ldshr-alg-uni-grouping-deprecated {
    container universal {
      status deprecated;
      description
        "Algorithm for use in most environments";
      leaf universal {
        status deprecated;
        type empty;
      }
      uses config-cef-get-fixed-id-grouping-deprecated;
    }
  }

  grouping config-af-cef-ldshr-alg-src-only-grouping-deprecated {
    container src-only {
      status deprecated;
      description
        "Algorithm that uses Src Addr Only (DEPRECATED)";
      leaf src-only {
        status deprecated;
        type empty;
      }
      uses config-cef-get-fixed-id-grouping-deprecated;
    }
  }

  grouping config-af-cef-ldshr-alg-orig-grouping-deprecated {
    container original {
      status deprecated;
      description
        "Original algorithm (DEPRECATED)";
      leaf original {
        status deprecated;
        type empty;
      }
    }
  }

  grouping config-v4-cef-load-sharing-grouping-deprecated {
    container load-sharing {
      status deprecated;
      description
        "Load sharing (DEPRECATED)";
      container algorithm {
        status deprecated;
        description
          "load sharing algorithm selection (DEPRECATED)";
        uses config-af-cef-ldshr-alg-uni-grouping-deprecated;
        uses config-af-cef-ldshr-alg-tun-grouping-deprecated;
        uses config-af-cef-ldshr-alg-orig-grouping-deprecated;
        uses config-af-cef-ldshr-alg-incl-ports-grouping-deprecated;
        uses config-af-cef-ldshr-alg-src-only-grouping-deprecated;
      }
      container key-control {
        status obsolete;
      }
    }
  }

  grouping config-v6-cef-load-sharing-grouping-deprecated {
    container load-sharing {
      status deprecated;
      description
        "Load sharing (DEPRECATED)";
      container algorithm {
        status deprecated;
        description
          "load sharing algorithm selection (DEPRECATED)";
        uses config-af-cef-ldshr-alg-tun-grouping-deprecated;
        uses config-af-cef-ldshr-alg-uni-grouping-deprecated;
        uses config-af-cef-ldshr-alg-orig-grouping-deprecated;
        uses config-af-cef-ldshr-alg-incl-ports-grouping-deprecated;
        uses config-af-cef-ldshr-alg-src-only-grouping-deprecated;
      }
      container key-control {
        status obsolete;
      }
    }
  }

  grouping config-af-cef-trfc-stats-grouping-deprecated {
    container traffic-statistics {
      status deprecated;
      description
        "Enable collection of traffic statistics (DEPRECATED)";
      leaf load-interval {
        status deprecated;
        description
          "Specify interval for load calculation (DEPRECATED)";
        type uint16 {
          range "30..600";
        }
      }
      leaf update-rate {
        status deprecated;
        description
          "Specify update rate for non-recursive prefix stats (DEPRECATED)";
        type uint16 {
          range "0..65535";
        }
      }
    }
  }

  grouping config-af-cef-acnt-opt-grouping-deprecated {
    container accounting {
      status deprecated;
      description
        "Enable CEF accounting (DEPRECATED)";
      leaf per-prefix {
        status deprecated;
        description
          "Enable per prefix accounting (DEPRECATED)";
        type empty;
      }
      leaf non-recursive {
        status deprecated;
        description
          "Enable accounting for traffic through non-recursive prefixes (DEPRECATED)";
        type empty;
      }
      leaf prefix-length {
        status deprecated;
        description
          "Enable prefix length accounting (DEPRECATED)";
        type empty;
      }
      leaf load-balance-hash {
        status deprecated;
        description
          "Enable load balance hash accounting (DEPRECATED)";
        type empty;
      }
    }
  }

  grouping config-af-cef-optimization-opt-grouping-deprecated {
    container optimize {
      status deprecated;
      description
        "Optimizations (DEPRECATED)";
      container neighbor {
        status deprecated;
        description
          "Optimizations for directly connected neighbors (DEPRECATED)";
        leaf resolution {
          status deprecated;
          description
            "Trigger layer 2 address resolution directly from CEF (DEPRECATED)";
          type empty;
        }
      }
    }
  }

  grouping config-af-cef-dist-grouping-deprecated {
    leaf distributed-boolean {
      status deprecated;
      description
        "Distributed Cisco Express Forwarding (DEPRECATED)";
      type boolean;
      default "true";
    }
    leaf distributed {
      status deprecated;
      description
        "Distributed Cisco Express Forwarding (DEPRECATED)";
      type empty;
    }
  }

  grouping config-af-cef-grouping-deprecated {
    uses config-af-cef-acnt-opt-grouping-deprecated;
    uses config-af-cef-dist-grouping-deprecated;
    uses config-af-cef-optimization-opt-grouping-deprecated;
    uses config-af-cef-trfc-stats-grouping-deprecated;
  }

  grouping config-ip-cef-grouping-deprecated {
    description
      "Cisco Express Forwarding for IPv4 (DEPRECATED)";
    uses config-af-cef-grouping-deprecated;
    uses config-v4-cef-load-sharing-grouping-deprecated;
  }

  grouping config-ipv6-cef-grouping-deprecated {
    description
      "Cisco Express Forwarding for IPv6 DEPRECATED";
    uses config-af-cef-grouping-deprecated;
    uses config-v6-cef-load-sharing-grouping-deprecated;
  }

  augment "/ios:native" {
    uses config-cef-grouping;
  }

  augment "/ios:native/ios:ip/ios:cef-v2" {
    uses config-ip-cef-grouping;
  }

  augment "/ios:native/ios:ip/ios:cef" {
    uses config-ip-cef-grouping-deprecated;
  }

  augment "/ios:native/ios:ipv6/ios:cef-v2" {
    uses config-ipv6-cef-grouping;
  }

  augment "/ios:native/ios:ipv6/ios:cef" {
    uses config-ipv6-cef-grouping-deprecated;
  }
}
