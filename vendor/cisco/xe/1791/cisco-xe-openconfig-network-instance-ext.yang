module cisco-xe-openconfig-network-instance-ext {
  namespace "http://cisco.com/ns/yang/cisco-xe-openconfig-network-instance-ext";
 
  prefix oc-netinst-cisco-ext;
 
  import openconfig-network-instance { prefix oc-netinst; }
  import openconfig-network-instance-types { prefix "oc-ni-types"; }
  import openconfig-interfaces { prefix "oc-if"; }
  import ietf-yang-types { prefix "yang"; }
  import cisco-semver { prefix cisco-semver; } 
  organization "Cisco Systems";
 
  description
    "Augment file for oc-network-instance";
 
  ////////////////////////////////////////////////////////////////////////////
  // REVISION
  ///////////////////////////////////////////////////////////////////////////
  revision 2021-11-01 {
    description
      "- Initial revision";
    cisco-semver:module-version "1.0.0";
  }

  grouping l2networkinstance {
    description
      "Configuration and operational state parameters relating
      to a Layer 2 network instance";
 
    container fdb {
      description
        "Operational state and configuration parameters relating to
        the forwarding database of the network instance";
 
        container config {
          description
            "Configuration parameters relating to the FDB";
          uses l2ni-fdb-mac-config;
        }
        container state {
          config false;
          description
            "Operational state parameters relating to the FDB";
          uses l2ni-fdb-mac-config;
        }
 
        uses l2ni-mac-table-top;
    }
  }

  grouping l2ni-fdb-mac-config {
    description
      "Parameters relating to FDB behaviour relating to MAC
      addresses";
 
    leaf mac-learning {
      type boolean;
      description
        "When this leaf is set to true, MAC learning is enabled for
        the network instance, such that MAC addresses are learned
        from ingress frames and added to the FDB.";
    }
 
    leaf mac-aging-time {
      // Cisco supports one aging time for local and remote, but
      // can specify this time is absolute or against inactivity.
      // ALU SROS supports different aging times for local and remote
      // but does not allow absolute/inactivity specification.
      // JNPR supports only a single aging time, and no specification
      // of whether inactivity/absolute is used.
      // It is easy to augment new options in here for local remote
      // and an extra leaf to allow specification of the type of aging
      // so this is left as a single value.
      type uint16;
      units seconds;
      description
        "The number of seconds of inactivity after which the entry
        in the local FDB is timed out.";
    }
 
    leaf maximum-entries {
      type uint16;
      description
        "The maximum number of MAC address entries that should be
        accepted into the FDB";
    }
  }
 

  grouping l2ni-mac-table-config {
    description
      "Configuration data for MAC table entries";
 
    leaf mac-address {
      type yang:mac-address;
      description
        "MAC address for the dynamic or static MAC table
        entry";
    }

    leaf vlan {
      //TODO(aashaikh): Consider whether this should just reflect the
      //VLAN id or be a union type to also support displaying/setting
      //the VLAN by name (i.e., global VLAN configured in the VLAN
      // model).
      type leafref {
        path "/oc-netinst:network-instances/oc-netinst:network-instance/oc-netinst:vlans/oc-netinst:vlan/oc-netinst:config/oc-netinst:vlan-id";
      }
      description
        "VLAN from which this MAC address was received";
    }
  }
 
  grouping l2ni-mac-table-state {
    description
      "Operational state data for MAC table entries";
 
    leaf age {
      type uint64;
      units seconds;
      description
        "The time in seconds since the MAC address has been in the
        table";
    }
 
    leaf entry-type {
      type enumeration {
        enum STATIC {
          description
            "Statically programmed MAC table entry";
        }
        enum DYNAMIC {
          description
            "Dynamically learned MAC table entry";
        }
      }
      description
        "Indicates whether the entry was statically configured, or
        dynamically learned.";
    }
 
  }
 
  grouping l2ni-mac-table-top {
    description
      "Top-level grouping for MAC table list";
  
    container mac-table {
      description
        "Table of learned or statically configured MAC addresses and
        corresponding VLANs in the bridge domain";
 
      container entries {
        description
          "Enclosing container for list of MAC table entries";
 
        list entry {
          key "mac-address vlan";
          description
            "List of learned MAC addresses";
 
          leaf mac-address {
            type leafref {
              path "../config/mac-address";
            }
            description
              "Reference to mac-address list key";
          }
           
          leaf vlan {
            type leafref {
              path "../config/vlan";
            }
            description
              "Reference to vlan list key";
          }
 
          container config {
            description
              "Configuration data for MAC table entries";
 
            uses l2ni-mac-table-config;
          }
 
          container state {
 
            config false;
 
            description
              "Operational state data for MAC table entries";
 
            uses l2ni-mac-table-config;
            uses l2ni-mac-table-state;
          }
 
          container interface {
            description
              "Reference to the base and/or subinterface for the
              MAC table entry";
 
            uses oc-if:interface-ref;
          }
        }
      }
    }
  } 
 
  augment "/oc-netinst:network-instances/oc-netinst:network-instance" {
    uses l2networkinstance {
      when "/oc-netinst:network-instances/oc-netinst:network-instance/oc-netinst:config/oc-netinst:type = 'oc-ni-types:L2VSI' or /oc-netinst:network-instances/oc-netinst:network-instance/oc-netinst:config/oc-netinst:type = 'oc-ni-types:L2P2P'" +
           " or /oc-netinst:network-instances/oc-netinst:network-instance/oc-netinst:config/oc-netinst:type = 'oc-ni-types:L2L3' or /oc-netinst:network-instances/oc-netinst:network-instance/oc-netinst:config/oc-netinst:type = 'oc-ni-types:DEFAULT_INSTANCE'" {
        description
          "Layer 2 configuration parameters included when
          a network instance is a Layer 2 instance or a
          combined L2L3 instance";
      }
    }
  }

}
