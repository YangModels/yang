module Cisco-IOS-XE-appqoe-serv-oper {
  yang-version 1;
  namespace "http://cisco.com/ns/yang/Cisco-IOS-XE-appqoe-serv-oper";
  prefix appqoe-xe-serv-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Application Quality of Experience (APPQOE) serviceability
     operational data. This includes overall and individual
     services status information, registered statistics for monitoring,
     and flows getting closed due to errors in different services.
     Copyright (c) 2020-2022 by Cisco Systems, Inc.
     All rights reserved.";

  revision 2022-07-01 {
    description
      "- Added detailed AppQoE active and expired flow operational data.
       - Added HTTP connect detect in active, expired and error flow entry.";
    reference
      "1.2.0";
    cisco-semver:module-version "1.2.0";
  }
  revision 2022-03-01 {
    description
      " - Added AppQoE active, expired and summary flow operational data.";
    reference
      "1.1.0";
    cisco-semver:module-version "1.1.0";
  }
  revision 2021-07-01 {
    description
      "Initial revision";
    reference
      "1.0.0";
    cisco-semver:module-version "1.0.0";
  }

  typedef appqoe-module {
    type enumeration {
      enum appqoe-module-invalid {
        value 0;
        description
          "APPQOE module is invalid";
      }
      enum appqoe-module-tcpproxy {
        value 1;
        description
          "APPQOE module is TCP proxy";
      }
      enum appqoe-module-sslproxy {
        value 2;
        description
          "APPQOE module is SSL proxy";
      }
      enum appqoe-module-rm {
        value 3;
        description
          "APPQOE module is Resource Manager(RM)";
      }
      enum appqoe-module-sc {
        value 4;
        description
          "APPQOE module is service chain";
      }
    }
    description
      "APPQOE services or modules";
  }

  typedef appqoe-module-status {
    type enumeration {
      enum appqoe-status-invalid {
        value 0;
        description
          "APPQOE status type invalid";
      }
      enum appqoe-status-green {
        value 1;
        description
          "APPQOE status type green";
      }
      enum appqoe-status-yellow {
        value 2;
        description
          "APPQOE status type yellow";
      }
      enum appqoe-status-red {
        value 3;
        description
          "APPQOE status type red";
      }
    }
    description
      "APPQOE overall status and each module status";
  }

  typedef appqoe-status-err {
    type enumeration {
      enum appqoe-err-undef {
        value 0;
        description
          "Error is undefined";
      }
      enum appqoe-err-ocsp-init-fail {
        value 1;
        description
          "SSL error: Online Certificate Status Protocol(OCSP) initialization fail";
      }
      enum appqoe-err-sign-ca-exp {
        value 2;
        description
          "SSL error: Certificate Authority(CA) signing certificate expired";
      }
      enum appqoe-err-ocsp-fail-ca-exp {
        value 3;
        description
          "SSL error: OCSP init fail and CA sign certificate expired";
      }
      enum appqoe-err-ca-tp-cfg {
        value 4;
        description
          "SSL error: CA Trust Point(TP) is not configured";
      }
      enum appqoe-err-ocsp-fail-ca-tp-cfg {
        value 5;
        description
          "SSL error: OCSP init fail and CA TP is not configured";
      }
      enum appqoe-err-ca-exp-ca-tp-cfg {
        value 6;
        description
          "SSL error: CA sign cert expired and CA TP is not configured";
      }
      enum appqoe-err-ocsp-fail-ca-exp-tp-cfg {
        value 7;
        description
          "SSL error: OCSP init fail, CA sign cert expired and CA TP is not configured";
      }
      enum appqoe-err-ca-bund-cfg {
        value 8;
        description
          "SSL error: CA bundle not configured";
      }
      enum appqoe-err-ocsp-fail-ca-bund-cfg {
        value 9;
        description
          "SSL error: OCSP init fail and CA bundle not configured";
      }
      enum appqoe-err-ca-exp-bund-cfg {
        value 10;
        description
          "SSL error: CA sign cert expired and CA bundle not configured";
      }
      enum appqoe-err-ocsp-fail-ca-exp-bund-cfg {
        value 11;
        description
          "SSL error: OCSP init fail, CA sign cert expired and CA bundle not configured";
      }
      enum appqoe-err-ca-tp-bund-cfg {
        value 12;
        description
          "SSL error: CA TP and CA bundle not configured";
      }
      enum appqoe-err-ocsp-fail-ca-tp-bund-cfg {
        value 13;
        description
          "SSL error: OCSP init fail, CA TP and CA bundle not configured";
      }
      enum appqoe-err-ca-exp-tp-bund-cfg {
        value 14;
        description
          "SSL error: CA sign cert expired, CA TP and CA bundle not configured";
      }
      enum appqoe-err-ocsp-ca-exp-tp-bund-cfg {
        value 15;
        description
          "SSL error: OCSP init fail, CA sign cert expired, CA TP and CA bundle not configured";
      }
      enum appqoe-err-ism-init-fail {
        value 16;
        description
          "SSL error: Interposer Session Manager(ISM) initialization fail";
      }
      enum appqoe-err-cert-mgr-init-fail {
        value 17;
        description
          "SSL error: Certificate manager initialization fail";
      }
      enum appqoe-err-rm-mem-limit-reach {
        value 18;
        description
          "RM error: Memory usage reached beyond allowed limit";
      }
      enum appqoe-err-rm-sess-limit-reach {
        value 19;
        description
          "RM error: Number of sessions reached beyond allowed limit";
      }
      enum appqoe-err-sc-channel-down {
        value 20;
        description
          "SC error: One or more communication channel is down";
      }
      enum appqoe-err-ssl-status-disabled {
        value 21;
        description
          "SSL proxy is disabled";
      }
    }
    description
      "Error details of APPQOE service or module when status is not green";
  }

  typedef tcpproxy-flow-err-tag {
    type enumeration {
      enum tcp-flow-err-tag-invalid {
        value 0;
        description
          "TCP-Proxy flow error is invalid";
      }
      enum tcp-flow-err-tag-accpt-conn-fail {
        value 1;
        description
          "TCP-Proxy accept conn fail";
      }
      enum tcp-flow-err-tag-rx-thr-fail {
        value 2;
        description
          "TCP-Proxy receive thread fail";
      }
      enum tcp-flow-err-tag-aoim-sync-fail {
        value 3;
        description
          "TCP-Proxy application optimiser information manager sync fail";
      }
      enum tcp-flow-err-tag-dre-resp-fail {
        value 4;
        description
          "TCP-Proxy DRE response create fail";
      }
      enum tcp-flow-err-tag-snort-resp-fail {
        value 5;
        description
          "TCP-Proxy SNORT response create fail";
      }
      enum tcp-flow-err-tag-utd-resp-fail {
        value 6;
        description
          "TCP-Proxy UTD response create fail";
      }
      enum tcp-flow-err-tag-close-by-utd {
        value 7;
        description
          "TCP-Proxy flow closed by UTD";
      }
      enum tcp-flow-err-tag-close-by-dre {
        value 8;
        description
          "TCP-Proxy flow closed by DRE";
      }
      enum tcp-flow-err-tag-close-by-ssl {
        value 9;
        description
          "TCP-Proxy flow closed by SSL";
      }
      enum tcp-flow-err-tag-reset-by-aoim {
        value 10;
        description
          "TCP-Proxy flow reset by application optimiser information manager";
      }
      enum tcp-flow-err-tag-create-dre-fail {
        value 11;
        description
          "TCP-Proxy flow create fail by DRE";
      }
      enum tcp-flow-err-tag-create-utd-fail {
        value 12;
        description
          "TCP-Proxy flow create fail by UTD";
      }
      enum tcp-flow-err-tag-create-ssl-fail {
        value 13;
        description
          "TCP-Proxy flow create fail by SSL";
      }
      enum tcp-flow-err-tag-syn-cache-purge {
        value 14;
        description
          "TCP-Proxy flow fail as syn cache purged";
      }
      enum tcp-flow-err-tag-ctimer-expire {
        value 15;
        description
          "TCP-Proxy flow cleanup timer expired";
      }
      enum tcp-flow-err-tag-cleanup-other {
        value 16;
        description
          "TCP-Proxy flow cleanup due to other reasons";
      }
      enum tcp-flow-err-tag-accept-failed {
        value 17;
        description
          "TCP-Proxy flow accept failed";
      }
      enum tcp-flow-err-tag-remote-conn-failed {
        value 18;
        description
          "TCP-Proxy flow remote connection failed";
      }
    }
    description
      "Error tag for flows which are closed by
       TCP-Proxy to indicate appropriate error message.";
  }

  typedef sslproxy-flow-err-tag {
    type enumeration {
      enum ssl-ism-err-none {
        value 0;
        description
          "SSL-Proxy ISM error invalid.";
      }
      enum ssl-ism-err-mem-alloc {
        value 1;
        description
          "Memory allocation fail at ISM.";
      }
      enum ssl-ism-err-pool {
        value 2;
        description
          "Unable to get memory from pool at ISM.";
      }
      enum ssl-ism-err-unsupp-cipher {
        value 3;
        description
          "Unsupported cipher.";
      }
      enum ssl-ism-err-hs-unsupported {
        value 4;
        description
          "Handshake unsupported at ISM.";
      }
      enum ssl-ism-err-vertverif-fail {
        value 5;
        description
          "Certificate verification fail at ISM.";
      }
      enum ssl-ism-err-endp-alert {
        value 6;
        description
          "End point alert in ISM.";
      }
      enum ssl-ism-err-close-before-hs {
        value 7;
        description
          "TCP close received before handshake complete.";
      }
      enum ssl-ism-err-proxy-cert {
        value 8;
        description
          "Unable to get proxy certificate.";
      }
      enum ssl-ism-err-expiered-cert {
        value 9;
        description
          "Certificate expired.";
      }
      enum ssl-ism-err-untrusted-cert {
        value 10;
        description
          "Untrusted certificate.";
      }
      enum ssl-ism-err-mem-access {
        value 11;
        description
          "Unable to access memory in ISM.";
      }
      enum ssl-lwssl-err-de-close {
        value 12;
        description
          "Received close request from DE.";
      }
      enum ssl-lwssl-err-de-flush-done {
        value 13;
        description
          "Flush done failed for DE.";
      }
      enum ssl-lwssl-err-nop-read {
        value 14;
        description
          "No operation read function called.";
      }
      enum ssl-lwssl-err-invalid-fsm-evt {
        value 15;
        description
          "Received invalid FSM event.";
      }
      enum ssl-lwssl-err-key-pkt-snd-fail {
        value 16;
        description
          "Failed to send key packet to ISM.";
      }
      enum ssl-lwssl-err-invalid-de-msg {
        value 17;
        description
          "Invalid message received from DE.";
      }
      enum ssl-lwssl-err-null-flow-ptr {
        value 18;
        description
          "Flow pointer is NULL";
      }
      enum ssl-lwssl-err-pd-reset {
        value 19;
        description
          "Reset due to push down";
      }
      enum ssl-lwssl-err-flush-done-fail {
        value 20;
        description
          "ISM flush done event handling is failed";
      }
      enum ssl-lwssl-err-ism-key-pkt-hdl-fail {
        value 21;
        description
          "ISM key packet handling is failed";
      }
      enum ssl-lwssl-err-invalid-ism-msg {
        value 22;
        description
          "Invalid message from ISM";
      }
      enum ssl-lwssl-err-invalid-peer {
        value 23;
        description
          "Invalid peer";
      }
      enum ssl-lwssl-err-min-tls-ver-act-rst {
        value 24;
        description
          "Unsupported protocol version action drop";
      }
      enum ssl-lwssl-err-null-ch-buf {
        value 25;
        description
          "Client hello buffer is null";
      }
      enum ssl-lwssl-err-snd-de-data-fail {
        value 26;
        description
          "Send DE data failed";
      }
      enum ssl-lwssl-err-fin-rst-pd {
        value 27;
        description
          "FIN or RST received during handshake";
      }
      enum ssl-lwssl-err-evt-in-inv-fsm-state {
        value 28;
        description
          "Invalid event in FSM state";
      }
      enum ssl-lwssl-err-evt-wrng-fsm-state {
        value 29;
        description
          "Event received in wrong FSM state";
      }
      enum ssl-lwssl-err-wrng-evt-in-de {
        value 30;
        description
          "Invalid event in DE init done state";
      }
      enum ssl-lwssl-err-snd-flush-fail {
        value 31;
        description
          "ISM send flush failed";
      }
      enum ssl-lwssl-err-evt-trig-rst {
        value 32;
        description
          "Trigger reset";
      }
      enum ssl-lwssl-err-one-side-key-pdg {
        value 33;
        description
          "One side key pending from ISM";
      }
      enum ssl-lwssl-err-null-ssl-rec {
        value 34;
        description
          "NULL SSL record in encrypted services buffer";
      }
      enum ssl-lwssl-err-ch-buf-alloc-fail {
        value 35;
        description
          "Buffer allocation failed for client hello";
      }
      enum ssl-lwssl-err-hs-parse-abort {
        value 36;
        description
          "Parse abort during handshake";
      }
      enum ssl-lwssl-err-hs-parse-incomp {
        value 37;
        description
          "Incomplete message during handshake";
      }
      enum ssl-lwssl-err-data-parse-abort {
        value 38;
        description
          "Data parse abort";
      }
      enum ssl-lwssl-err-data-parse-incomp {
        value 39;
        description
          "Incomplete message for data";
      }
      enum ssl-lwssl-err-invalid-ssl-rec {
        value 40;
        description
          "Invalid SSL record";
      }
      enum ssl-lwssl-err-fail-mode-rst {
        value 41;
        description
          "Failure mode reset";
      }
      enum ssl-lwssl-err-sslv2-fail-mode-rst {
        value 42;
        description
          "SSLv2 failure mode reset";
      }
      enum ssl-lwssl-err-peer-nop-read-fn {
        value 43;
        description
          "Peer no operation read function called";
      }
      enum ssl-lwssl-err-ssl-aut-trig-rst {
        value 44;
        description
          "SSL AUT triggering reset";
      }
      enum ssl-lwssl-err-send-ism-msg-fail {
        value 45;
        description
          "Unable to send handshake message to ISM";
      }
    }
    description
      "Error tag for flows which are closed by
       SSL-Proxy to indicate appropriate error message.";
  }

  typedef appqoe-flow-side {
    type enumeration {
      enum appqoe-flow-side-orig {
        value 0;
        description
          "The end point originated the flow";
      }
      enum appqoe-flow-side-term {
        value 1;
        description
          "The end point is terminating the flow";
      }
      enum appqoe-flow-sidr-none {
        value 2;
        description
          "The end point is unknown";
      }
    }
    description
      "The end point side in the flow establishment";
  }

  typedef appqoe-flow-tcpproxy-ad-states {
    type enumeration {
      enum appqoe-flow-tcp-ad-state-na {
        value 0;
        description
          "TCP Proxy AD state not applicable";
      }
      enum appqoe-flow-tcp-ad-state-init {
        value 1;
        description
          "TCP Proxy AD exchange not started";
      }
      enum appqoe-flow-tcp-ad-state-rx-syn {
        value 2;
        description
          "TCP Proxy AD Syn Rx handled";
      }
      enum appqoe-flow-tcp-ad-state-tx-syn-ack {
        value 3;
        description
          "TCP Proxy AD Syn-Ack Tx handled";
      }
      enum appqoe-flow-tcp-ad-state-rx-ack {
        value 4;
        description
          "TCP Proxy AD Ack Rx handled";
      }
      enum appqoe-flow-tcp-ad-state-tx-syn {
        value 5;
        description
          "TCP Proxy AD Syn Tx handled";
      }
      enum appqoe-flow-tcp-ad-state-rx-syn-ack {
        value 6;
        description
          "TCP Proxy AD Syn-Ack Rx handled";
      }
      enum appqoe-flow-tcp-ad-state-tx-ack {
        value 7;
        description
          "TCP Proxy AD Ack Tx handled";
      }
    }
    description
      "TCP Proxy AD states";
  }

  typedef appqoe-flow-tcpproxy-ad-roles {
    type enumeration {
      enum appqoe-flow-tcp-ad-role-none {
        value 0;
        description
          "TCP Proxy AD not enabled for flow";
      }
      enum appqoe-flow-tcp-ad-role-edge {
        value 1;
        description
          "TCP Proxy AD Edge role";
      }
      enum appqoe-flow-tcp-ad-role-core {
        value 2;
        description
          "TCP Proxy AD Core role";
      }
    }
    description
      "TCP Proxy AD roles";
  }

  typedef appqoe-flow-tcpproxy-flow-events {
    type enumeration {
      enum appqoe-flow-tcp-unknown {
        value 0;
        description
          "An unknown or unexpected TCP Proxy flow event has occurred";
      }
      enum appqoe-flow-tcp-created {
        value 1;
        description
          "The flow was created";
      }
      enum appqoe-flow-tcp-syncache-add {
        value 2;
        description
          "The syn-cache was added";
      }
      enum appqoe-flow-tcp-accpt-dne {
        value 3;
        description
          "The accept was completed";
      }
      enum appqoe-flow-tcp-accpt-fail {
        value 4;
        description
          "The accept failed";
      }
      enum appqoe-flow-tcp-conn-start {
        value 5;
        description
          "The connect started";
      }
      enum appqoe-flow-tcp-conn-dne {
        value 6;
        description
          "The connect was completed";
      }
      enum appqoe-flow-tcp-conn-fail {
        value 7;
        description
          "The connect failed";
      }
      enum appqoe-flow-tcp-aoim-syn-st {
        value 8;
        description
          "The AOIM sync started";
      }
      enum appqoe-flow-tcp-aoim-syn-dne {
        value 9;
        description
          "The AOIM sync was completed";
      }
      enum appqoe-flow-tcp-aoim-syn-err {
        value 10;
        description
          "The AOIM sync encountered an error";
      }
      enum appqoe-flow-tcp-ad-rx-syn-op {
        value 11;
        description
          "Auto-Discovery received Syn with options";
      }
      enum appqoe-flow-tcp-ad-rx-syn {
        value 12;
        description
          "Auto-Discovery received Syn without options";
      }
      enum appqoe-flow-tcp-ad-rx-edge-synack-op {
        value 13;
        description
          "Auto-Discovery received edge Syn-Ack with options";
      }
      enum appqoe-flow-tcp-ad-rx-edge-synack {
        value 14;
        description
          "Auto-Discovery received edge Syn-Ack without options";
      }
      enum appqoe-flow-tcp--ad-rx-core-synack {
        value 15;
        description
          "Auto-Discovery received core Syn-Ack";
      }
      enum appqoe-flow-tcp-ad-rx-core-ack-op {
        value 16;
        description
          "Auto-Discovery received core Ack with options";
      }
      enum appqoe-flow-tcp-ad-rx-core-ack {
        value 17;
        description
          "Auto-Discovery received core Ack without options";
      }
      enum appqoe-flow-tcp-ad-rx-edge-ack {
        value 18;
        description
          "Auto-Discovery received edge Ack";
      }
      enum appqoe-flow-tcp-ad-tx-edge-syn {
        value 19;
        description
          "Auto-Discovery edge sent syn";
      }
      enum appqoe-flow-tcp-ad-tx-edge-ack {
        value 20;
        description
          "Auto-Discovery edge sent Ack";
      }
      enum appqoe-flow-tcp-ad-tx-edge-synack {
        value 21;
        description
          "Auto-Discovery edge sent Syn-Ack without options";
      }
      enum appqoe-flow-tcp-ad-tx-core-synack {
        value 22;
        description
          "Auto-Discovery core sent Syn-Ack";
      }
      enum appqoe-flow-tcp-ad-tx-core-syn {
        value 23;
        description
          "Auto-Discovery core sent Syn without options";
      }
      enum appqoe-flow-tcp-ad-tx-core-ack {
        value 24;
        description
          "Auto-Discovery core sent Ack without options";
      }
      enum appqoe-flow-tcp-flow-cr-ssl-dne {
        value 25;
        description
          "SSL flow create completed";
      }
      enum appqoe-flow-tcp-flow-cr-ssl-fail {
        value 26;
        description
          "SSL flow create failed";
      }
      enum appqoe-flow-tcp-flow-cr-utd-st {
        value 27;
        description
          "Flow create request sent to UTD";
      }
      enum appqoe-flow-tcp-flow-del-utd-snt {
        value 28;
        description
          "Flow delete request sent to UTD";
      }
      enum appqoe-flow-tcp-flow-cr-utd-rsp-succ {
        value 29;
        description
          "Flow create success response received from UTD";
      }
      enum appqoe-flow-tcp-flow-cr-utd-rsp-fail {
        value 30;
        description
          "Flow create failed response received from UTD";
      }
      enum appqoe-flow-tcp-flow-cr-dre-snt {
        value 31;
        description
          "Flow create request sent to DRE";
      }
      enum appqoe-flow-tcp-dre-bypass-hint-snt {
        value 32;
        description
          "Flow bypass hint request sent to DRE";
      }
      enum appqoe-flow-tcp-del-dre-snt {
        value 33;
        description
          "Flow delete request sent to DRE";
      }
      enum appqoe-flow-tcp-cr-dre-rsp-succ {
        value 34;
        description
          "Flow create success received from DRE";
      }
      enum appqoe-flow-tcp-cr-dre-rsp-fail {
        value 35;
        description
          "Flow create failed received from DRE";
      }
      enum appqoe-flow-tcp-cr-http-snt {
        value 36;
        description
          "Flow create request sent to HTTP";
      }
      enum appqoe-flow-tcp-http-bypass-hint-snt {
        value 37;
        description
          "Flow bypass hint request sent to HTTP";
      }
      enum appqoe-flow-tcp-del-http-snt {
        value 38;
        description
          "Flow delete request sent to HTTP";
      }
      enum appqoe-flow-tcp-cr-http-rsp-succ {
        value 39;
        description
          "Flow create success received from HTTP";
      }
      enum appqoe-flow-tcp-cr-http-rsp-fail {
        value 40;
        description
          "Flow create failed received from HTTP";
      }
      enum appqoe-flow-tcp-ena-ssl {
        value 41;
        description
          "SSL flow enabled";
      }
      enum appqoe-flow-tcp-data-ena-succ {
        value 42;
        description
          "Data enable success";
      }
      enum appqoe-flow-tcp-data-ena-fail {
        value 43;
        description
          "Data enable failed";
      }
      enum appqoe-flow-tcp-fin-rcv-cli-c2s {
        value 44;
        description
          "Fin received for client-to-server client file descriptor";
      }
      enum appqoe-flow-tcp-fin-rcv-srv-s2c {
        value 45;
        description
          "Fin received for server-to-client server file descriptor";
      }
      enum appqoe-flow-tcp-rst-rcv-cli-c2s {
        value 46;
        description
          "Rst received for client-to-server client file descriptor";
      }
      enum appqoe-flow-tcp-rst-rcv-srv-s2c {
        value 47;
        description
          "Rst received for server-to-client server file descriptor";
      }
      enum appqoe-flow-tcp-do-oth-rst-c2s {
        value 48;
        description
          "Do other Rst client-to-server";
      }
      enum appqoe-flow-tcp-do-oth-rst-s2c {
        value 49;
        description
          "Do other Rst server-to-client";
      }
      enum appqoe-flow-tcp-rst-cli-ini-ssl-s2c {
        value 50;
        description
          "Rst client, initialize SSL server-to-client";
      }
      enum appqoe-flow-tcp-rst-srv-ini-ssl-c2s {
        value 51;
        description
          "Rst server, initialize SSL client-to-server";
      }
      enum appqoe-flow-tcp-rst-cli-ini-utd-c2s {
        value 52;
        description
          "Rst client, initialize UTD client-to-server";
      }
      enum appqoe-flow-tcp-rst-srv-ini-utd-s2c {
        value 53;
        description
          "Rst server, initialize UTD server-to-client";
      }
      enum appqoe-flow-tcp-rst-cli-ini-utd-s2c {
        value 54;
        description
          "Rst client, initialize UTD server-to-client";
      }
      enum appqoe-flow-tcp-rst-srv-ini-utd-c2s {
        value 55;
        description
          "Rst server, initialize UTD client-to-server";
      }
      enum appqoe-flow-tcp-rst-cli-ini-dre-c2s {
        value 56;
        description
          "Rst client, initialize DRE client-to-server";
      }
      enum appqoe-flow-tcp-rst-srv-ini-dre-s2c {
        value 57;
        description
          "Rst server, initialize DRE server-to-client";
      }
      enum appqoe-flow-tcp-rst-cli-ini-dre-s2c {
        value 58;
        description
          "Rst client, initialize DRE server-to-client";
      }
      enum appqoe-flow-tcp-rst-srv-ini-dre-c2s {
        value 59;
        description
          "Rst server, initialize DRE client-to-server";
      }
      enum appqoe-flow-tcp-dre-cls-cli-s2c {
        value 60;
        description
          "DRE client close, server-to-client";
      }
      enum appqoe-flow-tcp-dre-cls-srv-c2s {
        value 61;
        description
          "DRE server close, client-to-server";
      }
      enum appqoe-flow-tcp-rst-cli-ini-http-c2s {
        value 62;
        description
          "Rst client, initialize HTTP client-to-server";
      }
      enum appqoe-flow-tcp-rst-srv-ini-http-s2c {
        value 63;
        description
          "Rst server, initialize HTTP server-to-client";
      }
      enum appqoe-flow-tcp-rst-cli-ini-http-s2c {
        value 64;
        description
          "Rst client, initialize HTTP server-to-client";
      }
      enum appqoe-flow-tcp-rst-srv-ini-http-c2s {
        value 65;
        description
          "Rst server, initialize HTTP client-to-server";
      }
      enum appqoe-flow-tcp-fin-cli-ssl-snt {
        value 66;
        description
          "Fin client sent to SSL";
      }
      enum appqoe-flow-tcp-fin-cli-ssl-rcv {
        value 67;
        description
          "Fin client received from SSL";
      }
      enum appqoe-flow-tcp-fin-cli-utd-snt {
        value 68;
        description
          "Fin client sent to UTD";
      }
      enum appqoe-flow-tcp-fin-cli-utd-rcv {
        value 69;
        description
          "Fin client received from UTD";
      }
      enum appqoe-flow-tcp-fin-cli-dre-snt {
        value 70;
        description
          "Fin client sent to DRE";
      }
      enum appqoe-flow-tcp-fin-cli-dre-rcv {
        value 71;
        description
          "Fin client received from DRE";
      }
      enum appqoe-flow-tcp-fin-cli-http-snt {
        value 72;
        description
          "Fin client sent to HTTP";
      }
      enum appqoe-flow-tcp-fin-cli-http-rcv {
        value 73;
        description
          "Fin client received from HTTP";
      }
      enum appqoe-flow-tcp-fin-cli-svc-ssl-snt {
        value 74;
        description
          "Fin client service sent to SSL";
      }
      enum appqoe-flow-tcp-fin-cli-tcp-rcv {
        value 75;
        description
          "Fin client TCP transmit received";
      }
      enum appqoe-flow-tcp-rst-cli-ssl-snt {
        value 76;
        description
          "Rst client sent to SSL";
      }
      enum appqoe-flow-tcp-rst-cli-ssl-rcv {
        value 77;
        description
          "Rst client service received from SSL";
      }
      enum appqoe-flow-tcp-rst-cli-utd-snt {
        value 78;
        description
          "Rst client service sent to UTD";
      }
      enum appqoe-flow-tcp-rst-cli-utd-rcv {
        value 79;
        description
          "Rst client service received from UTD";
      }
      enum appqoe-flow-tcp-rst-clsvc-dre-snt {
        value 80;
        description
          "Rst client service sent to DRE";
      }
      enum appqoe-flow-tcp-rst-cli-dre-rcv {
        value 81;
        description
          "Rst client service received from DRE";
      }
      enum appqoe-flow-tcp-rst-clsvc-http-snt {
        value 82;
        description
          "Rst client service sent to HTTP";
      }
      enum appqoe-flow-tcp-rst-cli-http-rcv {
        value 83;
        description
          "Rst client service received from HTTP";
      }
      enum appqoe-flow-tcp-rst-clsvc-ssl-snt {
        value 84;
        description
          "Rst client service sent to SSL";
      }
      enum appqoe-flow-tcp-rst-cli-tcp-rcv {
        value 85;
        description
          "Rst client TCP transmit received";
      }
      enum appqoe-flow-tcp-fin-srv-ssl-snt {
        value 86;
        description
          "Fin server sent to SSL";
      }
      enum appqoe-flow-tcp-fin-srv-ssl-rcv {
        value 87;
        description
          "Fin server service received from SSL";
      }
      enum appqoe-flow-tcp-fin-srv-utd-snt {
        value 88;
        description
          "Fin server service sent to UTD";
      }
      enum appqoe-flow-tcp-fin-srv-utd-rcv {
        value 89;
        description
          "Fin server service received from UTD";
      }
      enum appqoe-flow-tcp-fin-srv-dre-snt {
        value 90;
        description
          "Fin server service sent to DRE";
      }
      enum appqoe-flow-tcp-fin-srv-dre-rcv {
        value 91;
        description
          "Fin server service received from DRE";
      }
      enum appqoe-flow-tcp-fin-src-http-snt {
        value 92;
        description
          "Fin server service sent to HTTP";
      }
      enum appqoe-flow-tcp-fin-srv-http-rcv {
        value 93;
        description
          "Fin server service received from HTTP";
      }
      enum appqoe-flow-tcp-fin-srv-svc-ssl-snt {
        value 94;
        description
          "Fin server service sent to SSL";
      }
      enum appqoe-flow-tcp-fin-src-tcp-rcv {
        value 95;
        description
          "Fin server TCP transmit received";
      }
      enum appqoe-flow-tcp-rst-srv-ssl-snt {
        value 96;
        description
          "Rst server sent to SSL";
      }
      enum appqoe-flow-tcp-rst-srv-ssl-rcv {
        value 97;
        description
          "Rst server service received from SSL";
      }
      enum appqoe-flow-tcp-rst-srv-utd-snt {
        value 98;
        description
          "Rst server service sent to UTD";
      }
      enum appqoe-flow-tcp-rst-srv-utd-rcv {
        value 99;
        description
          "Rst server service received from UTD";
      }
      enum appqoe-flow-tcp-rst-srv-dre-snt {
        value 100;
        description
          "Rst server service sent to DRE";
      }
      enum appqoe-flow-tcp-rst-srv-dre-rcv {
        value 101;
        description
          "Rst server service received from DRE";
      }
      enum appqoe-flow-tcp-rst-srv-http-snt {
        value 102;
        description
          "Rst server service sent to HTTP";
      }
      enum appqoe-flow-tcp-rst-srv-http-rcv {
        value 103;
        description
          "Rst server service received from HTTP";
      }
      enum appqoe-flow-tcp-rst-srv-svc-ssl-snt {
        value 104;
        description
          "Rst server service sent to SSL";
      }
      enum appqoe-flow-tcp-rst-srv-tcp-rcv {
        value 105;
        description
          "Rst server TCP transmit received";
      }
      enum appqoe-flow-tcp-fin-snt-cli-s2c {
        value 106;
        description
          "Fin client flow descriptor sent";
      }
      enum appqoe-flow-tcp-fin-snt-srv-c2s {
        value 107;
        description
          "Fin server flow descriptor sent";
      }
      enum appqoe-flow-tcp-dre-cls-snt-cli-s2c {
        value 108;
        description
          "DRE close client flow descriptor sent";
      }
      enum appqoe-flow-tcp-dre-cls-snt-srv-c2s {
        value 109;
        description
          "RE close server flow descriptor sent";
      }
      enum appqoe-flow-tcp-cls-cli-s2c {
        value 110;
        description
          "Client flow descriptor closed";
      }
      enum appqoe-flow-tcp-cls-srv-c2s {
        value 111;
        description
          "Server flow descriptor closed";
      }
      enum appqoe-flow-tcp-cli-tcp-clsd {
        value 112;
        description
          "Client TCP closed";
      }
      enum appqoe-flow-tcp-srv-tcp-clsd {
        value 113;
        description
          "Server TCP closed";
      }
      enum appqoe-flow-tcp-all-tcp-clsd-cln {
        value 114;
        description
          "All TCP closed and cleanup completed";
      }
      enum appqoe-flow-tcp-syn-purge-cln {
        value 115;
        description
          "Syn purge clean up";
      }
      enum appqoe-flow-tcp-oth-cln {
        value 116;
        description
          "Other clean up";
      }
      enum appqoe-flow-tcp-rst-cln-trig {
        value 117;
        description
          "Rst service clean up triggered";
      }
      enum appqoe-flow-tcp-rst-cln {
        value 118;
        description
          "Rst service clean up completed";
      }
      enum appqoe-flow-tcp-proxy-cls {
        value 119;
        description
          "Proxy close";
      }
      enum appqoe-flow-tcp-proxy-trig-cln {
        value 120;
        description
          "Proxy clean up trigger";
      }
      enum appqoe-flow-tcp-ena-rx-clsd-cli {
        value 121;
        description
          "Client receive socket on stack closed";
      }
      enum appqoe-flow-tcp-ena-rx-clsd-srv {
        value 122;
        description
          "Server receive socket on stack closed";
      }
      enum appqoe-flow-tcp-cln-complete {
        value 123;
        description
          "Cleanup complete";
      }
      enum appqoe-flow-tcp-cln-time-expire {
        value 124;
        description
          "Cleanup timer expired";
      }
      enum appqoe-flow-tcp-fin-ign-cli-cls-s2c {
        value 125;
        description
          "Ignore Fin, client flow descriptor already closed";
      }
      enum appqoe-flow-tcp-fin-ign-srv-cls-c2s {
        value 126;
        description
          "Ignore Fin, server flow descriptor already closed";
      }
      enum appqoe-flow-tcp-dre-cls-ign-cli-cls {
        value 127;
        description
          "Ignore DRE close, client flow descriptor already closed";
      }
      enum appqoe-flow-tcp-dre-cls-ign-srv-c2s {
        value 128;
        description
          "Ignore DRE close, server flow descriptor already closed";
      }
      enum appqoe-flow-tcp-ign-cls-data-pnd-c2s {
        value 129;
        description
          "Ignore socket close, data pending in socket client-to-server";
      }
      enum appqoe-flow-tcp-ign-cls-data-pnd-s2c {
        value 130;
        description
          "Ignore socket close, data pending in socket server-to-client";
      }
      enum appqoe-flow-tcp-no-data-pnd-c2s {
        value 131;
        description
          "No data pending in socket client-to-server";
      }
      enum appqoe-flow-tcp-no-data-pnd-s2c {
        value 132;
        description
          "No data pending in socket server-to-client";
      }
    }
    description
      "TCP Proxy flow events";
  }

  typedef appqoe-flow-sslproxy-lwssl-state {
    type enumeration {
      enum flow-sslproxy-lwssl-state-invalid {
        value 0;
        description
          "Invalid state";
      }
      enum flow-sslproxy-lwssl-state-init {
        value 1;
        description
          "Initialized, but not started";
      }
      enum flow-sslproxy-lwssl-state-fwd-clr {
        value 2;
        description
          "Forward all data to SCM without processing";
      }
      enum flow-sslproxy-lwssl-state-pre-ssl {
        value 3;
        description
          "Initial SSL exchange";
      }
      enum flow-sslproxy-lwssl-state-fwd {
        value 4;
        description
          "Forward all data to peer without processing";
      }
      enum flow-sslproxy-lwssl-state-hs {
        value 5;
        description
          "SSL handshake, send messages to ISM and send to peer";
      }
      enum flow-sslproxy-lwssl-state-fwd-hs {
        value 6;
        description
          "SSL handshake, parser and send it to peer";
      }
      enum flow-sslproxy-lwssl-state-export {
        value 7;
        description
          "Exporting SSL state";
      }
      enum flow-sslproxy-lwssl-state-import {
        value 8;
        description
          "Importing Proxy client and server state";
      }
      enum flow-sslproxy-lwssl-state-flush-de {
        value 9;
        description
          "Flush DE data based on direction";
      }
      enum flow-sslproxy-lwssl-state-app-data {
        value 10;
        description
          "In Active SSL data";
      }
      enum flow-sslproxy-lwssl-state-wire-clsd {
        value 11;
        description
          "Received Close Notify from client";
      }
      enum flow-sslproxy-lwssl-state-ao-clsd {
        value 12;
        description
          "Received Close Notify from server";
      }
      enum flow-sslproxy-lwssl-state-clsd {
        value 13;
        description
          "SSL is CLOSED, Close Notify is received from both side";
      }
      enum flow-sslproxy-lwssl-state-ss-clsd {
        value 14;
        description
          "AO terminated on one side";
      }
      enum flow-sslproxy-lwssl-state-tcp-clsd {
        value 15;
        description
          "SSL is closed or TCP closed before SSL is engaged";
      }
      enum flow-sslproxy-lwssl-state-pd {
        value 16;
        description
          "In Remove LWSSL from pipeline";
      }
      enum flow-sslproxy-lwssl-state-fs-done {
        value 17;
        description
          "In a limbo dont start a read/write";
      }
    }
    description
      "SSL Proxy flow states";
  }

  typedef appqoe-flow-sslproxy-lwssl-event {
    type enumeration {
      enum flow-ssl-lwssl-evt-invalid {
        value 0;
        description
          "Invalid Event";
      }
      enum flow-ssl-lwssl-evt-peer-init {
        value 1;
        description
          "Peer Initialization is done";
      }
      enum flow-ssl-lwssl-evt-start {
        value 2;
        description
          "SSL is starting";
      }
      enum flow-ssl-lwssl-evt-pre-ssl {
        value 3;
        description
          "All Pre-ssl data is read";
      }
      enum flow-ssl-lwssl-evt-hs-begin {
        value 4;
        description
          "pre-ssl data is read and handshake begins";
      }
      enum flow-ssl-lwssl-evt-ccs-fin-rcv {
        value 5;
        description
          "CCS + FIN received";
      }
      enum flow-ssl-lwssl-evt-rcv-wire-cn {
        value 6;
        description
          "Close notify received from wire";
      }
      enum flow-ssl-lwssl-evt-rcv-wine-fin {
        value 7;
        description
          "FIN received from wire";
      }
      enum flow-ssl-lwssl-evt-wire-rst {
        value 8;
        description
          "RST received from wire";
      }
      enum flow-ssl-lwssl-evt-rcv-ao-fin-cn {
        value 9;
        description
          "FIN from AO, as Close notify received on peer";
      }
      enum flow-ssl-lwssl-evt-rcv-ao-fin-no-cn {
        value 10;
        description
          "FIN from AO but No Close notify received";
      }
      enum flow-ssl-lwssl-evt-rcv-ao-rst {
        value 11;
        description
          "Received RST from AO";
      }
      enum flow-ssl-lwssl-evt-key-pkt-from-ism {
        value 12;
        description
          "Received Key packet from ISM";
      }
      enum flow-ssl-lwssl-evt-key-pkt-init {
        value 13;
        description
          "Key packet init done in DE";
      }
      enum flow-ssl-lwssl-evt-app-parser {
        value 14;
        description
          "Post parse done";
      }
      enum flow-ssl-lwssl-evt-ssl-clsd {
        value 15;
        description
          "SSL connection is closed, TCP is still open";
      }
      enum flow-ssl-event-pd {
        value 16;
        description
          "Push-Down connection";
      }
      enum flow-ssl-lwssl-evt-ism-flush {
        value 17;
        description
          "ISM flush is complete";
      }
      enum flow-ssl-lwssl-evt-de-flush {
        value 18;
        description
          "DE flush is complete";
      }
      enum flow-ssl-lwssl-evt-flush {
        value 19;
        description
          "ISM and DE flush is complete";
      }
      enum flow-ssl-lwssl-evt-self-fs-clsd {
        value 20;
        description
          "Self FS is Closed";
      }
      enum flow-ssl-lwssl-evt-peer-fs-clsd {
        value 21;
        description
          "Peer FS is Closed";
      }
      enum flow-ssl-lwssl-evt-trigger-rst {
        value 22;
        description
          "Self triggered RST";
      }
      enum flow-ssl-lwssl-evt-ism-renego-init {
        value 23;
        description
          "ISM renegotiation init done";
      }
    }
    description
      "SSL Proxy flow events";
  }

  typedef appqoe-flow-sslproxy-module {
    type enumeration {
      enum flow-ssl-module-none {
        value 0;
        description
          "No/Unknown Module";
      }
      enum flow-ssl-module-ism {
        value 1;
        description
          "ISM module";
      }
      enum flow-ssl-module-ssl {
        value 2;
        description
          "SSL encryption/decryption Module";
      }
      enum flow-ssl-module-fsm {
        value 3;
        description
          "Finite State Machine Module";
      }
    }
    description
      "SSL Proxy internal modules";
  }

  typedef appqoe-flow-sslproxy-tr-events {
    type enumeration {
      enum flow-ssl-evt-unknown {
        value 0;
        description
          "ERROR - Unknown Event";
      }
      enum flow-ssl-evt-ism-snd-ssl-msg {
        value 1;
        description
          "Trace event from ISM to SSL";
      }
      enum flow-ssl-evt-ism-pd {
        value 2;
        description
          "Push-down event generated by ISM";
      }
      enum flow-ssl-evt-ism-created {
        value 3;
        description
          "Created event generated by ISM";
      }
      enum flow-ssl-evt-ism-ssl-rec {
        value 4;
        description
          "SSL record event generated by ISM";
      }
      enum flow-ssl-evt-ism-ssl-data {
        value 5;
        description
          "SSL data event generated by ISM";
      }
      enum flow-ssl-evt-ism-ssl-data-or-c2s {
        value 6;
        description
          "SSL data is originating from client to server";
      }
      enum flow-ssl-evt-ism-ssl-data-or-s2c {
        value 7;
        description
          "SSL data is originating from server to client";
      }
      enum flow-ssl-evt-ism-cls {
        value 8;
        description
          "Close event generated by ISM";
      }
      enum flow-ssl-evt-ism-cls-notif-rcv {
        value 9;
        description
          "Close Notify Receive event generated by ISM";
      }
      enum flow-ssl-evt-ism-hello-req-rcv {
        value 10;
        description
          "Hello Request Receive event generated by ISM";
      }
      enum flow-ssl-evt-ism-de-flush {
        value 11;
        description
          "DE flush completed event generated by ISM";
      }
      enum flow-ssl-evt-ism-flush {
        value 12;
        description
          "Flush completed event generated by ISM";
      }
      enum flow-ssl-evt-ism-flush-c2s {
        value 13;
        description
          "Client to Server flush completed event generated by ISM";
      }
      enum flow-ssl-evt-ism-flush-s2c {
        value 14;
        description
          "Server to Client flush completed event generated by ISM";
      }
      enum flow-ssl-evt-ism-new {
        value 15;
        description
          "New ISM object event";
      }
      enum flow-ssl-evt-ism-key-pkt {
        value 16;
        description
          "ISM has detected a key packet";
      }
      enum flow-ssl-evt-ism-enc-st-init {
        value 17;
        description
          "Encryption Init event generated by ISM";
      }
      enum flow-ssl-evt-ism-conn-data {
        value 18;
        description
          "Connection data event gen..";
      }
      enum flow-ssl-evt-ism-de-key-pkt {
        value 19;
        description
          "DE key packet event generated by ISM";
      }
      enum flow-ssl-evt-ism-key-pkt-loaded {
        value 20;
        description
          "Key packet loaded event generated by ISM";
      }
      enum flow-ssl-evt-ism-hs {
        value 21;
        description
          "Handshake event generated by ISM";
      }
      enum flow-ssl-evt-ism-dscp-update {
        value 22;
        description
          "DSCP update event generated by ISM";
      }
      enum flow-ssl-evt-ism-hs-comp-ssl-rec {
        value 23;
        description
          "Handshake completed event generated by ISM";
      }
      enum flow-ssl-evt-ism-msg-code-max {
        value 24;
        description
          "Message code max event generated by ISM";
      }
      enum flow-ssl-evt-ism-trig-pd {
        value 25;
        description
          "Push-down triggered event generated by ISM";
      }
      enum flow-ssl-evt-ism-trig-rst {
        value 26;
        description
          "Trigger reset event generated by ISM";
      }
      enum flow-ssl-evt-ism-rx-alrt {
        value 27;
        description
          "ISM has received an alert";
      }
      enum flow-ssl-evt-ism-tx-alrt {
        value 28;
        description
          "ISM has sent an alert";
      }
      enum flow-ssl-evt-snd-ism-msg {
        value 29;
        description
          "SSL flow record event generated";
      }
      enum flow-ssl-evt-flow-ssl-rec {
        value 30;
        description
          "SSL flow record event generated";
      }
      enum flow-ssl-evt-flow-new {
        value 31;
        description
          "SSL new flow event generated";
      }
      enum flow-ssl-evt-flow-flush {
        value 32;
        description
          "SSL flow flush event generated";
      }
      enum flow-ssl-evt-flow-de-key {
        value 33;
        description
          "SSL DE key event generated";
      }
      enum flow-ssl-evt-flow-trig-pd {
        value 34;
        description
          "SSL flow trigger push-down event generated";
      }
      enum flow-ssl-evt-flow-cleanup {
        value 35;
        description
          "SSL flow cleanup event generated";
      }
      enum flow-ssl-evt-sake-list-rec-rsp {
        value 36;
        description
          "SAKE ";
      }
      enum flow-ssl-evt-sake-ske-rsp {
        value 37;
        description
          "SAKE response event generated";
      }
      enum flow-ssl-evt-sake-decr-cke-rsp {
        value 38;
        description
          "SAKE CKE decrypted response event generated";
      }
      enum flow-ssl-evt-sake-cke-secr-rsp {
        value 39;
        description
          "SAKE CKE secret response event generated";
      }
      enum flow-ssl-evt-sake-cert-ver-rsp {
        value 40;
        description
          "SAKE certificate verification response event generated";
      }
      enum flow-ssl-evt-sake-cli-cert-rsp {
        value 41;
        description
          "SAKE client certificate response generated";
      }
      enum flow-ssl-evt-sake-ocsp-srv-cert-vrfy {
        value 42;
        description
          "SAKE OCSP server certificate verification response event generated";
      }
      enum flow-ssl-evt-sake-ocsp-cli-cert-vrfy {
        value 43;
        description
          "SAKE OCSP client certificate verification response event generated";
      }
      enum flow-ssl-evt-snd-fin-tx {
        value 44;
        description
          "FIN to TX event generated by SSL";
      }
      enum flow-ssl-evt-snd-fin-sc {
        value 45;
        description
          "FIN to Service Chain event generated by SSL";
      }
      enum flow-ssl-evt-snd-rst-tx {
        value 46;
        description
          "RST to wire event generated by SSL";
      }
      enum flow-ssl-evt-snd-rst-sc {
        value 47;
        description
          "RST to Service Chain event generated by SSL";
      }
      enum flow-ssl-evt-snd-shrt-ckt-rst-tx {
        value 48;
        description
          "Short circuit Service Chain reset to TX generated by SSL";
      }
      enum flow-ssl-evt-snd-shrt-ckt-fin-tx {
        value 49;
        description
          "Short circuit Service Chain FIN to TX generated by SSL";
      }
      enum flow-ssl-evt-rcv-fin {
        value 50;
        description
          "SSL has received FIN message";
      }
      enum flow-ssl-evt-rcv-rst {
        value 51;
        description
          "SSL has received RST message";
      }
      enum flow-ssl-evt-trig-rst {
        value 52;
        description
          "Reset triggered event";
      }
      enum flow-ssl-evt-trig-td {
        value 53;
        description
          "Push-down triggered event";
      }
      enum flow-ssl-evt-data-ctrl-pause {
        value 54;
        description
          "Data control pause event";
      }
      enum flow-ssl-evt-data-ctrl-res-ntfy {
        value 55;
        description
          "Data control resume notify event";
      }
      enum flow-ssl-evt-data-ctrl-res {
        value 56;
        description
          "Data control resume event";
      }
      enum flow-ssl-evt-rd-pause {
        value 57;
        description
          "Read pause event generated by SSL";
      }
      enum flow-ssl-evt-rd-res-ntfy {
        value 58;
        description
          "Read resume notify event generated by SSL";
      }
      enum flow-ssl-evt-rd-res {
        value 59;
        description
          "Read resume event generated by SSL";
      }
      enum flow-ssl-evt-dre-tx-pause {
        value 60;
        description
          "Transmit pause event sent to DRE";
      }
      enum flow-ssl-evt-dre-tx-res-ntfy {
        value 61;
        description
          "Transmit resume notify event sent to DRE";
      }
      enum flow-ssl-evt-rd-ps-fin-defer {
        value 62;
        description
          "FIN deferred due to read pause event generated by SSL";
      }
      enum flow-ssl-evt-rd-ps-rst-defer {
        value 63;
        description
          "RST deferred due to read pause event generated by SSL";
      }
      enum flow-ssl-evt-rd-ps-def-fin-hdl {
        value 64;
        description
          "Handle deferred FIN due to read pause event generated by SSL";
      }
      enum flow-ssl-evt-rd-ps-def-rst-hdl {
        value 65;
        description
          "Handle deferred RST due to read pause event generated by SSL";
      }
      enum flow-ssl-evt-lfs-cls {
        value 66;
        description
          "LFS close event generated by SSL";
      }
      enum flow-ssl-evt-pa-ctrl-msg-rx {
        value 67;
        description
          "PA control message received event generated by SSL";
      }
      enum flow-ssl-evt-pa-ctrl-msg-tx {
        value 68;
        description
          "PA control message transmitted event generated by SSL";
      }
      enum flow-ssl-evt-fsm {
        value 69;
        description
          "SSL FSM event";
      }
      enum flow-ssl-evt-invalid {
        value 70;
        description
          "Invalid FSM event";
      }
      enum flow-ssl-evt-fsm-peer-init {
        value 71;
        description
          "Peer init done FSM event";
      }
      enum flow-ssl-evt-fsm-start-ssl {
        value 72;
        description
          "SSL has started";
      }
      enum flow-ssl-evt-fsm-pre-ssl {
        value 73;
        description
          "Pre SSL state has completed";
      }
      enum flow-ssl-evt-fsm-hs-begin {
        value 74;
        description
          "Handshake has started";
      }
      enum flow-ssl-evt-fsm-ccs-fin-rcv {
        value 75;
        description
          "CCS FIN message has been received";
      }
      enum flow-ssl-evt-fsm-rcvd-wire-cn {
        value 76;
        description
          "Close notify message received from wire";
      }
      enum flow-ssl-evt-fsm-rcvd-wire-fin {
        value 77;
        description
          "FIN message received from wire";
      }
      enum flow-ssl-evt-fsm-rcvd-wire-rst {
        value 78;
        description
          "Reset message received from wire";
      }
      enum flow-ssl-evt-fsm-rcvd-fin-peer-cn {
        value 79;
        description
          "Peer close notify message received from Service Chain";
      }
      enum flow-ssl-evt-fsm-rcvd-fin-peer-no-cn {
        value 80;
        description
          "Peer No close notify";
      }
      enum flow-ssl-evt-fsm-rcvd-rst {
        value 81;
        description
          "Reset received from SC";
      }
      enum flow-ssl-evt-fsm-key-pkt-ism {
        value 82;
        description
          "Key packet received from ISM";
      }
      enum flow-ssl-evt-fsm-key-pkt-init {
        value 83;
        description
          "Key packet init completed";
      }
      enum flow-ssl-evt-fsm-app-parser {
        value 84;
        description
          "Application data parser completed";
      }
      enum flow-ssl-evt-fsm-ssl-clsd {
        value 85;
        description
          "SSL closed event";
      }
      enum flow-ssl-evt-fsm-pd {
        value 86;
        description
          "FSM Push-down event";
      }
      enum flow-ssl-evt-fsm-ism-flush {
        value 87;
        description
          "ISM flush completed";
      }
      enum flow-ssl-evt-fsm-de-flush {
        value 88;
        description
          "DE flush completed";
      }
      enum flow-ssl-evt-fsm-flush {
        value 89;
        description
          "ISM and DE flush have both completed";
      }
      enum flow-ssl-evt-fsm-self-fs-clsd {
        value 90;
        description
          "Self flow segment closed event";
      }
      enum flow-ssl-evt-fsm-peer-fs-clsd {
        value 91;
        description
          "Peer flow segment closed event";
      }
      enum flow-ssl-evt-fsm-trig-rst {
        value 92;
        description
          "Reset is triggered by FSM";
      }
      enum flow-ssl-evt-fsm-ism-renego-init {
        value 93;
        description
          "ISM Renegotiation init has been completed";
      }
      enum flow-ssl-evt-fsm-pa {
        value 94;
        description
          "Peer adapter event";
      }
      enum flow-ssl-evt-fsm-pa-invalid {
        value 95;
        description
          "Invalid peer adapter event";
      }
      enum flow-ssl-evt-fsm-pa-peer-init {
        value 96;
        description
          "Peer init completed by peer adapter";
      }
      enum flow-ssl-evt-fsm-pa-start-ssl {
        value 97;
        description
          "Peer adapter started";
      }
      enum flow-ssl-evt-fsm-pa-hs-begin {
        value 98;
        description
          "Peer adapter handshake started";
      }
      enum flow-ssl-evt-fsm-pa-ccs-fin-rcv {
        value 99;
        description
          "Peer adapter change cipher spec handshake received";
      }
      enum flow-ssl-evt-fsm-pa-key-pck-init {
        value 100;
        description
          "Peer adapter key packet init completed";
      }
      enum flow-ssl-evt-fsm-pa-trig-rst {
        value 101;
        description
          "Peer adapter reset triggered";
      }
      enum flow-ssl-evt-fsm-pa-ism-renego-init {
        value 102;
        description
          "Peer adapter ISM renegotiation init completed";
      }
      enum flow-ssl-evt-fsm-pa-rcvd-wire-cn {
        value 103;
        description
          "Peer adapter close notify received on wire";
      }
      enum flow-ssl-evt-fsm-pa-rcvd-wire-fin {
        value 104;
        description
          "Peer adapter FIN received on wire";
      }
      enum flow-ssl-evt-fsm-pa-rcvd-wire-rst {
        value 105;
        description
          "Peer adapter RST received on wire";
      }
      enum flow-ssl-evt-fsm-pa-rcvd-fin-cn {
        value 106;
        description
          "Peer adapter received service chain close notify FIN";
      }
      enum flow-ssl-evt-fsm-pa-rcvd-fin-no-cn {
        value 107;
        description
          "Peer adapter received service chain no close notify FIN";
      }
      enum flow-ssl-evt-fsm-pa-rcvd-rst {
        value 108;
        description
          "Peer adapter received service chain reset";
      }
      enum flow-ssl-evt-fsm-pa-peer-fs-clsd {
        value 109;
        description
          "Peer adapter peer flow segment closed event";
      }
      enum flow-ssl-evt-fsm-pa-pd {
        value 110;
        description
          "Peer adapter push-down event";
      }
    }
    description
      "SSL Proxy TR events";
  }

  typedef appqoe-flow-sslproxy-state {
    type enumeration {
      enum flow-ssl-state-unknown {
        value 0;
        description
          "Unexpected error state";
      }
      enum flow-ssl-state-ism-none {
        value 1;
        description
          "ISM has no state.";
      }
      enum flow-ssl-state-ism-init {
        value 2;
        description
          "ISM in handshake initialised state";
      }
      enum flow-ssl-state-ism-ch {
        value 3;
        description
          "ISM in client hello state";
      }
      enum flow-ssl-state-ism-bgn {
        value 4;
        description
          "ISM in handshake begin state";
      }
      enum flow-ssl-state-ism-est {
        value 5;
        description
          "ISM in handshake established state";
      }
      enum flow-ssl-state-ism-intr {
        value 6;
        description
          "ISM in handshake ";
      }
      enum flow-ssl-state-ism-comp-cl {
        value 7;
        description
          "ISM in handshake completed by client state";
      }
      enum flow-ssl-state-ism-comp-sr {
        value 8;
        description
          "ISM in handshake completed by server state";
      }
      enum flow-ssl-state-ism-comp {
        value 9;
        description
          "ISM in handshake completed state";
      }
      enum flow-ssl-state-ism-pt {
        value 10;
        description
          "ISM Is in Pass-Through state";
      }
      enum flow-ssl-state-ism-rst {
        value 11;
        description
          "ISM is in reset state";
      }
      enum flow-ssl-state-ism-rst-dl {
        value 12;
        description
          "cscwa70148";
      }
      enum flow-ssl-state-pafs-invalid {
        value 13;
        description
          "Peer adapter is in an invalid state";
      }
      enum flow-ssl-state-pafs-init {
        value 14;
        description
          "Peer adapter is in initialised state";
      }
      enum flow-ssl-state-pafs-fwd-clr {
        value 15;
        description
          "Peer adapter is in forward clear state";
      }
      enum flow-ssl-state-pafs-fwd {
        value 16;
        description
          "Peer adapter is in forward state";
      }
      enum flow-ssl-state-pafs-fwd-hs {
        value 17;
        description
          "Peer adapter is in forward handshake state";
      }
      enum flow-ssl-state-pafs-imp {
        value 18;
        description
          "Peer adapter is in key import state";
      }
      enum flow-ssl-state-pafs-data {
        value 19;
        description
          "Peer adapter is in app data state";
      }
      enum flow-ssl-state-pafs-tcp-cls {
        value 20;
        description
          "Peer adapter is in TCP closing state";
      }
      enum flow-ssl-state-pafs-pd {
        value 21;
        description
          "Peer adapter is in push-down state";
      }
      enum flow-ssl-state-pafs {
        value 22;
        description
          "Peer adapter is in completed state";
      }
      enum flow-ssl-state-lwssl-invalid {
        value 23;
        description
          "Unexpected error state";
      }
      enum flow-ssl-state-lwssl-init {
        value 24;
        description
          "LWSSL is in initialised state";
      }
      enum flow-ssl-state-lwssl-fwd-clr {
        value 25;
        description
          "LWSSL is in forward clear state";
      }
      enum flow-ssl-state-lwssl-pre-ssl {
        value 26;
        description
          "LWSSL is in pre-SSL state";
      }
      enum flow-ssl-state-lwssl-fwd {
        value 27;
        description
          "LWSSL is in forward state";
      }
      enum flow-ssl-state-lwssl-hs {
        value 28;
        description
          "LWSSL is in handshake state";
      }
      enum flow-ssl-state-lwssl-fwd-hs {
        value 29;
        description
          "LWSSL is in handshake forward state";
      }
      enum flow-ssl-state-lwssl-export {
        value 30;
        description
          "LWSSL is in export state";
      }
      enum flow-ssl-state-lwssl-import {
        value 31;
        description
          "LWSSL is in import state";
      }
      enum flow-ssl-state-lwssl-flush-ds {
        value 32;
        description
          "LWSSL is in flush DE state";
      }
      enum flow-ssl-state-lwssl-app-data {
        value 33;
        description
          "LWSSL is in Application data state";
      }
      enum flow-ssl-state-lwssl-wire-clsd {
        value 34;
        description
          "LWSSL is in wire closed state";
      }
      enum flow-ssl-state-lwssl-ao-clsd {
        value 35;
        description
          "LWSSL is in service chain closed state";
      }
      enum flow-ssl-state-lwssl-clsd {
        value 36;
        description
          "LWSSL is in closed state";
      }
      enum flow-ssl-state-lwssl-ss-clsd {
        value 37;
        description
          "LWSSL is in single side closed state";
      }
      enum flow-ssl-state-lwssl-tcp-clsd {
        value 38;
        description
          "LWSSL is in TCP closed state";
      }
      enum flow-ssl-state-lwssl-pd {
        value 39;
        description
          "LWSSL is in push-down state";
      }
      enum flow-ssl-state-lwssl-fs {
        value 40;
        description
          "LWSSL is in flow segment completed state";
      }
    }
    description
      "SSL Proxy SSL state";
  }

  typedef appqoe-flow-status {
    type enumeration {
      enum appqoe-flow-status-active {
        value 0;
        description
          "APPQOE flow is active";
      }
      enum appqoe-flow-status-expired {
        value 1;
        description
          "APPQOE flow has expired";
      }
      enum appqoe-flow-status-error {
        value 2;
        description
          "APPQOE flow has been closed due to an error";
      }
    }
    description
      "Current status of an AppQoE flow";
  }

  typedef appqoe-flow-dreopt-bp-code {
    type enumeration {
      enum appqoe-flow-dreopt-bp-code-na {
        value 0;
        description
          "DRE Optimization successfully applied to flow.";
      }
      enum appqoe-flow-dreopt-bp-code-low-mem {
        value 1;
        description
          "Insufficient System Memory.";
      }
      enum appqoe-flow-dreopt-bp-code-sync {
        value 2;
        description
          "DRE Optimization cache is out of sync.";
      }
      enum appqoe-flow-dreopt-bp-loc-cache-init {
        value 3;
        description
          "The local DRE Optimization cache has not completed initialization.";
      }
      enum appqoe-flow-dreopt-bp-rem-cache-init {
        value 4;
        description
          "The remote DRE Optimization cache has not completed initialization.";
      }
      enum appqoe-flow-dreopt-bp-incompatibl {
        value 5;
        description
          "The Remote (Peer) DRE Optimization cache is not compatible.";
      }
      enum appqoe-flow-dreopt-bp-exceed-ackq {
        value 6;
        description
          "Exceeded ack-Q capability.";
      }
      enum appqoe-flow-dreopt-bp-rem-waitq {
        value 7;
        description
          "Remote wait-Q due to nack.";
      }
      enum appqoe-flow-dreopt-bp-loc-disk-ol {
        value 8;
        description
          "Local DRE Optimization disk over load.";
      }
      enum appqoe-flow-dreopt-bp-rem-disk-ol {
        value 9;
        description
          "Remote (Peer) DRE Optimization disk over load.";
      }
      enum appqoe-flow-dreopt-bp-loc-disk-io {
        value 10;
        description
          "Local DRE Optimization disk IO error.";
      }
      enum appqoe-flow-dreopt-bp-rem-disk-io {
        value 11;
        description
          "Remote (Peer) DRE Optimization disk IO error.";
      }
      enum appqoe-flow-dreopt-bp-flow-type {
        value 12;
        description
          "Flow type cannot be DRE Optimized.";
      }
      enum appqoe-flow-dreopt-bp-chunk-bytes {
        value 13;
        description
          "Last partial chunk.";
      }
      enum appqoe-flow-dreopt-bp-skip-bytes {
        value 14;
        description
          "Skipped frame header.";
      }
      enum appqoe-flow-dreopt-bp-low-comp {
        value 15;
        description
          "DRE Optimization low compression.";
      }
    }
    description
      "Reason why DRE Optimization has been bypassed";
  }

  typedef appqoe-flow-dreopt-policy {
    type enumeration {
      enum appqoe-flow-dreopt-policy-unknown {
        value 0;
        description
          "TCP Flow Optimization policy is unknown";
      }
      enum appqoe-flow-dreopt-policy-tfo-only {
        value 1;
        description
          "TCP Flow Optimization only policy";
      }
      enum appqoe-flow-dreopt-policy-dre-only {
        value 2;
        description
          "DRE Optimization only policy";
      }
      enum appqoe-flow-dreopt-policy-lz-only {
        value 3;
        description
          "LZ Compression only policy";
      }
      enum appqoe-flow-dreopt-policy-dre-lz {
        value 4;
        description
          "DRE Optimization and LZ Compression policy";
      }
    }
    description
      "The DRE Optimization policy.";
  }

  typedef appqoe-flow-dreopt-reset-reason {
    type enumeration {
      enum appqoe-flow-dreopt-rst-none {
        value 0;
        description
          "The DRE Optimized flow has not been reset.";
      }
      enum appqoe-flow-dreopt-rst-wr-fail {
        value 1;
        description
          "The DRE Optimized flow was reset due to write failure";
      }
      enum appqoe-flow-dreopt-rst-rd-fail {
        value 2;
        description
          "The DRE Optimized flow was reset due to read failure";
      }
      enum appqoe-flow-dreopt-rst-wr-wt {
        value 3;
        description
          "The DRE Optimized flow was reset due to write wait";
      }
      enum appqoe-flow-dreopt-rst-no-opt-wr-wt {
        value 4;
        description
          "The DRE Optimized flow was reset due to non optimized write wait";
      }
      enum appqoe-flow-dreopt-rst-opt-rd-wt {
        value 5;
        description
          "The DRE Optimized flow was reset due to read wait";
      }
      enum appqoe-flow-dreopt-rst-no-opt-rd-wt {
        value 6;
        description
          "The DRE Optimized flow was reset due to a reset being received from Service Chain while DRE was in the read wait state";
      }
      enum appqoe-flow-dreopt-rst-decode-fail {
        value 7;
        description
          "The DRE Optimized flow was reset due to decode failure";
      }
      enum appqoe-flow-dreopt-rst-encode-fail {
        value 8;
        description
          "The DRE Optimized flow was reset due to encode failure";
      }
      enum appqoe-flow-dreopt-rst-conn-init {
        value 9;
        description
          "The DRE Optimized flow was reset due to connection initialization failure";
      }
      enum appqoe-flow-dreopt-rst-opt-rd-enexp {
        value 10;
        description
          "The DRE Optimized flow was reset due to an unexpected reset from the WAN side";
      }
      enum appqoe-flow-dreopt-rst-overload {
        value 11;
        description
          "The DRE Optimized flow was reset due to the max supported flow limit having been reached";
      }
      enum appqoe-flow-dreopt-rst-bufmgr-fail {
        value 12;
        description
          "The DRE Optimized flow was reset due to a buffer allocation failure";
      }
      enum appqoe-flow-dreopt-rst-peer-rst-req {
        value 13;
        description
          "The DRE Optimized flow was reset due to a peer reset request";
      }
      enum appqoe-flow-dreopt-rst-conn-state {
        value 14;
        description
          "The DRE Optimized flow was reset due to the flow state being out of sync";
      }
      enum appqoe-flow-dreopt-rst-buff-alloc {
        value 15;
        description
          "The DRE Optimized flow was reset due to buffer allocation failure";
      }
      enum appqoe-flow-dreopt-rst-ssl-replumb {
        value 16;
        description
          "The DRE Optimized flow was reset due to flow a re-plumbing failure";
      }
      enum appqoe-flow-dreopt-rst-tcp-seq-no {
        value 17;
        description
          "The DRE Optimized flow was reset due to a TCP sequence number error";
      }
    }
    description
      "The reasons why a DRE Optimized flow may be reset..";
  }

  typedef appqoe-flow-dreopt-close-state {
    type enumeration {
      enum appqoe-flow-dreopt-close-state-undef {
        value 0;
        description
          "The DRE Optimized close state is undefined.";
      }
      enum appqoe-flow-dreopt-close-state-none {
        value 1;
        description
          "The DRE Optimized flow is not in closed state.";
      }
      enum appqoe-flow-dreopt-close-state-fin {
        value 2;
        description
          "The DRE Optimized flow was closed due to a FIN.";
      }
      enum appqoe-flow-dreopt-close-state-reset {
        value 3;
        description
          "The DRE Optimized flow was closed due to a RESET.";
      }
    }
    description
      "The reasons why a DRE Optimized flow may be reset.";
  }

  typedef appqoe-flow-dreopt-mode {
    type enumeration {
      enum appqoe-flow-dreopt-mode-none {
        value 0;
        description
          "DRE Optimization classification mode not specified";
      }
      enum appqoe-flow-dreopt-mode-uni {
        value 1;
        description
          "Unidirectional DRE Optimization.";
      }
      enum appqoe-flow-dreopt-mode-adaptive {
        value 2;
        description
          "Adaptive DRE Optimization.";
      }
      enum appqoe-flow-dreopt-mode-bi {
        value 3;
        description
          "Bidirectional DRE Optimization";
      }
    }
    description
      "The DRE Optimization classification mode.";
  }

  typedef appqoe-flow-dreopt-conn-types {
    type enumeration {
      enum appqoe-flow-dreopt-conn-type-unknown {
        value 0;
        description
          "The local connection type is unknown.";
      }
      enum appqoe-flow-dreopt-conn-type-orig {
        value 1;
        description
          "The local connection type is Originating.";
      }
      enum appqoe-flow-dreopt-conn-type-term {
        value 2;
        description
          "The local connection type is Terminating.";
      }
    }
    description
      "The local connection type.";
  }

  typedef appqoe-flow-dreopt-buff-block-reason {
    type enumeration {
      enum appqoe-flow-dreopt-buff-block-none {
        value 0;
        description
          "Buffer block allocation is not currently blocked";
      }
      enum appqoe-flow-dreopt-buff-block-buff {
        value 1;
        description
          "Buffer block allocation is currently blocked due to high buffer usage";
      }
      enum appqoe-flow-dreopt-buff-block-ackq {
        value 2;
        description
          "Buffer block allocation is currently blocked due to high ack Queue usage";
      }
      enum appqoe-flow-dreopt-buff-block-flow {
        value 3;
        description
          "Buffer block allocation is currently blocked due to flow control";
      }
      enum appqoe-flow-dreopt-buff-block-task {
        value 4;
        description
          "Buffer block allocation is currently blocked due to task blockage";
      }
      enum appqoe-flow-dreopt-buff-block-lock {
        value 5;
        description
          "Buffer block allocation is currently blocked due to buffer locked";
      }
    }
    description
      "DRE Optimized flow connection buffer block reasons.";
  }

  typedef appqoe-flow-dreopt-flow-events {
    type enumeration {
      enum appqoe-flow-dreopt-unknown {
        value 0;
        description
          "An unknown or unexpected TCP Proxy flow event has occurred";
      }
      enum appqoe-flow-dreopt-cr-rsp-snt {
        value 1;
        description
          "The flow create response message has been sent to TCP Proxy";
      }
      enum appqoe-flow-dreopt-cls-fin-rcv-c {
        value 2;
        description
          "DRE Optimization service has received a client FIN message from TCP Proxy";
      }
      enum appqoe-flow-dreopt-cls-fin-rcv-s {
        value 3;
        description
          "DRE Optimization service has received a server FIN message from TCP Proxy";
      }
      enum appqoe-flow-dreopt-cls-rst-rcv-c {
        value 4;
        description
          "DRE Optimization service has received a client RST message from TCP Proxy";
      }
      enum appqoe-flow-dreopt-cls-rst-rcv-s {
        value 5;
        description
          "DRE Optimization service has received a server RST message from TCP Proxy";
      }
      enum appqoe-flow-dreopt-cls-srv-rst-rcv-c {
        value 6;
        description
          "DRE Optimization service has received a close RST client";
      }
      enum appqoe-flow-dreopt-cls-srv-rst-rcv-s {
        value 7;
        description
          "DRE Optimization service has received a close RST server";
      }
      enum appqoe-flow-dreopt-cls-fin-req-snt-c {
        value 8;
        description
          "FIN close request sent client-to-server";
      }
      enum appqoe-flow-dreopt-cls-fin-rsp-snt-c {
        value 9;
        description
          "FIN close response received client-to-server";
      }
      enum appqoe-flow-dreopt-cls-fin-rsp-sta-c {
        value 10;
        description
          "FIN close with stats response sent client-to-server";
      }
      enum appqoe-flow-dreopt-cls-fin-ini-snt-c {
        value 11;
        description
          "FIN init close sent client-to-server";
      }
      enum appqoe-flow-dreopt-cls-fin-req-snt-s {
        value 12;
        description
          "FIN close request sent server-to-client";
      }
      enum appqoe-flow-dreopt-cls-fin-rsp-snt-s {
        value 13;
        description
          "FIN close response sent server-to-client";
      }
      enum appqoe-flow-dreopt-cls-fin-rsp-sta-s {
        value 14;
        description
          "FIN close with stats response sent server-to-client ";
      }
      enum appqoe-flow-dreopt-cls-fin-ini-snt-s {
        value 15;
        description
          "FIN init close sent server-to-client";
      }
      enum appqoe-flow-dreopt-cls-rst-req-snt-c {
        value 16;
        description
          "RST close request sent client-to-server";
      }
      enum appqoe-flow-dreopt-cls-rst-rsp-snt-c {
        value 17;
        description
          "RST close response sent client-to-server";
      }
      enum appqoe-flow-dreopt-cls-rst-rsp-sta-c {
        value 18;
        description
          "RST close with stats response sent client-to-server";
      }
      enum appqoe-flow-dreopt-cls-rst-ini-snt-c {
        value 19;
        description
          "RST init close sent client-to-server";
      }
      enum appqoe-flow-dreopt-cls-rst-req-snt-s {
        value 20;
        description
          "RST close request sent server-to-client";
      }
      enum appqoe-flow-dreopt-cls-rst-rsp-snt-s {
        value 21;
        description
          "RST close response sent server-to-client";
      }
      enum appqoe-flow-dreopt-cls-rst-rsp-sta-s {
        value 22;
        description
          "RST close with stats response sent server-to-client";
      }
      enum appqoe-flow-dreopt-cls-rst-ini-snt-s {
        value 23;
        description
          "RST init close sent server-to-client";
      }
      enum appqoe-flow-dreopt-eor-req-snt {
        value 24;
        description
          "End of transmission request sent";
      }
      enum appqoe-flow-dreopt-eot-ack-rcv {
        value 25;
        description
          "End of transmission ACK received";
      }
      enum appqoe-flow-dreopt-eot-req-rcv {
        value 26;
        description
          "End of transmission request received";
      }
      enum appqoe-flow-dreopt-eor-ack-snt {
        value 27;
        description
          "End of transmission ACK sent";
      }
      enum appqoe-flow-dreopt-ao-rd-shut {
        value 28;
        description
          "Application Optimiser read socket shutdown";
      }
      enum appqoe-flow-dreopt-ao-wr-shut {
        value 29;
        description
          "Application Optimiser write socket shutdown";
      }
      enum appqoe-flow-dreopt-wan-rd-shut {
        value 30;
        description
          "WAN read socket shutdown";
      }
      enum appqoe-flow-dreopt-wan-wr-shut {
        value 31;
        description
          "WAN write socket shutdown";
      }
      enum appqoe-flow-dreopt-internal-rst {
        value 32;
        description
          "FLow was reset due to an internal reset";
      }
      enum appqoe-flow-dreopt-cls-stat-snt {
        value 33;
        description
          "FLow closed, statistics sent to TCP Proxy";
      }
    }
    description
      "DRE Optimized flow events.";
  }

  typedef appqoe-flow-httpopt-flow-events {
    type enumeration {
      enum appqoe-flow-httpopt-unknown {
        value 0;
        description
          "The default HTTP Optimized flow event.";
      }
      enum appqoe-flow-httpopt-snt-cr-rsp {
        value 1;
        description
          "The flow create response message has been sent to TCP Proxy";
      }
      enum appqoe-flow-httpopt-rcv-fin-c {
        value 2;
        description
          "HTTP Optimization service has received a client FIN message from TCP Proxy";
      }
      enum appqoe-flow-httpopt-rcv-rst-c {
        value 3;
        description
          "HTTP Optimization service has received a client RST message from TCP Proxy";
      }
      enum appqoe-flow-httpopt-rcv-srv-rst-c {
        value 4;
        description
          "HTTP Optimization service has received a client RST message from the server";
      }
      enum appqoe-flow-httpopt-rcv-fin-s {
        value 5;
        description
          "HTTP Optimization service has received a server FIN message from TCP Proxy";
      }
      enum appqoe-flow-httpopt-rcv-rst-s {
        value 6;
        description
          "HTTP Optimization service has received a server RST message from TCP Proxy";
      }
      enum appqoe-flow-httpopt-rcv-srv-rst-s {
        value 7;
        description
          "HTTP Optimization service has received a server RST message from the server";
      }
      enum appqoe-flow-httpopt-snt-fin-rsp-c {
        value 8;
        description
          "HTTP Optimization service has sent a response to the client FIN message received from TCP Proxy";
      }
      enum appqoe-flow-httpopt-snt-fin-rsp-st-c {
        value 9;
        description
          "HTTP Optimization service has sent a response to the client FIN message received from TCP Proxy that also includes the flow statistics";
      }
      enum appqoe-flow-httpopt-snt-rst-rsp-c {
        value 10;
        description
          "HTTP Optimization service has sent a response to the client RST message received from TCP Proxy";
      }
      enum appqoe-flow-httpopt-snt-rsp-rsp-st-c {
        value 11;
        description
          "HTTP Optimization service has sent a response to the client RST message received from TCP Proxy that also includes the flow statistics";
      }
      enum appqoe-flow-httpopt-snt-fin-rsp-s {
        value 12;
        description
          "HTTP Optimization service has sent a response to the server FIN message received from TCP Proxy";
      }
      enum appqoe-flow-httpopt-snt-fin-rsp-st-s {
        value 13;
        description
          "HTTP Optimization service has sent a response to the server FIN message received from TCP Proxy that also includes the flow statistics";
      }
      enum appqoe-flow-httpopt-snt-rst-rsp-s {
        value 14;
        description
          "HTTP Optimization service has sent a response to the server RST message received from TCP Proxy";
      }
      enum appqoe-flow-httpopt-snt-rst-rsp-st-s {
        value 15;
        description
          "HTTP Optimization service has sent a response to the server RST message received from TCP Proxy that also includes the flow statistics";
      }
      enum appqoe-flow-httpopt-snt-int-rst-c {
        value 16;
        description
          "HTTP Optimization service has sent a client-side internal RST message to TCP Proxy";
      }
      enum appqoe-flow-httpopt-snt-int-rst-st-c {
        value 17;
        description
          "HTTP Optimization service has sent a client-side internal RST message with flow stats to TCP Proxy";
      }
      enum appqoe-flow-httpopt-snt-int-rst-s {
        value 18;
        description
          "HTTP Optimization service has sent a server-side internal RST message to TCP Proxy";
      }
      enum appqoe-flow-httpopt-snt-int-rst-st-s {
        value 19;
        description
          "HTTP Optimization service has sent a server-side internal RST message with flow stats to TCP Proxy";
      }
      enum appqoe-flow-httpopt-lan-vconn-clsd {
        value 20;
        description
          "Client-side connection between HTTP Optimization service and HTTP Cache Engine has been closed";
      }
      enum appqoe-flow-httpopt-wan-vconn-clsd {
        value 21;
        description
          "Server-side connection between HTTP Optimization service and HTTP Cache Engine has been closed";
      }
      enum appqoe-flow-httpopt-lan-vconn-abrtd {
        value 22;
        description
          "Client-side connection between HTTP Optimization service and HTTP Cache Engine has been closed due to an error";
      }
      enum appqoe-flow-httpopt-wan-vconn-abrtd {
        value 23;
        description
          "Server-side connection between HTTP Optimization service and HTTP Cache Engine has been closed due to an error";
      }
      enum appqoe-flow-httpopt-lan-conn-clsd {
        value 24;
        description
          "Client-side connection between HTTP Optimization service and TCP Proxy has been closed";
      }
      enum appqoe-flow-httpopt-wan-conn-clsd {
        value 25;
        description
          "Server-side connection between HTTP Optimization service and TCP Proxy has been closed";
      }
    }
    description
      "HTTP Optimized flow events.";
  }

  typedef appqoe-stats-label {
    type enumeration {
      enum appqoe-stat-undef {
        value 0;
        description
          "APPQOE statistics label is not defined";
      }
      enum appqoe-stat-ssl-drop-untrusted-cert {
        value 1;
        description
          "APPQOE statistics label SSL drop due to untrusted certificate";
      }
      enum appqoe-stat-ssl-drop-no-proxy-cert {
        value 2;
        description
          "APPQOE statistics label SSL drop as unable to get proxy certificate";
      }
      enum appqoe-stat-ssl-drop-expired-cert {
        value 3;
        description
          "APPQOE statistics label SSL drop due to certificate expired";
      }
      enum appqoe-stat-ssl-drop-ocsp-cert-verif {
        value 4;
        description
          "APPQOE statistics label SSL due to OCSP certificate verification fail";
      }
      enum appqoe-stat-ssl-drop-endpoint-alert {
        value 5;
        description
          "APPQOE statistics label SSL drop due to endpoint alert";
      }
      enum appqoe-stat-ssl-drop-tcp-close-hs {
        value 6;
        description
          "APPQOE statistics label SSL drop due to TCP close received";
      }
      enum appqoe-stat-ssl-session-alloc-fail {
        value 7;
        description
          "APPQOE statistics label SSL could not allocate sessions";
      }
      enum appqoe-stat-ssl-c2s-wcapi-deny-pkt {
        value 8;
        description
          "APPQOE statistics label SSL client to server packet denied";
      }
      enum appqoe-stat-ssl-s2c-wcapi-deny-pkt {
        value 9;
        description
          "APPQOE statistics label SSL server to client packet denied";
      }
      enum appqoe-stat-rm-res-tcp-used-sess {
        value 10;
        description
          "APPQOE statistics label RM number of sessions used by TCP";
      }
      enum appqoe-stat-rm-res-ssl-used-sess {
        value 11;
        description
          "APPQOE statistics label RM number of sessions used by SSL";
      }
      enum appqoe-stat-rm-health-yellow {
        value 12;
        description
          "APPQOE statistics label RM number of times health status changed to yellow";
      }
      enum appqoe-stat-rm-health-green {
        value 13;
        description
          "APPQOE statistics label RM number of times health status changed to green";
      }
      enum appqoe-stat-rm-tcp-sess-alloc {
        value 14;
        description
          "APPQOE statistics label RM number of sessions allocated by TCP";
      }
      enum appqoe-stat-rm-tcp-sess-free {
        value 15;
        description
          "APPQOE statistics label RM number of sessions freed by TCP";
      }
      enum appqoe-stat-rm-ssl-sess-alloc {
        value 16;
        description
          "APPQOE statistics label RM number of sessions allocated by SSL";
      }
      enum appqoe-stat-rm-ssl-sess-free {
        value 17;
        description
          "APPQOE statistics label RM number of sessions freed by SSL";
      }
      enum appqoe-stat-tcp-tot-conn {
        value 18;
        description
          "APPQOE statistics label TCP total number of connections";
      }
      enum appqoe-stat-tcp-tot-flow-create {
        value 19;
        description
          "APPQOE statistics label TCP total number of flows created";
      }
      enum appqoe-stat-tcp-tot-flow-delete {
        value 20;
        description
          "APPQOE statistics label TCP total number of flows deleted";
      }
      enum appqoe-stat-tcp-tot-curr-conn {
        value 21;
        description
          "APPQOE statistics label TCP total number of current connections";
      }
      enum appqoe-stat-tcp-tot-fail-conn {
        value 22;
        description
          "APPQOE statistics label TCP total number of failed connections";
      }
      enum appqoe-stat-tcp-tot-syncache-add {
        value 23;
        description
          "APPQOE statistics label TCP total number of SYN cache added";
      }
      enum appqoe-stat-vp-tot-syn-drop-pps {
        value 24;
        description
          "APPQOE statistics label transport channel total SYN dropped due to packet per second limit reached";
      }
      enum appqoe-stat-vp-tot-new-conn-fail {
        value 25;
        description
          "APPQOE statistics label transport channel total new connection failed";
      }
      enum appqoe-stat-bbr-act-conn {
        value 26;
        description
          "APPQOE statistics label Bottleneck Bandwidth and Round-trip propagation time(BBR) total active connections";
      }
      enum appqoe-stat-bbr-tot-sendmap-fail {
        value 27;
        description
          "APPQOE statistics label BBR total send map allocation failed";
      }
      enum appqoe-stat-sppi-pkt-avail {
        value 28;
        description
          "APPQOE statistics label Service Plane Packet Interface(SPPI) total available packets";
      }
      enum appqoe-stat-sppi-rx-fail {
        value 29;
        description
          "APPQOE statistics label SPPI failed received packets";
      }
      enum appqoe-stat-sppi-tx-fail {
        value 30;
        description
          "APPQOE statistics label SPPI failed transmit packets";
      }
      enum appqoe-stat-sppi-pipe-disconnect {
        value 31;
        description
          "APPQOE statistics label SPPI pipe disconnected";
      }
      enum appqoe-stat-hput-sys-callout-del {
        value 32;
        description
          "APPQOE statistics label system timer call-out deleted";
      }
      enum appqoe-stat-hput-hpt-callout-del {
        value 33;
        description
          "APPQOE statistics label HPTS(high precision timers) timer call-out deleted";
      }
      enum appqoe-stat-hput-sys-timer-del {
        value 34;
        description
          "APPQOE statistics label system timer deleted";
      }
      enum appqoe-stat-hput-hpt-timer-del {
        value 35;
        description
          "APPQOE statistics label high precision timer deleted";
      }
      enum appqoe-stat-hput-sys-node-empty {
        value 36;
        description
          "APPQOE statistics label system timer node is empty";
      }
      enum appqoe-stat-hput-hpt-node-empty {
        value 37;
        description
          "APPQOE statistics label high precision timer node is empty";
      }
    }
    description
      "APPQOE services registered statistics label";
  }

  typedef appqoe-flow-services {
    type bits {
      bit appqoe-flow-services-tcpproxy {
        position 0;
        description
          "Flow was handled by TCP-Proxy";
      }
      bit appqoe-flow-services-sslproxy {
        position 1;
        description
          "Flow was handled by SSL-Proxy";
      }
      bit appqoe-flow-services-utd {
        position 2;
        description
          "Flow was handled by UTD";
      }
      bit appqoe-flow-services-dreopt {
        position 3;
        description
          "Flow was handled by DRE Optimization";
      }
      bit appqoe-flow-services-httpopt {
        position 4;
        description
          "Flow was handled by HTTP Optimization";
      }
    }
    description
      "Services involved in flow optimization";
  }

  grouping appqoe-modules {
    description
      "Status of each APPQOE service or module.";
    leaf module {
      type appqoe-xe-serv-oper:appqoe-module;
      description
        "Service or module name";
    }
    leaf status {
      type appqoe-xe-serv-oper:appqoe-module-status;
      description
        "Service or module status";
    }
    leaf err-tag {
      type appqoe-xe-serv-oper:appqoe-status-err;
      description
        "Error details when service or module status is not green";
    }
  }

  grouping appqoe-status-details {
    description
      "APPQOE overall status along with
       each service or module registered status.
       Also displays error details when a service or module
       is inactive";
    leaf appqoe-status {
      type appqoe-xe-serv-oper:appqoe-module-status;
      description
        "APPQOE overall status";
    }
    list module-status {
      description
        "Status of APPQOE module registered
         with status infra";
      uses appqoe-xe-serv-oper:appqoe-modules;
    }
  }

  grouping appqoe-flow-tcpproxy-stats {
    description
      "General TCP Proxy flow statistics";
    leaf bytes-sent {
      type uint64;
      units "bytes";
      description
        "Total number of bytes sent";
    }
    leaf bytes-recv {
      type uint64;
      units "bytes";
      description
        "Total number of bytes received";
    }
    leaf bytes-to-ssl {
      type uint64;
      units "bytes";
      description
        "Total number of bytes sent (client) or received (server) to/from SSL Proxy";
    }
    leaf iptos {
      type uint8;
      description
        "IP TOS value received in packets";
    }
    leaf rx-pause {
      type uint32;
      description
        "Proxy has paused to read from socket";
    }
    leaf tx-enabled {
      type uint32;
      description
        "Proxy has enabled writing to socket";
    }
    leaf flow-pause-state {
      type uint32;
      description
        "Flow Pause State of the socket";
    }
    leaf flow-control {
      type uint32;
      description
        "Flow Control bits";
    }
    leaf close-done {
      type uint32;
      description
        "TCP Proxy has closed the socket";
    }
    leaf fin-rcvd {
      type uint32;
      description
        "TCP Proxy has received a FIN message";
    }
    leaf rst-rcvd {
      type uint32;
      description
        "TCP Proxy has received a RST message";
    }
    leaf fin-sent {
      type uint32;
      description
        "TCP Proxy has sent a FIN message";
    }
    leaf res-enqueued {
      type uint32;
      description
        "Number of resume enqueued";
    }
    leaf res-enqueue-ignored {
      type uint32;
      description
        "Number of resume ignored while enqueuing";
    }
    leaf res-processed {
      type uint32;
      description
        "Number of resume processed";
    }
    leaf res-process-ignored {
      type uint32;
      description
        "Number of resume ignored while processing";
    }
  }

  grouping appqoe-flow-tcpproxy-ssl {
    description
      "TCP Proxy & SSL Proxy interaction statistics";
    leaf rd-pause {
      type uint32;
      description
        "Read resume pause";
    }
    leaf rd-pause-fail {
      type uint32;
      description
        "Read resume fail";
    }
    leaf rd-resume-notify {
      type uint32;
      description
        "Read resume notify";
    }
    leaf rd-resume {
      type uint32;
      description
        "Read resume";
    }
  }

  grouping appqoe-flow-tcpproxy-dir {
    description
      "TCP Proxy Client to Server or Server to Client statistics";
    leaf to-dre-bytes {
      type uint64;
      units "bytes";
      description
        "Total number of bytes sent from TCP Proxy to DRE Optimization service";
    }
    leaf to-dre-pkts {
      type uint64;
      description
        "Total number of packets sent from TCP Proxy to DRE Optimization service";
    }
    leaf from-dre-bytes {
      type uint64;
      units "bytes";
      description
        "Total number of bytes sent from DRE Optimization to TCP Proxy";
    }
    leaf from-dre-pkts {
      type uint64;
      description
        "Total number of packets sent from DRE Optimization to TCP Proxy";
    }
    leaf to-http-bytes {
      type uint64;
      units "bytes";
      description
        "Total number of bytes sent from TCP Proxy to HTTP Optimization service";
    }
    leaf to-http-pkts {
      type uint64;
      description
        "Total number of packets sent from TCP Proxy to HTTP Optimization service";
    }
    leaf from-http-bytes {
      type uint64;
      units "bytes";
      description
        "Total number of bytes sent from HTTP Optimization service to TCP Proxy";
    }
    leaf from-http-pkts {
      type uint64;
      description
        "Total number of packets sent from HTTP Optimization service to TCP Proxy";
    }
    leaf dre-paused {
      type uint16;
      description
        "Total number of flow-control pause messages sent from DRE Optimization service to TCP Proxy";
    }
    leaf dre-res-sent {
      type uint16;
      description
        "Total number of flow-control resume messages sent to DRE Optimization service from TCP Proxy";
    }
    leaf dre-res-recv {
      type uint16;
      description
        "Total number of flow-control resume messages received by TCP Proxy from DRE Optimization service";
    }
    leaf http-paused {
      type uint16;
      description
        "Total number of flow-control pause messages sent from HTTP Optimization service to TCP Proxy";
    }
    leaf http-res-sent {
      type uint16;
      description
        "Total number of flow-control resume messages sent to HTTP Optimization service from TCP Proxy";
    }
    leaf http-res-recv {
      type uint16;
      description
        "Total number of flow-control resume messages received by TCP Proxy from HTTP Optimization service";
    }
    leaf tcp-tx-pkts-success {
      type uint64;
      description
        "Total number of packets successfully sent to TCP socket by TCP Proxy";
    }
    leaf tcp-tx-pkts-fail {
      type uint64;
      description
        "Total number of packets that failed to be sent to TCP socket by TCP Proxy";
    }
    leaf svc-bytes-to-ssl {
      type uint64;
      units "bytes";
      description
        "Total number of bytes sent to SSL Proxy from service chain (one or more of UTD, DRE, HTTP)";
    }
    leaf ssl-to-tcp-tx-pkts {
      type uint64;
      description
        "Total number of packets sent to TCP Tx from SSL Proxy";
    }
    leaf ssl-to-tcp-tx-bytes {
      type uint64;
      units "bytes";
      description
        "Total number of bytes sent to TCP Tx from SSL Proxy";
    }
    container ssl-orig {
      description
        "SSL originating stats";
      uses appqoe-xe-serv-oper:appqoe-flow-tcpproxy-ssl;
    }
    container ssl-term {
      description
        "SSL terminating stats";
      uses appqoe-xe-serv-oper:appqoe-flow-tcpproxy-ssl;
    }
    leaf ssl-client-bytes {
      type uint32;
      units "bytes";
      description
        "Total client bytes sent to SSL Proxy";
    }
    leaf ssl-server-bytes {
      type uint32;
      units "bytes";
      description
        "Total server bytes sent to SSL Proxy";
    }
  }

  grouping appqoe-flow-tcpproxy-ad {
    description
      "TCP Proxy Auto Discovery metrics";
    leaf state {
      type appqoe-xe-serv-oper:appqoe-flow-tcpproxy-ad-states;
      description
        "The current Auto Discovery state";
    }
    leaf role {
      type appqoe-xe-serv-oper:appqoe-flow-tcpproxy-ad-roles;
      description
        "The negotiated Auto Discovery role";
    }
    leaf peer-id {
      type uint32;
      description
        "Identifier of the Auto Discovery Peer";
    }
    leaf configured-policy {
      type uint8;
      description
        "The Auto Discovery Configured policy";
    }
    leaf derived-policy {
      type uint8;
      description
        "The Auto Discovery Derived policy after negotiation with the peer";
    }
    leaf peer-policy {
      type uint8;
      description
        "The Auto Discovery peer policy";
    }
    leaf applied-policy {
      type uint8;
      description
        "The Auto Discovery applied policy";
    }
    leaf sync-needed {
      type boolean;
      description
        "Is a sync with the peer required [true | false]";
    }
  }

  grouping appqoe-flow-tcpproxy-bbr-trans {
    description
      "TCP Proxy BBR state transition counters";
    leaf startup-to-drain {
      type uint64;
      description
        "Total of Startup to Drain state transitions";
    }
    leaf startup-to-probebw {
      type uint64;
      description
        "Total of Startup to Probe-BW state transitions";
    }
    leaf startup-to-probertt {
      type uint64;
      description
        "Total Startup to Probe-RTT state transitions";
    }
    leaf drain-to-probebw {
      type uint64;
      description
        "Total Drain to Probe-BW state transitions";
    }
    leaf probebw-to-probertt {
      type uint64;
      description
        "Total Probe-BW to Probe-RTT state transitions";
    }
    leaf probertt-to-startup {
      type uint64;
      description
        "Total Probe-RTT to Startup state transitions";
    }
    leaf probertt-to-probebw {
      type uint64;
      description
        "Total Probe-RTT to Probe-BW state transitions";
    }
    leaf idleexit-to-probebw {
      type uint64;
      description
        "Total Idle-Exit to Probe-BW state transitions";
    }
  }

  grouping appqoe-flow-tcpproxy-bbr-hpts-start-timers {
    description
      "Count of how many times TCP Proxy HPTS Timers were started";
    leaf wrong {
      type uint64;
      description
        "Total number of times Wrong timer was started.";
    }
    leaf persistent {
      type uint64;
      description
        "Total number of times Persistent timer was started.";
    }
    leaf keepalive {
      type uint64;
      description
        "Total number of times Keepalive timer was started.";
    }
    leaf connection-init {
      type uint64;
      description
        "Total number of times Connection-Init timer was started.";
    }
    leaf bbr-segment-unlock1 {
      type uint64;
      description
        "Total number of times BBR Segment Unlock 1 timer was started.";
    }
    leaf bbr-segment-unlock2 {
      type uint64;
      description
        "Total number of times BBR Segment Unlock 2 timer was started.";
    }
    leaf pace-segment {
      type uint64;
      description
        "Total number of times PACE Segment timer was started.";
    }
    leaf bbr-out-wtime-msg-size {
      type uint64;
      description
        "Total number of times BBR output time error message size  timer was started.";
    }
    leaf bbr-out-wtime-default {
      type uint64;
      description
        "Total number of times BBR output time default timer was started.";
    }
    leaf bbr-out-wtime-no-buffs {
      type uint64;
      description
        "Total number of times BBR do time error no buffs timer was started.";
    }
  }

  grouping appqoe-flow-tcpproxy-bbr-hpts-stop-timers {
    description
      "Count of how many times TCP Proxy HPTS Timers were stopped";
    leaf wrong {
      type uint64;
      description
        "Total number of times Wrong timer was stopped.";
    }
    leaf cancel {
      type uint64;
      description
        "Total number of times Cancel timer was stopped.";
    }
    leaf persistent {
      type uint64;
      description
        "Total number of times Persistent timer was stopped.";
    }
    leaf bbr-segment-unlock {
      type uint64;
      description
        "Total number of times BBR segment unlock timer was stopped.";
    }
    leaf pace-packet {
      type uint64;
      description
        "Total number of times PACE packet timer was stopped.";
    }
    leaf early-exempt {
      type uint64;
      description
        "Total number of times Early Exempt timer was stopped.";
    }
    leaf delay-exceed {
      type uint64;
      description
        "Total number of times Delay Exceed timer was stopped.";
    }
    leaf connection-closed {
      type uint64;
      description
        "Total number of times Connection Closed timer was stopped.";
    }
  }

  grouping appqoe-flow-tcpproxy-bbr-pd {
    description
      "Pacing delay (micro-seconds) distribution";
    leaf pd-0 {
      type uint64;
      description
        "Total number of times Pacing Delay was equal to 0";
    }
    leaf pd-1-to-5 {
      type uint64;
      description
        "Total number of times Pacing Delay was between 1 us and 5 us";
    }
    leaf pd-6-to-10 {
      type uint64;
      description
        "Total number of times Pacing Delay was between 6 us and 10 us";
    }
    leaf pd-11-to-20 {
      type uint64;
      description
        "Total number of times Pacing Delay was between 11 us and 20 us";
    }
    leaf pd-21-to-50 {
      type uint64;
      description
        "Total number of times Pacing Delay was between 21 us and 50 us";
    }
    leaf pd-51-to-100 {
      type uint64;
      description
        "Total number of times Pacing Delay was between 51 us and 100 us";
    }
    leaf pd-101-to-500 {
      type uint64;
      description
        "Total number of times Pacing Delay was between 101 us and 500 us";
    }
    leaf pd-501-to-1000 {
      type uint64;
      description
        "Total number of times Pacing Delay was between 501 us and 1000 us";
    }
    leaf pd-greater-than-1000 {
      type uint64;
      description
        "Total number of times Pacing Delay was greater than 1000 us";
    }
  }

  grouping appqoe-flow-tcpproxy-bbr-rtt {
    description
      "Round Trip Time (milli-seconds) distribution";
    leaf rtt-less-than-1 {
      type uint64;
      description
        "Total number of times RTT was less than 1 ms";
    }
    leaf rtt-1 {
      type uint64;
      description
        "Total number of times RTT was equal to 1 ms";
    }
    leaf rtt-1-to-50 {
      type uint64;
      description
        "Total number of times RTT was between 1 ms and 50 ms";
    }
    leaf rtt-51-to-100 {
      type uint64;
      description
        "Total number of times RTT was between 51 ms and 100 ms";
    }
    leaf rtt-101-to-150 {
      type uint64;
      description
        "Total number of times RTT was between 101 ms and 150 ms";
    }
    leaf rtt-151-to-200 {
      type uint64;
      description
        "Total number of times RTT was between 151 ms and 200 ms";
    }
    leaf rtt-greater-than-200 {
      type uint64;
      description
        "Total number of times RTT was greater than 200 ms";
    }
  }

  grouping appqoe-flow-tcpproxy-bbr-bw {
    description
      "Bandwidth utilization distribution";
    leaf bw-less-than-1k {
      type uint64;
      description
        "Total number of times Bandwidth utilization was less than 1 KBps";
    }
    leaf bw-1k-to-250k {
      type uint64;
      description
        "Total number of times Bandwidth utilization was between 1 KBps and 250 KBps";
    }
    leaf bw-250k-to-500k {
      type uint64;
      description
        "Total number of times Bandwidth utilization was between 250 KBps and 500 KBps";
    }
    leaf bw-500k-to-1m {
      type uint64;
      description
        "Total number of times Bandwidth utilization was between 500 KBps and 1 MBps";
    }
    leaf bw-1m-to-2m {
      type uint64;
      description
        "Total number of times Bandwidth utilization was between 1 MBps and 2 MBps";
    }
    leaf bw-2m-to-5m {
      type uint64;
      description
        "Total number of times Bandwidth utilization was between 2 MBps and 5 MBps";
    }
    leaf bw-5m-to-10m {
      type uint64;
      description
        "Total number of times Bandwidth utilization was between 5 MBps and 10 MBps";
    }
    leaf bw-greater-than-10m {
      type uint64;
      description
        "Total number of times Bandwidth utilization was greater than 10 MBps";
    }
  }

  grouping appqoe-flow-tcpproxy-bbr-hpts {
    description
      "TCP Proxy BBR statistics";
    leaf early-timer-expiration {
      type uint64;
      description
        "BBR HPTS early timer expiration counter";
    }
    leaf delayed-timer-expiration {
      type uint64;
      description
        "BBR HPTS delayed timer expiration counter";
    }
    leaf callout-scheduled {
      type uint64;
      description
        "BBR HPTS call-out scheduled counter";
    }
    leaf last-tick-gt-curr-tick {
      type uint64;
      description
        "BBR HPTS last tick is greater than current tick counter";
    }
    leaf max-tick-overflow {
      type uint64;
      description
        "BBR HPTS maximum tick overflow counter";
    }
    leaf timer-wakeup {
      type uint64;
      description
        "BBR HPTS wake-up timer counter";
    }
    leaf inp-same-slot {
      type uint64;
      description
        "Indicates error condition if non-zero, contact TAC";
    }
    leaf dist-to-travel-overflow {
      type uint64;
      description
        "Indicates error condition if non-zero, contact TAC";
    }
    leaf avail-on-wheel-overflow {
      type uint64;
      description
        "Indicates error condition if non-zero, contact TAC";
    }
    leaf avail-on-wheel-lt-pacer {
      type uint64;
      description
        "Indicates error condition if non-zero, contact TAC";
    }
    leaf hpts-hopelessly-behind {
      type uint64;
      description
        "Incremented each time the HPTS processing unit is invoked more than 10 times in a single time interrupt";
    }
    leaf hpts-stuck-in-loop {
      type uint64;
      description
        "HPTS timer is processing the same items on multiple timer events";
    }
    leaf hpts-back-on-sleep {
      type uint64;
      description
        "Incremented when there are no TCP sessions in the HTPS timer wheel";
    }
    leaf hpts-wheel-wrapped {
      type uint64;
      description
        "Indicates error condition if non-zero, contact TAC";
    }
    leaf hpts-wheel-time-exceeded {
      type uint64;
      description
        "Indicates error condition if non-zero, contact TAC";
    }
    leaf fin-wait-2-force {
      type uint64;
      description
        "TCP connection is closed in FIN_WAIT_2 state";
    }
  }

  grouping appqoe-flow-tcpproxy-bbr {
    description
      "TCP Proxy BBR statistics";
    container bbr-state-trans {
      description
        "TCP Proxy BBR state transition counters";
      uses appqoe-xe-serv-oper:appqoe-flow-tcpproxy-bbr-trans;
    }
    container timers-started {
      description
        "Count of how many times each TCP Proxy HPTS Timer were started";
      uses appqoe-xe-serv-oper:appqoe-flow-tcpproxy-bbr-hpts-start-timers;
    }
    container timers-stopped {
      description
        "Count of how many times each TCP Proxy HPTS Timer were stopped";
      uses appqoe-xe-serv-oper:appqoe-flow-tcpproxy-bbr-hpts-stop-timers;
    }
    container pacing-delay {
      description
        "Pacing delay (micro-seconds) distribution";
      uses appqoe-xe-serv-oper:appqoe-flow-tcpproxy-bbr-pd;
    }
    container rtt-stats {
      description
        "Round Trip Time (milli-seconds) distribution";
      uses appqoe-xe-serv-oper:appqoe-flow-tcpproxy-bbr-rtt;
    }
    container bandwidth {
      description
        "Bandwidth utilization distribution";
      uses appqoe-xe-serv-oper:appqoe-flow-tcpproxy-bbr-bw;
    }
    leaf output-bytes {
      type uint64;
      units "bytes";
      description
        "BBR Output Bytes";
    }
    leaf segments-lost {
      type uint64;
      description
        "TCP Segments Lost";
    }
    leaf segments-sent {
      type uint64;
      description
        "TCP Segments Sent";
    }
    leaf retransmitted-segments {
      type uint64;
      description
        "Retransmitted Segments";
    }
    leaf no-progress-pkts-dropped {
      type uint64;
      description
        "Connections dropped due to no progress";
    }
    leaf hpts-tcp-setments {
      type uint64;
      description
        "TCP Segment Sent through HPTS";
    }
    leaf max-send-buffer {
      type uint64;
      description
        "Maximum Send Buffer Reached";
    }
    leaf max-send-congestion-window {
      type uint64;
      description
        "Maximum Send Congestion Window";
    }
    leaf curr-send-window {
      type uint64;
      description
        "Current TCP Send Window";
    }
    container hpts-stats {
      description
        "BBR HPTS statistics";
      uses appqoe-xe-serv-oper:appqoe-flow-tcpproxy-bbr-hpts;
    }
  }

  grouping appqoe-flow-tcpproxy-flow-event {
    description
      "TCP Proxy flow event";
    leaf id {
      type uint8;
      description
        "Unique flow event identifier";
    }
    leaf event {
      type appqoe-xe-serv-oper:appqoe-flow-tcpproxy-flow-events;
      description
        "The TCP Proxy flow event that occurred";
    }
  }

  grouping appqoe-flow-tcpproxy {
    description
      "TCP Proxy flow metrics";
    container client {
      description
        "Client side TCP Proxy flow metrics";
      uses appqoe-xe-serv-oper:appqoe-flow-tcpproxy-stats;
    }
    container server {
      description
        "Server side TCP Proxy flow metrics";
      uses appqoe-xe-serv-oper:appqoe-flow-tcpproxy-stats;
    }
    container c2s {
      description
        "TCP Proxy flow metrics in the client to server flow direction";
      uses appqoe-xe-serv-oper:appqoe-flow-tcpproxy-dir;
    }
    container s2c {
      description
        "TCP Proxy flow metrics in the server to client flow direction";
      uses appqoe-xe-serv-oper:appqoe-flow-tcpproxy-dir;
    }
    container bbr-client {
      description
        "Client side TCP Proxy BBR metrics";
      uses appqoe-xe-serv-oper:appqoe-flow-tcpproxy-bbr;
    }
    container bbr-server {
      description
        "Server side TCP Proxy BBR metrics";
      uses appqoe-xe-serv-oper:appqoe-flow-tcpproxy-bbr;
    }
    container auto-discovery {
      description
        "TCP Proxy Auto Discovery metrics";
      uses appqoe-xe-serv-oper:appqoe-flow-tcpproxy-ad;
    }
    list event {
      description
        "The list of TCP Proxy flow events";
      uses appqoe-xe-serv-oper:appqoe-flow-tcpproxy-flow-event;
    }
  }

  grouping appqoe-flow-sslproxy-fsm {
    description
      "SSL Proxy flow Finite State Machine";
    leaf event {
      type appqoe-xe-serv-oper:appqoe-flow-sslproxy-lwssl-event;
      description
        "The FSM event";
    }
    leaf state {
      type appqoe-xe-serv-oper:appqoe-flow-sslproxy-lwssl-state;
      description
        "The FSM state as a result of the event";
    }
  }

  grouping appqoe-flow-sslproxy-traces {
    description
      "SSL Proxy flow state traces";
    leaf-list state {
      type appqoe-xe-serv-oper:appqoe-flow-sslproxy-lwssl-state;
      ordered-by user;
      description
        "The list of states the SSL Proxy flow has transitioned to";
    }
    list fsm {
      description
        "The list of FSM state transitions for an SSL Proxy flow";
      uses appqoe-xe-serv-oper:appqoe-flow-sslproxy-fsm;
    }
  }

  grouping appqoe-flow-sslproxy-dir-stats {
    description
      "SSL Proxy flow directional statistics - client to server or server to client";
    leaf encrypt-bytes-wr {
      type uint64;
      units "bytes";
      description
        "SSL encrypted bytes written";
    }
    leaf decrypt-bytes-wr {
      type uint64;
      units "bytes";
      description
        "SSL decrypted bytes written";
    }
    leaf encrypt-bytes-rd {
      type uint64;
      units "bytes";
      description
        "SSL encrypted bytes read";
    }
    leaf decrypt-bytes-rd {
      type uint64;
      units "bytes";
      description
        "SSL decrypted bytes read";
    }
    leaf clear-bytes-fwd {
      type uint64;
      units "bytes";
      description
        "Clear/Unencrypted bytes sent to TCP Proxy";
    }
    leaf clear-bytes-to-sc {
      type uint64;
      units "bytes";
      description
        "Clear/Unencrypted bytes sent to Service Controller";
    }
  }

  grouping appqoe-flow-sslproxy-flow-event {
    description
      "SSL Proxy Flow event details";
    leaf id {
      type uint16;
      description
        "Chronological event id";
    }
    leaf module {
      type appqoe-xe-serv-oper:appqoe-flow-sslproxy-module;
      description
        "The module that generated the event";
    }
    leaf side {
      type appqoe-xe-serv-oper:appqoe-flow-side;
      description
        "Originating or Terminating end of the flow";
    }
    leaf event {
      type appqoe-xe-serv-oper:appqoe-flow-sslproxy-tr-events;
      description
        "The generated event";
    }
    leaf context {
      type uint32;
      description
        "The event context";
    }
    leaf orig-state {
      type appqoe-xe-serv-oper:appqoe-flow-sslproxy-state;
      description
        "The originating state";
    }
    leaf term-state {
      type appqoe-xe-serv-oper:appqoe-flow-sslproxy-state;
      description
        "The terminating state";
    }
    leaf-list orig-flag {
      type uint32;
      ordered-by user;
      description
        "The originating flag(s)";
    }
    leaf-list term-flag {
      type uint32;
      ordered-by user;
      description
        "The terminating flag(s)";
    }
  }

  grouping appqoe-flow-sslproxy {
    description
      "SSL Proxy flow metrics";
    container c2s {
      description
        "SSL Proxy flow client to server byte counters";
      uses appqoe-xe-serv-oper:appqoe-flow-sslproxy-dir-stats;
    }
    container s2c {
      description
        "SSL Proxy flow server to client byte counters";
      uses appqoe-xe-serv-oper:appqoe-flow-sslproxy-dir-stats;
    }
    container client-trace {
      description
        "The list of states the SSL Proxy flow has transitioned to";
      uses appqoe-xe-serv-oper:appqoe-flow-sslproxy-traces;
    }
    container server-trace {
      description
        "The list of FSM state transitions for an SSL Proxy flow";
      uses appqoe-xe-serv-oper:appqoe-flow-sslproxy-traces;
    }
    list event {
      description
        "The chronological list of events that occurred on the flow";
      uses appqoe-xe-serv-oper:appqoe-flow-sslproxy-flow-event;
    }
  }

  grouping appqoe-flow-dreopt-summary {
    description
      "DRE Optimized flow summary";
    leaf orig-bytes-read {
      type uint64;
      units "bytes";
      description
        "Total number of original bytes read.";
    }
    leaf opt-bytes-read {
      type uint64;
      units "bytes";
      description
        "Total number of optimized bytes read.";
    }
    leaf orig-bytes-written {
      type uint64;
      units "bytes";
      description
        "Total number of original bytes written.";
    }
    leaf opt-bytes-written {
      type uint64;
      units "bytes";
      description
        "Total number of optimized bytes written.";
    }
    leaf orig-bytes-total {
      type uint64;
      units "bytes";
      description
        "Total number of original bytes read and written.";
    }
    leaf opt-bytes-total {
      type uint64;
      units "bytes";
      description
        "Total number of optimized bytes read and written.";
    }
    leaf reduction-ratio {
      type decimal64 {
        fraction-digits 2;
      }
      description
        "The total reduction ratio achieved for this flow.";
    }
  }

  grouping appqoe-flow-dreopt-msg-sizes {
    description
      "DRE Optimization message size distribution.";
    leaf ms-0-to-1k {
      type decimal64 {
        fraction-digits 2;
      }
      description
        "Message size is between 0 and 1 KB.";
    }
    leaf ms-1k-to-5k {
      type decimal64 {
        fraction-digits 2;
      }
      description
        "Message size is between 1 KB and 5 KB.";
    }
    leaf ms-5k-to-15k {
      type decimal64 {
        fraction-digits 2;
      }
      description
        "Message size is between 5 KB and 15 KB.";
    }
    leaf ms-15k-to-25k {
      type decimal64 {
        fraction-digits 2;
      }
      description
        "Message size is between 15 KB and 25 KB.";
    }
    leaf ms-25k-to-40k {
      type decimal64 {
        fraction-digits 2;
      }
      description
        "Message size is between 25 KB and 40 KB.";
    }
    leaf ms-greater-than-40k {
      type decimal64 {
        fraction-digits 2;
      }
      description
        "Message size is greater than 40 KB.";
    }
  }

  grouping appqoe-flow-dreopt-metrics {
    description
      "DRE Optimized flow metrics";
    leaf num-msgs {
      type uint64;
      description
        "Number of messages received by DRE Optimization service";
    }
    leaf in-bytes {
      type uint64;
      units "bytes";
      description
        "Number of bytes received by DRE Optimization service";
    }
    leaf out-bytes {
      type uint64;
      units "bytes";
      description
        "Number of bytes sent by DRE Optimization service";
    }
    leaf re-in-bytes {
      type uint64;
      units "bytes";
      description
        "Number of bytes received by RE service";
    }
    leaf re-out-bytes {
      type uint64;
      units "bytes";
      description
        "Number of bytes sent by RE service";
    }
    leaf bypass-num-msgs {
      type uint64;
      description
        "Number of messages bypassed by DRE Optimization service";
    }
    leaf bypass-bytes {
      type uint64;
      units "bytes";
      description
        "Number of bytes bypassed by DRE Optimization service";
    }
    leaf lz-num-msgs {
      type uint64;
      description
        "Number of messages received by LZ service";
    }
    leaf lz-in-bytes {
      type uint64;
      units "bytes";
      description
        "Number of bytes received by LZ service";
    }
    leaf lz-out-bytes {
      type uint64;
      units "bytes";
      description
        "Number of bytes sent by LZ service";
    }
    container msg-size-distr {
      description
        "DRE Optimized message size distribution.";
      uses appqoe-xe-serv-oper:appqoe-flow-dreopt-msg-sizes;
    }
  }

  grouping appqoe-flow-dreopt-bp-reason {
    description
      "DRE Optimized bypass reason.";
    leaf code {
      type appqoe-xe-serv-oper:appqoe-flow-dreopt-bp-code;
      description
        "The bypass code identifying why the flow was not optimized";
    }
    leaf count {
      type uint64;
      description
        "The total number of packets bypassed for the specified reason";
    }
    leaf bytes {
      type uint64;
      units "bytes";
      description
        "The total number of bytes bypassed for the specified reason";
    }
  }

  grouping appqoe-flow-dreopt-lz-latency {
    description
      "DRE Optimized LZ latency.";
    leaf time-in-ms {
      type decimal64 {
        fraction-digits 2;
      }
      description
        "The average latency per message added by LZ compression (encode/decode).";
    }
    leaf avg-msg-size {
      type uint32;
      description
        "The average size of each LZ compressed message.";
    }
  }

  grouping appqoe-flow-dreopt-eot-state {
    description
      "DRE Optimized flow End Of Transaction states";
    leaf req-send {
      type boolean;
      description
        "The request send state [true | false].";
    }
    leaf ack-send {
      type boolean;
      description
        "The ack send state [true | false].";
    }
    leaf req-recv {
      type boolean;
      description
        "The request receive state [true | false].";
    }
    leaf ack-recv {
      type boolean;
      description
        "The ack receive state [true | false].";
    }
  }

  grouping appqoe-flow-dreopt-end-pt-states {
    description
      "DRE Optimized flow end point states";
    leaf read-shut {
      type boolean;
      description
        "Is the endpoint read shut [true | false].";
    }
    leaf write-shut {
      type boolean;
      description
        "Is the endpoint write shut [true | false].";
    }
    leaf close-recv {
      type appqoe-xe-serv-oper:appqoe-flow-dreopt-close-state;
      description
        "Has close message been received [true | false].";
    }
    leaf close-sent {
      type appqoe-xe-serv-oper:appqoe-flow-dreopt-close-state;
      description
        "Has close message been sent [true | false].";
    }
    leaf peer-choke-on {
      type boolean;
      description
        "[true | false].";
    }
  }

  grouping appqoe-flow-dreopt-classification {
    description
      "DRE Optimized flow classification information.";
    leaf loc-cfg-mode {
      type appqoe-xe-serv-oper:appqoe-flow-dreopt-mode;
      description
        "Locally configured classification mode.";
    }
    leaf rem-cfg-mode {
      type appqoe-xe-serv-oper:appqoe-flow-dreopt-mode;
      description
        "Remote configured classification mode.";
    }
    leaf applied-mode {
      type appqoe-xe-serv-oper:appqoe-flow-dreopt-mode;
      description
        "The applied classification mode.";
    }
    leaf mode-negotiated {
      type boolean;
      description
        "Was the classification mode negotiated [true | false].";
    }
  }

  grouping appqoe-flow-dreopt-conn-read {
    description
      "DRE Optimized flow connection read statistics.";
    leaf total-bytes {
      type uint64;
      units "bytes";
      description
        "Total number of bytes read";
    }
    leaf total-reads {
      type uint64;
      description
        "Total number of read operations";
    }
    leaf avg-size {
      type uint32;
      description
        "Average size of each read operation";
    }
    leaf sched-latency {
      type decimal64 {
        fraction-digits 2;
      }
      description
        "Average schedule latency for read thread";
    }
    leaf stop-latency {
      type decimal64 {
        fraction-digits 2;
      }
      description
        "Average stop latency for read thread";
    }
    leaf read-latency {
      type decimal64 {
        fraction-digits 2;
      }
      description
        "Average read latency for read thread";
    }
    leaf flow-ctrl-stop {
      type uint64;
      description
        "Read thread is currently stopped due to flow control";
    }
    leaf peer-choke {
      type uint64;
      description
        "True when we are unable to send traffic to DRE peer as it cannot handle more traffic";
    }
    leaf processed-ack-frames {
      type uint64;
      description
        "Number of ACK frames that have been processed";
    }
  }

  grouping appqoe-flow-dreopt-conn-write {
    description
      "DRE Optimized flow connection write statistics";
    leaf total-bytes {
      type uint64;
      units "bytes";
      description
        "Total number of bytes written";
    }
    leaf total-writes {
      type uint64;
      description
        "Total number of write operations";
    }
    leaf avg-size {
      type uint64;
      description
        "Average size of each write operation";
    }
    leaf latency {
      type uint64;
      description
        "Average write latency";
    }
  }

  grouping appqoe-flow-dreopt-conn-tcpproxy {
    description
      "Flow statistics between DRE Optimization and TCP Proxy.";
    leaf total-calls {
      type uint64;
      description
        "Total number of times encode/decode is called";
    }
    leaf latency {
      type decimal64 {
        fraction-digits 2;
      }
      description
        "Average read/write latency";
    }
    leaf total-send-frames {
      type uint64;
      description
        "Total number of data/ack frames that have been sent";
    }
    leaf total-bypass-pkts {
      type uint64;
      description
        "Total number of packets that have been bypassed";
    }
    leaf total-bypass-bytes {
      type uint64;
      units "bytes";
      description
        "Total number of bytes that have been bypassed";
    }
    leaf max-byte-size {
      type uint64;
      units "bytes";
      description
        "Maximum message size";
    }
    leaf curr-byte-size {
      type uint64;
      units "bytes";
      description
        "Size of the current message";
    }
    leaf total-pkts {
      type uint64;
      description
        "Total number of packets sent";
    }
    leaf avg-bytes {
      type uint64;
      units "bytes";
      description
        "Average message size";
    }
    leaf max-pkts {
      type uint64;
      description
        "Maximum number of packets queued";
    }
    leaf curr-pkts {
      type uint64;
      description
        "Current number of packets queued";
    }
    leaf avg-pkts {
      type uint64;
      description
        "Average number of packets queued";
    }
  }

  grouping appqoe-flow-dreopt-conn-pending {
    description
      "DRE Optimized flow connection writer pending queue statistics.";
    leaf max-size {
      type uint64;
      description
        "Maximum number of packets in the writer pending queue at any point in time";
    }
    leaf curr-size {
      type uint64;
      description
        "Current number of packets in the writer pending queue";
    }
    leaf avg-size {
      type uint64;
      description
        "Average number of packets in the writer pending queue over the life of the connection";
    }
    leaf flow-ctrl-stop {
      type uint64;
      description
        "Is the writer currently stopped due to flow control congestion [true | false]|";
    }
    leaf paused {
      type boolean;
      description
        "Is the writer thread currently paused [true | false]";
    }
  }

  grouping appqoe-flow-dreopt-conn-flow-ctrl {
    description
      "DRE Optimized flow connection flow control statistics.";
    leaf total-pause {
      type uint32;
      description
        "Total number of times DRE Optimization has been paused";
    }
    leaf total-resume-sent {
      type uint64;
      description
        "Total number of times DRE Optimization sent a resume message";
    }
    leaf total-resume-recv {
      type uint64;
      description
        "Total number of times DRE Optimization received a resume message";
    }
    leaf buff-ctrl-block {
      type uint64;
      description
        "Is task currently blocked due to buffer control [true | false]";
    }
    leaf flow-ctrl-block {
      type uint64;
      description
        "Is task currently blocked due to flow control [true | false]";
    }
    leaf ackq-ctrl-block {
      type uint64;
      description
        "Is task currently blocked due to ack queue control [true | false]";
    }
    leaf locked-block {
      type uint64;
      description
        "Is task currently blocked due to the task being locked [true | false]";
    }
    leaf task-block {
      type uint64;
      description
        "Is task currently blocked [true | false]";
    }
    leaf ack-queue-pause {
      type uint64;
      description
        "Is task currently paused due to ack queue [true | false]";
    }
    leaf buff-ctrl-pause {
      type uint64;
      description
        "Is task currently paused due to buffer control [true | false]";
    }
    leaf buff-block-reason {
      type appqoe-xe-serv-oper:appqoe-flow-dreopt-buff-block-reason;
      description
        "The reason why the buffer is blocked";
    }
  }

  grouping appqoe-flow-dreopt-conn {
    description
      "DRE Optimized flow connection information";
    leaf type {
      type appqoe-xe-serv-oper:appqoe-flow-dreopt-conn-types;
      description
        "The connection type";
    }
    container bypass-reason {
      description
        "The reason why DRE Optimization was bypassed for this flow.";
      uses appqoe-xe-serv-oper:appqoe-flow-dreopt-bp-reason;
    }
    leaf total-num-nack {
      type uint64;
      description
        "Total number of negative acknowledgment messages.";
    }
    leaf num-col-nack {
      type uint64;
      description
        "Total number of col negative acknowledgment messages.";
    }
    leaf num-miss-nack {
      type uint64;
      description
        "Total number of miss negative acknowledgment messages.";
    }
    leaf num-cache-not-ready-nack {
      type uint64;
      description
        "Total number of cache not ready negative
         acknowledgment messages.";
    }
    leaf total-num-rtx {
      type uint64;
      description
        "Total number of NACK messages sent";
    }
    leaf num-col-rtx {
      type uint64;
      description
        "Total number of NACK messages sent due to a checksum collision during decode";
    }
    leaf num-miss-rtx {
      type uint64;
      description
        "Total number of NACK messages sent due to missing chunk during decode";
    }
    leaf num-cache-not-ready-rtx {
      type uint64;
      description
        "Total number of NACK messages sent due to cache not being ready during decode";
    }
    container encode-lz-latency {
      description
        "LZ compression encoding latency statistics";
      uses appqoe-xe-serv-oper:appqoe-flow-dreopt-lz-latency;
    }
    container decode-lz-latency {
      description
        "LZ compression decoding latency statistics";
      uses appqoe-xe-serv-oper:appqoe-flow-dreopt-lz-latency;
    }
    leaf policy {
      type appqoe-xe-serv-oper:appqoe-flow-dreopt-policy;
      description
        "The DRE policy applied to the flow. Default: DRE + LZ";
    }
    container eot-state {
      description
        "The end of transaction state.";
      uses appqoe-xe-serv-oper:appqoe-flow-dreopt-eot-state;
    }
    leaf reset-reason {
      type appqoe-xe-serv-oper:appqoe-flow-dreopt-reset-reason;
      description
        "The reason why the flow was reset in the case of an error. For normal flow termination, set to NONE";
    }
    container end-pt-states {
      description
        "The flow end points (LAN / WAN) states";
      uses appqoe-xe-serv-oper:appqoe-flow-dreopt-end-pt-states;
    }
    container classification {
      description
        "The DRE mode negotiated with the peer";
      uses appqoe-xe-serv-oper:appqoe-flow-dreopt-classification;
    }
    container encode-read {
      description
        "The encode read statistics";
      uses appqoe-xe-serv-oper:appqoe-flow-dreopt-conn-read;
    }
    container decode-read {
      description
        "The decode read statistics";
      uses appqoe-xe-serv-oper:appqoe-flow-dreopt-conn-read;
    }
    container encode-write {
      description
        "The encode write statistics";
      uses appqoe-xe-serv-oper:appqoe-flow-dreopt-conn-write;
    }
    container decode-write {
      description
        "The decode write statistics";
      uses appqoe-xe-serv-oper:appqoe-flow-dreopt-conn-write;
    }
    container encode-tcpproxy {
      description
        "Encode statistics between DRE and TCP Proxy";
      uses appqoe-xe-serv-oper:appqoe-flow-dreopt-conn-tcpproxy;
    }
    container decode-tcpproxy {
      description
        "Decode statistics between DRE and TCP Proxy";
      uses appqoe-xe-serv-oper:appqoe-flow-dreopt-conn-tcpproxy;
    }
    container decoder-pend {
      description
        "The decoder pending queue statistics";
      uses appqoe-xe-serv-oper:appqoe-flow-dreopt-conn-pending;
    }
    container writer-encode-pend {
      description
        "The writer encode pending queue statistics";
      uses appqoe-xe-serv-oper:appqoe-flow-dreopt-conn-pending;
    }
    container writer-decode-pend {
      description
        "The writer decode pending queue statistics";
      uses appqoe-xe-serv-oper:appqoe-flow-dreopt-conn-pending;
    }
    container encode-flow-ctrl {
      description
        "The encode flow control statistics";
      uses appqoe-xe-serv-oper:appqoe-flow-dreopt-conn-flow-ctrl;
    }
    container decode-flow-ctrl {
      description
        "The decode flow control statistics";
      uses appqoe-xe-serv-oper:appqoe-flow-dreopt-conn-flow-ctrl;
    }
  }

  grouping appqoe-flow-dreopt-flow-event {
    description
      "A DRE Optimization flow event";
    leaf id {
      type uint8;
      description
        "Unique flow event identifier";
    }
    leaf event {
      type appqoe-xe-serv-oper:appqoe-flow-dreopt-flow-events;
      description
        "The DRE Optimization flow event that occurred";
    }
  }

  grouping appqoe-flow-dreopt {
    description
      "DRE Optimized flow metrics";
    leaf peer-no {
      type uint32;
      description
        "Peer Number of DRE peer handling this flow";
    }
    leaf start-time {
      type yang:date-and-time;
      description
        "Timestamp when DRE Optimization started";
    }
    leaf end-time {
      type yang:date-and-time;
      description
        "Timestamp when DRE Optimization ended";
    }
    leaf status {
      type appqoe-xe-serv-oper:appqoe-flow-status;
      description
        "Current DRE Optimization flow status";
    }
    container opt-summary {
      description
        "OPtimization summary statistics";
      uses appqoe-xe-serv-oper:appqoe-flow-dreopt-summary;
    }
    container encode {
      description
        "Encode statistics";
      uses appqoe-xe-serv-oper:appqoe-flow-dreopt-metrics;
    }
    container decode {
      description
        "Decode statistics";
      uses appqoe-xe-serv-oper:appqoe-flow-dreopt-metrics;
    }
    container connection {
      description
        "Connection statistics";
      uses appqoe-xe-serv-oper:appqoe-flow-dreopt-conn;
    }
    list event {
      description
        "DRE Optimized flow events";
      uses appqoe-xe-serv-oper:appqoe-flow-dreopt-flow-event;
    }
  }

  grouping appqoe-flow-httpopt-bytes {
    description
      "HTTP Optimized read and write byte counters";
    leaf wcapi-bytes-rd {
      type uint32;
      units "bytes";
      description
        "Bytes received from TCP Proxy";
    }
    leaf wcapi-bytes-wr {
      type uint32;
      units "bytes";
      description
        "Bytes written to TCP Proxy";
    }
    leaf vconn-bytes-rd {
      type uint32;
      units "bytes";
      description
        "Bytes read from the HTTP cache engine";
    }
    leaf vconn-bytes-wr {
      type uint32;
      units "bytes";
      description
        "Bytes written to the HTTP cache engine";
    }
  }

  grouping appqoe-flow-httpopt-io-close {
    description
      "HTTP Optimization service IO close metrics";
    leaf pending {
      type uint8;
      units "bytes";
      description
        "Bytes that were pending to be sent during connection close";
    }
    leaf sent {
      type uint64;
      units "bytes";
      description
        "Bytes that were successfully sent during connection close";
    }
    leaf send-failed {
      type uint64;
      units "bytes";
      description
        "Bytes that we failed to send during connection close";
    }
  }

  grouping appqoe-flow-httpopt-io-pending {
    description
      "HTTP Optimization IO pending metrics";
    leaf max-queue-size {
      type uint32;
      description
        "The maximum number of bytes in the IO pending queue at any point in time";
    }
    leaf cur-queue-size {
      type uint32;
      description
        "The current number of bytes in the IO pending queue to be sent";
    }
    leaf tot-packet-count {
      type uint32;
      description
        "The total number of packets in the IO pending queue over the life of the flow";
    }
    leaf max-packet-count {
      type uint32;
      description
        "The maximum number of packets in the IO pending queue at any point in time";
    }
  }

  grouping appqoe-flow-httpopt-flow-ctrl {
    description
      "HTTP Optimization service flow control metrics";
    leaf paused {
      type uint32;
      description
        "The total number of times the flow was paused";
    }
    leaf resume-sent {
      type uint32;
      description
        "The total number of times HTTP Optimization service resumed the flow";
    }
    leaf resume-rcvd {
      type uint32;
      description
        "The total number of times TCP Proxy resumed the flow";
    }
  }

  grouping appqoe-flow-httpopt-state-conn {
    description
      "HTTP Optimization service connection states";
    leaf rd-shut {
      type boolean;
      description
        "When True, HTTP Optimization service will not read packets from TCP Proxy";
    }
    leaf wr-shut {
      type boolean;
      description
        "When True, HTTP Optimization service will not write packets to TCP Proxy";
    }
    leaf proxy-rd-shut {
      type boolean;
      description
        "When True, HTTP Cache Engine will not read any packets from the server";
    }
    leaf proxy-wr-shut {
      type boolean;
      description
        "When True, HTTP Cache Engine will not write any packets to the server";
    }
  }

  grouping appqoe-flow-httpopt-flow-state {
    description
      "HTTP Optimization service flow state";
    leaf reset-code {
      type uint32;
      description
        "Indicates if the flow has been reset due to an error";
    }
    container client {
      description
        "Client side flow state";
      uses appqoe-xe-serv-oper:appqoe-flow-httpopt-state-conn;
    }
    container server {
      description
        "Server side flow state";
      uses appqoe-xe-serv-oper:appqoe-flow-httpopt-state-conn;
    }
  }

  grouping appqoe-flow-httpopt-flow-event {
    description
      "A HTTP Optimization flow event";
    leaf id {
      type uint8;
      description
        "Unique flow event identifier";
    }
    leaf event {
      type appqoe-xe-serv-oper:appqoe-flow-httpopt-flow-events;
      description
        "The HTTP Optimization flow event that occurred";
    }
  }

  grouping appqoe-flow-httpopt {
    description
      "HTTP Optimization service flow metrics";
    leaf server-vconn-started {
      type uint32;
      description
        "Total number of connections established from HTTP Optimization service to the server for this flow";
    }
    leaf server-vconn-closed {
      type uint32;
      description
        "Total number of connections between HTTP Optimization service and the server for this flow that have been closed";
    }
    leaf server-vconn-aborted {
      type uint32;
      description
        "Total number of connections between HTTP Optimization service and the server for this flow that have been closed due to an error";
    }
    container client-bytes {
      description
        "Client-side byte metrics";
      uses appqoe-xe-serv-oper:appqoe-flow-httpopt-bytes;
    }
    container server-bytes {
      description
        "Server-side byte metrics";
      uses appqoe-xe-serv-oper:appqoe-flow-httpopt-bytes;
    }
    container client-io-close {
      description
        "Client-side IO close metrics";
      uses appqoe-xe-serv-oper:appqoe-flow-httpopt-io-close;
    }
    container server-io-close {
      description
        "Server-side IO close metrics";
      uses appqoe-xe-serv-oper:appqoe-flow-httpopt-io-close;
    }
    container client-io-pending {
      description
        "Client-side IO pending metrics";
      uses appqoe-xe-serv-oper:appqoe-flow-httpopt-io-pending;
    }
    container server-io-pending {
      description
        "Server-side IO pending metrics";
      uses appqoe-xe-serv-oper:appqoe-flow-httpopt-io-pending;
    }
    container client-flow-ctrl {
      description
        "Client-side flow control metrics";
      uses appqoe-xe-serv-oper:appqoe-flow-httpopt-flow-ctrl;
    }
    container server-flow-ctrl {
      description
        "Server-side flow control metrics";
      uses appqoe-xe-serv-oper:appqoe-flow-httpopt-flow-ctrl;
    }
    container state {
      description
        "The current state of the flow";
      uses appqoe-xe-serv-oper:appqoe-flow-httpopt-flow-state;
    }
    list event {
      description
        "List of HTTP Optimization service flow events";
      uses appqoe-xe-serv-oper:appqoe-flow-httpopt-flow-event;
    }
  }

  grouping appqoe-flow-brief-key {
    description
      "Active flow unique identifier attributes.";
    leaf vpn-id {
      type uint32;
      description
        "Flow VPN identifier.";
    }
    leaf client-ip {
      type inet:ip-address;
      description
        "Flow client IP address.";
    }
    leaf client-port {
      type uint16;
      description
        "Flow client port number.";
    }
    leaf server-ip {
      type inet:ip-address;
      description
        "Flow server IP address.";
    }
    leaf server-port {
      type uint16;
      description
        "Flow server port number.";
    }
    leaf index {
      type uint32;
      description
        "The index when combined with the other key fields ensures flow uniqueness.";
    }
  }

  grouping appqoe-flow-brief {
    description
      "Brief AppQoE flow attributes and statistics.";
    leaf flow-id {
      type uint64;
      description
        "Unique Flow identifier. This field should be used to retrieve the detailed attributes of a specific flow";
    }
    leaf services {
      type appqoe-xe-serv-oper:appqoe-flow-services;
      description
        "Bitmap representing services that handled the flow";
    }
    leaf start-time {
      type yang:date-and-time;
      description
        "Timestamp of when flow was started";
    }
    leaf end-time {
      type yang:date-and-time;
      description
        "Timestamp if the flow has expired";
    }
    leaf rx-bytes {
      type uint64;
      units "bytes";
      description
        "Total number of bytes received";
    }
    leaf tx-bytes {
      type uint64;
      units "bytes";
      description
        "Total number of bytes sent";
    }
    leaf connect-detect {
      type uint16;
      description
        "HTTP connect detected counter.";
    }
  }

  grouping appqoe-flow-detail {
    description
      "Active flow attributes and statistics.";
    leaf flow-id {
      type uint64;
      description
        "Flow identifier.";
    }
    leaf vpn-id {
      type uint32;
      description
        "Flow VPN identifier.";
    }
    leaf client-ip {
      type inet:ip-address;
      description
        "Flow client IP address.";
    }
    leaf client-port {
      type uint16;
      description
        "Flow client port number.";
    }
    leaf server-ip {
      type inet:ip-address;
      description
        "Flow server IP address.";
    }
    leaf server-port {
      type uint16;
      description
        "Flow server port number.";
    }
    leaf services {
      type appqoe-xe-serv-oper:appqoe-flow-services;
      description
        "Bitmap representing services that handled the flow";
    }
    leaf start-time {
      type yang:date-and-time;
      description
        "Timestamp of when flow was started";
    }
    leaf end-time {
      type yang:date-and-time;
      description
        "Timestamp if the flow has expired";
    }
    leaf rx-bytes {
      type uint64;
      units "bytes";
      description
        "Total number of bytes received";
    }
    leaf tx-bytes {
      type uint64;
      units "bytes";
      description
        "Total number of bytes sent";
    }
    container sslproxy {
      description
        "SSL Proxy flow metrics.";
      uses appqoe-xe-serv-oper:appqoe-flow-sslproxy;
    }
    container tcpproxy {
      description
        "TCP Proxy/Optimization flow metrics.";
      uses appqoe-xe-serv-oper:appqoe-flow-tcpproxy;
    }
    container dreopt {
      description
        "DRE Optimization flow metrics.";
      uses appqoe-xe-serv-oper:appqoe-flow-dreopt;
    }
    container httpopt {
      description
        "HTTP Optimization flow metrics.";
      uses appqoe-xe-serv-oper:appqoe-flow-httpopt;
    }
  }

  grouping appqoe-flow-error-entry {
    description
      "Flows closed due to errors in any of APPQOE services.";
    leaf flow-id {
      type uint64;
      description
        "Flow identifier.";
    }
    leaf vpn-id {
      type uint32;
      description
        "Flow VPN identifier.";
    }
    leaf client-ip {
      type inet:ip-address;
      description
        "Flow client IP address.";
    }
    leaf client-port {
      type uint16;
      description
        "Flow client port number.";
    }
    leaf server-ip {
      type inet:ip-address;
      description
        "Flow server IP address.";
    }
    leaf server-port {
      type uint16;
      description
        "Flow server port number.";
    }
    leaf services {
      type appqoe-xe-serv-oper:appqoe-flow-services;
      description
        "Bitmap representing services that handled the flow.";
    }
    leaf start-time {
      type yang:date-and-time;
      description
        "Timestamp of when flow was started.";
    }
    leaf tx-bytes {
      type uint64;
      units "bytes";
      description
        "Total number of bytes sent.";
    }
    leaf rx-bytes {
      type uint64;
      units "bytes";
      description
        "Total number of bytes received.";
    }
    leaf tcpproxy-err-tag {
      type appqoe-xe-serv-oper:tcpproxy-flow-err-tag;
      description
        "Error details set by TCP-Proxy service.";
    }
    leaf sslproxy-err-tag {
      type appqoe-xe-serv-oper:sslproxy-flow-err-tag;
      description
        "Error details set by SSL-Proxy service.";
    }
    leaf connect-detect {
      type uint16;
      description
        "Error flow HTTP connect detected counter.";
    }
  }

  grouping appqoe-flow-error {
    description
      "Flows closed due to errors in any of APPQOE services.";
    leaf flow-count {
      type uint32;
      description
        "Current number of flows closed due to error.";
    }
    list appqoe-flow-error-entry {
      key "flow-id";
      description
        "List of flows closed due to error.";
      uses appqoe-xe-serv-oper:appqoe-flow-error-entry;
    }
  }

  grouping appqoe-flow-summary {
    description
      "Summary of aggregated flow statistics.";
    leaf total-flows {
      type uint64;
      description
        "Total number of flows handled by AppQoE services.";
    }
    leaf active-flows {
      type uint32;
      description
        "Current active optimized flow count.";
    }
    leaf expired-flows {
      type uint64;
      description
        "Total number of flows that have been successfully optimized since last clear or AppQoE service restart.";
    }
    leaf error-flows {
      type uint64;
      description
        "Total number of flows that were not optimized due to an error since last clear or AppQoE service restart.";
    }
    leaf max-concurrent-flows {
      type uint32;
      description
        "The maximum number of flows handled concurrently by AppQoE Services.";
    }
    leaf flows-in-progress {
      type uint32;
      description
        "Total number of flows in connection establishment/initialisation state.";
    }
  }

  grouping appqoe-stats-recent {
    description
      "APPQOE statistics holding the current value, 30 and 60 sec prior values";
    leaf stat-current {
      type uint64;
      description
        "APPQOE current value of statistics";
    }
    leaf stat-30s {
      type uint64;
      description
        "APPQOE statistics updated 30 seconds ago";
    }
    leaf stat-60s {
      type uint64;
      description
        "APPQOE statistics updated 60 seconds ago";
    }
    leaf label {
      type appqoe-xe-serv-oper:appqoe-stats-label;
      description
        "APPQOE services registered statistics label";
    }
  }

  grouping appqoe-stats-recent-db {
    description
      "APPQOE services registered statistics database";
    list stats-rec {
      description
        "Registered statistics at different time intervals";
      uses appqoe-xe-serv-oper:appqoe-stats-recent;
    }
  }

  container appqoe-serv-oper-data {
    config false;
    description
      "APPQOE serviceability operational data, such as
          APPQOE overall status along with individual service status,
          flows closed due to error with reason,
          statistics for monitoring failure.";
    container appqoe-status-details {
      presence "appqoe-status-details";
      description
        "APPQOE overall status along with individual service status,
         also displays the reason if any services is inactive";
      uses appqoe-xe-serv-oper:appqoe-status-details;
    }
    list appqoe-flow-active-brief {
      key "vpn-id client-ip client-port server-ip server-port index";
      description
        "Brief statistics and metrics of Current real-time active flows handled by SD-WAN AppQoE services. The response is currently limited to 50 flows.";
      uses appqoe-xe-serv-oper:appqoe-flow-brief-key;
      uses appqoe-xe-serv-oper:appqoe-flow-brief;
    }
    list appqoe-flow-active-detail {
      key "flow-id";
      description
        "Brief statistics and metrics of Current real-time active flows handled by SD-WAN AppQoE services.";
      uses appqoe-xe-serv-oper:appqoe-flow-detail;
    }
    list appqoe-flow-expired-brief {
      key "vpn-id client-ip client-port server-ip server-port index";
      description
        "Brief statistics and metrics of the 100 most recent expired flows handled by SD-WAN AppQoE services.";
      uses appqoe-xe-serv-oper:appqoe-flow-brief-key;
      uses appqoe-xe-serv-oper:appqoe-flow-brief;
    }
    list appqoe-flow-expired-detail {
      key "flow-id";
      description
        "Detailed statistics and metrics of the most recent expired flows handled by SD-WAN AppQoE services.";
      uses appqoe-xe-serv-oper:appqoe-flow-detail;
    }
    container appqoe-flow-error {
      presence "appqoe-flow-error";
      description
        "Flows closed due to errors by respective services are listed.
            Flows closed without errors are excluded.";
      uses appqoe-xe-serv-oper:appqoe-flow-error;
    }
    container appqoe-flow-summary {
      presence "appqoe-flow-summary";
      description
        "Summary of aggregated SD-WAN AppQoE flow statistics.";
      uses appqoe-xe-serv-oper:appqoe-flow-summary;
    }
    container appqoe-stats-recent {
      presence "appqoe-stats-recent";
      description
        "APPQOE services registered counters that helps in abnormal
            behavior is seen with connections or flows.";
      uses appqoe-xe-serv-oper:appqoe-stats-recent-db;
    }
  }
}
