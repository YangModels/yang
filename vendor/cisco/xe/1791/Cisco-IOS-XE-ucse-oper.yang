module Cisco-IOS-XE-ucse-oper {
  yang-version 1;
  namespace "http://cisco.com/ns/yang/Cisco-IOS-XE-ucse-oper";
  prefix ucse-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for UCSE (Unified Computing System E-Series) operational data.
     Copyright (c) 2019 by Cisco Systems, Inc.
     All rights reserved.";

  revision 2019-05-01 {
    description
      "Added semantic version";
    reference
      "1.0.1";
    cisco-semver:module-version "1.0.1";
  }
  revision 2019-01-08 {
    description
      "Initial revision";
    reference
      "1.0.0";
    cisco-semver:module-version "1.0.0";
  }

  grouping ucse-command-stats {
    description
      "UCSE (Unified Computing System E-Series) command statistics";
    leaf shutdown-count {
      type uint64;
      description
        "Number of times shutdown command executed";
    }
    leaf status-count {
      type uint64;
      description
        "Number of times status command executed";
    }
    leaf server-raid-password-reset-count {
      type uint64;
      description
        "Number of times server RAID (Redundant Array of Independent Disks) password-reset command executed";
    }
    leaf server-bios-password-reset-count {
      type uint64;
      description
        "Number of times server BIOS password-reset command executed";
    }
    leaf server-reload-count {
      type uint64;
      description
        "Number of times server reload command executed";
    }
    leaf server-reset-count {
      type uint64;
      description
        "Number of times server reset command executed";
    }
    leaf server-start-count {
      type uint64;
      description
        "Number of times server restart command executed";
    }
    leaf server-stop-count {
      type uint64;
      description
        "Number of times server stop command executed";
    }
    leaf imc-password-reset-count {
      type uint64;
      description
        "Number of times IMC (Integrated Management Controller) password-reset command executed";
    }
    leaf imc-vlan-count {
      type uint64;
      description
        "Number of times IMC (Integrated Management Controller) VLAN command executed";
    }
    leaf imc-access-port-count {
      type uint64;
      description
        "Number of times IMC (Integrated Management Controller) access-port command executed";
    }
    leaf imc-ip-count {
      type uint64;
      description
        "Number of times IMC (Integrated Management Controller) IP command executed";
    }
    leaf stats-start-time {
      type yang:date-and-time;
      description
        "Start time of statistics collection";
    }
  }

  grouping ucse-stats {
    description
      "UCSE (Unified Computing System E-Series) statistics";
    container command-stats {
      description
        "UCSE (Unified Computing System E-Series) command statistics";
      uses ucse-ios-xe-oper:ucse-command-stats;
    }
  }

  grouping ucse-slot-info-key {
    description
      "Key information";
    leaf slot-num {
      type uint32;
      description
        "Slot number";
    }
    leaf subslot-num {
      type uint32;
      description
        "Sub Slot number";
    }
  }

  container ucse-oper-data {
    config false;
    description
      "UCSE (Unified Computing System E-Series) operational data";
    list ucse-stats {
      key "slot-num subslot-num";
      description
        "UCSE (Unified Computing System E-Series) statistics";
      uses ucse-ios-xe-oper:ucse-slot-info-key;
      uses ucse-ios-xe-oper:ucse-stats;
    }
  }
}
