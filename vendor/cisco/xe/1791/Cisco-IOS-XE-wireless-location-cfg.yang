module Cisco-IOS-XE-wireless-location-cfg {
  yang-version 1;
  namespace "http://cisco.com/ns/yang/Cisco-IOS-XE-wireless-location-cfg";
  prefix wireless-location-cfg;

  import Cisco-IOS-XE-wireless-enum-types {
    prefix wireless-enum-types;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Model for managing location configurations
     Copyright (c) 2016-2022 by Cisco Systems, Inc.
     All rights reserved.";

  revision 2022-07-01 {
    description
      "Added Operator parameters for AAA Location";
    reference
      "3.2.0";
    cisco-semver:module-version "3.2.0";
  }
  revision 2019-05-01 {
    description
      "Added semantic version";
    reference
      "3.1.0";
    cisco-semver:module-version "3.1.0";
  }
  revision 2019-03-12 {
    description
      "convert location presence container into a non-presence container";
    reference
      "3.0.0";
    cisco-semver:module-version "3.0.0";
  }
  revision 2018-01-31 {
    description
      "CMX cloud support";
    reference
      "2.1.0";
    cisco-semver:module-version "2.1.0";
  }
  revision 2018-01-24 {
    description
      "The first generally available version";
    reference
      "2.0.0";
    cisco-semver:module-version "2.0.0";
  }
  revision 2017-05-05 {
    description
      "Initial revision";
    reference
      "1.0.0";
    cisco-semver:module-version "1.0.0";
  }

  grouping location {
    description
      "Configuring the timeouts for calibration and notification";
    leaf location-algorithm {
      type wireless-enum-types:apf-location-algorithm-type;
      default "loc-alg-average";
      description
        "The algorithm used to average RSSI and SNR values, a balance of accuracy and CPU";
    }
    leaf location-notify-client-threshold {
      type uint32 {
        range "0 .. 10";
      }
      default "0";
      description
        "NMSP notification threshold for clients";
    }
    leaf location-rssi-client-threshold {
      type wireless-enum-types:half-life-time;
      default "half-life-time-0";
      description
        "NMSP notification threshold for clients";
    }
    leaf location-rssi-cal-client-threshold {
      type wireless-enum-types:half-life-time;
      default "half-life-time-0";
      description
        "Half life for calibrating clients";
    }
    leaf location-rssi-rogue-ap-threshold {
      type wireless-enum-types:half-life-time;
      default "half-life-time-0";
      description
        "Half life for Rogue APs";
    }
    leaf location-expiry-client-threshold {
      type uint32 {
        range "5 .. 3600";
      }
      default "15";
      description
        "Timeout for RSSI values";
    }
    leaf location-expiry-cal-client-threshold {
      type uint32 {
        range "1 .. 3600";
      }
      default "5";
      description
        "Timeout for calibrating clients";
    }
  }

  grouping operator-location {
    description
      "AAA Location Operator parameters";
    leaf loc-oper-id {
      type string {
        length "0..215";
      }
      description
        "AAA Location Operator ID";
    }
    leaf loc-oper-name {
      type string {
        length "0..250";
      }
      default "";
      description
        "AAA Location Operator Name";
    }
    leaf loc-ns-id {
      type wireless-enum-types:enm-location-namespace-id;
      default "loc-ns-id-realm";
      description
        "AAA Location Namespace ID";
    }
  }

  grouping st-nmsp-cloud-params {
    description
      "Configuring the parameters for CMX cloud";
    leaf enable {
      type boolean;
      default "false";
      description
        "Enable NMSP CMX cloud services";
    }
    leaf server-url {
      type string;
      default "";
      description
        "Server URL for CMX cloud services";
    }
    leaf proxy-hostname {
      type string;
      default "";
      description
        "Hostname for the proxy";
    }
    leaf proxy-port {
      type uint16 {
        range "1 .. 65535";
      }
      default "1";
      description
        "Port to use for the proxy";
    }
    leaf auth-token {
      type string;
      default "";
      description
        "Authentication token for the CMX cloud services";
    }
  }

  grouping nmsp-config {
    description
      "NMSP notification parameters";
    leaf enable {
      type boolean;
      default "false";
      description
        "Enable NMSP server";
    }
    leaf is-secure {
      type boolean;
      default "false";
      description
        "Enable strong ciphers for NMSP server";
    }
    leaf rssi-measurement-notify-interval {
      type uint32 {
        range "1 .. 180";
      }
      default "2";
      description
        "RSSI measurement notify interval";
    }
    leaf client-notify-interval {
      type uint32 {
        range "1 .. 180";
      }
      default "2";
      description
        "Measurement interval for clients in seconds";
    }
    leaf rogue-client-notify-interval {
      type uint32 {
        range "1 .. 180";
      }
      default "2";
      description
        "Measurement interval for rogue clients";
    }
    leaf rogue-ap-notify-interval {
      type uint32 {
        range "1 .. 180";
      }
      default "2";
      description
        "Measurement interval for rogue APs";
    }
    leaf spectrum-notify-interval {
      type uint32 {
        range "1 .. 180";
      }
      default "2";
      description
        "Measurement interval for spectrum interferers";
    }
    container cloud-params {
      description
        "Configuring the parameters for CMX cloud";
      uses wireless-location-cfg:st-nmsp-cloud-params;
    }
  }

  container location-cfg-data {
    description
      "yang model for location config";
    container operator-locations {
      description
        "AAA Location Operators";
      list operator-location {
        key "loc-oper-id";
        description
          "Configuration parameters for AAA Location Operators";
        uses wireless-location-cfg:operator-location;
      }
    }
    container nmsp-config {
      presence "nmsp-config";
      description
        "NMSP notification parameters";
      uses wireless-location-cfg:nmsp-config;
    }
    container location {
      description
        "location config parameters";
      uses wireless-location-cfg:location;
    }
  }
}
