module Cisco-IOS-XE-wireless-hyperlocation-oper {
  yang-version 1;
  namespace "http://cisco.com/ns/yang/Cisco-IOS-XE-wireless-hyperlocation-oper";
  prefix wireless-hyperlocation-oper;

  import Cisco-IOS-XE-wireless-ap-types {
    prefix ap-types;
  }
  import Cisco-IOS-XE-wireless-types {
    prefix wireless-types;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for wireless Hyperlocation operational data.
     Copyright (c) 2018-2019, 2022 by Cisco Systems, Inc.
     All rights reserved.";

  revision 2022-07-01 {
    description
      "- Added NTP server to hyperlocation profile";
    reference
      "1.2.0";
    cisco-semver:module-version "1.2.0";
  }
  revision 2019-05-01 {
    description
      "Added semantic version";
    reference
      "1.1.0";
    cisco-semver:module-version "1.1.0";
  }
  revision 2018-07-09 {
    description
      "Initial revision";
    reference
      "1.0.0";
    cisco-semver:module-version "1.0.0";
  }

  grouping ewlc-hyperlocation-profile {
    description
      "Hyperlocation AP profile data";
    leaf name {
      type string;
      description
        "AP profile name";
    }
    container hyperlocation-data {
      description
        "Cisco AP hyperlocation details";
      uses ap-types:st-hyperlocation;
    }
    leaf ntp-server {
      type inet:ip-address;
      description
        "Configured hyperlocation NTP server";
    }
    leaf status {
      type boolean;
      description
        "Operational status";
    }
    leaf reason-down {
      type wireless-types:enm-hyperlocation-reason;
      description
        "Reason for operational status being down";
    }
    leaf oper-ntp-server {
      type inet:ip-address;
      description
        "Operational NTP server";
    }
  }

  container hyperlocation-oper-data {
    config false;
    description
      "Hyperlocation operational data";
    list ewlc-hyperlocation-profile {
      key "name";
      description
        "Hyperlocation AP profile data";
      uses wireless-hyperlocation-oper:ewlc-hyperlocation-profile;
    }
  }
}
