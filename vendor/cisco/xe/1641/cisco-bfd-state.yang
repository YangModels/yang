module cisco-bfd-state {

    yang-version 1;

    namespace "urn:cisco:params:xml:ns:yang:cisco-bfd-state";
    prefix bfd;

    import ietf-inet-types {
        prefix inet;
    }

    organization
       "Cisco Systems, Inc.";

    contact
       " Cisco Systems, Inc.
         Customer Service

         Postal: 170 W Tasman Drive
         San Jose, CA 95134

         Tel: +1 1800 553-NETS

         E-mail: cs-yang@cisco.com";
    
    description
       " This module contains a collection of YANG definitions for
         monitoring BFD neighborship.";
    
    reference "TODO";

    revision 2015-04-09 {
        description "Proposed";
    }

    grouping bfd-neighbor-params {
        leaf ld {
            type uint32;
            description "local-discriminator";
        }

        leaf rd {
            type uint32;
            description "remote-discriminator";
        }

        leaf remote-state {
            type enumeration {
                enum up;
                enum down;
                enum init;
                enum admindown;
                enum invalid;
            }
            description " Remote Heard. RH state of BFD version '0' 
                          is also mapped to up/down. ";
        }

        leaf state {
            type enumeration {
                enum admindown;
                enum down;
                enum fail;
                enum init;
                enum up;
                enum invalid;
            }
        }
    }

    container bfd-state {
        config false;

        description
          "Data nodes for BFD neighbors.";

	list sessions {
	    key "type";
	    leaf type {
		type enumeration {
		    enum ipv4;
		    enum ipv6;
		    enum vccv;
		    enum mpls-tp;
		    enum ipv4-multihop;
		    enum ipv6-multihop;
		}
	    }

	    list tunnel-path {
                when "../type='mpls-tp'";
                key "interface lsp-type";

                leaf interface {
                    type  string;
                }

                leaf lsp-type {
	            type enumeration {
		        enum working;
		        enum protect;
			enum unknown;
                    }
                }
                uses bfd-neighbor-params;
            }

	    list circuit {
		when "../type='vccv'";
		key "interface vcid";

		leaf interface {
		    type  string;
		}

		leaf vcid {
		    type uint32;
		}
		uses bfd-neighbor-params;
	    }

	    list nbr {
                when "../type!='mpls-tp' and ../type!='vccv'";
                key "ip interface";

                leaf ip {
                    type inet:ip-address;
                }

                leaf interface {
                    type string;
                }

                uses bfd-neighbor-params;
            
                description
                    "This is for directly connected neighbor case.";
            }

            list mhop-nbr {
                when "../type='ipv4-multihop' or ../type='ipv6-multihop'";
                key "ip";

                leaf ip {
                    type inet:ip-address;
                }

                uses bfd-neighbor-params;
            
                description
                    "This is for multi hop neighbor scenario 
                     for global VRF (no VRF).";
            }

	    list mhop-vrf-nbr {
                when "../type='ipv4-multihop' or ../type='ipv6-multihop'";
                key "ip vrf";

                leaf ip {
                    type inet:ip-address;
                }

                leaf vrf {
                    type string;
                }
	        uses bfd-neighbor-params;

                description
                    "This is for multi hop neighbor scenario 
                     for non-global VRF.";
	    }
        }
    }

}
