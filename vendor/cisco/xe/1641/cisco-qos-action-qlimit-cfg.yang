/*-------------------------------------------------------------------
 *  cisco-qos-action-qlimit-cfg.yang - Action queue limit 
 * 
 *  April, Xia Wu   
 *                                           
 *  Copyright (c) 2015 by Cisco Systems, Inc.
 *  All rights reserved.                     
 *-------------------------------------------------------------------
 */

module cisco-qos-action-qlimit-cfg {
    namespace "urn:cisco:params:xml:ns:yang:cisco-qos-action-qlimit-cfg";
    prefix ql;

    import cisco-qos-common {
        prefix qos;
    }

    import ietf-diffserv-policy {
        prefix policy;
    }

    import ietf-diffserv-action {
        prefix action;
    }

    organization "Cisco Systems";
    contact
        "Editor:   Xia Wu
        <mailto:xiaw2@cisco.com>";
    description
        "This module contains YANG definitions for
        configuring queue limit

        Copyright (c) 2015 by Cisco Systems, Inc.
        All rights reserved.";

    revision 2015-05-09 {
        description "first revision";
        reference "ietf-diffserv-action.yang";
    }

    feature disc-class-based-queuing-support {
        description "The feature to allow the discard class based \
            queuing to be configured";
    }
    feature mpls-exp-based-queuing-support {
        description "The feature to allow the mpls exp based \
            queuing to be configured";
    }
    feature qos-grp-based-queuing-support {
        description "The feature to allow the qos group based \
            queuing to be configured";
    }

    grouping QUEUELIMIT{
            description "Queue limit parameters except for dscp-based";
            container qlimit-default-thresh {
                uses qos:THRESHOLD;
                description "default threshold";
            }

            container qlimit-cos-thresh-lists {
                description "Lists for cos-based queue limit";
                list qlimit-cos-thresh-list {
                    key "cos-min cos-max";
                    uses qos:COS-RANGE;
                    uses qos:THRESHOLD;
                    description "List for cos-based queue limit";
                }
            }

            container qlimit-disc-class-thresh-lists {
                description "Lists for discard-class-based queue limit";
                list qlimit-disc-class-thresh-list {
                    if-feature disc-class-based-queuing-support;
                    key "disc-class-min disc-class-max";
                    uses qos:DISC-CLASS-RANGE;
                    uses qos:THRESHOLD;
                    description "List for discard-class-based queue limit";
                }
            }

            container qlimit-qos-grp-thresh-lists {
                description "Lists for qos-group-based queue limit";
                list qlimit-qos-grp-thresh-list {
                    if-feature qos-grp-based-queuing-support;
                    key "qos-group-min qos-group-max";
                    uses qos:QOS-GRP-RANGE;
                    uses qos:THRESHOLD;
                    description "List for qos-group-based queue limit";
                }    
            }

            container qlimit-mpls-exp-thresh-lists {
                description "Lists for mpls-exp-based queue limit";
                list qlimit-mpls-exp-thresh-list {
                    if-feature qos-grp-based-queuing-support;
                    key "exp-min exp-max";
                    uses qos:MPLS-EXP-RANGE;
                    uses qos:THRESHOLD;
                    description "List for mpls-exp-based queue limit";
                }
            }
    }

/*
    augment "/policy:policies/policy:policy-entry"
        + "/policy:classifier-entry"
        + "/policy:classifier-action-entry-cfg/"
        + "policy:action-cfg-params" 
        + "/action:algorithmic-drop/action:drop-algorithm"
        + "/action:tail-drop/action:tail-drop-cfg" {
            description "Extend the tail-drop-cfg to add more \
                based types for queue-limit";
            uses QUEUELIMIT;
        }
    augment "/policy:policies/policy:policy-entry"
        + "/policy:classifier-entry"
        + "/policy:classifier-action-entry-cfg/"
        + "policy:action-cfg-params" 
        + "/action:algorithmic-drop/action:drop-algorithm"
        + "/action:tail-drop/action:tail-drop-cfg/"
        + "action:qlimit-dscp-thresh/action:threshold/"
        + "action:threshold-type/action:size"   { 
            description "Extend the threshold to add the units";
            uses qos:THRESH-SIZE-UNIT;
        } 

    augment  "/policy:policies/policy:policy-entry"
        + "/policy:classifier-entry"
        + "/policy:classifier-action-entry-cfg/"
        + "policy:action-cfg-params" 
        + "/action:algorithmic-drop/action:drop-algorithm"
        + "/action:tail-drop/action:tail-drop-cfg/"
        + "action:qlimit-dscp-thresh/action:threshold/"
        + "action:threshold-type/action:interval"   {
            description "Extend the threshold to add the units"; 
            uses qos:THRESH-INTERVAL-UNIT;
        }
*/

}
