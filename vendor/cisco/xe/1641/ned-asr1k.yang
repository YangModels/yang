module ned-asr1k {
    namespace "http://cisco.com/ns/yang/ned/ios/asr1k";
    prefix asr1k;

    import tailf-common {
       prefix tailf;
    }

    import ned {
       prefix ned;
    }

    description
      "Copyright (c) 2016 by Cisco Systems, Inc."+
      "All rights reserved.";

    revision 2016-04-07 {
      description
        "Update description with copyright notice.";
    }

    revision 2016-02-26 {
       description "ASR1k CLIs for platform specific config";
    }

    augment /ned:native/ned:platform/ned:punt-policer {
        list punt-num {
            tailf:cli-drop-node-name;
            tailf:cli-suppress-mode;
            tailf:cli-compact-syntax;
            tailf:cli-sequence-commands {
               tailf:cli-reset-siblings;
            }
            tailf:cli-incomplete-command;
            tailf:info "Configure punt cause to be policed";
            description "Configure punt cause to be policed";
            key "cause";
            leaf cause {
              type uint8 {
                 tailf:info "<1-89>;;Punt cause to be policed";
                 range "1..89";
              }
            }
            leaf max-rate {
               tailf:cli-drop-node-name;
               type uint16 {
                 tailf:info "<10-32000>;;max punt rate for cause MPLS ICMP Can't Frag";
                 range "10..32000";
               }
            }
            leaf high {
               tailf:info "High priority traffic only";
               description "High priority traffic only";
               type empty;
            }
        }
    }
}
