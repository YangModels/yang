module cisco-memory-stats {

    yang-version 1;

    namespace "urn:cisco:params:xml:ns:yang:cisco-memory-stats";
    prefix mstats;


    organization
        "Cisco Systems, Inc.";

    contact
        " Cisco Systems, Inc.
          Customer Service

          Postal: 170 W Tasman Drive
          San Jose, CA 95134

          Tel: +1 1800 553-NETS

          E-mail: cs-yang@cisco.com";
    
    description
        " This module contains a collection of YANG definitions for
          monitoring memory in a Network Element.";
    
    reference "TODO";

    revision 2015-04-09 {
        description "Proposed";
    }


    container memory-stats {
        config false;

        description
          "Data nodes for All Memory Pool Statistics.";

        list pool {
            key "name";

            description
                "The list of software memory pools in the system.";

            leaf name {
                type string;
                description
                    "The name of the memory pool.";
            }

            leaf total-memory {
                type uint64;
                units "bytes";
                description "Total memory in the pool (bytes)";
            }

            leaf used-memory {
                type uint64;
                units "bytes";
                description "Total used memory in the pool (bytes)";
            }

            leaf free-memory {
                type uint64;
                units "bytes";
                description "Total free memory in the pool (bytes)";
            }

            leaf lowest-usage {
                type uint64;
                units "bytes";
                description "Historical lowest memory usage (bytes)";
            }

            leaf highest-usage {
                type uint64;
                units "bytes";
                description "Historical highest memory usage (bytes)";
            }
        }
    }

}
