/*
 * Generated by confdc --mib2yang-std
 * Source: mgmt/dmi/model/common/mib-source/SONET-MIB.mib
 */
/*
 * This YANG module has been generated by smidump 0.5.0:
 *
 *      smidump -f yang SONET-MIB
 *
 * Do not edit. Edit the source file instead!
 */

module SONET-MIB {

  namespace "urn:ietf:params:xml:ns:yang:smiv2:SONET-MIB";
  prefix SONET-MIB;

  import IF-MIB {
    prefix "if-mib";
  }

  import PerfHist-TC-MIB {
    prefix "perfhist-tc";
  }

  import SNMPv2-TC {
    prefix "snmpv2-tc";
  }

  import ietf-yang-smiv2 {
    prefix "smiv2";
  }

  organization
   "IETF AToM MIB Working Group";

  contact
   "WG charter:
    http://www.ietf.org/html.charters/atommib-charter.html
    
    Mailing Lists:
    General Discussion: atommib@research.telcordia.com
    To Subscribe: atommib-request@research.telcordia.com
    
    Kaj Tesink
    Telcordia Technologies
    Tel: (732) 758-5254
    Fax: (732) 758-2269
    E-mail: kaj@research.telcordia.com.";

  description
   "The MIB module to describe SONET/SDH interface objects.
    
    Copyright (C) The Internet Society (2003).  This version
    of this MIB module is part of RFC 3592;  see the RFC
    itself for full legal notices.";

  revision 2003-08-11 {
    description
     "The key changes made to this MIB module
      since its publication in RFC 2558
      are as follows.
      
      (1) Corrected typographical error
          (bellcore1991(2) in sonetSESthresholdSet)
      
      (2) Added support for sts192cSTM64(6) and
          sts768cSTM256(7) in sonetPathCurrentWidth
      
      (3) Corrected description of the applicability
          of VTs for SDH for improved accuracy
      
      (4) Added clarification in the SES description that
          CV counts should be frozen during SESs
      
      (5) Corrected typographical errors:
          - Line Alarm Indication Signal description of the
            Terminology section (20.5 --> 2.5 seconds)
          - In the Terminology section
            sonetSESThresholdSet  --> sonetSESthresholdSet
          ";
  }

  revision 1998-10-19 {
    description
     "The RFC 2558 version of this MIB module.
      The key changes made to this MIB module
      since its initial publication in RFC 1595
      are as follows.
      
      (1) The MODULE-IDENTITY has been updated to reflect the
          changes to the MIB.
      
      (2) Where applicable, the textual conventions
          PerfCurrentCount and PerfIntervalCount from
          PerfHist-TC-MIB have been used in place of Gauge32.
      
      (3) An agent now has the option to delay updates to
          the various performance counts in lieu of performing
          retroactive adjustments upon entering into or exiting
          from unavailable time. This implementation option is
          described in Appendix A of this memo.
      
      (4) In order to make the SONET-MIB more useful for
          circuit provisioning, the formerly read-only objects
          sonetMediumType, sonetMediumLineCoding,
          sonetMediumLineType, and sonetMediumCircuitIdentifier
          have been given a MAX-ACCESS of read-write. The
          MIN-ACCESS remains read-only.
      
      (5) The DESCRIPTION clause for sonetMediumTimeElapsed has
          been updated to describe its behaviour if the duration
          of the current interval exceeds the maximum value.
      
      (6) The DESCRIPTION clause for sonetMediumValidIntervals
          has been updated to describe its behaviour when some
          intervals may be unavailable, and the object
          sonetMediumInvalidIntervals has been added to keep
          count of the number of missing intervals (if any).
      
      (7) The object sonetMediumLoopbackConfig has been added
          to enable or disable loopback configurations.
      
      (8) Because the error count thresholds for declaring
          severely errored seconds that are specified in ANSI
          T1.231-1993, ITU-T G.826-1995, and ANSI T1.231-1997
          are all different from each other and from the thresholds
          specified in RFC 1595, an enumerated INTEGER object
          sonetSESthresholdSet has been added to allow an agent
          to specify which threshold set is in use. Text has
          been added to Section 3 stating that if this object is
          not implemented the thresholds specified in RFC 1595
          should be assumed, and the table containing those
          thresholds has been moved to Appendix B of this memo.
      
      (9) A column with SYNTAX TruthValue has been added to each
          interval table.  The purpose of the additional column
          is to indicate, for each interval, whether the data
          is valid in the sense intended by ANSI T1.231 clause
          9.1.2.2 [T1.231a][T1.231b]. The objects in question are:
      
              sonetSectionIntervalValidData
              sonetLineIntervalValidData
              sonetFarEndLineIntervalValidData
              sonetPathIntervalValidData
              sonetFarEndPathIntervalValidData
              sonetVTIntervalValidData
              sonetFarEndVTIntervalValidData
      
      (10) The ranges for sonetPathCurrentStatus and
          sonetVTCurrentStatus have been made consistent
          with the DESCRIPTION clauses.
      
      (11) The conformance information has been updated. Previous
          conformance information from RFC 1595 has been
          deprecated. Some typographical errors in the deprecated
          section have been corrected in order to prevent
          MIB compilation errors.";
  }

  revision 1994-01-03 {
    description
     "The RFC 1595 version of this MIB module.";
  }


  container SONET-MIB {
    config false;

    container sonetMedium {
      smiv2:oid "1.3.6.1.2.1.10.39.1.1";

      leaf sonetSESthresholdSet {
        type enumeration {
          enum "other" {
            value "1";
          }
          enum "bellcore1991" {
            value "2";
          }
          enum "ansi1993" {
            value "3";
          }
          enum "itu1995" {
            value "4";
          }
          enum "ansi1997" {
            value "5";
          }
        }
        description
         "An enumerated integer indicating which
          recognized set of SES thresholds that
          the agent uses for determining severely
          errored seconds and unavailable time.
          
          other(1)
            None of the following.
          
          bellcore1991(2)
            Bellcore TR-NWT-000253, 1991 [TR253], or
            ANSI T1M1.3/93-005R2, 1993 [T1M1.3].
            See also Appendix B.
          
          ansi1993(3)
            ANSI T1.231, 1993 [T1.231a], or
            Bellcore GR-253-CORE, Issue 2, 1995 [GR253]
          
          itu1995(4)
            ITU Recommendation G.826, 1995 [G.826]
          
          ansi1997(5)
            ANSI T1.231, 1997 [T1.231b]
          
          If a manager changes the value of this
          object then the SES statistics collected
          prior to this change must be invalidated.";
        smiv2:max-access "read-write";
        smiv2:oid "1.3.6.1.2.1.10.39.1.1.2";
      }
    }

    container sonetMediumTable {
      description
       "The SONET/SDH Medium table.";
      smiv2:oid "1.3.6.1.2.1.10.39.1.1.1";

      list sonetMediumEntry {
        key "ifIndex";
        description
         "An entry in the SONET/SDH Medium table.";
        smiv2:oid "1.3.6.1.2.1.10.39.1.1.1.1";

        leaf ifIndex {
          type leafref {
            path "/if-mib:IF-MIB/if-mib:ifTable/if-mib:ifEntry/if-mib:ifIndex";
          }
        }

        leaf sonetMediumType {
          type enumeration {
            enum "sonet" {
              value "1";
            }
            enum "sdh" {
              value "2";
            }
          }
          description
           "This variable identifies whether a SONET
            or a SDH signal is used across this interface.";
          smiv2:max-access "read-write";
          smiv2:oid "1.3.6.1.2.1.10.39.1.1.1.1.1";
        }

        leaf sonetMediumTimeElapsed {
          type int32 {
            range "1..900";
          }
          description
           "The number of seconds, including partial seconds,
            that have elapsed since the beginning of the current
            measurement period. If, for some reason, such as an
            adjustment in the system's time-of-day clock, the
            current interval exceeds the maximum value, the
            agent will return the maximum value.";
          smiv2:max-access "read-only";
          smiv2:oid "1.3.6.1.2.1.10.39.1.1.1.1.2";
        }

        leaf sonetMediumValidIntervals {
          type int32 {
            range "0..96";
          }
          description
           "The number of previous 15-minute intervals
            for which data was collected.
            A SONET/SDH interface must be capable
            of supporting at least n intervals.
            The minimum value of n is 4.
            The default of n is 32.
            The maximum value of n is 96.
            The value will be <n> unless the measurement was
            (re-)started within the last (<n>*15) minutes, in which
            case the value will be the number of complete 15
            minute intervals for which the agent has at least
            some data. In certain cases (e.g., in the case
            where the agent is a proxy) it is possible that some
            intervals are unavailable.  In this case, this
            interval is the maximum interval number for
            which data is available. ";
          smiv2:max-access "read-only";
          smiv2:oid "1.3.6.1.2.1.10.39.1.1.1.1.3";
        }

        leaf sonetMediumLineCoding {
          type enumeration {
            enum "sonetMediumOther" {
              value "1";
            }
            enum "sonetMediumB3ZS" {
              value "2";
            }
            enum "sonetMediumCMI" {
              value "3";
            }
            enum "sonetMediumNRZ" {
              value "4";
            }
            enum "sonetMediumRZ" {
              value "5";
            }
          }
          description
           "This variable describes the line coding for
            this interface. The B3ZS and CMI are used for
            electrical SONET/SDH signals (STS-1 and STS-3).
            The Non-Return to Zero (NRZ) and the Return
            to Zero are used for optical SONET/SDH signals.";
          smiv2:max-access "read-write";
          smiv2:oid "1.3.6.1.2.1.10.39.1.1.1.1.4";
        }

        leaf sonetMediumLineType {
          type enumeration {
            enum "sonetOther" {
              value "1";
            }
            enum "sonetShortSingleMode" {
              value "2";
            }
            enum "sonetLongSingleMode" {
              value "3";
            }
            enum "sonetMultiMode" {
              value "4";
            }
            enum "sonetCoax" {
              value "5";
            }
            enum "sonetUTP" {
              value "6";
            }
          }
          description
           "This variable describes the line type for
            this interface. The line types are
            Short and Long Range
            Single Mode fiber or Multi-Mode fiber interfaces,
            and coax and UTP for electrical interfaces.  The
            value sonetOther should be used when the Line Type is
            not one of the listed values.";
          smiv2:max-access "read-write";
          smiv2:oid "1.3.6.1.2.1.10.39.1.1.1.1.5";
        }

        leaf sonetMediumCircuitIdentifier {
          type snmpv2-tc:DisplayString {
            length "0..255";
          }
          description
           "This variable contains the transmission
            vendor's circuit identifier, for the
            purpose of facilitating troubleshooting.
            Note that the circuit identifier, if available,
            is also represented by ifPhysAddress.";
          smiv2:max-access "read-write";
          smiv2:oid "1.3.6.1.2.1.10.39.1.1.1.1.6";
        }

        leaf sonetMediumInvalidIntervals {
          type int32 {
            range "0..96";
          }
          description
           "The number of intervals in the range from
            0 to sonetMediumValidIntervals for which no
            data is available. This object will typically
            be zero except in cases where the data for some
            intervals are not available (e.g., in proxy
            situations).";
          smiv2:max-access "read-only";
          smiv2:oid "1.3.6.1.2.1.10.39.1.1.1.1.7";
        }

        leaf sonetMediumLoopbackConfig {
          type bits {
            bit sonetNoLoop {
              position "0";
            }
            bit sonetFacilityLoop {
              position "1";
            }
            bit sonetTerminalLoop {
              position "2";
            }
            bit sonetOtherLoop {
              position "3";
            }
          }
          description
           "The current loopback state of the SONET/SDH interface.  The
            values mean:
            
              sonetNoLoop
                 Not in the loopback state. A device that is not
                 capable of performing a loopback on this interface
                 shall always return this value.
            
              sonetFacilityLoop
                 The received signal at this interface is looped back
                 out through the corresponding transmitter in the return
                 direction.
            
              sonetTerminalLoop
                 The signal that is about to be transmitted is connected
                 to the associated incoming receiver.
            
              sonetOtherLoop
                 Loopbacks that are not defined here.";
          smiv2:max-access "read-write";
          smiv2:oid "1.3.6.1.2.1.10.39.1.1.1.1.8";
        }
      }
    }

    container sonetSectionCurrentTable {
      description
       "The SONET/SDH Section Current table.";
      smiv2:oid "1.3.6.1.2.1.10.39.1.2.1";

      list sonetSectionCurrentEntry {
        key "ifIndex";
        description
         "An entry in the SONET/SDH Section Current table.";
        smiv2:oid "1.3.6.1.2.1.10.39.1.2.1.1";

        leaf ifIndex {
          type leafref {
            path "/if-mib:IF-MIB/if-mib:ifTable/if-mib:ifEntry/if-mib:ifIndex";
          }
        }

        leaf sonetSectionCurrentStatus {
          type int32 {
            range "1..6";
          }
          description
           "This variable indicates the
            status of the interface.
            The sonetSectionCurrentStatus
            is a bit map represented
            as a sum, therefore,
            it can represent multiple defects
            simultaneously.
            The sonetSectionNoDefect should be
            set if and only if
            no other flag is set.
            
            The various bit positions are:
                  1   sonetSectionNoDefect
                  2   sonetSectionLOS
                  4   sonetSectionLOF";
          smiv2:max-access "read-only";
          smiv2:oid "1.3.6.1.2.1.10.39.1.2.1.1.1";
        }

        leaf sonetSectionCurrentESs {
          type perfhist-tc:PerfCurrentCount;
          description
           "The counter associated with the number of Errored
            Seconds encountered by a SONET/SDH
            Section in the current 15 minute interval.";
          smiv2:max-access "read-only";
          smiv2:oid "1.3.6.1.2.1.10.39.1.2.1.1.2";
        }

        leaf sonetSectionCurrentSESs {
          type perfhist-tc:PerfCurrentCount;
          description
           "The counter associated with the number of
            Severely Errored Seconds
            encountered by a SONET/SDH Section in the current 15
            minute interval.";
          smiv2:max-access "read-only";
          smiv2:oid "1.3.6.1.2.1.10.39.1.2.1.1.3";
        }

        leaf sonetSectionCurrentSEFSs {
          type perfhist-tc:PerfCurrentCount;
          description
           "The counter associated with the number of
            Severely Errored Framing Seconds
            encountered by a SONET/SDH Section in the current
            15 minute interval.";
          smiv2:max-access "read-only";
          smiv2:oid "1.3.6.1.2.1.10.39.1.2.1.1.4";
        }

        leaf sonetSectionCurrentCVs {
          type perfhist-tc:PerfCurrentCount;
          description
           "The counter associated with the number of Coding
            Violations encountered by a
            SONET/SDH Section in the current 15 minute interval.";
          smiv2:max-access "read-only";
          smiv2:oid "1.3.6.1.2.1.10.39.1.2.1.1.5";
        }
      }
    }

    container sonetSectionIntervalTable {
      description
       "The SONET/SDH Section Interval table.";
      smiv2:oid "1.3.6.1.2.1.10.39.1.2.2";

      list sonetSectionIntervalEntry {
        key "ifIndex sonetSectionIntervalNumber";
        description
         "An entry in the SONET/SDH Section Interval table.";
        smiv2:oid "1.3.6.1.2.1.10.39.1.2.2.1";

        leaf ifIndex {
          type leafref {
            path "/if-mib:IF-MIB/if-mib:ifTable/if-mib:ifEntry/if-mib:ifIndex";
          }
        }

        leaf sonetSectionIntervalNumber {
          type int32 {
            range "1..96";
          }
          description
           "A number between 1 and 96, which identifies the
            interval for which the set of statistics is available.
            The interval identified by 1 is the most recently
            completed 15 minute interval,
            and the interval identified
            by N is the interval immediately preceding the
            one identified
            by N-1.";
          smiv2:max-access "not-accessible";
          smiv2:oid "1.3.6.1.2.1.10.39.1.2.2.1.1";
        }

        leaf sonetSectionIntervalESs {
          type perfhist-tc:PerfIntervalCount;
          description
           "The counter associated with the number of
            Errored Seconds encountered
            by a SONET/SDH Section in a
            particular 15-minute interval
            in the past 24 hours.";
          smiv2:max-access "read-only";
          smiv2:oid "1.3.6.1.2.1.10.39.1.2.2.1.2";
        }

        leaf sonetSectionIntervalSESs {
          type perfhist-tc:PerfIntervalCount;
          description
           "The counter associated with the number of
            Severely Errored Seconds
            encountered by a SONET/SDH Section in a
            particular 15-minute interval
            in the past 24 hours.";
          smiv2:max-access "read-only";
          smiv2:oid "1.3.6.1.2.1.10.39.1.2.2.1.3";
        }

        leaf sonetSectionIntervalSEFSs {
          type perfhist-tc:PerfIntervalCount;
          description
           "The counter associated with the number of
            Severely Errored Framing Seconds
            encountered by a SONET/SDH Section in a
            particular 15-minute interval
            in the past 24 hours.";
          smiv2:max-access "read-only";
          smiv2:oid "1.3.6.1.2.1.10.39.1.2.2.1.4";
        }

        leaf sonetSectionIntervalCVs {
          type perfhist-tc:PerfIntervalCount;
          description
           "The counter associated with the number of Coding
            Violations encountered by a
            SONET/SDH Section in a particular 15-minute interval
            in the past 24 hours.";
          smiv2:max-access "read-only";
          smiv2:oid "1.3.6.1.2.1.10.39.1.2.2.1.5";
        }

        leaf sonetSectionIntervalValidData {
          type boolean;
          description
           "This variable indicates if the data for this
            interval is valid.";
          smiv2:max-access "read-only";
          smiv2:oid "1.3.6.1.2.1.10.39.1.2.2.1.6";
        }
      }
    }

    container sonetLineCurrentTable {
      description
       "The SONET/SDH Line Current table.";
      smiv2:oid "1.3.6.1.2.1.10.39.1.3.1";

      list sonetLineCurrentEntry {
        key "ifIndex";
        description
         "An entry in the SONET/SDH Line Current table.";
        smiv2:oid "1.3.6.1.2.1.10.39.1.3.1.1";

        leaf ifIndex {
          type leafref {
            path "/if-mib:IF-MIB/if-mib:ifTable/if-mib:ifEntry/if-mib:ifIndex";
          }
        }

        leaf sonetLineCurrentStatus {
          type int32 {
            range "1..6";
          }
          description
           "This variable indicates the
            status of the interface.
            The sonetLineCurrentStatus
            is a bit map represented
            as a sum, therefore,
            it can represent multiple defects
            simultaneously.
            The sonetLineNoDefect should be
            set if and only if
            no other flag is set.
            
            The various bit positions are:
             1   sonetLineNoDefect
             2   sonetLineAIS
             4   sonetLineRDI";
          smiv2:max-access "read-only";
          smiv2:oid "1.3.6.1.2.1.10.39.1.3.1.1.1";
        }

        leaf sonetLineCurrentESs {
          type perfhist-tc:PerfCurrentCount;
          description
           "The counter associated with the number of Errored
            Seconds encountered by a SONET/SDH
            Line in the current 15 minute interval.";
          smiv2:max-access "read-only";
          smiv2:oid "1.3.6.1.2.1.10.39.1.3.1.1.2";
        }

        leaf sonetLineCurrentSESs {
          type perfhist-tc:PerfCurrentCount;
          description
           "The counter associated with the number of
            Severely Errored Seconds
            encountered by a SONET/SDH Line in the current 15
            minute
            interval.";
          smiv2:max-access "read-only";
          smiv2:oid "1.3.6.1.2.1.10.39.1.3.1.1.3";
        }

        leaf sonetLineCurrentCVs {
          type perfhist-tc:PerfCurrentCount;
          description
           "The counter associated with the number of Coding
            Violations encountered by a
            SONET/SDH Line in the current 15 minute interval.";
          smiv2:max-access "read-only";
          smiv2:oid "1.3.6.1.2.1.10.39.1.3.1.1.4";
        }

        leaf sonetLineCurrentUASs {
          type perfhist-tc:PerfCurrentCount;
          description
           "The counter associated with the number of
            Unavailable Seconds
            encountered by a SONET/SDH Line in the current 15
            minute
            interval.";
          smiv2:max-access "read-only";
          smiv2:oid "1.3.6.1.2.1.10.39.1.3.1.1.5";
        }
      }
    }

    container sonetLineIntervalTable {
      description
       "The SONET/SDH Line Interval table.";
      smiv2:oid "1.3.6.1.2.1.10.39.1.3.2";

      list sonetLineIntervalEntry {
        key "ifIndex sonetLineIntervalNumber";
        description
         "An entry in the SONET/SDH Line Interval table.";
        smiv2:oid "1.3.6.1.2.1.10.39.1.3.2.1";

        leaf ifIndex {
          type leafref {
            path "/if-mib:IF-MIB/if-mib:ifTable/if-mib:ifEntry/if-mib:ifIndex";
          }
        }

        leaf sonetLineIntervalNumber {
          type int32 {
            range "1..96";
          }
          description
           "A number between 1 and 96, which identifies the
            interval for which the set of statistics is available.
            The interval identified by 1 is the most recently
            completed 15 minute interval,
            and the interval identified
            by N is the interval immediately preceding the
            one identified
            by N-1.";
          smiv2:max-access "not-accessible";
          smiv2:oid "1.3.6.1.2.1.10.39.1.3.2.1.1";
        }

        leaf sonetLineIntervalESs {
          type perfhist-tc:PerfIntervalCount;
          description
           "The counter associated with the number of
            Errored Seconds encountered
            by a SONET/SDH Line in a
            particular 15-minute interval
            in the past 24 hours.";
          smiv2:max-access "read-only";
          smiv2:oid "1.3.6.1.2.1.10.39.1.3.2.1.2";
        }

        leaf sonetLineIntervalSESs {
          type perfhist-tc:PerfIntervalCount;
          description
           "The counter associated with the number of
            Severely Errored Seconds
            encountered by a SONET/SDH Line in a
            particular 15-minute interval
            in the past 24 hours.";
          smiv2:max-access "read-only";
          smiv2:oid "1.3.6.1.2.1.10.39.1.3.2.1.3";
        }

        leaf sonetLineIntervalCVs {
          type perfhist-tc:PerfIntervalCount;
          description
           "The counter associated with the number of Coding
            Violations encountered by a
            SONET/SDH Line in a
            particular 15-minute interval
            in the past 24 hours.";
          smiv2:max-access "read-only";
          smiv2:oid "1.3.6.1.2.1.10.39.1.3.2.1.4";
        }

        leaf sonetLineIntervalUASs {
          type perfhist-tc:PerfIntervalCount;
          description
           "The counter associated with the
            number of Unavailable Seconds
            encountered by a SONET/SDH Line in
            a particular 15-minute interval
            in the past 24 hours.";
          smiv2:max-access "read-only";
          smiv2:oid "1.3.6.1.2.1.10.39.1.3.2.1.5";
        }

        leaf sonetLineIntervalValidData {
          type boolean;
          description
           "This variable indicates if the data for this
            interval is valid.";
          smiv2:max-access "read-only";
          smiv2:oid "1.3.6.1.2.1.10.39.1.3.2.1.6";
        }
      }
    }

    container sonetFarEndLineCurrentTable {
      description
       "The SONET/SDH Far End Line Current table.";
      smiv2:oid "1.3.6.1.2.1.10.39.1.4.1";

      list sonetFarEndLineCurrentEntry {
        key "ifIndex";
        description
         "An entry in the SONET/SDH Far End Line Current table.";
        smiv2:oid "1.3.6.1.2.1.10.39.1.4.1.1";

        leaf ifIndex {
          type leafref {
            path "/if-mib:IF-MIB/if-mib:ifTable/if-mib:ifEntry/if-mib:ifIndex";
          }
        }

        leaf sonetFarEndLineCurrentESs {
          type perfhist-tc:PerfCurrentCount;
          description
           "The counter associated with the number of Far
            End Errored Seconds encountered by a SONET/SDH
            interface in the current 15 minute interval.";
          smiv2:max-access "read-only";
          smiv2:oid "1.3.6.1.2.1.10.39.1.4.1.1.1";
        }

        leaf sonetFarEndLineCurrentSESs {
          type perfhist-tc:PerfCurrentCount;
          description
           "The counter associated with the number of
            Far End Severely Errored Seconds
            encountered by a SONET/SDH Medium/Section/Line
            interface in the current 15 minute
            interval.";
          smiv2:max-access "read-only";
          smiv2:oid "1.3.6.1.2.1.10.39.1.4.1.1.2";
        }

        leaf sonetFarEndLineCurrentCVs {
          type perfhist-tc:PerfCurrentCount;
          description
           "The counter associated with the number of
            Far End Coding Violations reported via
            the far end block error count
            encountered by a
            SONET/SDH Medium/Section/Line
            interface in the current 15 minute interval.";
          smiv2:max-access "read-only";
          smiv2:oid "1.3.6.1.2.1.10.39.1.4.1.1.3";
        }

        leaf sonetFarEndLineCurrentUASs {
          type perfhist-tc:PerfCurrentCount;
          description
           "The counter associated with the number of
            Far End Unavailable Seconds
            encountered by a
            SONET/SDH Medium/Section/Line
            interface in the current 15 minute interval.";
          smiv2:max-access "read-only";
          smiv2:oid "1.3.6.1.2.1.10.39.1.4.1.1.4";
        }
      }
    }

    container sonetFarEndLineIntervalTable {
      description
       "The SONET/SDH Far End Line Interval table.";
      smiv2:oid "1.3.6.1.2.1.10.39.1.4.2";

      list sonetFarEndLineIntervalEntry {
        key "ifIndex sonetFarEndLineIntervalNumber";
        description
         "An entry in the SONET/SDH Far
          End Line Interval table.";
        smiv2:oid "1.3.6.1.2.1.10.39.1.4.2.1";

        leaf ifIndex {
          type leafref {
            path "/if-mib:IF-MIB/if-mib:ifTable/if-mib:ifEntry/if-mib:ifIndex";
          }
        }

        leaf sonetFarEndLineIntervalNumber {
          type int32 {
            range "1..96";
          }
          description
           "A number between 1 and 96, which identifies the
            interval for which the set of statistics is available.
            The interval identified by 1 is the most recently
            completed 15 minute interval,
            and the interval identified
            by N is the interval immediately preceding the
            one identified
            by N-1.";
          smiv2:max-access "not-accessible";
          smiv2:oid "1.3.6.1.2.1.10.39.1.4.2.1.1";
        }

        leaf sonetFarEndLineIntervalESs {
          type perfhist-tc:PerfIntervalCount;
          description
           "The counter associated with the number of
            Far End Errored Seconds encountered
            by a SONET/SDH Line
            interface in a particular 15-minute interval
            in the past 24 hours.";
          smiv2:max-access "read-only";
          smiv2:oid "1.3.6.1.2.1.10.39.1.4.2.1.2";
        }

        leaf sonetFarEndLineIntervalSESs {
          type perfhist-tc:PerfIntervalCount;
          description
           "The counter associated with the number of
            Far End Severely Errored Seconds
            encountered by a SONET/SDH Line
            interface in a particular 15-minute interval
            in the past 24 hours.";
          smiv2:max-access "read-only";
          smiv2:oid "1.3.6.1.2.1.10.39.1.4.2.1.3";
        }

        leaf sonetFarEndLineIntervalCVs {
          type perfhist-tc:PerfIntervalCount;
          description
           "The counter associated with the number of
            Far End Coding Violations reported via
            the far end block error count
            encountered by a
            SONET/SDH Line
            interface in a particular 15-minute interval
            in the past 24 hours.";
          smiv2:max-access "read-only";
          smiv2:oid "1.3.6.1.2.1.10.39.1.4.2.1.4";
        }

        leaf sonetFarEndLineIntervalUASs {
          type perfhist-tc:PerfIntervalCount;
          description
           "The counter associated with the number of
            Far End Unavailable Seconds
            encountered by a
            SONET/SDH Line
            interface in a particular 15-minute interval
            in the past 24 hours.";
          smiv2:max-access "read-only";
          smiv2:oid "1.3.6.1.2.1.10.39.1.4.2.1.5";
        }

        leaf sonetFarEndLineIntervalValidData {
          type boolean;
          description
           "This variable indicates if the data for this
            interval is valid.";
          smiv2:max-access "read-only";
          smiv2:oid "1.3.6.1.2.1.10.39.1.4.2.1.6";
        }
      }
    }

    container sonetPathCurrentTable {
      description
       "The SONET/SDH Path Current table.";
      smiv2:oid "1.3.6.1.2.1.10.39.2.1.1";

      list sonetPathCurrentEntry {
        key "ifIndex";
        description
         "An entry in the SONET/SDH Path Current table.";
        smiv2:oid "1.3.6.1.2.1.10.39.2.1.1.1";

        leaf ifIndex {
          type leafref {
            path "/if-mib:IF-MIB/if-mib:ifTable/if-mib:ifEntry/if-mib:ifIndex";
          }
        }

        leaf sonetPathCurrentWidth {
          type enumeration {
            enum "sts1" {
              value "1";
            }
            enum "sts3cSTM1" {
              value "2";
            }
            enum "sts12cSTM4" {
              value "3";
            }
            enum "sts24c" {
              value "4";
            }
            enum "sts48cSTM16" {
              value "5";
            }
            enum "sts192cSTM64" {
              value "6";
            }
            enum "sts768cSTM256" {
              value "7";
            }
          }
          description
           "A value that indicates the type of the SONET/SDH
            Path.  For SONET, the assigned types are
            the STS-Nc SPEs, where N = 1, 3, 12, 24, 48, 192 and 768.
            STS-1 is equal to 51.84 Mbps.  For SDH, the assigned
            types are the STM-Nc VCs, where N = 1, 4, 16, 64 and 256.";
          smiv2:max-access "read-write";
          smiv2:oid "1.3.6.1.2.1.10.39.2.1.1.1.1";
        }

        leaf sonetPathCurrentStatus {
          type int32 {
            range "1..62";
          }
          description
           "This variable indicates the
            status of the interface.
            The sonetPathCurrentStatus
            is a bit map represented
            as a sum, therefore,
            it can represent multiple defects
            simultaneously.
            The sonetPathNoDefect should be
            set if and only if
            no other flag is set.
            
            The various bit positions are:
               1   sonetPathNoDefect
               2   sonetPathSTSLOP
               4   sonetPathSTSAIS
               8   sonetPathSTSRDI
              16   sonetPathUnequipped
              32   sonetPathSignalLabelMismatch";
          smiv2:max-access "read-only";
          smiv2:oid "1.3.6.1.2.1.10.39.2.1.1.1.2";
        }

        leaf sonetPathCurrentESs {
          type perfhist-tc:PerfCurrentCount;
          description
           "The counter associated with the number of Errored
            Seconds encountered by a SONET/SDH
            Path in the current 15 minute interval.";
          smiv2:max-access "read-only";
          smiv2:oid "1.3.6.1.2.1.10.39.2.1.1.1.3";
        }

        leaf sonetPathCurrentSESs {
          type perfhist-tc:PerfCurrentCount;
          description
           "The counter associated with the number of
            Severely Errored Seconds
            encountered by a SONET/SDH Path in the current 15
            minute
            interval.";
          smiv2:max-access "read-only";
          smiv2:oid "1.3.6.1.2.1.10.39.2.1.1.1.4";
        }

        leaf sonetPathCurrentCVs {
          type perfhist-tc:PerfCurrentCount;
          description
           "The counter associated with the number of Coding
            Violations encountered by a
            SONET/SDH Path in the current 15 minute interval.";
          smiv2:max-access "read-only";
          smiv2:oid "1.3.6.1.2.1.10.39.2.1.1.1.5";
        }

        leaf sonetPathCurrentUASs {
          type perfhist-tc:PerfCurrentCount;
          description
           "The counter associated with the number of
            Unavailable Seconds
            encountered by a Path in the current
            15 minute interval.";
          smiv2:max-access "read-only";
          smiv2:oid "1.3.6.1.2.1.10.39.2.1.1.1.6";
        }
      }
    }

    container sonetPathIntervalTable {
      description
       "The SONET/SDH Path Interval table.";
      smiv2:oid "1.3.6.1.2.1.10.39.2.1.2";

      list sonetPathIntervalEntry {
        key "ifIndex sonetPathIntervalNumber";
        description
         "An entry in the SONET/SDH Path Interval table.";
        smiv2:oid "1.3.6.1.2.1.10.39.2.1.2.1";

        leaf ifIndex {
          type leafref {
            path "/if-mib:IF-MIB/if-mib:ifTable/if-mib:ifEntry/if-mib:ifIndex";
          }
        }

        leaf sonetPathIntervalNumber {
          type int32 {
            range "1..96";
          }
          description
           "A number between 1 and 96, which identifies the
            interval for which the set of statistics is available.
            The interval identified by 1 is the most recently
            completed 15 minute interval,
            and the interval identified
            by N is the interval immediately preceding the
            one identified
            by N-1.";
          smiv2:max-access "not-accessible";
          smiv2:oid "1.3.6.1.2.1.10.39.2.1.2.1.1";
        }

        leaf sonetPathIntervalESs {
          type perfhist-tc:PerfIntervalCount;
          description
           "The counter associated with the number of
            Errored Seconds encountered
            by a SONET/SDH Path in a
            particular 15-minute interval
            in the past 24 hours.";
          smiv2:max-access "read-only";
          smiv2:oid "1.3.6.1.2.1.10.39.2.1.2.1.2";
        }

        leaf sonetPathIntervalSESs {
          type perfhist-tc:PerfIntervalCount;
          description
           "The counter associated with the number of
            Severely Errored Seconds
            encountered by a SONET/SDH Path in
            a particular 15-minute interval
            in the past 24 hours.";
          smiv2:max-access "read-only";
          smiv2:oid "1.3.6.1.2.1.10.39.2.1.2.1.3";
        }

        leaf sonetPathIntervalCVs {
          type perfhist-tc:PerfIntervalCount;
          description
           "The counter associated with the number of Coding
            Violations encountered by a
            SONET/SDH Path in a particular 15-minute interval
            in the past 24 hours.";
          smiv2:max-access "read-only";
          smiv2:oid "1.3.6.1.2.1.10.39.2.1.2.1.4";
        }

        leaf sonetPathIntervalUASs {
          type perfhist-tc:PerfIntervalCount;
          description
           "The counter associated with the number of
            Unavailable Seconds
            encountered by a Path in a
            particular 15-minute interval
            in the past 24 hours.";
          smiv2:max-access "read-only";
          smiv2:oid "1.3.6.1.2.1.10.39.2.1.2.1.5";
        }

        leaf sonetPathIntervalValidData {
          type boolean;
          description
           "This variable indicates if the data for this
            interval is valid.";
          smiv2:max-access "read-only";
          smiv2:oid "1.3.6.1.2.1.10.39.2.1.2.1.6";
        }
      }
    }

    container sonetFarEndPathCurrentTable {
      description
       "The SONET/SDH Far End Path Current table.";
      smiv2:oid "1.3.6.1.2.1.10.39.2.2.1";

      list sonetFarEndPathCurrentEntry {
        key "ifIndex";
        description
         "An entry in the SONET/SDH Far End Path Current table.";
        smiv2:oid "1.3.6.1.2.1.10.39.2.2.1.1";

        leaf ifIndex {
          type leafref {
            path "/if-mib:IF-MIB/if-mib:ifTable/if-mib:ifEntry/if-mib:ifIndex";
          }
        }

        leaf sonetFarEndPathCurrentESs {
          type perfhist-tc:PerfCurrentCount;
          description
           "The counter associated with the number of Far
            End Errored Seconds encountered by a SONET/SDH
            interface in the current 15 minute interval.";
          smiv2:max-access "read-only";
          smiv2:oid "1.3.6.1.2.1.10.39.2.2.1.1.1";
        }

        leaf sonetFarEndPathCurrentSESs {
          type perfhist-tc:PerfCurrentCount;
          description
           "The counter associated with the number of
            Far End Severely Errored Seconds
            encountered by a SONET/SDH Path
            interface in the current 15 minute
            interval.";
          smiv2:max-access "read-only";
          smiv2:oid "1.3.6.1.2.1.10.39.2.2.1.1.2";
        }

        leaf sonetFarEndPathCurrentCVs {
          type perfhist-tc:PerfCurrentCount;
          description
           "The counter associated with the number of
            Far End Coding Violations reported via
            the far end block error count
            encountered by a
            SONET/SDH Path interface in
            the current 15 minute interval.";
          smiv2:max-access "read-only";
          smiv2:oid "1.3.6.1.2.1.10.39.2.2.1.1.3";
        }

        leaf sonetFarEndPathCurrentUASs {
          type perfhist-tc:PerfCurrentCount;
          description
           "The counter associated with the number of
            Far End Unavailable Seconds
            encountered by a
            SONET/SDH Path interface in
            the current 15 minute interval.";
          smiv2:max-access "read-only";
          smiv2:oid "1.3.6.1.2.1.10.39.2.2.1.1.4";
        }
      }
    }

    container sonetFarEndPathIntervalTable {
      description
       "The SONET/SDH Far End Path Interval table.";
      smiv2:oid "1.3.6.1.2.1.10.39.2.2.2";

      list sonetFarEndPathIntervalEntry {
        key "ifIndex sonetFarEndPathIntervalNumber";
        description
         "An entry in the SONET/SDH Far
          End Path Interval table.";
        smiv2:oid "1.3.6.1.2.1.10.39.2.2.2.1";

        leaf ifIndex {
          type leafref {
            path "/if-mib:IF-MIB/if-mib:ifTable/if-mib:ifEntry/if-mib:ifIndex";
          }
        }

        leaf sonetFarEndPathIntervalNumber {
          type int32 {
            range "1..96";
          }
          description
           "A number between 1 and 96, which identifies the
            interval for which the set of statistics is available.
            The interval identified by 1 is the most recently
            completed 15 minute interval,
            and the interval identified
            by N is the interval immediately preceding the
            one identified
            by N-1.";
          smiv2:max-access "not-accessible";
          smiv2:oid "1.3.6.1.2.1.10.39.2.2.2.1.1";
        }

        leaf sonetFarEndPathIntervalESs {
          type perfhist-tc:PerfIntervalCount;
          description
           "The counter associated with the number of
            Far End Errored Seconds encountered
            by a SONET/SDH Path interface in a
            particular 15-minute interval
            in the past 24 hours.";
          smiv2:max-access "read-only";
          smiv2:oid "1.3.6.1.2.1.10.39.2.2.2.1.2";
        }

        leaf sonetFarEndPathIntervalSESs {
          type perfhist-tc:PerfIntervalCount;
          description
           "The counter associated with the number of
            Far End Severely Errored Seconds
            encountered by a SONET/SDH Path interface
            in a particular 15-minute interval
            in the past 24 hours.";
          smiv2:max-access "read-only";
          smiv2:oid "1.3.6.1.2.1.10.39.2.2.2.1.3";
        }

        leaf sonetFarEndPathIntervalCVs {
          type perfhist-tc:PerfIntervalCount;
          description
           "The counter associated with the number of
            Far End Coding Violations reported via
            the far end block error count
            encountered by a
            SONET/SDH Path interface
            in a particular 15-minute interval
            in the past 24 hours.";
          smiv2:max-access "read-only";
          smiv2:oid "1.3.6.1.2.1.10.39.2.2.2.1.4";
        }

        leaf sonetFarEndPathIntervalUASs {
          type perfhist-tc:PerfIntervalCount;
          description
           "The counter associated with the number of
            Far End Unavailable Seconds
            encountered by a
            SONET/SDH Path interface in
            a particular 15-minute interval
            in the past 24 hours.";
          smiv2:max-access "read-only";
          smiv2:oid "1.3.6.1.2.1.10.39.2.2.2.1.5";
        }

        leaf sonetFarEndPathIntervalValidData {
          type boolean;
          description
           "This variable indicates if the data for this
            interval is valid.";
          smiv2:max-access "read-only";
          smiv2:oid "1.3.6.1.2.1.10.39.2.2.2.1.6";
        }
      }
    }

    container sonetVTCurrentTable {
      description
       "The SONET/SDH VT Current table.";
      smiv2:oid "1.3.6.1.2.1.10.39.3.1.1";

      list sonetVTCurrentEntry {
        key "ifIndex";
        description
         "An entry in the SONET/SDH VT Current table.";
        smiv2:oid "1.3.6.1.2.1.10.39.3.1.1.1";

        leaf ifIndex {
          type leafref {
            path "/if-mib:IF-MIB/if-mib:ifTable/if-mib:ifEntry/if-mib:ifIndex";
          }
        }

        leaf sonetVTCurrentWidth {
          type enumeration {
            enum "vtWidth15VC11" {
              value "1";
            }
            enum "vtWidth2VC12" {
              value "2";
            }
            enum "vtWidth3" {
              value "3";
            }
            enum "vtWidth6VC2" {
              value "4";
            }
            enum "vtWidth6c" {
              value "5";
            }
          }
          description
           "A value that indicates the type of the SONET
            VT and SDH VC.  Assigned widths are
            VT1.5/VC11, VT2/VC12, VT3, VT6/VC2, and VT6c.";
          smiv2:max-access "read-write";
          smiv2:oid "1.3.6.1.2.1.10.39.3.1.1.1.1";
        }

        leaf sonetVTCurrentStatus {
          type int32 {
            range "1..126";
          }
          description
           "This variable indicates the
            status of the interface.
            The sonetVTCurrentStatus
            is a bit map represented
            as a sum, therefore,
            it can represent multiple defects
            and failures
            simultaneously.
            The sonetVTNoDefect should be
            set if and only if
            no other flag is set.
            
            The various bit positions are:
               1   sonetVTNoDefect
               2   sonetVTLOP
               4   sonetVTPathAIS
               8   sonetVTPathRDI
              16   sonetVTPathRFI
              32   sonetVTUnequipped
              64   sonetVTSignalLabelMismatch";
          smiv2:max-access "read-only";
          smiv2:oid "1.3.6.1.2.1.10.39.3.1.1.1.2";
        }

        leaf sonetVTCurrentESs {
          type perfhist-tc:PerfCurrentCount;
          description
           "The counter associated with the number of Errored
            Seconds encountered by a SONET/SDH
            VT in the current 15 minute interval.";
          smiv2:max-access "read-only";
          smiv2:oid "1.3.6.1.2.1.10.39.3.1.1.1.3";
        }

        leaf sonetVTCurrentSESs {
          type perfhist-tc:PerfCurrentCount;
          description
           "The counter associated with the number of
            Severely Errored Seconds
            encountered by a SONET/SDH VT in the current 15 minute
            interval.";
          smiv2:max-access "read-only";
          smiv2:oid "1.3.6.1.2.1.10.39.3.1.1.1.4";
        }

        leaf sonetVTCurrentCVs {
          type perfhist-tc:PerfCurrentCount;
          description
           "The counter associated with the number of Coding
            Violations encountered by a
            SONET/SDH VT in the current 15 minute interval.";
          smiv2:max-access "read-only";
          smiv2:oid "1.3.6.1.2.1.10.39.3.1.1.1.5";
        }

        leaf sonetVTCurrentUASs {
          type perfhist-tc:PerfCurrentCount;
          description
           "The counter associated with the number of
            Unavailable Seconds
            encountered by a VT in the current
            15 minute interval.";
          smiv2:max-access "read-only";
          smiv2:oid "1.3.6.1.2.1.10.39.3.1.1.1.6";
        }
      }
    }

    container sonetVTIntervalTable {
      description
       "The SONET/SDH VT Interval table.";
      smiv2:oid "1.3.6.1.2.1.10.39.3.1.2";

      list sonetVTIntervalEntry {
        key "ifIndex sonetVTIntervalNumber";
        description
         "An entry in the SONET/SDH VT Interval table.";
        smiv2:oid "1.3.6.1.2.1.10.39.3.1.2.1";

        leaf ifIndex {
          type leafref {
            path "/if-mib:IF-MIB/if-mib:ifTable/if-mib:ifEntry/if-mib:ifIndex";
          }
        }

        leaf sonetVTIntervalNumber {
          type int32 {
            range "1..96";
          }
          description
           "A number between 1 and 96, which identifies the
            interval for which the set of statistics is available.
            The interval identified by 1 is the most recently
            completed 15 minute interval,
            and the interval identified
            by N is the interval immediately preceding the
            one identified
            by N-1.";
          smiv2:max-access "not-accessible";
          smiv2:oid "1.3.6.1.2.1.10.39.3.1.2.1.1";
        }

        leaf sonetVTIntervalESs {
          type perfhist-tc:PerfIntervalCount;
          description
           "The counter associated with the number of
            Errored Seconds encountered
            by a SONET/SDH VT in a particular 15-minute interval
            in the past 24 hours.";
          smiv2:max-access "read-only";
          smiv2:oid "1.3.6.1.2.1.10.39.3.1.2.1.2";
        }

        leaf sonetVTIntervalSESs {
          type perfhist-tc:PerfIntervalCount;
          description
           "The counter associated with the number of
            Severely Errored Seconds
            encountered by a SONET/SDH VT
            in a particular 15-minute interval
            in the past 24 hours.";
          smiv2:max-access "read-only";
          smiv2:oid "1.3.6.1.2.1.10.39.3.1.2.1.3";
        }

        leaf sonetVTIntervalCVs {
          type perfhist-tc:PerfIntervalCount;
          description
           "The counter associated with the number of Coding
            Violations encountered by a
            SONET/SDH VT in a particular 15-minute interval
            in the past 24 hours.";
          smiv2:max-access "read-only";
          smiv2:oid "1.3.6.1.2.1.10.39.3.1.2.1.4";
        }

        leaf sonetVTIntervalUASs {
          type perfhist-tc:PerfIntervalCount;
          description
           "The counter associated with the number of
            Unavailable Seconds
            encountered by a VT in a particular 15-minute interval
            in the past 24 hours.";
          smiv2:max-access "read-only";
          smiv2:oid "1.3.6.1.2.1.10.39.3.1.2.1.5";
        }

        leaf sonetVTIntervalValidData {
          type boolean;
          description
           "This variable indicates if the data for this
            interval is valid.";
          smiv2:max-access "read-only";
          smiv2:oid "1.3.6.1.2.1.10.39.3.1.2.1.6";
        }
      }
    }

    container sonetFarEndVTCurrentTable {
      description
       "The SONET/SDH Far End VT Current table.";
      smiv2:oid "1.3.6.1.2.1.10.39.3.2.1";

      list sonetFarEndVTCurrentEntry {
        key "ifIndex";
        description
         "An entry in the SONET/SDH Far End VT Current table.";
        smiv2:oid "1.3.6.1.2.1.10.39.3.2.1.1";

        leaf ifIndex {
          type leafref {
            path "/if-mib:IF-MIB/if-mib:ifTable/if-mib:ifEntry/if-mib:ifIndex";
          }
        }

        leaf sonetFarEndVTCurrentESs {
          type perfhist-tc:PerfCurrentCount;
          description
           "The counter associated with the number of Far
            End Errored Seconds encountered by a SONET/SDH
            interface in the current 15 minute interval.";
          smiv2:max-access "read-only";
          smiv2:oid "1.3.6.1.2.1.10.39.3.2.1.1.1";
        }

        leaf sonetFarEndVTCurrentSESs {
          type perfhist-tc:PerfCurrentCount;
          description
           "The counter associated with the number of
            Far End Severely Errored Seconds
            encountered by a SONET/SDH VT interface
            in the current 15 minute
            interval.";
          smiv2:max-access "read-only";
          smiv2:oid "1.3.6.1.2.1.10.39.3.2.1.1.2";
        }

        leaf sonetFarEndVTCurrentCVs {
          type perfhist-tc:PerfCurrentCount;
          description
           "The counter associated with the number of
            Far End Coding Violations reported via
            the far end block error count
            encountered by a
            SONET/SDH VT interface
            in the current 15 minute interval.";
          smiv2:max-access "read-only";
          smiv2:oid "1.3.6.1.2.1.10.39.3.2.1.1.3";
        }

        leaf sonetFarEndVTCurrentUASs {
          type perfhist-tc:PerfCurrentCount;
          description
           "The counter associated with the number of
            Far End Unavailable Seconds
            encountered by a
            SONET/SDH VT interface
            in the current 15 minute interval.";
          smiv2:max-access "read-only";
          smiv2:oid "1.3.6.1.2.1.10.39.3.2.1.1.4";
        }
      }
    }

    container sonetFarEndVTIntervalTable {
      description
       "The SONET/SDH Far End VT Interval table.";
      smiv2:oid "1.3.6.1.2.1.10.39.3.2.2";

      list sonetFarEndVTIntervalEntry {
        key "ifIndex sonetFarEndVTIntervalNumber";
        description
         "An entry in the SONET/SDH Far
          End VT Interval table.";
        smiv2:oid "1.3.6.1.2.1.10.39.3.2.2.1";

        leaf ifIndex {
          type leafref {
            path "/if-mib:IF-MIB/if-mib:ifTable/if-mib:ifEntry/if-mib:ifIndex";
          }
        }

        leaf sonetFarEndVTIntervalNumber {
          type int32 {
            range "1..96";
          }
          description
           "A number between 1 and 96, which identifies the
            interval for which the set of statistics is available.
            The interval identified by 1 is the most recently
            completed 15 minute interval,
            and the interval identified
            by N is the interval immediately preceding the
            one identified
            by N-1.";
          smiv2:max-access "not-accessible";
          smiv2:oid "1.3.6.1.2.1.10.39.3.2.2.1.1";
        }

        leaf sonetFarEndVTIntervalESs {
          type perfhist-tc:PerfIntervalCount;
          description
           "The counter associated with the number of
            Far End Errored Seconds encountered
            by a SONET/SDH VT interface
            in a particular 15-minute interval
            in the past 24 hours.";
          smiv2:max-access "read-only";
          smiv2:oid "1.3.6.1.2.1.10.39.3.2.2.1.2";
        }

        leaf sonetFarEndVTIntervalSESs {
          type perfhist-tc:PerfIntervalCount;
          description
           "The counter associated with the number of
            Far End Severely Errored Seconds
            encountered by a SONET/SDH VT interface
            in a particular 15-minute interval
            in the past 24 hours.";
          smiv2:max-access "read-only";
          smiv2:oid "1.3.6.1.2.1.10.39.3.2.2.1.3";
        }

        leaf sonetFarEndVTIntervalCVs {
          type perfhist-tc:PerfIntervalCount;
          description
           "The counter associated with the number of
            Far End Coding Violations reported via
            the far end block error count
            encountered by a
            SONET/SDH VT interface in a
            particular 15-minute interval
            in the past 24 hours.";
          smiv2:max-access "read-only";
          smiv2:oid "1.3.6.1.2.1.10.39.3.2.2.1.4";
        }

        leaf sonetFarEndVTIntervalUASs {
          type perfhist-tc:PerfIntervalCount;
          description
           "The counter associated with the number of
            Far End Unavailable Seconds
            encountered by a
            SONET/SDH VT interface in a
            particular 15-minute interval
            in the past 24 hours.";
          smiv2:max-access "read-only";
          smiv2:oid "1.3.6.1.2.1.10.39.3.2.2.1.5";
        }

        leaf sonetFarEndVTIntervalValidData {
          type boolean;
          description
           "This variable indicates if the data for this
            interval is valid.";
          smiv2:max-access "read-only";
          smiv2:oid "1.3.6.1.2.1.10.39.3.2.2.1.6";
        }
      }
    }
  }

  smiv2:alias "sonetMIB" {
    smiv2:oid "1.3.6.1.2.1.10.39";
  }

  smiv2:alias "sonetObjects" {
    smiv2:oid "1.3.6.1.2.1.10.39.1";
  }

  smiv2:alias "sonetMedium" {
    smiv2:oid "1.3.6.1.2.1.10.39.1.1";
  }

  smiv2:alias "sonetSection" {
    smiv2:oid "1.3.6.1.2.1.10.39.1.2";
  }

  smiv2:alias "sonetLine" {
    smiv2:oid "1.3.6.1.2.1.10.39.1.3";
  }

  smiv2:alias "sonetFarEndLine" {
    smiv2:oid "1.3.6.1.2.1.10.39.1.4";
  }

  smiv2:alias "sonetObjectsPath" {
    smiv2:oid "1.3.6.1.2.1.10.39.2";
  }

  smiv2:alias "sonetPath" {
    smiv2:oid "1.3.6.1.2.1.10.39.2.1";
  }

  smiv2:alias "sonetFarEndPath" {
    smiv2:oid "1.3.6.1.2.1.10.39.2.2";
  }

  smiv2:alias "sonetObjectsVT" {
    smiv2:oid "1.3.6.1.2.1.10.39.3";
  }

  smiv2:alias "sonetVT" {
    smiv2:oid "1.3.6.1.2.1.10.39.3.1";
  }

  smiv2:alias "sonetFarEndVT" {
    smiv2:oid "1.3.6.1.2.1.10.39.3.2";
  }

  smiv2:alias "sonetConformance" {
    smiv2:oid "1.3.6.1.2.1.10.39.4";
  }

  smiv2:alias "sonetGroups" {
    smiv2:oid "1.3.6.1.2.1.10.39.4.1";
  }

  smiv2:alias "sonetCompliances" {
    smiv2:oid "1.3.6.1.2.1.10.39.4.2";
  }

}
