/*
 * Generated by confdc --mib2yang-std
 * Source: mgmt/dmi/model/common/mib-source/CISCO-ATM-EXT-MIB.mib
 */
/*
 * This YANG module has been generated by smidump 0.5.0:
 *
 *      smidump -f yang CISCO-ATM-EXT-MIB
 *
 * Do not edit. Edit the source file instead!
 */

module CISCO-ATM-EXT-MIB {

  namespace "urn:ietf:params:xml:ns:yang:smiv2:CISCO-ATM-EXT-MIB";
  prefix CISCO-ATM-EXT-MIB;

  import ATM-MIB {
    prefix "atm-mib";
  }

  import ietf-yang-smiv2 {
    prefix "smiv2";
  }

  import ietf-yang-types {
    prefix "yang";
  }

  organization
   "Cisco Systems, Inc.";

  contact
   "       Cisco Systems
    Customer Service
    
    Postal:	170 W. Tasman Drive
    San Jose, CA  95134
    USA
    
    Tel: +1 800 553-NETS
    
    E-mail: cs-atm@cisco.com";

  description
   "An extension to the Cisco ATM MIB module for managing
    ATM implementations.
    
    Acronyms and terms used in the MIB module:
    
    AAL5        -- ATM adaptation layer 5.
    AIS         -- Alarm Indication Signal.
    CC          -- Continuity Check.
    End-to-end  -- End-to-end continuity checking.
                   Monitoring occurs on the entire VC
                   between two ATM end stations.
    F5 OAM      -- OAM information flow between 
                   network elements (NEs) used within 
                   virtual connections to report degraded 
                   virtual channel performance.
    OAM         -- Operations, Administration 
                   and Maintenance.
    RDI         -- Remote Detection Indication.
    Segment     -- Segment continuity checking. 
                   Monitoring occurs on a VC segment
                   between a router and a first-hop 
                   ATM switch.
    VC          -- Virtual Channel.
    VCC         -- Virtual Channel Connection.
    VCL         -- Virtual Channel Link.";

  revision 2003-01-06 {
    description
     "Added ciscoAtmVclExtOamTable for OAM configuration
      and state information.";
  }

  revision 1997-06-20 {
    description
     "Initial version of this MIB module.";
  }

  typedef OamCCStatus {
    type enumeration {
      enum "ready" {
        value "1";
      }
      enum "waitActiveResponse" {
        value "2";
      }
      enum "waitActiveConfirm" {
        value "3";
      }
      enum "active" {
        value "4";
      }
      enum "waitDeactiveConfirm" {
        value "5";
      }
    }
    description
     "OAM Continuity check (CC) status.
      ready(1)               -- CC is not activated on VC.
      waitActiveResponse(2)  -- Waiting for active-response.
      waitActiveConfirm(3)   -- Waiting for active-confirm.
      active(4)              -- CC is activated on VC.
      waitDeactiveConfirm(5) -- Waiting for deactivate 
                                confirm.";
  }

  typedef OamCCVcState {
    type enumeration {
      enum "verified" {
        value "1";
      }
      enum "aisrdi" {
        value "2";
      }
      enum "notManaged" {
        value "3";
      }
    }
    description
     "OAM Continuity check (CC) VC state.
      verified(1)            -- CC is successful. VC is up.
      aisrdi(2)              -- CC failed. VC is down.
      notManaged(3)          -- VC is not managed by CC.";
  }

  smiv2:alias "cAal5VccExtTable" {
    description
     "This table contains AAL5 VCC performance 
      parameters beyond that provided by cAal5VccEntry.";
    smiv2:oid "1.3.6.1.4.1.9.9.88.1.1.1";
  }

  smiv2:alias "cAal5VccExtEntry" {
    description
     "This list contains the additinal AAL5 VCC performance
      parameters beyond that provided by cAal5VccEntry.";
    smiv2:oid "1.3.6.1.4.1.9.9.88.1.1.1.1";
  }

  augment "/atm-mib:ATM-MIB/atm-mib:aal5VccTable/atm-mib:aal5VccEntry" {
    description
     "This list contains the additinal AAL5 VCC performance
      parameters beyond that provided by cAal5VccEntry.";
    smiv2:oid "1.3.6.1.4.1.9.9.88.1.1.1.1";

    leaf cAal5VccExtCompEnabled {
      type boolean;
      description
       "Boolean, if compression enabled for VCC.";
      smiv2:max-access "read-only";
      smiv2:oid "1.3.6.1.4.1.9.9.88.1.1.1.1.1";
    }

    leaf cAal5VccExtVoice {
      type boolean;
      description
       "Boolean, TRUE if VCC is used to carry voice.";
      smiv2:max-access "read-only";
      smiv2:oid "1.3.6.1.4.1.9.9.88.1.1.1.1.2";
    }

    leaf cAal5VccExtInF5OamCells {
      type yang:counter32;
      description
       "Number of OAM F5 end to end loopback cells 
        received through the VCC.";
      smiv2:max-access "read-only";
      smiv2:oid "1.3.6.1.4.1.9.9.88.1.1.1.1.3";
    }

    leaf cAal5VccExtOutF5OamCells {
      type yang:counter32;
      description
       "Number of OAM F5 end to end loopback cells sent 
        through the VCC.";
      smiv2:max-access "read-only";
      smiv2:oid "1.3.6.1.4.1.9.9.88.1.1.1.1.4";
    }
  }

  smiv2:alias "catmxVclOamTable" {
    description
     "This table contains Virtual Channel Link (VCL) 
      Oam configuration and state information. 
      This table augments the atmVclTable.";
    smiv2:oid "1.3.6.1.4.1.9.9.88.1.2.1";
  }

  smiv2:alias "catmxVclOamEntry" {
    description
     "This list contains Virtual Channel Link (VCL) 
      configuration and state information beyond that 
      provided by atmVclEntry.";
    smiv2:oid "1.3.6.1.4.1.9.9.88.1.2.1.1";
  }

  augment "/atm-mib:ATM-MIB/atm-mib:atmVclTable/atm-mib:atmVclEntry" {
    description
     "This list contains Virtual Channel Link (VCL) 
      configuration and state information beyond that 
      provided by atmVclEntry.";
    smiv2:oid "1.3.6.1.4.1.9.9.88.1.2.1.1";

    leaf catmxVclOamLoopbackFreq {
      type uint32;
      units "seconds";
      description
       "Specifies OAM loopback frequency.";
      smiv2:max-access "read-write";
      smiv2:oid "1.3.6.1.4.1.9.9.88.1.2.1.1.1";
    }

    leaf catmxVclOamRetryFreq {
      type uint32;
      units "seconds";
      description
       "Specifies OAM retry polling frequency.";
      smiv2:max-access "read-write";
      smiv2:oid "1.3.6.1.4.1.9.9.88.1.2.1.1.2";
    }

    leaf catmxVclOamUpRetryCount {
      type uint32;
      description
       "Specifies OAM retry count before declaring a VC 
        is up.";
      smiv2:max-access "read-write";
      smiv2:oid "1.3.6.1.4.1.9.9.88.1.2.1.1.3";
    }

    leaf catmxVclOamDownRetryCount {
      type uint32;
      description
       "Specifies OAM retry count before declaring a VC 
        is down.";
      smiv2:max-access "read-write";
      smiv2:oid "1.3.6.1.4.1.9.9.88.1.2.1.1.4";
    }

    leaf catmxVclOamEndCCActCount {
      type uint32;
      description
       "Specifies OAM End-to-end Continuity check (CC) 
        Activation retry count.";
      smiv2:max-access "read-write";
      smiv2:oid "1.3.6.1.4.1.9.9.88.1.2.1.1.5";
    }

    leaf catmxVclOamEndCCDeActCount {
      type uint32;
      description
       "Specifies OAM End-to-end Continuity check (CC) 
        Deactivation retry count.";
      smiv2:max-access "read-write";
      smiv2:oid "1.3.6.1.4.1.9.9.88.1.2.1.1.6";
    }

    leaf catmxVclOamEndCCRetryFreq {
      type uint32;
      units "seconds";
      description
       "Specifies OAM End-to-end Continuity check (CC) 
        Activation/Deactivation retry frequency.";
      smiv2:max-access "read-write";
      smiv2:oid "1.3.6.1.4.1.9.9.88.1.2.1.1.7";
    }

    leaf catmxVclOamSegCCActCount {
      type uint32;
      description
       "Specifies OAM Segment Continuity check (CC) 
        Activation retry count.";
      smiv2:max-access "read-write";
      smiv2:oid "1.3.6.1.4.1.9.9.88.1.2.1.1.8";
    }

    leaf catmxVclOamSegCCDeActCount {
      type uint32;
      description
       "Specifies OAM Segment Continuity check (CC) 
        Deactivation retry count.";
      smiv2:max-access "read-write";
      smiv2:oid "1.3.6.1.4.1.9.9.88.1.2.1.1.9";
    }

    leaf catmxVclOamSegCCRetryFreq {
      type uint32;
      units "seconds";
      description
       "Specifies OAM Segment Continuity check (CC) 
        Activation/Deactivation retry frequency.";
      smiv2:max-access "read-write";
      smiv2:oid "1.3.6.1.4.1.9.9.88.1.2.1.1.10";
    }

    leaf catmxVclOamManage {
      type boolean;
      description
       "Specifies OAM Enable/Disable on the VC.
        true(1) indicates that OAM is enabled on the VC.
        false(2) indicates that OAM is disabled on the VC.";
      smiv2:defval "false";
      smiv2:max-access "read-write";
      smiv2:oid "1.3.6.1.4.1.9.9.88.1.2.1.1.11";
    }

    leaf catmxVclOamLoopBkStatus {
      type enumeration {
        enum "disabled" {
          value "1";
        }
        enum "sent" {
          value "2";
        }
        enum "received" {
          value "3";
        }
        enum "failed" {
          value "4";
        }
      }
      description
       "Indicates OAM loopback status of the VC.
        disabled(1)  --   No OAMs on this VC.
        sent(2)      --   OAM sent, waiting for echo.
        received(3)  --   OAM received from target.
        failed(4)    --   Last OAM did not return.";
      smiv2:max-access "read-only";
      smiv2:oid "1.3.6.1.4.1.9.9.88.1.2.1.1.12";
    }

    leaf catmxVclOamVcState {
      type enumeration {
        enum "downRetry" {
          value "1";
        }
        enum "verified" {
          value "2";
        }
        enum "notVerified" {
          value "3";
        }
        enum "upRetry" {
          value "4";
        }
        enum "aisRDI" {
          value "5";
        }
        enum "aisOut" {
          value "6";
        }
        enum "notManaged" {
          value "7";
        }
      }
      description
       "Indicates the state of VC OAM.
        downRetry(1)   --  Loopback failed. Retry sending 
                           loopbacks with retry frequency. 
                           VC is up.
        verified(2)    --  Loopback is successful.
        notVerified(3) --  Not verified by loopback, 
                           AIS/RDI conditions are cleared.
        upRetry(4)     --  Retry successive loopbacks. 
                           VC is down.
        aisRDI(5)      --  Received AIS/RDI. Loopback are 
                           not sent in this state.
        aisOut(6)      --  Sending AIS. Loopback and reply are 
                           not sent in this state.
        notManaged(7)  --  VC is not managed by OAM.";
      smiv2:max-access "read-only";
      smiv2:oid "1.3.6.1.4.1.9.9.88.1.2.1.1.13";
    }

    leaf catmxVclOamEndCCStatus {
      type CISCO-ATM-EXT-MIB:OamCCStatus;
      description
       "Indicates OAM End-to-end Continuity check (CC) 
        status.";
      smiv2:max-access "read-only";
      smiv2:oid "1.3.6.1.4.1.9.9.88.1.2.1.1.14";
    }

    leaf catmxVclOamSegCCStatus {
      type CISCO-ATM-EXT-MIB:OamCCStatus;
      description
       "Indicates OAM Segment Continuity check (CC) status.";
      smiv2:max-access "read-only";
      smiv2:oid "1.3.6.1.4.1.9.9.88.1.2.1.1.15";
    }

    leaf catmxVclOamEndCCVcState {
      type CISCO-ATM-EXT-MIB:OamCCVcState;
      description
       "Indicates OAM End-to-end Continuity check (CC) 
        VC state.";
      smiv2:max-access "read-only";
      smiv2:oid "1.3.6.1.4.1.9.9.88.1.2.1.1.16";
    }

    leaf catmxVclOamSegCCVcState {
      type CISCO-ATM-EXT-MIB:OamCCVcState;
      description
       "Indicates OAM Segment Continuity check (CC) VC 
        state.";
      smiv2:max-access "read-only";
      smiv2:oid "1.3.6.1.4.1.9.9.88.1.2.1.1.17";
    }

    leaf catmxVclOamCellsReceived {
      type yang:counter32;
      units "cells";
      description
       "Indicates the number of OAM cells received on 
        this VC.";
      smiv2:max-access "read-only";
      smiv2:oid "1.3.6.1.4.1.9.9.88.1.2.1.1.18";
    }

    leaf catmxVclOamCellsSent {
      type yang:counter32;
      units "cells";
      description
       "Indicates the number of OAM cells sent on 
        this VC.";
      smiv2:max-access "read-only";
      smiv2:oid "1.3.6.1.4.1.9.9.88.1.2.1.1.19";
    }

    leaf catmxVclOamCellsDropped {
      type yang:counter32;
      units "cells";
      description
       "Indicates the number of OAM cells dropped on 
        this VC.";
      smiv2:max-access "read-only";
      smiv2:oid "1.3.6.1.4.1.9.9.88.1.2.1.1.20";
    }

    leaf catmxVclOamInF5ais {
      type yang:counter32;
      units "cells";
      description
       "Indicates the number of received OAM 
        F5 Alarm Indication Signal (AIS) cells from the VC.";
      smiv2:max-access "read-only";
      smiv2:oid "1.3.6.1.4.1.9.9.88.1.2.1.1.21";
    }

    leaf catmxVclOamOutF5ais {
      type yang:counter32;
      units "cells";
      description
       "Indicates the number of transmitted OAM 
        F5 Alarm Indication Signal (AIS) cells to the VC.";
      smiv2:max-access "read-only";
      smiv2:oid "1.3.6.1.4.1.9.9.88.1.2.1.1.22";
    }

    leaf catmxVclOamInF5rdi {
      type yang:counter32;
      units "cells";
      description
       "Indicates the number of received OAM 
        F5 Remote Detection Indication (RDI) cells from 
        the VC.";
      smiv2:max-access "read-only";
      smiv2:oid "1.3.6.1.4.1.9.9.88.1.2.1.1.23";
    }

    leaf catmxVclOamOutF5rdi {
      type yang:counter32;
      units "cells";
      description
       "Indicates the number of transmitted OAM 
        F5 Remote Detection Indication (RDI) cells to the VC.";
      smiv2:max-access "read-only";
      smiv2:oid "1.3.6.1.4.1.9.9.88.1.2.1.1.24";
    }
  }

  smiv2:alias "ciscoAtmExtMIB" {
    smiv2:oid "1.3.6.1.4.1.9.9.88";
  }

  smiv2:alias "ciscoAtmExtMIBObjects" {
    smiv2:oid "1.3.6.1.4.1.9.9.88.1";
  }

  smiv2:alias "cAal5VccExtMIBObjects" {
    smiv2:oid "1.3.6.1.4.1.9.9.88.1.1";
  }

  smiv2:alias "catmxVcl" {
    smiv2:oid "1.3.6.1.4.1.9.9.88.1.2";
  }

  smiv2:alias "ciscoAal5ExtMIBConformance" {
    smiv2:oid "1.3.6.1.4.1.9.9.88.2";
  }

  smiv2:alias "ciscoAal5ExtMIBCompliances" {
    smiv2:oid "1.3.6.1.4.1.9.9.88.2.1";
  }

  smiv2:alias "ciscoAal5ExtMIBGroups" {
    smiv2:oid "1.3.6.1.4.1.9.9.88.2.2";
  }

}
