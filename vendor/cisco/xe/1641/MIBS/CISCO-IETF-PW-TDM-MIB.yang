/*
 * Generated by confdc --mib2yang-std
 * Source: mgmt/dmi/model/common/mib-source/CISCO-IETF-PW-TDM-MIB.mib
 */
/*
 * This YANG module has been generated by smidump 0.5.0:
 *
 *      smidump -f yang CISCO-IETF-PW-TDM-MIB
 *
 * Do not edit. Edit the source file instead!
 */

module CISCO-IETF-PW-TDM-MIB {

  namespace "urn:ietf:params:xml:ns:yang:smiv2:CISCO-IETF-PW-TDM-MIB";
  prefix CISCO-IETF-PW-TDM-MIB;

  import CISCO-IETF-PW-MIB {
    prefix "cisco-ietf";
  }

  import IF-MIB {
    prefix "if-mib";
  }

  import PerfHist-TC-MIB {
    prefix "perfhist-tc";
  }

  import SNMPv2-TC {
    prefix "snmpv2-tc";
  }

  import ietf-yang-smiv2 {
    prefix "smiv2";
  }

  import ietf-yang-types {
    prefix "yang";
  }

  organization
   "Cisco Systems, Inc.";

  contact
   "Cisco Systems
    Customer Service
    
    Postal: 170 W. Tasman Drive
          San Jose, CA  95134
          SA
    
    Tel: +1 800 553-NETS
    
    Email: cs-atm@cisco.com";

  description
   "This MIB contains managed object definitions for
    encapsulating TDM (T1,E1, T3, E3, NxDS0) as
    pseudo-wires over packet-switching networks (PSN).
    
    This MIB supplements the CISCO-IETF-PW-MIB.
    The CISCO-IETF-PW-MIB contains structures and MIB
    associations generic to Pseudo-Wire (PW) emulation.
    PW-specific MIBs (such as this) contain config and stats for
    specific PW types.";

  revision 2006-07-21 {
    description
     "Cisco'ized the IETF draft: draft-ietf-pwe3-tdm-mib-05.txt
      1-Align object names with CISCO-IETF-PW-MIB and
      CISCO-IETF-PW-TC-MIB
      2-Used cpwVcType instead of pwType
      3-Used cpwVcTable instead of pwTable";
  }

  revision 2006-03-01 {
    description
     "Changes since last draft:
      1-Remove Vc from all objects
      2-Move MIB root to transmission
      3-Change default of pwCTDMCfgSetUp2SynchTimeOut
        to 5000ms
      4-Change PM running counters to daily intervals
      5-Enhance description of pwCTDMCfgPktReplacePolicy
      6-Enhance description of ES, SES, and UAS
      7-Aligned objects with other PW MIBs";
  }

  revision 2005-10-23 {
    description
     "Changes since last draft:
      1-Align object names with CISCO-IETF-PW-MIB and
      PW-TC-STD-MIB 
      2-clean up some text
      3-pwCTDMCfgIndexNext SYNTAX was changed to TestAndIncr
      4-Add explanation to descriptions of few objects
      5-Performance objecs were modified to better represent
        their counts and type";
  }

  revision 2005-07-12 {
    description
     "Changes since last draft:
      1-Merged all configurable objects from Satop MIB with
      objects of pwCTDMCfgTable in this MIB module.
      2-pwCTDMCfgJtrBfrDepth-changed units to microsec.
      3-pwCTDMAvePktLossTimeWindow moved to the
        pwCTDMCfgTable.
      4-In pwCTDMCfgConfErr, the enum(1)was renamed to
      PayloadSize.
      5-Renamed pwCSatopCfgConsecPktsLoss2Normal and
      pwCSatopCfgConsecMissPktNorma2Loss to
      pwCTDMCfgConsecPktsInSynch and to
      pwCTDMCfgConsecMissPktsOutSynch respectively.";
  }

  revision 2004-04-20 {
    description
     "Initial version, published as
      draft-ietf-pwe3-TDM-mib-00.txt";
  }

  typedef CpwTDMCfgIndex {
    type uint32;
    description
     "Index into any of the relevant pwCXXXCfgTable.";
  }


  container CISCO-IETF-PW-TDM-MIB {
    config false;

    container cpwCTDMObjects {
      smiv2:oid "1.3.6.1.4.1.9.10.131.1";

      leaf cpwCTDMCfgIndexNext {
        type uint32;
        description
         "This object contains the value to be used for
          cpwCTDMCfgIndex when creating entries in the
          cpwCTDMCfgTable. The value 0 indicates that no
          unassigned entries are available.  To obtain the
          value of cpwCTDMCfgIndexNext for a new entry in the
          cpwCTDMCfgTable, the manager issues a management
          protocol retrieval operation. The agent will
          determine through its local policy when this
          index value will be made available for reuse.";
        smiv2:max-access "read-only";
        smiv2:oid "1.3.6.1.4.1.9.10.131.1.2";
      }
    }

    container cpwCTDMTable {
      description
       "This table contains basic information including ifIndex,
        and pointers to entries in the relevant TDM config
        tables for this TDM PW.";
      smiv2:oid "1.3.6.1.4.1.9.10.131.1.1";

      list cpwCTDMEntry {
        key "cpwVcIndex";
        description
         "This table is indexed by the same index that was
          created for the associated entry in the VC Table
          (in the CISCO-IETF-PW-MIB).
          
            - The CpwVcIndex.
          
          An entry is created in this table by the agent for every
          entry in the cpwVcTable with a cpwVcType equal to one of the
          following:
          e1Satop(12), t1Satop(13), e3Satop(14), t3Satop(15),
          basicCesPsn(16), basicTdmIp(17),  tdmCasCesPsn(18),
          tdmCasTdmIp(19).";
        smiv2:oid "1.3.6.1.4.1.9.10.131.1.1.1";

        leaf cpwVcIndex {
          type leafref {
            path "/cisco-ietf:CISCO-IETF-PW-MIB/cisco-ietf:cpwVcTable/cisco-ietf:cpwVcEntry/cisco-ietf:cpwVcIndex";
          }
        }

        leaf cpwCTDMRate {
          type int32;
          description
           "The parameter represents the bit-rate of the TDM service
            in multiples of the 'basic' 64 Kbit/s rate. It complements
            the definition of cpwVcType used in CISCO-IETF-PW-MIB.
            For structure-agnostic the following should be used:
            a) Satop E1 - 32
            b) Satop T1 emulation:
               i)   MUST be set to 24 in the basic emulation mode
               ii)  MUST be set to 25 for the 'Octet-aligned T1'
                    emulation mode
            c) Satop E3 - 535
            d) Satop T3 - 699
            For all kinds of structure-aware emulation, this parameter
            MUST be set to N where N is the number of DS0 channels
            in the corresponding attachment circuit.";
          reference
           "Control Protocol Extensions for Setup of TDM
            Pseudowires [TDMCP-EXT], describes extension to the PWE3
            control protocol and PWE3 IANA allocations required for
            setup of TDM pseudo wires.";
          smiv2:defval "32";
          smiv2:max-access "read-write";
          smiv2:oid "1.3.6.1.4.1.9.10.131.1.1.1.1";
        }

        leaf cpwCTDMIfIndex {
          type if-mib:InterfaceIndexOrZero;
          description
           "This is a unique index within the ifTable. It represents
            the interface index of the full link or the interface
            index for the bundle holding the group of
            time slots to be transmitted via this PW connection.
            
            A value of zero indicates an interface index that has yet
            to be determined.
            Once set, if the TDM ifIndex is (for some reason) later
            removed, the agent SHOULD delete the associated PW rows
            (e.g., this cpwCTDMTable entry). If the agent does not
            delete the rows,  the agent MUST set this object to
            zero.";
          smiv2:max-access "read-write";
          smiv2:oid "1.3.6.1.4.1.9.10.131.1.1.1.2";
        }

        leaf cpwCGenTDMCfgIndex {
          type CISCO-IETF-PW-TDM-MIB:CpwTDMCfgIndex;
          description
           "Index to the generic parameters in the TDM configuration
            table that appears in this MIB module. It is likely that
            multiple TDM PWs of the same characteristic will share
            a single TDM Cfg entry.";
          smiv2:max-access "read-write";
          smiv2:oid "1.3.6.1.4.1.9.10.131.1.1.1.3";
        }

        leaf cpwCRelTDMCfgIndex {
          type CISCO-IETF-PW-TDM-MIB:CpwTDMCfgIndex;
          description
           "Index to the relevant TDM configuration table entry
            that appears in one of the related MIB modules
            such as TDMoIP or CESoPSN. It is likely that
            multiple TDM PWs of the same characteristic will share
            a single configuration entry of the relevant type.
            The value 0 implies no entry in other related MIB";
          smiv2:max-access "read-write";
          smiv2:oid "1.3.6.1.4.1.9.10.131.1.1.1.4";
        }

        leaf cpwCTDMConfigError {
          type bits {
            bit other {
              position "0";
            }
            bit tdmTypeIncompatible {
              position "1";
            }
            bit peerRtpIncompatible {
              position "2";
            }
            bit peerPayloadSizeIncompatible {
              position "3";
            }
          }
          description
           "Any of the bits are set if the local configuration is
            not compatible with the peer configuration as available
            from the various parameters options.
            
            -tdmTypeIncompatible bit is set if the local configuration
            is not carrying the same TDM type as the peer configuration.
            
            -peerRtpIncompatible bit is set if the local configuration
            is configured to send RTP packets for this PW, and the
            remote is not capable of accepting RTP packets.
            
            -peerPayloadSizeIncompatible bit is set if the local
            configuration is not carrying the same Payload Size as the
            peer configuration.";
          smiv2:max-access "read-only";
          smiv2:oid "1.3.6.1.4.1.9.10.131.1.1.1.5";
        }

        leaf cpwCTDMTimeElapsed {
          type int32 {
            range "1..900";
          }
          units "seconds";
          description
           "The number of seconds, including partial seconds,
            that have elapsed since the beginning of the current
            measurement period. If, for some reason, such as an
            adjustment in the system's time-of-day clock, the
            current interval exceeds the maximum value, the
            agent will return the maximum value.";
          smiv2:max-access "read-only";
          smiv2:oid "1.3.6.1.4.1.9.10.131.1.1.1.6";
        }

        leaf cpwCTDMValidIntervals {
          type int32 {
            range "0..96";
          }
          units "minutes";
          description
           "The number of previous 15-minute intervals for which data
            was collected.
            An agent with TDM capability must be capable of supporting
            at least n intervals. The minimum value of n is 4, The
            default of n is 32 and the maximum value of n is 96.
            The value will be <n> unless the measurement was (re-)
            started within the last (<n>*15) minutes, in which case
            the value will be the number of complete 15 minute
            intervals for which the agent has at least some data.
            In certain cases(e.g., in the case where the agent is
            a proxy) it is possible that some intervals are unavailable.
            In this case, this interval is the maximum interval number
            for which data is available.";
          smiv2:max-access "read-only";
          smiv2:oid "1.3.6.1.4.1.9.10.131.1.1.1.7";
        }

        leaf cpwCTDMValidDayIntervals {
          type int32 {
            range "0..30";
          }
          units "days";
          description
           "The number of previous days for which data
            was collected.
            An agent with TDM capability must be capable of supporting
            at least n intervals. The minimum value of n is 1, The
            default of n is 1 and the maximum value of n is 30.";
          smiv2:max-access "read-only";
          smiv2:oid "1.3.6.1.4.1.9.10.131.1.1.1.8";
        }

        leaf cpwCTDMCurrentIndications {
          type bits {
            bit other {
              position "0";
            }
            bit strayPacket {
              position "1";
            }
            bit malformedPacket {
              position "2";
            }
            bit excessivePktLossRate {
              position "3";
            }
            bit bufferOverrun {
              position "4";
            }
            bit bufferUnderrun {
              position "5";
            }
            bit remotePktLoss {
              position "6";
            }
            bit pktMisOrder {
              position "7";
            }
            bit packetLoss {
              position "8";
            }
            bit tdmFault {
              position "9";
            }
          }
          description
           "The following defects should be detected and reported
            upon request:
            
            -Stray packets MAY be detected by the PSN and multiplexing
            layers. Stray packets MUST be discarded by the CE-bound IWF
            and their detection MUST NOT affect mechanisms for
            detection of packet loss.
            
            -Malformed packets are detected by mismatch between the
            expected packet size (taking the value of the L bit into
            account) and the actual packet size inferred from the PSN
            and multiplexing layers. Malformed in-order packets MUST be
            discarded by the CE-bound IWF and replacement data
            generated as for lost packets.
            
            -Excessive packet loss rate is detected by computing the
            average packet loss rate over the value of
            cpwCTDMAvePktLossTimeWindow and comparing it with a
            preconfigured threshold [SATOP].
            
            -Buffer overrun is detected in the normal operation state
            when the CE bound IWF's jitter buffer cannot accommodate
            newly arrived packets.
            
            -Remote packet loss is indicated by reception of packets 
            with their R bit set.
            
            -Packet misorder is detected by looking at the Sequence
            number provided by the control word.
            
            -TDM Fault, if L bit in the control word is set, it
            indicates that TDM data carried in the payload is invalid
            due an attachment circuit fault.  When the L bit is set the
            payload MAY be omitted in order to conserve bandwidth.
            
            Note: the algorithm used to capture these indications
            is implementation specific.";
          smiv2:max-access "read-only";
          smiv2:oid "1.3.6.1.4.1.9.10.131.1.1.1.9";
        }

        leaf cpwCTDMLatchedIndications {
          type bits {
            bit other {
              position "0";
            }
            bit staryPacket {
              position "1";
            }
            bit malformedPacket {
              position "2";
            }
            bit excessivePktLossRate {
              position "3";
            }
            bit bufferOverrun {
              position "4";
            }
            bit bufferUnderrun {
              position "5";
            }
            bit remotePktLoss {
              position "6";
            }
            bit pktMisOrder {
              position "7";
            }
            bit packetLoss {
              position "8";
            }
            bit tdmFault {
              position "9";
            }
          }
          description
           "The state of TDM indicators when the TDM PW last declared
            an error second (either as ES, SES or a second with
            errors inside a UAS) condition. At this time, only LOPS
            can create a failure. Since indicators other than LOPS are
            useful, all are latched here. For bit definitions, see
            cpwCTDMCurrentIndications above.
            
            Note: the algorithm used to latch these indications when
            entering a defect state is implementation specific.";
          smiv2:max-access "read-only";
          smiv2:oid "1.3.6.1.4.1.9.10.131.1.1.1.10";
        }

        leaf cpwCTDMLastEsTimeStamp {
          type yang:timestamp;
          description
           "The value of sysUpTime at the most recent occasion at
            which the TDM PW entered the ES or SES state.";
          smiv2:max-access "read-only";
          smiv2:oid "1.3.6.1.4.1.9.10.131.1.1.1.11";
        }
      }
    }

    container cpwCTDMCfgTable {
      description
       "This table contains a set of parameters that may be
        referenced by one or more TDM PWs in cpwCTDMTable.";
      smiv2:oid "1.3.6.1.4.1.9.10.131.1.3";

      list cpwCTDMCfgEntry {
        key "cpwCTDMCfgIndex";
        description
         "These parameters define the characteristics of a
          TDM PW. They are grouped here to ease NMS burden.
          Once an entry is created here it may be re-used
          by many PWs.";
        smiv2:oid "1.3.6.1.4.1.9.10.131.1.3.1";

        leaf cpwCTDMCfgIndex {
          type CISCO-IETF-PW-TDM-MIB:CpwTDMCfgIndex;
          description
           "Index to an entry in this table. The value is a copy of
            the assigned cpwCTDMCfgIndexNext.";
          smiv2:max-access "not-accessible";
          smiv2:oid "1.3.6.1.4.1.9.10.131.1.3.1.1";
        }

        leaf cpwCTDMCfgConfErr {
          type bits {
            bit other {
              position "0";
            }
            bit payloadSize {
              position "1";
            }
            bit jtrBfrDepth {
              position "2";
            }
          }
          description
           "This object indicates the various configuration errors,
            illegal settings within the cpwCTDMCfg table. The errors
            can be due to several reasons, like Payload size mismatch
            or Jitter Buffer depth value mistmatch. 
            
            payloadSize - This bit is set if there is Payload size
                          mismatch between the local and peer
                          configurations. 
            jtrBfrDepth - This bit is set if there is Jitter Buffer
                          depth value mistmatch.
            other       - This bit is set if the error is not due to
                          payloadSize and jtrBfrDepth mismatch.";
          smiv2:max-access "read-only";
          smiv2:oid "1.3.6.1.4.1.9.10.131.1.3.1.2";
        }

        leaf cpwCTDMCfgPayloadSize {
          type uint32;
          units "bytes";
          description
           "The value of this object indicates the PayLoad Size (in
            bytes) to be defined during the PW setUp. Upon TX,
            implementation must be capable of carrying that amount of
            bytes. Upon RX, when the LEN field is set to 0, the
            payload of packet  MUST assume this size, and if the actual
            packet size is inconsistent with this length,
            the packet MUST be considered to be malformed.";
          smiv2:defval "32";
          smiv2:max-access "read-write";
          smiv2:oid "1.3.6.1.4.1.9.10.131.1.3.1.3";
        }

        leaf cpwCTDMCfgPktReorder {
          type boolean;
          description
           "If set to true, CE bound packets are queued in the
            jitter buffer, out of order packets are re-ordered. The
            maximum sequence number differential (i.e., the range in
            which re-sequencing can occur) is dependant on the depth
            of the jitter buffer. See cpwCTDMCfgJtrBfrDepth.";
          smiv2:defval "true";
          smiv2:max-access "read-write";
          smiv2:oid "1.3.6.1.4.1.9.10.131.1.3.1.4";
        }

        leaf cpwCTDMCfgRtpHdrUsed {
          type boolean;
          description
           "If the value of this object is set to false, then a
            RTP header is not pre-pended to the TDM packet.";
          reference
           "RFC 4553, which describes a pseudowire
            encapsulation for TDM (T1, E1, T3, E3) bit-streams
            disregards any structure that may be imposed on these
            streams.";
          smiv2:defval "false";
          smiv2:max-access "read-write";
          smiv2:oid "1.3.6.1.4.1.9.10.131.1.3.1.5";
        }

        leaf cpwCTDMCfgJtrBfrDepth {
          type uint32;
          units "microsecond";
          description
           "The size of this buffer SHOULD be locally
            configured to allow accommodation to the PSN-specific
            packet delay variation.
            
            If configured to a value not supported by the
            implementation, the agent MUST return an error code
            'jtrBfrDepth' in 'cpwCTDMConfigError '.
            Jitter buffers are a limited resource to be managed.
            The actual size should be at least twice as big as the
            value of cpwCTDMCfgJtrBfrDepth";
          smiv2:defval "3000";
          smiv2:max-access "read-write";
          smiv2:oid "1.3.6.1.4.1.9.10.131.1.3.1.6";
        }

        leaf cpwCTDMCfgPayloadSuppression {
          type enumeration {
            enum "enable" {
              value "1";
            }
            enum "disable" {
              value "2";
            }
          }
          description
           "This object indicates whether the Payload suppression
            is eanbled or disabled.
            Payload MAY be omitted in order to conserve bandwidth.
            
            enable  - Payload suppression is allowed.
            disable - No Payload suppresion under any condition.";
          smiv2:defval "disable";
          smiv2:max-access "read-write";
          smiv2:oid "1.3.6.1.4.1.9.10.131.1.3.1.7";
        }

        leaf cpwCTDMCfgConsecPktsInSynch {
          type uint32;
          units "packets";
          description
           "The number of consecutive packets with sequential
            sequence numbers that are required to exit the
            Loss of Packets (LOPS) state.";
          reference
           "RFC 4553, which describes a pseudowire
            encapsulation for TDM (T1, E1, T3, E3) bit-streams
            that disregards any structure that may be imposed
            on these streams.";
          smiv2:defval "2";
          smiv2:max-access "read-write";
          smiv2:oid "1.3.6.1.4.1.9.10.131.1.3.1.8";
        }

        leaf cpwCTDMCfgConsecMissPktsOutSynch {
          type uint32;
          units "packets";
          description
           "The number of consecutive missing packets that are
            required to enter the LOPS state.";
          reference
           "RFC 4553, which describes a pseudowire
            encapsulation for TDM (T1, E1, T3, E3) bit-streams
            that disregards any structure that may be imposed
            on these streams.";
          smiv2:defval "10";
          smiv2:max-access "read-write";
          smiv2:oid "1.3.6.1.4.1.9.10.131.1.3.1.9";
        }

        leaf cpwCTDMCfgSetUp2SynchTimeOut {
          type uint32;
          units "millisecond";
          description
           "The amount of time the host should wait before declaring
            the pseudo wire in down state,  if the number of consecutive
            TDM packets that have been received after changing the
            administrative status to up and after finalization of
            signaling (if supported) between the two PEs is smaller
            than cpwCTDMCfgConsecPktsInSynch. Once the the PW has
            OperStatus of 'up' this parameter is no longer valid. This
            parameter is defined to ensure that the host does not
            prematurely inform failure of the PW. In particular PW
            'down' notifications should not be sent before expiration of
            this timer. This parameter is valid only after adminisrative
            changes of the status of the PW. If the PW fails due to
            network impairments a 'down' notification should be sent.";
          smiv2:defval "5000";
          smiv2:max-access "read-write";
          smiv2:oid "1.3.6.1.4.1.9.10.131.1.3.1.10";
        }

        leaf cpwCTDMCfgPktReplacePolicy {
          type enumeration {
            enum "ais" {
              value "1";
            }
            enum "implementationSpecific" {
              value "2";
            }
          }
          description
           "This parameter determines the value to be played when CE
            bound packets have over/underflow the jitter buffer, or are
            missing for any reason. This AIS (Alarm Indication Signal)
            pattern is sent (played) on the TDM line.
            
            ais                    - AIS (Alarm Indication Signal)
                                     pattern is sent (played) on
                                     the TDM line. 
            implementationSpecific - Implementation specific pattern is
                                     sent on the TDM line.";
          smiv2:defval "ais";
          smiv2:max-access "read-write";
          smiv2:oid "1.3.6.1.4.1.9.10.131.1.3.1.11";
        }

        leaf cpwCTDMCfgAvePktLossTimeWindow {
          type int32;
          units "millisecond";
          description
           "The length of time over which the average packet
            loss rate should be computed to detect Excessive packet
            loss rate";
          smiv2:defval "20";
          smiv2:max-access "read-write";
          smiv2:oid "1.3.6.1.4.1.9.10.131.1.3.1.12";
        }

        leaf cpwCTDMCfgExcessivePktLossThreshold {
          type uint32;
          description
           "Excessive packet loss rate is detected by computing the
            average packetloss rate over a 
            cpwCTDMCfgAvePktLossTimeWindow amount of time and
            comparing it with this threshold value.";
          smiv2:defval "2";
          smiv2:max-access "read-write";
          smiv2:oid "1.3.6.1.4.1.9.10.131.1.3.1.13";
        }

        leaf cpwCTDMCfgAlarmThreshold {
          type uint32;
          units "milliseconds";
          description
           "Alarms are only reported when the defect state persists
            for the length of time specified by this object.
            The object's unit is millisec";
          smiv2:defval "2500";
          smiv2:max-access "read-write";
          smiv2:oid "1.3.6.1.4.1.9.10.131.1.3.1.14";
        }

        leaf cpwCTDMCfgClearAlarmThreshold {
          type uint32;
          units "milliseconds";
          description
           "Alarm MUST be cleared after the corresponding defect is
            undetected for the amount of time specified by this object.
            The object's unit is millisec";
          smiv2:defval "10000";
          smiv2:max-access "read-write";
          smiv2:oid "1.3.6.1.4.1.9.10.131.1.3.1.15";
        }

        leaf cpwCTDMCfgMissingPktsToSes {
          type uint32;
          units "seconds";
          description
           "Number of missing packets detected (consecutive or not)
            within a 1 second window to cause a Severely Error
            Second (SES) to be counted.";
          smiv2:defval "3";
          smiv2:max-access "read-write";
          smiv2:oid "1.3.6.1.4.1.9.10.131.1.3.1.16";
        }

        leaf cpwCTDMCfgTimestampMode {
          type enumeration {
            enum "notApplicable" {
              value "1";
            }
            enum "absolute" {
              value "2";
            }
            enum "differential" {
              value "3";
            }
          }
          description
           "Timestamp generation MAY be used in one of the following
            modes:
            1. Absolute mode: the PSN-bound IWF sets timestamps
             using the clock recovered from the incoming TDM attachment
             circuit. As a consequence, the timestamps are closely
             correlated with the sequence numbers. All TDM 
             implementations that support usage of the RTP header MUST
             support this mode.
            2. Differential mode: Both IWFs have access to a common
             high-quality timing source, and this source is used for
             timestamp generation. Support of this mode is OPTIONAL.";
          smiv2:defval "absolute";
          smiv2:max-access "read-write";
          smiv2:oid "1.3.6.1.4.1.9.10.131.1.3.1.17";
        }

        leaf cpwCTDMCfgStorageType {
          type snmpv2-tc:StorageType;
          description
           "This variable indicates the storage type for this row.
            The following are the read-write objects in permanent(4)
            rows, that an agent must allow to be writable:
            cpwCTDMCfgPayloadSize, cpwCTDMCfgPktReorder,
            cpwCTDMCfgRtpHdrUsed, cpwCTDMCfgJtrBfrDepth,
            cpwCTDMCfgPayloadSuppression, cpwCTDMCfgConfErr.";
          smiv2:defval "nonVolatile";
          smiv2:max-access "read-write";
          smiv2:oid "1.3.6.1.4.1.9.10.131.1.3.1.18";
        }

        leaf cpwCTDMCfgRowStatus {
          type snmpv2-tc:RowStatus;
          description
           "The status of this conceptual row.
            
            To create a row in this table, a manager must
            set this object to either createAndGo(4) or
            createAndWait(5).
            
            All of the columnar objects have to be set to
            valid values before the row can be activated.
            Default value will be automatically provisioned
            if for those objects not specified during row
            creation. 
            No objects in cascading tables have to be populated with
            related data before the row can be activated.
            
            The following objects cannot be modified if the
            RowStatus is active:
            cpwCTDMCfgPayloadSize, cpwCTDMCfgRtpHdrUsed,
            cpwCTDMCfgJtrBfrDepth, and cpwCTDMCfgPayloadSuppression.
            
            If the RowStatus is active, the following parameters can be
            modified: 
            cpwCTDMCfgConfErr, cpwCTDMCfgPktReorder, 
            cpwCTDMCfgConsecPktsInSynch,
            cpwCTDMCfgConsecMissPktsOutSynch,
            cpwCTDMCfgSetUp2SynchTimeOut, cpwCTDMCfgPktReplacePolicy,
            cpwCTDMCfgAvePktLossTimeWindow, 
            cpwCTDMCfgExcessivePktLossThreshold,
            cpwCTDMCfgAlarmThreshold, cpwCTDMCfgClearAlarmThreshold,
            cpwCTDMCfgMissingPktsToSes, cpwCTDMCfgTimestampMode,
            cpwCTDMCfgStorageType.
            
            A row may be deleted by setting the RowStatus to 'destroy'.";
          smiv2:max-access "read-write";
          smiv2:oid "1.3.6.1.4.1.9.10.131.1.3.1.19";
        }
      }
    }

    container cpwCTDMPerfCurrentTable {
      description
       "This table provides TDM PW performance information.
        This includes current 15 minute interval counts. 
        
        The table includes counters that work together to
        integrate errors and the lack of errors on the TDM PW.
        An error is caused by a missing packet. Missing packet
        can be a result of, packet loss in the network,
        (uncorrectable) packet out of sequence, packet length error,
        jitter buffer overflow, and jitter buffer underflow.
        The result is declaring whether or not the TDM PW is in
        Loss of Packet (LOPS) state.";
      smiv2:oid "1.3.6.1.4.1.9.10.131.1.5";

      list cpwCTDMPerfCurrentEntry {
        key "cpwVcIndex";
        description
         "An entry in this table is created by the agent for every
          cpwCTDMTable entry. After 15 minutes, the contents of this
          table entry are copied to a new entry in the
          cpwCTDMPerfInterval table and the counts in this entry
          are reset to zero.";
        smiv2:oid "1.3.6.1.4.1.9.10.131.1.5.1";

        leaf cpwVcIndex {
          type leafref {
            path "/cisco-ietf:CISCO-IETF-PW-MIB/cisco-ietf:cpwVcTable/cisco-ietf:cpwVcEntry/cisco-ietf:cpwVcIndex";
          }
        }

        leaf cpwCTDMPerfCurrentMissingPkts {
          type perfhist-tc:PerfCurrentCount;
          units "packets";
          description
           "Number of missing packets (as detected via control word
            sequence number gaps).";
          smiv2:max-access "read-only";
          smiv2:oid "1.3.6.1.4.1.9.10.131.1.5.1.1";
        }

        leaf cpwCTDMPerfCurrentPktsReOrder {
          type perfhist-tc:PerfCurrentCount;
          units "packets";
          description
           "Number of packets detected out of sequence (via control
            word sequence number), but successfully re-ordered.";
          smiv2:max-access "read-only";
          smiv2:oid "1.3.6.1.4.1.9.10.131.1.5.1.2";
        }

        leaf cpwCTDMPerfCurrentJtrBfrUnderruns {
          type perfhist-tc:PerfCurrentCount;
          description
           "Number of times a packet needed to be played
            out and the jitter buffer was empty.";
          smiv2:max-access "read-only";
          smiv2:oid "1.3.6.1.4.1.9.10.131.1.5.1.3";
        }

        leaf cpwCTDMPerfCurrentMisOrderDropped {
          type perfhist-tc:PerfCurrentCount;
          units "packets";
          description
           "Number of packets detected out of order(via control word
            sequence numbers), and could not be re-ordered, or could
            not fit in the jitter buffer.";
          smiv2:max-access "read-only";
          smiv2:oid "1.3.6.1.4.1.9.10.131.1.5.1.4";
        }

        leaf cpwCTDMPerfCurrentMalformedPkt {
          type perfhist-tc:PerfCurrentCount;
          units "packets";
          description
           "Number of packets detected with unexpected size, or
            bad headers' stack";
          smiv2:max-access "read-only";
          smiv2:oid "1.3.6.1.4.1.9.10.131.1.5.1.5";
        }

        leaf cpwCTDMPerfCurrentESs {
          type perfhist-tc:PerfCurrentCount;
          units "seconds";
          description
           "The counter associated with the number of Error
            Seconds encountered. Any malformed packet, sequence error
            and similar are considered as error second";
          smiv2:max-access "read-only";
          smiv2:oid "1.3.6.1.4.1.9.10.131.1.5.1.6";
        }

        leaf cpwCTDMPerfCurrentSESs {
          type perfhist-tc:PerfCurrentCount;
          units "seconds";
          description
           "The counter associated with the number of
            Severely Error Seconds encountered.";
          smiv2:max-access "read-only";
          smiv2:oid "1.3.6.1.4.1.9.10.131.1.5.1.7";
        }

        leaf cpwCTDMPerfCurrentUASs {
          type perfhist-tc:PerfCurrentCount;
          units "seconds";
          description
           "The counter associated with the number of
            Unavailable Seconds encountered. Any consequtive
            five seconds of SES are counted as one UAS";
          smiv2:max-access "read-only";
          smiv2:oid "1.3.6.1.4.1.9.10.131.1.5.1.8";
        }

        leaf cpwCTDMPerfCurrentFC {
          type perfhist-tc:PerfCurrentCount;
          description
           "This object represents the number of TDM failure
            events. A failure event begins when the LOPS failure
            is declared, and ends when the failure is cleared. A
            failure event that begins in one period and ends in
            another period is counted only in the period in which
            it begins.";
          smiv2:max-access "read-only";
          smiv2:oid "1.3.6.1.4.1.9.10.131.1.5.1.9";
        }
      }
    }

    container cpwCTDMPerfIntervalTable {
      description
       "This table provides performance information per TDM PW
        similar to the cpwCTDMPerfCurrentTable above. However,
        these counts represent historical 15 minute intervals.
        Typically, this table will have a maximum of 96 entries
        for a 24 hour period, but is not limited to this.";
      smiv2:oid "1.3.6.1.4.1.9.10.131.1.6";

      list cpwCTDMPerfIntervalEntry {
        key "cpwVcIndex cpwCTDMPerfIntervalNumber";
        description
         "An entry in this table is created by the agent for
          every cpwCTDMPerfCurrentEntry that is 15 minutes old.
          The contents of the Current entry are copied to the new
          entry here. The Current entry, then resets its counts
          to zero for the next current 15 minute interval.";
        smiv2:oid "1.3.6.1.4.1.9.10.131.1.6.1";

        leaf cpwVcIndex {
          type leafref {
            path "/cisco-ietf:CISCO-IETF-PW-MIB/cisco-ietf:cpwVcTable/cisco-ietf:cpwVcEntry/cisco-ietf:cpwVcIndex";
          }
        }

        leaf cpwCTDMPerfIntervalNumber {
          type uint32;
          description
           "This object indicates a number (normally between 1 and
            96 to cover a 24 hour period) which identifies the interval
            for which the set of statistics is available. The interval
            identified by 1 is the most recently completed 15 minute
            interval, and the interval identified by N is the interval
            immediately preceding the one identified by N-1.
            The minimum range of N is 1 through 4.The default range
            is 1 through 32. The maximum value of N is 1 through 96.";
          smiv2:max-access "not-accessible";
          smiv2:oid "1.3.6.1.4.1.9.10.131.1.6.1.1";
        }

        leaf cpwCTDMPerfIntervalValidData {
          type boolean;
          description
           "This variable indicates if the data for this interval
            is valid.";
          smiv2:max-access "read-only";
          smiv2:oid "1.3.6.1.4.1.9.10.131.1.6.1.2";
        }

        leaf cpwCTDMPerfIntervalDuration {
          type uint32;
          units "seconds";
          description
           "The duration of a particular interval in seconds.
            Adjustments in the system's time-of-day clock, may
            cause the interval to be greater or less than, the
            normal value. Therefore this actual interval value
            is provided.";
          smiv2:defval "900";
          smiv2:max-access "read-only";
          smiv2:oid "1.3.6.1.4.1.9.10.131.1.6.1.3";
        }

        leaf cpwCTDMPerfIntervalMissingPkts {
          type perfhist-tc:PerfIntervalCount;
          units "packets";
          description
           "Number of missing packets (as detected via control
            word sequence number gaps).";
          smiv2:max-access "read-only";
          smiv2:oid "1.3.6.1.4.1.9.10.131.1.6.1.4";
        }

        leaf cpwCTDMPerfIntervalPktsReOrder {
          type perfhist-tc:PerfIntervalCount;
          units "packets";
          description
           "Number of packets detected out of sequence (via control
            word sequence number), but successfully re-ordered.";
          smiv2:max-access "read-only";
          smiv2:oid "1.3.6.1.4.1.9.10.131.1.6.1.5";
        }

        leaf cpwCTDMPerfIntervalJtrBfrUnderruns {
          type perfhist-tc:PerfIntervalCount;
          description
           "Number of times a packet needed to be played
            out and the jitter buffer was empty.";
          smiv2:max-access "read-only";
          smiv2:oid "1.3.6.1.4.1.9.10.131.1.6.1.6";
        }

        leaf cpwCTDMPerfIntervalMisOrderDropped {
          type perfhist-tc:PerfIntervalCount;
          units "packets";
          description
           "Number of packets detected out of order(via control word
            sequence numbers), and could not be re-ordered, or could
            not fit in the jitter buffer.";
          smiv2:max-access "read-only";
          smiv2:oid "1.3.6.1.4.1.9.10.131.1.6.1.7";
        }

        leaf cpwCTDMPerfIntervalMalformedPkt {
          type perfhist-tc:PerfIntervalCount;
          units "packets";
          description
           "Number of packets detected with unexpected size, or
            bad headers' stack";
          smiv2:max-access "read-only";
          smiv2:oid "1.3.6.1.4.1.9.10.131.1.6.1.8";
        }

        leaf cpwCTDMPerfIntervalESs {
          type perfhist-tc:PerfIntervalCount;
          units "seconds";
          description
           "The counter associated with the number of Error
            Seconds encountered.";
          smiv2:max-access "read-only";
          smiv2:oid "1.3.6.1.4.1.9.10.131.1.6.1.9";
        }

        leaf cpwCTDMPerfIntervalSESs {
          type perfhist-tc:PerfIntervalCount;
          description
           "The counter associated with the number of
            Severely Error Seconds encountered.";
          smiv2:max-access "read-only";
          smiv2:oid "1.3.6.1.4.1.9.10.131.1.6.1.10";
        }

        leaf cpwCTDMPerfIntervalUASs {
          type perfhist-tc:PerfIntervalCount;
          units "seconds";
          description
           "The counter associated with the number of
            Unavailable Seconds encountered.";
          smiv2:max-access "read-only";
          smiv2:oid "1.3.6.1.4.1.9.10.131.1.6.1.11";
        }

        leaf cpwCTDMPerfIntervalFC {
          type perfhist-tc:PerfIntervalCount;
          description
           "This object represents the number of TDM failure
            events. A failure event begins when the LOPS failure
            is declared, and ends when the failure is cleared. A
            failure event that begins in one period and ends in
            another period is counted only in the period in which
            it begins.";
          smiv2:max-access "read-only";
          smiv2:oid "1.3.6.1.4.1.9.10.131.1.6.1.12";
        }
      }
    }

    container cpwCTDMPerf1DayIntervalTable {
      description
       "This table provides performance information per TDM PW
        similar to the cpwCTDMPerfIntervalTable above. However,
        these counters represent historical 1 day intervals up to
        one full month. The table consists of real time data, as
        such it is not persistence across re-boot.";
      smiv2:oid "1.3.6.1.4.1.9.10.131.1.7";

      list cpwCTDMPerf1DayIntervalEntry {
        key "cpwVcIndex cpwCTDMPerf1DayIntervalNumber";
        description
         "An entry is created in this table by the agent
          for every entry in the cpwCTDMTable table.";
        smiv2:oid "1.3.6.1.4.1.9.10.131.1.7.1";

        leaf cpwVcIndex {
          type leafref {
            path "/cisco-ietf:CISCO-IETF-PW-MIB/cisco-ietf:cpwVcTable/cisco-ietf:cpwVcEntry/cisco-ietf:cpwVcIndex";
          }
        }

        leaf cpwCTDMPerf1DayIntervalNumber {
          type uint32;
          description
           "The number of interval, where 1 indicates current day
            measured period and 2 and above indicate previous days
            respectively";
          smiv2:max-access "not-accessible";
          smiv2:oid "1.3.6.1.4.1.9.10.131.1.7.1.1";
        }

        leaf cpwCTDMPerf1DayIntervalValidData {
          type boolean;
          description
           "This variable indicates if the data for this interval
            is valid.";
          smiv2:max-access "read-only";
          smiv2:oid "1.3.6.1.4.1.9.10.131.1.7.1.2";
        }

        leaf cpwCTDMPerf1DayIntervalDuration {
          type uint32;
          units "seconds";
          description
           "The duration of a particular interval in seconds,
            Adjustments in the system's time-of-day clock, may
            cause the interval to be greater or less than, the
            normal value. Therefore this actual interval value
            is provided.";
          smiv2:max-access "read-only";
          smiv2:oid "1.3.6.1.4.1.9.10.131.1.7.1.3";
        }

        leaf cpwCTDMPerf1DayIntervalMissingPkts {
          type yang:counter32;
          units "packets";
          description
           "Number of missing packets (as detected via control word
            sequence number gaps).";
          smiv2:max-access "read-only";
          smiv2:oid "1.3.6.1.4.1.9.10.131.1.7.1.4";
        }

        leaf cpwCTDMPerf1DayIntervalPktsReOrder {
          type yang:counter32;
          units "packets";
          description
           "Number of packets detected out of sequence (via control
            word sequence number), but successfully re-ordered.";
          smiv2:max-access "read-only";
          smiv2:oid "1.3.6.1.4.1.9.10.131.1.7.1.5";
        }

        leaf cpwCTDMPerf1DayIntervalJtrBfrUnderruns {
          type yang:counter32;
          description
           "Number of times a packet needed to be played
            out and the jitter buffer was empty.";
          smiv2:max-access "read-only";
          smiv2:oid "1.3.6.1.4.1.9.10.131.1.7.1.6";
        }

        leaf cpwCTDMPerf1DayIntervalMisOrderDropped {
          type yang:counter32;
          units "packets";
          description
           "Number of packets detected out of order(via control word
            sequence numbers), and could not be re-ordered, or could
            not fit in the jitter buffer.";
          smiv2:max-access "read-only";
          smiv2:oid "1.3.6.1.4.1.9.10.131.1.7.1.7";
        }

        leaf cpwCTDMPerf1DayIntervalMalformedPkt {
          type yang:counter32;
          units "packets";
          description
           "Number of packets detected with unexpected size, or
            bad headers' stack.";
          smiv2:max-access "read-only";
          smiv2:oid "1.3.6.1.4.1.9.10.131.1.7.1.8";
        }

        leaf cpwCTDMPerf1DayIntervalESs {
          type yang:counter32;
          units "seconds";
          description
           "The counter associated with the number of Error
            Seconds encountered.";
          smiv2:max-access "read-only";
          smiv2:oid "1.3.6.1.4.1.9.10.131.1.7.1.9";
        }

        leaf cpwCTDMPerf1DayIntervalSESs {
          type yang:counter32;
          units "seconds";
          description
           "The counter associated with the number of Severely
            Error Seconds.";
          smiv2:max-access "read-only";
          smiv2:oid "1.3.6.1.4.1.9.10.131.1.7.1.10";
        }

        leaf cpwCTDMPerf1DayIntervalUASs {
          type yang:counter32;
          units "seconds";
          description
           "The counter associated with the number of
            UnAvailable Seconds.
            When first entering the UAS state, the number
            of SES To UAS is added to this object, then as each
            additional UAS occurs, this object increments by one.";
          smiv2:max-access "read-only";
          smiv2:oid "1.3.6.1.4.1.9.10.131.1.7.1.11";
        }

        leaf cpwCTDMPerf1DayIntervalFC {
          type yang:counter32;
          description
           "This object represents the number of TDM failure
            events. A failure event begins when the LOPS failure
            is declared, and ends when the failure is cleared.";
          smiv2:max-access "read-only";
          smiv2:oid "1.3.6.1.4.1.9.10.131.1.7.1.12";
        }
      }
    }
  }

  smiv2:alias "cpwCTDMMIB" {
    smiv2:oid "1.3.6.1.4.1.9.10.131";
  }

  smiv2:alias "cpwCTDMNotifications" {
    smiv2:oid "1.3.6.1.4.1.9.10.131.0";
  }

  smiv2:alias "cpwCTDMObjects" {
    smiv2:oid "1.3.6.1.4.1.9.10.131.1";
  }

  smiv2:alias "cpwCTDMConformance" {
    smiv2:oid "1.3.6.1.4.1.9.10.131.2";
  }

  smiv2:alias "cpwCTDMGroups" {
    smiv2:oid "1.3.6.1.4.1.9.10.131.2.1";
  }

  smiv2:alias "cpwCTDMCompliances" {
    smiv2:oid "1.3.6.1.4.1.9.10.131.2.2";
  }

}
