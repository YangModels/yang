/*
 * Generated by confdc --mib2yang-std
 * Source: mgmt/dmi/model/common/mib-source/CISCO-IPSEC-FLOW-MONITOR-MIB.mib
 */
/*
 * This YANG module has been generated by smidump 0.5.0:
 *
 *      smidump -f yang CISCO-IPSEC-FLOW-MONITOR-MIB
 *
 * Do not edit. Edit the source file instead!
 */

module CISCO-IPSEC-FLOW-MONITOR-MIB {

  namespace "urn:ietf:params:xml:ns:yang:smiv2:CISCO-IPSEC-FLOW-MONITOR-MIB";
  prefix CISCO-IPSEC-FLOW-MONITOR-MIB;

  import CISCO-MEDIA-GATEWAY-MIB {
    prefix "cisco-media";
  }

  import SNMPv2-TC {
    prefix "snmpv2-tc";
  }

  import ietf-yang-smiv2 {
    prefix "smiv2";
  }

  import ietf-yang-types {
    prefix "yang";
  }

  organization
   "Tivoli Systems and Cisco Systems";

  contact
   "Tivoli Systems
    Research Triangle Park, NC
    
    Cisco Systems
    170 W Tasman Drive
    San Jose, CA  95134
    USA
    
    Tel: +1 800 553-NETS
    E-mail: cs-ipsecurity@cisco.com";

  description
   "This is a MIB Module for monitoring the
    structures in IPSec-based Virtual Private Networks.
    The MIB has been designed to be adopted as an IETF
    standard. Hence Cisco-specific features of IPSec
    protocol are excluded from this MIB. 
    
    Acronyms
    The following acronyms are used in this document:
    
     IPSec:      Secure IP Protocol
    
     VPN:        Virtual Private Network
    
     ISAKMP:     Internet Security Association and Key Exchange
                 Protocol
    
     IKE:        Internet Key Exchange Protocol
    
     SA:         Security Association
    
     MM:         Main Mode - the process of setting up
                 a Phase 1 SA to secure the exchanges
                 required to setup Phase 2 SAs
    
     QM:         Quick Mode - the process of setting up
                 Phase 2 Security Associations using 
                 a Phase 1 SA.
    
    
     Overview of IPsec MIB
    
    The MIB contains six major groups of objects which are
    used to manage the IPSec Protocol. These groups include
    a Levels Group, a Phase-1 Group, a Phase-2 Group,
    a History Group, a Failure Group and a TRAP Control Group.
    The following table illustrates the structure of the
    IPSec MIB.
    
    The Phase 1 group models objects pertaining to
    IKE negotiations and tunnels.
    
    The Phase 2 group models objects pertaining to
    IPSec data tunnels.
    
    The History group is to aid applications that do
    trending analysis.
    
    The Failure group is to enable an operator to
    do troubleshooting and debugging of the VPN Router.
    Further, counters are supported to aid Intrusion 
    Detection.
    
    In addition to the five major MIB Groups, there are
    a number of Notifications. The following table
    illustrates the name and description of the 
    IPSec TRAPs.
    
    For a detailed discussion, please refer to the IETF
    draft draft-ietf-ipsec-flow-monitoring-mib-00.txt.";

  revision 2007-10-24 {
    description
     "In the description of cipSecTunHistHcInDecompOctets,
      cipSecTunHcInOctets has been changed to 
      cipSecTunHistHcInOctets.   
      
      In the description of cipSecTunHistOutUncompOctets,
      cipSecTunOutOctets has been changed to 
      cipSecTunHistOutOctets.
      
      In the description of cipSecTunHistHcOutUncompOctets,
      cipSecTunHcOutOctets has been changed to 
      cipSecTunHistHcOutOctets.
      
      In the description of cipSecTunHistInDecompOctets,
      cipSecTunInOctets has been changed to 
      cipSecTunHistInOctets.";
  }

  revision 2004-10-12 {
    description
     "Added two table for media gateway stats
      information:
          cikePhase1GWStatsTable (phase-1 IKE)
          cipSecPhase2GWStatsTable (phase-2 IPsec)";
  }

  revision 2000-10-13 {
    description
     "Changed cipSecSpiValue to Unsigned32.
      Changed Protocol ranges to
      start at 0 instead of 1.
      Removed comment(s) incorrectly indicating
      this MIB was CiscoExperiment.";
  }

  revision 2000-08-17 {
    description
     "Initial version of this MIB module.";
  }

  typedef IPSIpAddress {
    type binary {
      length "4|16";
    }
    description
     "An IP V4 or V6 Address.";
  }

  typedef IkePeerType {
    type enumeration {
      enum "ipAddrPeer" {
        value "1";
      }
      enum "namePeer" {
        value "2";
      }
    }
    description
     "The type of IPsec Phase-1 IKE peer identity.
      The IKE peer may be identified by:
       1. an IP address, or
       2. a host name.";
  }

  typedef IkeNegoMode {
    type enumeration {
      enum "main" {
        value "1";
      }
      enum "aggressive" {
        value "2";
      }
    }
    description
     "The IPsec Phase-1 IKE negotiation mode.";
  }

  typedef IkeHashAlgo {
    type enumeration {
      enum "none" {
        value "1";
      }
      enum "md5" {
        value "2";
      }
      enum "sha" {
        value "3";
      }
    }
    description
     "The hash algorithm used in IPsec Phase-1
      IKE negotiations.";
  }

  typedef IkeAuthMethod {
    type enumeration {
      enum "none" {
        value "1";
      }
      enum "preSharedKey" {
        value "2";
      }
      enum "rsaSig" {
        value "3";
      }
      enum "rsaEncrypt" {
        value "4";
      }
      enum "revPublicKey" {
        value "5";
      }
    }
    description
     "The authentication method used in IPsec Phase-1 IKE
      negotiations.";
  }

  typedef DiffHellmanGrp {
    type enumeration {
      enum "none" {
        value "1";
      }
      enum "dhGroup1" {
        value "2";
      }
      enum "dhGroup2" {
        value "3";
      }
    }
    description
     "The Diffie Hellman Group used in negotiations.";
  }

  typedef KeyType {
    type enumeration {
      enum "ike" {
        value "1";
      }
      enum "manual" {
        value "2";
      }
    }
    description
     "The type of key used by an IPsec Phase-2 Tunnel.";
  }

  typedef EncapMode {
    type enumeration {
      enum "tunnel" {
        value "1";
      }
      enum "transport" {
        value "2";
      }
    }
    description
     "The encapsulation mode used by an IPsec Phase-2
      Tunnel.";
  }

  typedef EncryptAlgo {
    type enumeration {
      enum "none" {
        value "1";
      }
      enum "des" {
        value "2";
      }
      enum "des3" {
        value "3";
      }
    }
    description
     "The encryption algorithm used in negotiations.";
  }

  typedef AuthAlgo {
    type enumeration {
      enum "none" {
        value "1";
      }
      enum "hmacMd5" {
        value "2";
      }
      enum "hmacSha" {
        value "3";
      }
    }
    description
     "The authentication algorithm used by a
      security association of an IPsec Phase-2 Tunnel.";
  }

  typedef CompAlgo {
    type enumeration {
      enum "none" {
        value "1";
      }
      enum "ldf" {
        value "2";
      }
    }
    description
     "The compression algorithm used by a
      security association of an IPsec Phase-2 Tunnel.";
  }

  typedef EndPtType {
    type enumeration {
      enum "singleIpAddr" {
        value "1";
      }
      enum "ipAddrRange" {
        value "2";
      }
      enum "ipSubnet" {
        value "3";
      }
    }
    description
     "The type of identity use to specify an IPsec End Point.";
  }

  typedef TunnelStatus {
    type enumeration {
      enum "active" {
        value "1";
      }
      enum "destroy" {
        value "2";
      }
    }
    description
     "The status of a Tunnel.  Objects of this type may
      be used to bring the tunnel down by setting
      value of this object to destroy(2).  Objects of this
      type cannot be used to create a Tunnel.";
  }

  typedef TrapStatus {
    type enumeration {
      enum "enabled" {
        value "1";
      }
      enum "disabled" {
        value "2";
      }
    }
    description
     "The administrative status for sending a TRAP.";
  }


  container CISCO-IPSEC-FLOW-MONITOR-MIB {
    config false;

    container cipSecLevels {
      smiv2:oid "1.3.6.1.4.1.9.9.171.1.1";

      leaf cipSecMibLevel {
        type int32 {
          range "1..4096";
        }
        description
         "The level of the IPsec MIB.";
        smiv2:max-access "read-only";
        smiv2:oid "1.3.6.1.4.1.9.9.171.1.1.1";
      }
    }

    container cikeGlobalStats {
      smiv2:oid "1.3.6.1.4.1.9.9.171.1.2.1";

      leaf cikeGlobalActiveTunnels {
        type yang:gauge32;
        description
         "The number of currently active IPsec
          Phase-1 IKE Tunnels.";
        smiv2:max-access "read-only";
        smiv2:oid "1.3.6.1.4.1.9.9.171.1.2.1.1";
      }

      leaf cikeGlobalPreviousTunnels {
        type yang:counter32;
        units "SAs";
        description
         "The total number of previously active
          IPsec Phase-1 IKE Tunnels.";
        smiv2:max-access "read-only";
        smiv2:oid "1.3.6.1.4.1.9.9.171.1.2.1.2";
      }

      leaf cikeGlobalInOctets {
        type yang:counter32;
        units "Octets";
        description
         "The total number of octets received by all currently
          and previously active IPsec Phase-1 IKE Tunnels.";
        smiv2:max-access "read-only";
        smiv2:oid "1.3.6.1.4.1.9.9.171.1.2.1.3";
      }

      leaf cikeGlobalInPkts {
        type yang:counter32;
        units "Packets";
        description
         "The total number of packets received by all
          currently and previously active IPsec 
          Phase-1 IKE Tunnels.";
        smiv2:max-access "read-only";
        smiv2:oid "1.3.6.1.4.1.9.9.171.1.2.1.4";
      }

      leaf cikeGlobalInDropPkts {
        type yang:counter32;
        units "Packets";
        description
         "The total number of packets which were
          dropped during receive processing by all 
          currently and previously
           active IPsec Phase-1 IKE Tunnels.";
        smiv2:max-access "read-only";
        smiv2:oid "1.3.6.1.4.1.9.9.171.1.2.1.5";
      }

      leaf cikeGlobalInNotifys {
        type yang:counter32;
        units "Notification Payloads";
        description
         "The total number of notifys received by
          all currently and previously active IPsec 
          Phase-1 IKE Tunnels.";
        smiv2:max-access "read-only";
        smiv2:oid "1.3.6.1.4.1.9.9.171.1.2.1.6";
      }

      leaf cikeGlobalInP2Exchgs {
        type yang:counter32;
        units "SA Payloads";
        description
         "The total number of IPsec Phase-2 exchanges
          received by all currently and previously 
          active IPsec Phase-1 IKE Tunnels.";
        smiv2:max-access "read-only";
        smiv2:oid "1.3.6.1.4.1.9.9.171.1.2.1.7";
      }

      leaf cikeGlobalInP2ExchgInvalids {
        type yang:counter32;
        units "SA Payloads";
        description
         "The total number of IPsec Phase-2 exchanges
          which were received and found to be invalid 
          by all currently and previously active IPsec 
          Phase-1 IKE Tunnels.";
        smiv2:max-access "read-only";
        smiv2:oid "1.3.6.1.4.1.9.9.171.1.2.1.8";
      }

      leaf cikeGlobalInP2ExchgRejects {
        type yang:counter32;
        units "SA Payloads";
        description
         "The total number of IPsec Phase-2 exchanges
          which were received and rejected by all 
          currently and previously active IPsec Phase-1 
          IKE Tunnels.";
        smiv2:max-access "read-only";
        smiv2:oid "1.3.6.1.4.1.9.9.171.1.2.1.9";
      }

      leaf cikeGlobalInP2SaDelRequests {
        type yang:counter32;
        units "Notification Payloads";
        description
         "The total number of IPsec Phase-2 security
          association delete requests received by all 
          currently and previously
           active and IPsec Phase-1 IKE Tunnels.";
        smiv2:max-access "read-only";
        smiv2:oid "1.3.6.1.4.1.9.9.171.1.2.1.10";
      }

      leaf cikeGlobalOutOctets {
        type yang:counter32;
        units "Octets";
        description
         "The total number of octets sent by all currently
          and previously active and IPsec Phase-1 
          IKE Tunnels.";
        smiv2:max-access "read-only";
        smiv2:oid "1.3.6.1.4.1.9.9.171.1.2.1.11";
      }

      leaf cikeGlobalOutPkts {
        type yang:counter32;
        units "Packets";
        description
         "The total number of packets sent by all currently
          and previously active and IPsec Phase-1 
          Tunnels.";
        smiv2:max-access "read-only";
        smiv2:oid "1.3.6.1.4.1.9.9.171.1.2.1.12";
      }

      leaf cikeGlobalOutDropPkts {
        type yang:counter32;
        units "Packets";
        description
         "The total number of packets which were dropped
          during send processing by all currently 
          and previously
           active IPsec Phase-1 IKE Tunnels.";
        smiv2:max-access "read-only";
        smiv2:oid "1.3.6.1.4.1.9.9.171.1.2.1.13";
      }

      leaf cikeGlobalOutNotifys {
        type yang:counter32;
        units "Notification Payloads";
        description
         "The total number of notifys sent by all currently
          and previously active IPsec Phase-1 IKE Tunnels.";
        smiv2:max-access "read-only";
        smiv2:oid "1.3.6.1.4.1.9.9.171.1.2.1.14";
      }

      leaf cikeGlobalOutP2Exchgs {
        type yang:counter32;
        units "SA Payloads";
        description
         "The total number of IPsec Phase-2 exchanges
          which were sent by all currently and previously 
          active IPsec Phase-1 IKE Tunnels.";
        smiv2:max-access "read-only";
        smiv2:oid "1.3.6.1.4.1.9.9.171.1.2.1.15";
      }

      leaf cikeGlobalOutP2ExchgInvalids {
        type yang:counter32;
        units "SA Payloads";
        description
         "The total number of IPsec Phase-2 exchanges
          which were sent and found to be invalid by 
          all currently and previously active IPsec Phase-1 
          Tunnels.";
        smiv2:max-access "read-only";
        smiv2:oid "1.3.6.1.4.1.9.9.171.1.2.1.16";
      }

      leaf cikeGlobalOutP2ExchgRejects {
        type yang:counter32;
        units "SA Payloads";
        description
         "The total number of IPsec Phase-2 exchanges
          which were sent and rejected by all currently and
           previously active IPsec Phase-1 IKE Tunnels.";
        smiv2:max-access "read-only";
        smiv2:oid "1.3.6.1.4.1.9.9.171.1.2.1.17";
      }

      leaf cikeGlobalOutP2SaDelRequests {
        type yang:counter32;
        units "Notification Payloads";
        description
         "The total number of IPsec Phase-2 SA
          delete requests sent by all currently and 
          previously active IPsec Phase-1 IKE Tunnels.";
        smiv2:max-access "read-only";
        smiv2:oid "1.3.6.1.4.1.9.9.171.1.2.1.18";
      }

      leaf cikeGlobalInitTunnels {
        type yang:counter32;
        units "SAs";
        description
         "The total number of IPsec Phase-1 IKE
          Tunnels which were locally initiated.";
        smiv2:max-access "read-only";
        smiv2:oid "1.3.6.1.4.1.9.9.171.1.2.1.19";
      }

      leaf cikeGlobalInitTunnelFails {
        type yang:counter32;
        units "SAs";
        description
         "The total number of IPsec Phase-1 IKE Tunnels
          which were locally initiated and failed to activate.";
        smiv2:max-access "read-only";
        smiv2:oid "1.3.6.1.4.1.9.9.171.1.2.1.20";
      }

      leaf cikeGlobalRespTunnelFails {
        type yang:counter32;
        units "SAs";
        description
         "The total number of IPsec Phase-1 IKE Tunnels
          which were remotely initiated and failed to activate.";
        smiv2:max-access "read-only";
        smiv2:oid "1.3.6.1.4.1.9.9.171.1.2.1.21";
      }

      leaf cikeGlobalSysCapFails {
        type yang:counter32;
        units "Failures";
        description
         "The total number of system capacity failures
          which occurred during processing of all current 
          and previously active IPsec Phase-1 IKE Tunnels.";
        smiv2:max-access "read-only";
        smiv2:oid "1.3.6.1.4.1.9.9.171.1.2.1.22";
      }

      leaf cikeGlobalAuthFails {
        type yang:counter32;
        units "Failures";
        description
         "The total number of authentications which ended
          in failure by all current and previous IPsec Phase-1
          IKE Tunnels.";
        smiv2:max-access "read-only";
        smiv2:oid "1.3.6.1.4.1.9.9.171.1.2.1.23";
      }

      leaf cikeGlobalDecryptFails {
        type yang:counter32;
        units "Failures";
        description
         "The total number of decryptions which ended
          in failure by all current and previous IPsec Phase-1
          IKE Tunnels.";
        smiv2:max-access "read-only";
        smiv2:oid "1.3.6.1.4.1.9.9.171.1.2.1.24";
      }

      leaf cikeGlobalHashValidFails {
        type yang:counter32;
        units "Failures";
        description
         "The total number of hash validations which ended
          in failure by all current and previous IPsec Phase-1
          IKE Tunnels.";
        smiv2:max-access "read-only";
        smiv2:oid "1.3.6.1.4.1.9.9.171.1.2.1.25";
      }

      leaf cikeGlobalNoSaFails {
        type yang:counter32;
        units "Failures";
        description
         "The total number of non-existent Security Association
          in failures which occurred during processing of 
          all current and previous IPsec Phase-1 IKE Tunnels.";
        smiv2:max-access "read-only";
        smiv2:oid "1.3.6.1.4.1.9.9.171.1.2.1.26";
      }
    }

    container cipSecGlobalStats {
      smiv2:oid "1.3.6.1.4.1.9.9.171.1.3.1";

      leaf cipSecGlobalActiveTunnels {
        type yang:gauge32;
        description
         "The total number of currently active
          IPsec Phase-2 Tunnels.";
        smiv2:max-access "read-only";
        smiv2:oid "1.3.6.1.4.1.9.9.171.1.3.1.1";
      }

      leaf cipSecGlobalPreviousTunnels {
        type yang:counter32;
        units "Phase-2 Tunnels";
        description
         "The total number of previously active
          IPsec Phase-2 Tunnels.";
        smiv2:max-access "read-only";
        smiv2:oid "1.3.6.1.4.1.9.9.171.1.3.1.2";
      }

      leaf cipSecGlobalInOctets {
        type yang:counter32;
        units "Octets";
        description
         "The total number of octets received by all
          current and previous IPsec Phase-2 Tunnels. 
          This value is
          accumulated BEFORE determining whether or not
          the packet should be decompressed. See also
          cipSecGlobalInOctWraps for the number of times
          this counter has wrapped.";
        smiv2:max-access "read-only";
        smiv2:oid "1.3.6.1.4.1.9.9.171.1.3.1.3";
      }

      leaf cipSecGlobalHcInOctets {
        type yang:counter64;
        description
         "A high capacity count of the total number of
          octets received by all current and previous
          IPsec Phase-2 Tunnels. This value is accumulated
          BEFORE determining whether or not the packet
          should be decompressed.";
        smiv2:max-access "read-only";
        smiv2:oid "1.3.6.1.4.1.9.9.171.1.3.1.4";
      }

      leaf cipSecGlobalInOctWraps {
        type yang:counter32;
        units "Integral units";
        description
         "The number of times the global octets received
          counter (cipSecGlobalInOctets) has wrapped.";
        smiv2:max-access "read-only";
        smiv2:oid "1.3.6.1.4.1.9.9.171.1.3.1.5";
      }

      leaf cipSecGlobalInDecompOctets {
        type yang:counter32;
        units "Octets";
        description
         "The total number of decompressed octets received
          by all current and previous IPsec Phase-2 Tunnels.  
          This value is accumulated AFTER the packet is 
          decompressed. If compression is not being used, 
          this value will match the value of cipSecGlobalInOctets. 
          See also cipSecGlobalInDecompOctWraps
           for the number of times this counter has wrapped.";
        smiv2:max-access "read-only";
        smiv2:oid "1.3.6.1.4.1.9.9.171.1.3.1.6";
      }

      leaf cipSecGlobalHcInDecompOctets {
        type yang:counter64;
        description
         "A high capacity count of the total number
          of decompressed octets received by all current 
          and previous IPsec Phase-2 Tunnels.  This value 
          is accumulated AFTER the packet is decompressed.
           If compression is not being used, this value 
           will match the value of cipSecGlobalHcInOctets.";
        smiv2:max-access "read-only";
        smiv2:oid "1.3.6.1.4.1.9.9.171.1.3.1.7";
      }

      leaf cipSecGlobalInDecompOctWraps {
        type yang:counter32;
        units "Integral units";
        description
         "The number of times the global decompressed
          octets received counter
           (cipSecGlobalInDecompOctets) has wrapped.";
        smiv2:max-access "read-only";
        smiv2:oid "1.3.6.1.4.1.9.9.171.1.3.1.8";
      }

      leaf cipSecGlobalInPkts {
        type yang:counter32;
        units "Packets";
        description
         "The total number of packets received
          by all current and previous
           IPsec Phase-2 Tunnels.";
        smiv2:max-access "read-only";
        smiv2:oid "1.3.6.1.4.1.9.9.171.1.3.1.9";
      }

      leaf cipSecGlobalInDrops {
        type yang:counter32;
        units "Packets";
        description
         "The total number of packets dropped
          during receive processing by all current and previous 
          IPsec Phase-2 Tunnels. This count does
          NOT include packets dropped due to 
          Anti-Replay processing.";
        smiv2:max-access "read-only";
        smiv2:oid "1.3.6.1.4.1.9.9.171.1.3.1.10";
      }

      leaf cipSecGlobalInReplayDrops {
        type yang:counter32;
        units "Packets";
        description
         "The total number of packets dropped during
          receive processing due to Anti-Replay 
          processing by all current and previous IPsec
           Phase-2 Tunnels.";
        smiv2:max-access "read-only";
        smiv2:oid "1.3.6.1.4.1.9.9.171.1.3.1.11";
      }

      leaf cipSecGlobalInAuths {
        type yang:counter32;
        units "Events";
        description
         "The total number of inbound authentication's
          performed by all current and previous IPsec 
          Phase-2 Tunnels.";
        smiv2:max-access "read-only";
        smiv2:oid "1.3.6.1.4.1.9.9.171.1.3.1.12";
      }

      leaf cipSecGlobalInAuthFails {
        type yang:counter32;
        units "Failures";
        description
         "The total number of inbound authentication's
          which ended in failure by all current and previous 
          IPsec Phase-2 Tunnels.";
        smiv2:max-access "read-only";
        smiv2:oid "1.3.6.1.4.1.9.9.171.1.3.1.13";
      }

      leaf cipSecGlobalInDecrypts {
        type yang:counter32;
        units "Packets";
        description
         "The total number of inbound decryption's
          performed by all current and previous IPsec 
          Phase-2 Tunnels.";
        smiv2:max-access "read-only";
        smiv2:oid "1.3.6.1.4.1.9.9.171.1.3.1.14";
      }

      leaf cipSecGlobalInDecryptFails {
        type yang:counter32;
        units "Packets";
        description
         "The total number of inbound decryption's
          which ended in failure by all current and 
          previous IPsec Phase-2 Tunnels.";
        smiv2:max-access "read-only";
        smiv2:oid "1.3.6.1.4.1.9.9.171.1.3.1.15";
      }

      leaf cipSecGlobalOutOctets {
        type yang:counter32;
        units "Octets";
        description
         "The total number of octets sent by all
          current and previous IPsec Phase-2 Tunnels.  
          This value is accumulated AFTER determining 
          whether or not the packet should be compressed.  
          See also cipSecGlobalOutOctWraps for the
           number of times this counter has wrapped.";
        smiv2:max-access "read-only";
        smiv2:oid "1.3.6.1.4.1.9.9.171.1.3.1.16";
      }

      leaf cipSecGlobalHcOutOctets {
        type yang:counter64;
        description
         "A high capacity count of the total number
          of octets sent by all current and previous 
          IPsec Phase-2 Tunnels.  This value is accumulated 
          AFTER determining whether or not the packet should 
          be compressed.";
        smiv2:max-access "read-only";
        smiv2:oid "1.3.6.1.4.1.9.9.171.1.3.1.17";
      }

      leaf cipSecGlobalOutOctWraps {
        type yang:counter32;
        units "Integral units";
        description
         "The number of times the global octets sent counter
          (cipSecGlobalOutOctets) has wrapped.";
        smiv2:max-access "read-only";
        smiv2:oid "1.3.6.1.4.1.9.9.171.1.3.1.18";
      }

      leaf cipSecGlobalOutUncompOctets {
        type yang:counter32;
        units "Octets";
        description
         "The total number of uncompressed octets sent
          by all current and previous IPsec Phase-2 Tunnels.  
          This value is accumulated BEFORE the packet is 
          compressed. If compression is not being used, this 
          value will match the value of cipSecGlobalOutOctets. 
          See also cipSecGlobalOutDecompOctWraps for the number 
          of times this counter has wrapped.";
        smiv2:max-access "read-only";
        smiv2:oid "1.3.6.1.4.1.9.9.171.1.3.1.19";
      }

      leaf cipSecGlobalHcOutUncompOctets {
        type yang:counter64;
        units "Octets";
        description
         "A high capacity count of the total number of
          uncompressed octets sent by all current and previous 
          IPsec Phase-2 Tunnels.  This value is accumulated 
          BEFORE the packet is compressed.  If compression is 
          not being used, this value will match the
                value of cipSecGlobalHcOutOctets.";
        smiv2:max-access "read-only";
        smiv2:oid "1.3.6.1.4.1.9.9.171.1.3.1.20";
      }

      leaf cipSecGlobalOutUncompOctWraps {
        type yang:counter32;
        units "Integral units";
        description
         "The number of times the global uncompressed
          octets sent counter (cipSecGlobalOutUncompOctets) 
          has wrapped.";
        smiv2:max-access "read-only";
        smiv2:oid "1.3.6.1.4.1.9.9.171.1.3.1.21";
      }

      leaf cipSecGlobalOutPkts {
        type yang:counter32;
        units "Packets";
        description
         "The total number of packets sent by all
          current and previous
           IPsec Phase-2 Tunnels.";
        smiv2:max-access "read-only";
        smiv2:oid "1.3.6.1.4.1.9.9.171.1.3.1.22";
      }

      leaf cipSecGlobalOutDrops {
        type yang:counter32;
        units "Packets";
        description
         "The total number of packets dropped during send
          processing by all current and previous IPsec 
          Phase-2 Tunnels.";
        smiv2:max-access "read-only";
        smiv2:oid "1.3.6.1.4.1.9.9.171.1.3.1.23";
      }

      leaf cipSecGlobalOutAuths {
        type yang:counter32;
        units "Events";
        description
         "The total number of outbound authentication's
          performed by all current and previous IPsec 
          Phase-2 Tunnels.";
        smiv2:max-access "read-only";
        smiv2:oid "1.3.6.1.4.1.9.9.171.1.3.1.24";
      }

      leaf cipSecGlobalOutAuthFails {
        type yang:counter32;
        units "Failures";
        description
         "The total number of outbound authentication's
          which ended in failure
           by all current and previous IPsec Phase-2 Tunnels.";
        smiv2:max-access "read-only";
        smiv2:oid "1.3.6.1.4.1.9.9.171.1.3.1.25";
      }

      leaf cipSecGlobalOutEncrypts {
        type yang:counter32;
        units "Packets";
        description
         "The total number of outbound encryption's performed
          by all current and previous IPsec Phase-2 Tunnels.";
        smiv2:max-access "read-only";
        smiv2:oid "1.3.6.1.4.1.9.9.171.1.3.1.26";
      }

      leaf cipSecGlobalOutEncryptFails {
        type yang:counter32;
        units "Failures";
        description
         "The total number of outbound encryption's
          which ended in failure by all current and 
          previous IPsec Phase-2 Tunnels.";
        smiv2:max-access "read-only";
        smiv2:oid "1.3.6.1.4.1.9.9.171.1.3.1.27";
      }

      leaf cipSecGlobalProtocolUseFails {
        type yang:counter32;
        units "Failures";
        description
         "The total number of protocol use failures
          which occurred during processing of all current 
          and previously active IPsec Phase-2 Tunnels.";
        smiv2:max-access "read-only";
        smiv2:oid "1.3.6.1.4.1.9.9.171.1.3.1.28";
      }

      leaf cipSecGlobalNoSaFails {
        type yang:counter32;
        units "Failures";
        description
         "The total number of non-existent
          Security Association in failures which occurred 
          during processing of all current
           and previous IPsec Phase-2 Tunnels.";
        smiv2:max-access "read-only";
        smiv2:oid "1.3.6.1.4.1.9.9.171.1.3.1.29";
      }

      leaf cipSecGlobalSysCapFails {
        type yang:counter32;
        units "Failures";
        description
         "The total number of system capacity failures
          which occurred during processing of all current 
          and previously active IPsec Phase-2 Tunnels.";
        smiv2:max-access "read-only";
        smiv2:oid "1.3.6.1.4.1.9.9.171.1.3.1.30";
      }
    }

    container cipSecHistGlobalCntl {
      smiv2:oid "1.3.6.1.4.1.9.9.171.1.4.1.1";

      leaf cipSecHistTableSize {
        type int32 {
          range "1..2147483647";
        }
        description
         "The window size of the IPsec Phase-1 and Phase-2
          History Tables.
          
          The IPsec Phase-1 and Phase-2 History Tables are
          implemented as a sliding window in which only the
          last n entries are maintained.  This object is used
          specify the number of entries which will be 
          maintained in the IPsec Phase-1 and 
          Phase-2 History Tables.
          
          An implementation may choose suitable minimum and 
          maximum values for this element based on the local 
          policy and available resources. If an SNMP SET request 
          specifies a value outside this window for this element, 
          a BAD VALUE may be returned.";
        smiv2:max-access "read-write";
        smiv2:oid "1.3.6.1.4.1.9.9.171.1.4.1.1.1";
      }

      leaf cipSecHistCheckPoint {
        type enumeration {
          enum "ready" {
            value "1";
          }
          enum "checkPoint" {
            value "2";
          }
        }
        description
         "The current state of check point processing.
          
          This object will return ready when the agent is 
          ready to create on-demand history entries for 
          active IPsec Tunnels or checkPoint when the 
          agent is currently creating on-demand history 
          entries for active IPsec Tunnels.
          
          By setting this value to checkPoint, the agent 
          will create:
          a) an entry in the IPsec Phase-1 Tunnel History 
             for each active IPsec Phase-1 Tunnel and
          b) an entry in the IPsec Phase-2 Tunnel History 
             Table and an entry in the IPsec Phase-2 
             Tunnel EndPoint History Table
             for each active IPsec Phase-2 Tunnel.";
        smiv2:max-access "read-write";
        smiv2:oid "1.3.6.1.4.1.9.9.171.1.4.1.1.2";
      }
    }

    container cipSecFailGlobalCntl {
      smiv2:oid "1.3.6.1.4.1.9.9.171.1.5.1.1";

      leaf cipSecFailTableSize {
        type int32 {
          range "1..2147483647";
        }
        description
         "The window size of the IPsec Phase-1 and Phase-2
          Failure Tables.
          
          The IPsec Phase-1 and Phase-2 Failure Tables are
          implemented as a sliding window in which only the
          last n entries are maintained.  This object is used
          specify the number of entries which will be 
          maintained in the IPsec Phase-1 and Phase-2 Failure 
          Tables.
          
          An implementation may choose suitable minimum and 
          maximum values for this element based on the local 
          policy and available resources. If an SNMP SET request 
          specifies a value outside this window for this element, 
          a BAD VALUE may be returned.";
        smiv2:max-access "read-write";
        smiv2:oid "1.3.6.1.4.1.9.9.171.1.5.1.1.1";
      }
    }

    container cipSecTrapCntl {
      smiv2:oid "1.3.6.1.4.1.9.9.171.1.6";

      leaf cipSecTrapCntlIkeTunnelStart {
        type CISCO-IPSEC-FLOW-MONITOR-MIB:TrapStatus;
        description
         "This object defines the administrative state of
          sending the IPsec IKE Phase-1 Tunnel Start TRAP";
        smiv2:defval "disabled";
        smiv2:max-access "read-write";
        smiv2:oid "1.3.6.1.4.1.9.9.171.1.6.1";
      }

      leaf cipSecTrapCntlIkeTunnelStop {
        type CISCO-IPSEC-FLOW-MONITOR-MIB:TrapStatus;
        description
         "This object defines the administrative state
          of sending the
           IPsec IKE Phase-1 Tunnel Stop TRAP";
        smiv2:defval "disabled";
        smiv2:max-access "read-write";
        smiv2:oid "1.3.6.1.4.1.9.9.171.1.6.2";
      }

      leaf cipSecTrapCntlIkeSysFailure {
        type CISCO-IPSEC-FLOW-MONITOR-MIB:TrapStatus;
        description
         "This object defines the administrative state
          of sending the
           IPsec IKE Phase-1 System Failure TRAP";
        smiv2:defval "disabled";
        smiv2:max-access "read-write";
        smiv2:oid "1.3.6.1.4.1.9.9.171.1.6.3";
      }

      leaf cipSecTrapCntlIkeCertCrlFailure {
        type CISCO-IPSEC-FLOW-MONITOR-MIB:TrapStatus;
        description
         "This object defines the administrative
          state of sending the
           IPsec IKE Phase-1 Certificate/CRL Failure TRAP";
        smiv2:defval "disabled";
        smiv2:max-access "read-write";
        smiv2:oid "1.3.6.1.4.1.9.9.171.1.6.4";
      }

      leaf cipSecTrapCntlIkeProtocolFail {
        type CISCO-IPSEC-FLOW-MONITOR-MIB:TrapStatus;
        description
         "This object defines the administrative
          state of sending the
           IPsec IKE Phase-1 Protocol Failure TRAP";
        smiv2:defval "disabled";
        smiv2:max-access "read-write";
        smiv2:oid "1.3.6.1.4.1.9.9.171.1.6.5";
      }

      leaf cipSecTrapCntlIkeNoSa {
        type CISCO-IPSEC-FLOW-MONITOR-MIB:TrapStatus;
        description
         "This object defines the administrative
          state of sending the
           IPsec IKE Phase-1 No Security Association TRAP";
        smiv2:defval "disabled";
        smiv2:max-access "read-write";
        smiv2:oid "1.3.6.1.4.1.9.9.171.1.6.6";
      }

      leaf cipSecTrapCntlIpSecTunnelStart {
        type CISCO-IPSEC-FLOW-MONITOR-MIB:TrapStatus;
        description
         "This object defines the administrative state
          of sending the IPsec
           Phase-2 Tunnel Start TRAP";
        smiv2:defval "disabled";
        smiv2:max-access "read-write";
        smiv2:oid "1.3.6.1.4.1.9.9.171.1.6.7";
      }

      leaf cipSecTrapCntlIpSecTunnelStop {
        type CISCO-IPSEC-FLOW-MONITOR-MIB:TrapStatus;
        description
         "This object defines the administrative
          state of sending the IPsec
           Phase-2 Tunnel Stop TRAP";
        smiv2:defval "disabled";
        smiv2:max-access "read-write";
        smiv2:oid "1.3.6.1.4.1.9.9.171.1.6.8";
      }

      leaf cipSecTrapCntlIpSecSysFailure {
        type CISCO-IPSEC-FLOW-MONITOR-MIB:TrapStatus;
        description
         "This object defines the administrative state
          of sending the IPsec
           Phase-2 System Failure TRAP";
        smiv2:defval "disabled";
        smiv2:max-access "read-write";
        smiv2:oid "1.3.6.1.4.1.9.9.171.1.6.9";
      }

      leaf cipSecTrapCntlIpSecSetUpFailure {
        type CISCO-IPSEC-FLOW-MONITOR-MIB:TrapStatus;
        description
         "This object defines the administrative state
          of sending the IPsec
           Phase-2 Set Up Failure TRAP";
        smiv2:defval "disabled";
        smiv2:max-access "read-write";
        smiv2:oid "1.3.6.1.4.1.9.9.171.1.6.10";
      }

      leaf cipSecTrapCntlIpSecEarlyTunTerm {
        type CISCO-IPSEC-FLOW-MONITOR-MIB:TrapStatus;
        description
         "This object defines the administrative state
          of sending the IPsec
           Phase-2 Early Tunnel Termination TRAP";
        smiv2:defval "disabled";
        smiv2:max-access "read-write";
        smiv2:oid "1.3.6.1.4.1.9.9.171.1.6.11";
      }

      leaf cipSecTrapCntlIpSecProtocolFail {
        type CISCO-IPSEC-FLOW-MONITOR-MIB:TrapStatus;
        description
         "This object defines the administrative state
          of sending the IPsec
           Phase-2 Protocol Failure TRAP";
        smiv2:defval "disabled";
        smiv2:max-access "read-write";
        smiv2:oid "1.3.6.1.4.1.9.9.171.1.6.12";
      }

      leaf cipSecTrapCntlIpSecNoSa {
        type CISCO-IPSEC-FLOW-MONITOR-MIB:TrapStatus;
        description
         "This object defines the administrative state
          of sending the IPsec
           Phase-2  No Security Association TRAP";
        smiv2:defval "disabled";
        smiv2:max-access "read-write";
        smiv2:oid "1.3.6.1.4.1.9.9.171.1.6.13";
      }
    }

    container cikePeerTable {
      description
       "The IPsec Phase-1 Internet Key Exchange Peer Table.
        There is one entry in this table for each IPsec
        Phase-1 IKE peer association which is currently
        associated with an active IPsec Phase-1 Tunnel.
        The IPsec Phase-1 IKE Tunnel associated with this
        IPsec Phase-1 IKE peer association may or may not
        be currently active.";
      smiv2:oid "1.3.6.1.4.1.9.9.171.1.2.2";

      list cikePeerEntry {
        key "cikePeerLocalType cikePeerLocalValue cikePeerRemoteType cikePeerRemoteValue cikePeerIntIndex";
        description
         "Each entry contains the attributes associated
          with an IPsec Phase-1 IKE peer association.";
        smiv2:oid "1.3.6.1.4.1.9.9.171.1.2.2.1";

        leaf cikePeerLocalType {
          type CISCO-IPSEC-FLOW-MONITOR-MIB:IkePeerType;
          description
           "The type of local peer identity.  The local peer
            may be identified by:
            1. an IP address, or
            2. a host name.";
          smiv2:max-access "not-accessible";
          smiv2:oid "1.3.6.1.4.1.9.9.171.1.2.2.1.1";
        }

        leaf cikePeerLocalValue {
          type snmpv2-tc:DisplayString;
          description
           "The value of the local peer identity.
            
            If the local peer type is an IP Address, then this
            is the IP Address used to identify the local peer.
            
            If the local peer type is a host name, then this is
            the host name used to identify the local peer.";
          smiv2:max-access "not-accessible";
          smiv2:oid "1.3.6.1.4.1.9.9.171.1.2.2.1.2";
        }

        leaf cikePeerRemoteType {
          type CISCO-IPSEC-FLOW-MONITOR-MIB:IkePeerType;
          description
           "The type of remote peer identity.  The remote peer
            may be identified by:
            1. an IP address, or
            2. a host name.";
          smiv2:max-access "not-accessible";
          smiv2:oid "1.3.6.1.4.1.9.9.171.1.2.2.1.3";
        }

        leaf cikePeerRemoteValue {
          type snmpv2-tc:DisplayString;
          description
           "The value of the remote peer identity.
            
            If the remote peer type is an IP Address, then this
            is the IP Address used to identify the remote peer.
            
            If the remote peer type is a host name, then this is
            the host name used to identify the remote peer.";
          smiv2:max-access "not-accessible";
          smiv2:oid "1.3.6.1.4.1.9.9.171.1.2.2.1.4";
        }

        leaf cikePeerIntIndex {
          type int32 {
            range "1..2147483647";
          }
          description
           "The internal index of the local-remote
            peer association.  This internal index is used 
            to uniquely identify multiple associations between 
            the local and remote peer.";
          smiv2:max-access "not-accessible";
          smiv2:oid "1.3.6.1.4.1.9.9.171.1.2.2.1.5";
        }

        leaf cikePeerLocalAddr {
          type CISCO-IPSEC-FLOW-MONITOR-MIB:IPSIpAddress;
          description
           "The IP address of the local peer.";
          smiv2:max-access "read-only";
          smiv2:oid "1.3.6.1.4.1.9.9.171.1.2.2.1.6";
        }

        leaf cikePeerRemoteAddr {
          type CISCO-IPSEC-FLOW-MONITOR-MIB:IPSIpAddress;
          description
           "The IP address of the remote peer.";
          smiv2:max-access "read-only";
          smiv2:oid "1.3.6.1.4.1.9.9.171.1.2.2.1.7";
        }

        leaf cikePeerActiveTime {
          type snmpv2-tc:TimeInterval;
          description
           "The length of time that the peer association has
            existed in hundredths of a second.";
          smiv2:max-access "read-only";
          smiv2:oid "1.3.6.1.4.1.9.9.171.1.2.2.1.8";
        }

        leaf cikePeerActiveTunnelIndex {
          type int32 {
            range "1..2147483647";
          }
          description
           "The index of the active IPsec Phase-1 IKE Tunnel
            (cikeTunIndex in the cikeTunnelTable) for this peer
            association.  If an IPsec Phase-1 IKE Tunnel is
            not currently active, then the value of this
            object will be zero.";
          smiv2:max-access "read-only";
          smiv2:oid "1.3.6.1.4.1.9.9.171.1.2.2.1.9";
        }
      }
    }

    container cikeTunnelTable {
      description
       "The IPsec Phase-1 Internet Key Exchange Tunnel Table.
        There is one entry in this table for each active IPsec
        Phase-1 IKE Tunnel.";
      smiv2:oid "1.3.6.1.4.1.9.9.171.1.2.3";

      list cikeTunnelEntry {
        key "cikeTunIndex";
        description
         "Each entry contains the attributes associated with
          an active IPsec Phase-1 IKE Tunnel.";
        smiv2:oid "1.3.6.1.4.1.9.9.171.1.2.3.1";

        leaf cikeTunIndex {
          type int32 {
            range "1..2147483647";
          }
          description
           "The index of the IPsec Phase-1 IKE Tunnel Table.
            The value of the index is a number which begins 
            at one and is incremented with each tunnel that 
            is created. The value of this object will 
            wrap at 2,147,483,647.";
          smiv2:max-access "not-accessible";
          smiv2:oid "1.3.6.1.4.1.9.9.171.1.2.3.1.1";
        }

        leaf cikeTunLocalType {
          type CISCO-IPSEC-FLOW-MONITOR-MIB:IkePeerType;
          description
           "The type of local peer identity.  The local
            peer may be identified by:
             1. an IP address, or
             2. a host name.";
          smiv2:max-access "read-only";
          smiv2:oid "1.3.6.1.4.1.9.9.171.1.2.3.1.2";
        }

        leaf cikeTunLocalValue {
          type snmpv2-tc:DisplayString;
          description
           "The value of the local peer identity.
            
            If the local peer type is an IP Address, then this
            is the IP Address used to identify the local peer.
            
            If the local peer type is a host name, then this is
            the host name used to identify the local peer.";
          smiv2:max-access "read-only";
          smiv2:oid "1.3.6.1.4.1.9.9.171.1.2.3.1.3";
        }

        leaf cikeTunLocalAddr {
          type CISCO-IPSEC-FLOW-MONITOR-MIB:IPSIpAddress;
          description
           "The IP address of the local endpoint for the IPsec
            Phase-1 IKE Tunnel.";
          smiv2:max-access "read-only";
          smiv2:oid "1.3.6.1.4.1.9.9.171.1.2.3.1.4";
        }

        leaf cikeTunLocalName {
          type snmpv2-tc:DisplayString;
          description
           "The DNS name of the local IP address for
            the IPsec Phase-1 IKE Tunnel. If the DNS 
            name associated with the local tunnel endpoint 
            is not known, then the value of this
             object will be a NULL string.";
          smiv2:max-access "read-only";
          smiv2:oid "1.3.6.1.4.1.9.9.171.1.2.3.1.5";
        }

        leaf cikeTunRemoteType {
          type CISCO-IPSEC-FLOW-MONITOR-MIB:IkePeerType;
          description
           "The type of remote peer identity.
            The remote peer may be identified by:
             1. an IP address, or
             2. a host name.";
          smiv2:max-access "read-only";
          smiv2:oid "1.3.6.1.4.1.9.9.171.1.2.3.1.6";
        }

        leaf cikeTunRemoteValue {
          type snmpv2-tc:DisplayString;
          description
           "The value of the remote peer identity.
            
            If the remote peer type is an IP Address, then this
            is the IP Address used to identify the remote peer.
            
            If the remote peer type is a host name, then 
            this is the host name used to identify the 
            remote peer.";
          smiv2:max-access "read-only";
          smiv2:oid "1.3.6.1.4.1.9.9.171.1.2.3.1.7";
        }

        leaf cikeTunRemoteAddr {
          type CISCO-IPSEC-FLOW-MONITOR-MIB:IPSIpAddress;
          description
           "The IP address of the remote endpoint for the IPsec
            Phase-1 IKE Tunnel.";
          smiv2:max-access "read-only";
          smiv2:oid "1.3.6.1.4.1.9.9.171.1.2.3.1.8";
        }

        leaf cikeTunRemoteName {
          type snmpv2-tc:DisplayString;
          description
           "The DNS name of the remote IP address of IPsec Phase-1
            IKE Tunnel. If the DNS name associated with the remote
            tunnel endpoint is not known, then the value of this
            object will be a NULL string.";
          smiv2:max-access "read-only";
          smiv2:oid "1.3.6.1.4.1.9.9.171.1.2.3.1.9";
        }

        leaf cikeTunNegoMode {
          type CISCO-IPSEC-FLOW-MONITOR-MIB:IkeNegoMode;
          description
           "The negotiation mode of the IPsec Phase-1 IKE Tunnel.";
          smiv2:max-access "read-only";
          smiv2:oid "1.3.6.1.4.1.9.9.171.1.2.3.1.10";
        }

        leaf cikeTunDiffHellmanGrp {
          type CISCO-IPSEC-FLOW-MONITOR-MIB:DiffHellmanGrp;
          description
           "The Diffie Hellman Group used in IPsec Phase-1 IKE
            negotiations.";
          smiv2:max-access "read-only";
          smiv2:oid "1.3.6.1.4.1.9.9.171.1.2.3.1.11";
        }

        leaf cikeTunEncryptAlgo {
          type CISCO-IPSEC-FLOW-MONITOR-MIB:EncryptAlgo;
          description
           "The encryption algorithm used in IPsec Phase-1 IKE
            negotiations.";
          smiv2:max-access "read-only";
          smiv2:oid "1.3.6.1.4.1.9.9.171.1.2.3.1.12";
        }

        leaf cikeTunHashAlgo {
          type CISCO-IPSEC-FLOW-MONITOR-MIB:IkeHashAlgo;
          description
           "The hash algorithm used in IPsec Phase-1 IKE
            negotiations.";
          smiv2:max-access "read-only";
          smiv2:oid "1.3.6.1.4.1.9.9.171.1.2.3.1.13";
        }

        leaf cikeTunAuthMethod {
          type CISCO-IPSEC-FLOW-MONITOR-MIB:IkeAuthMethod;
          description
           "The authentication method used in IPsec Phase-1 IKE
            negotiations.";
          smiv2:max-access "read-only";
          smiv2:oid "1.3.6.1.4.1.9.9.171.1.2.3.1.14";
        }

        leaf cikeTunLifeTime {
          type int32 {
            range "1..2147483647";
          }
          units "seconds";
          description
           "The negotiated LifeTime of the IPsec Phase-1 IKE Tunnel
            in seconds.";
          smiv2:max-access "read-only";
          smiv2:oid "1.3.6.1.4.1.9.9.171.1.2.3.1.15";
        }

        leaf cikeTunActiveTime {
          type snmpv2-tc:TimeInterval;
          description
           "The length of time the IPsec Phase-1 IKE tunnel has been
            active in hundredths of seconds.";
          smiv2:max-access "read-only";
          smiv2:oid "1.3.6.1.4.1.9.9.171.1.2.3.1.16";
        }

        leaf cikeTunSaRefreshThreshold {
          type int32 {
            range "1..2147483647";
          }
          units "seconds";
          description
           "The security association refresh threshold in seconds.";
          smiv2:max-access "read-only";
          smiv2:oid "1.3.6.1.4.1.9.9.171.1.2.3.1.17";
        }

        leaf cikeTunTotalRefreshes {
          type yang:counter32;
          units "QM Exchanges";
          description
           "The total number of security associations
            refreshes performed.";
          smiv2:max-access "read-only";
          smiv2:oid "1.3.6.1.4.1.9.9.171.1.2.3.1.18";
        }

        leaf cikeTunInOctets {
          type yang:counter32;
          units "Octets";
          description
           "The total number of octets received by
            this IPsec Phase-1 IKE Tunnel.";
          smiv2:max-access "read-only";
          smiv2:oid "1.3.6.1.4.1.9.9.171.1.2.3.1.19";
        }

        leaf cikeTunInPkts {
          type yang:counter32;
          units "Packets";
          description
           "The total number of packets received by
            this IPsec Phase-1 IKE Tunnel.";
          smiv2:max-access "read-only";
          smiv2:oid "1.3.6.1.4.1.9.9.171.1.2.3.1.20";
        }

        leaf cikeTunInDropPkts {
          type yang:counter32;
          units "Packets";
          description
           "The total number of packets dropped
            by this IPsec Phase-1 IKE Tunnel during 
            receive processing.";
          smiv2:max-access "read-only";
          smiv2:oid "1.3.6.1.4.1.9.9.171.1.2.3.1.21";
        }

        leaf cikeTunInNotifys {
          type yang:counter32;
          units "Notification Payloads";
          description
           "The total number of notifys received by
            this IPsec Phase-1 IKE Tunnel.";
          smiv2:max-access "read-only";
          smiv2:oid "1.3.6.1.4.1.9.9.171.1.2.3.1.22";
        }

        leaf cikeTunInP2Exchgs {
          type yang:counter32;
          units "SA Payloads";
          description
           "The total number of IPsec Phase-2
            exchanges received by
             this IPsec Phase-1 IKE Tunnel.";
          smiv2:max-access "read-only";
          smiv2:oid "1.3.6.1.4.1.9.9.171.1.2.3.1.23";
        }

        leaf cikeTunInP2ExchgInvalids {
          type yang:counter32;
          units "SA Payloads";
          description
           "The total number of IPsec Phase-2
            exchanges received and found to be invalid 
            by this IPsec Phase-1 IKE Tunnel.";
          smiv2:max-access "read-only";
          smiv2:oid "1.3.6.1.4.1.9.9.171.1.2.3.1.24";
        }

        leaf cikeTunInP2ExchgRejects {
          type yang:counter32;
          units "SA Payloads";
          description
           "The total number of IPsec Phase-2 exchanges
            received and rejected by this IPsec Phase-1 
            Tunnel.";
          smiv2:max-access "read-only";
          smiv2:oid "1.3.6.1.4.1.9.9.171.1.2.3.1.25";
        }

        leaf cikeTunInP2SaDelRequests {
          type yang:counter32;
          units "Notification Payloads";
          description
           "The total number of IPsec Phase-2
            security association delete requests received 
            by this IPsec Phase-1 IKE Tunnel.";
          smiv2:max-access "read-only";
          smiv2:oid "1.3.6.1.4.1.9.9.171.1.2.3.1.26";
        }

        leaf cikeTunOutOctets {
          type yang:counter32;
          units "Octets";
          description
           "The total number of octets sent by this IPsec Phase-1
            IKE Tunnel.";
          smiv2:max-access "read-only";
          smiv2:oid "1.3.6.1.4.1.9.9.171.1.2.3.1.27";
        }

        leaf cikeTunOutPkts {
          type yang:counter32;
          units "Packets";
          description
           "The total number of packets sent by this IPsec Phase-1
            IKE Tunnel.";
          smiv2:max-access "read-only";
          smiv2:oid "1.3.6.1.4.1.9.9.171.1.2.3.1.28";
        }

        leaf cikeTunOutDropPkts {
          type yang:counter32;
          units "Packets";
          description
           "The total number of packets dropped by this
            IPsec Phase-1 IKE Tunnel during send processing.";
          smiv2:max-access "read-only";
          smiv2:oid "1.3.6.1.4.1.9.9.171.1.2.3.1.29";
        }

        leaf cikeTunOutNotifys {
          type yang:counter32;
          units "Notification Payloads";
          description
           "The total number of notifys sent by this
            IPsec Phase-1 Tunnel.";
          smiv2:max-access "read-only";
          smiv2:oid "1.3.6.1.4.1.9.9.171.1.2.3.1.30";
        }

        leaf cikeTunOutP2Exchgs {
          type yang:counter32;
          units "SA Payloads";
          description
           "The total number of IPsec Phase-2 exchanges sent by
            this IPsec Phase-1 IKE Tunnel.";
          smiv2:max-access "read-only";
          smiv2:oid "1.3.6.1.4.1.9.9.171.1.2.3.1.31";
        }

        leaf cikeTunOutP2ExchgInvalids {
          type yang:counter32;
          units "SA Payloads";
          description
           "The total number of IPsec Phase-2 exchanges sent and
            found to be invalid by this IPsec Phase-1 IKE Tunnel.";
          smiv2:max-access "read-only";
          smiv2:oid "1.3.6.1.4.1.9.9.171.1.2.3.1.32";
        }

        leaf cikeTunOutP2ExchgRejects {
          type yang:counter32;
          units "SA Payloads";
          description
           "The total number of IPsec Phase-2 exchanges sent and
            rejected by this IPsec Phase-1 IKE Tunnel.";
          smiv2:max-access "read-only";
          smiv2:oid "1.3.6.1.4.1.9.9.171.1.2.3.1.33";
        }

        leaf cikeTunOutP2SaDelRequests {
          type yang:counter32;
          units "Notification Payloads";
          description
           "The total number of IPsec Phase-2 security association
            delete requests sent by this IPsec Phase-1 IKE Tunnel.";
          smiv2:max-access "read-only";
          smiv2:oid "1.3.6.1.4.1.9.9.171.1.2.3.1.34";
        }

        leaf cikeTunStatus {
          type CISCO-IPSEC-FLOW-MONITOR-MIB:TunnelStatus;
          description
           "The status of the MIB table row.
            
            This object can be used to bring the tunnel down 
            by setting value of this object to destroy(2).
            
            This object cannot be used to create 
            a MIB table row.";
          smiv2:max-access "read-write";
          smiv2:oid "1.3.6.1.4.1.9.9.171.1.2.3.1.35";
        }
      }
    }

    container cikePeerCorrTable {
      description
       "The IPsec Phase-1 Internet Key Exchange Peer
        Association to IPsec Phase-2 Tunnel
        Correlation Table. There is one entry in
        this table for each active IPsec Phase-2
        Tunnel.";
      smiv2:oid "1.3.6.1.4.1.9.9.171.1.2.4";

      list cikePeerCorrEntry {
        key "cikePeerCorrLocalType cikePeerCorrLocalValue cikePeerCorrRemoteType cikePeerCorrRemoteValue cikePeerCorrIntIndex cikePeerCorrSeqNum";
        description
         "Each entry contains the attributes of an
          IPsec Phase-1 IKE Peer Association to IPsec
          Phase-2 Tunnel Correlation.";
        smiv2:oid "1.3.6.1.4.1.9.9.171.1.2.4.1";

        leaf cikePeerCorrLocalType {
          type CISCO-IPSEC-FLOW-MONITOR-MIB:IkePeerType;
          description
           "The type of local peer identity. The local peer
            may be identified by:
            1. an IP address, or
            2. a host name.";
          smiv2:max-access "not-accessible";
          smiv2:oid "1.3.6.1.4.1.9.9.171.1.2.4.1.1";
        }

        leaf cikePeerCorrLocalValue {
          type snmpv2-tc:DisplayString;
          description
           "The value of the local peer identity.
            
            If the local peer type is an IP Address, then this
            is the IP Address used to identify the local peer.
            
            If the local peer type is a host name, then this is
            the host name used to identify the local peer.";
          smiv2:max-access "not-accessible";
          smiv2:oid "1.3.6.1.4.1.9.9.171.1.2.4.1.2";
        }

        leaf cikePeerCorrRemoteType {
          type CISCO-IPSEC-FLOW-MONITOR-MIB:IkePeerType;
          description
           "The type of remote peer identity. The remote peer
            may be identified by:
            1. an IP address, or
            2. a host name.";
          smiv2:max-access "not-accessible";
          smiv2:oid "1.3.6.1.4.1.9.9.171.1.2.4.1.3";
        }

        leaf cikePeerCorrRemoteValue {
          type snmpv2-tc:DisplayString;
          description
           "The value of the remote peer identity.
            
            If the remote peer type is an IP Address, then this
            is the IP Address used to identify the remote peer.
            
            If the remote peer type is a host name, then this is
            the host name used to identify the remote peer.";
          smiv2:max-access "not-accessible";
          smiv2:oid "1.3.6.1.4.1.9.9.171.1.2.4.1.4";
        }

        leaf cikePeerCorrIntIndex {
          type int32 {
            range "1..2147483647";
          }
          description
           "The internal index of the local-remote
            peer association.  This internal index is 
            used to uniquely identify multiple associations 
            between the local and remote peer.";
          smiv2:max-access "not-accessible";
          smiv2:oid "1.3.6.1.4.1.9.9.171.1.2.4.1.5";
        }

        leaf cikePeerCorrSeqNum {
          type int32 {
            range "1..2147483647";
          }
          description
           "The sequence number of the local-remote
            peer association.  This sequence number is 
            used to uniquely identify multiple instances 
            of an unique association between
             the local and remote peer.";
          smiv2:max-access "not-accessible";
          smiv2:oid "1.3.6.1.4.1.9.9.171.1.2.4.1.6";
        }

        leaf cikePeerCorrIpSecTunIndex {
          type int32 {
            range "1..2147483647";
          }
          description
           "The index of the active IPsec Phase-2 Tunnel
            (cipSecTunIndex in the cipSecTunnelTable) for this
            IPsec Phase-1 IKE Peer Association.";
          smiv2:max-access "read-only";
          smiv2:oid "1.3.6.1.4.1.9.9.171.1.2.4.1.7";
        }
      }
    }

    container cikePhase1GWStatsTable {
      description
       "Phase-1 IKE stats information is included in this table.
        Each entry is related to a specific gateway which is 
        identified by 'cmgwIndex'.";
      smiv2:oid "1.3.6.1.4.1.9.9.171.1.2.5";

      list cikePhase1GWStatsEntry {
        key "cmgwIndex";
        description
         "Each entry contains the attributes of an Phase-1 IKE stats
          information for the related gateway.
          
          There is only one entry for each gateway. The entry 
          is created when a gateway up and cannot be deleted.";
        smiv2:oid "1.3.6.1.4.1.9.9.171.1.2.5.1";

        leaf cmgwIndex {
          type leafref {
            path "/cisco-media:CISCO-MEDIA-GATEWAY-MIB/cisco-media:cMediaGwTable/cisco-media:cMediaGwEntry/cisco-media:cmgwIndex";
          }
        }

        leaf cikePhase1GWActiveTunnels {
          type yang:gauge32;
          description
           "The number of currently active IPsec
            Phase-1 IKE Tunnels.";
          smiv2:max-access "read-only";
          smiv2:oid "1.3.6.1.4.1.9.9.171.1.2.5.1.1";
        }

        leaf cikePhase1GWPreviousTunnels {
          type yang:counter32;
          units "SAs";
          description
           "The total number of previously active
            IPsec Phase-1 IKE Tunnels.";
          smiv2:max-access "read-only";
          smiv2:oid "1.3.6.1.4.1.9.9.171.1.2.5.1.2";
        }

        leaf cikePhase1GWInOctets {
          type yang:counter32;
          units "Octets";
          description
           "The total number of octets received by all currently
            and previously active IPsec Phase-1 IKE Tunnels.";
          smiv2:max-access "read-only";
          smiv2:oid "1.3.6.1.4.1.9.9.171.1.2.5.1.3";
        }

        leaf cikePhase1GWInPkts {
          type yang:counter32;
          units "Packets";
          description
           "The total number of packets received by all
            currently and previously active IPsec 
            Phase-1 IKE Tunnels.";
          smiv2:max-access "read-only";
          smiv2:oid "1.3.6.1.4.1.9.9.171.1.2.5.1.4";
        }

        leaf cikePhase1GWInDropPkts {
          type yang:counter32;
          units "Packets";
          description
           "The total number of packets which were
            dropped during receive processing by all 
            currently and previously
            active IPsec Phase-1 IKE Tunnels.";
          smiv2:max-access "read-only";
          smiv2:oid "1.3.6.1.4.1.9.9.171.1.2.5.1.5";
        }

        leaf cikePhase1GWInNotifys {
          type yang:counter32;
          units "Notification Payloads";
          description
           "The total number of notifys received by
            all currently and previously active IPsec 
            Phase-1 IKE Tunnels.";
          smiv2:max-access "read-only";
          smiv2:oid "1.3.6.1.4.1.9.9.171.1.2.5.1.6";
        }

        leaf cikePhase1GWInP2Exchgs {
          type yang:counter32;
          units "SA Payloads";
          description
           "The total number of IPsec Phase-2 exchanges
            received by all currently and previously 
            active IPsec Phase-1 IKE Tunnels.";
          smiv2:max-access "read-only";
          smiv2:oid "1.3.6.1.4.1.9.9.171.1.2.5.1.7";
        }

        leaf cikePhase1GWInP2ExchgInvalids {
          type yang:counter32;
          units "SA Payloads";
          description
           "The total number of IPsec Phase-2 exchanges
            which were received and found to be invalid 
            by all currently and previously active IPsec 
            Phase-1 IKE Tunnels.";
          smiv2:max-access "read-only";
          smiv2:oid "1.3.6.1.4.1.9.9.171.1.2.5.1.8";
        }

        leaf cikePhase1GWInP2ExchgRejects {
          type yang:counter32;
          units "SA Payloads";
          description
           "The total number of IPsec Phase-2 exchanges
            which were received and rejected by all 
            currently and previously active IPsec Phase-1 
            IKE Tunnels.";
          smiv2:max-access "read-only";
          smiv2:oid "1.3.6.1.4.1.9.9.171.1.2.5.1.9";
        }

        leaf cikePhase1GWInP2SaDelRequests {
          type yang:counter32;
          units "Notification Payloads";
          description
           "The total number of IPsec Phase-2 'Security
            Association' delete requests received by all 
            currently and previously active and IPsec 
            Phase-1 IKE Tunnels.";
          smiv2:max-access "read-only";
          smiv2:oid "1.3.6.1.4.1.9.9.171.1.2.5.1.10";
        }

        leaf cikePhase1GWOutOctets {
          type yang:counter32;
          units "Octets";
          description
           "The total number of octets sent by all currently
            and previously active and IPsec Phase-1 
            IKE Tunnels.";
          smiv2:max-access "read-only";
          smiv2:oid "1.3.6.1.4.1.9.9.171.1.2.5.1.11";
        }

        leaf cikePhase1GWOutPkts {
          type yang:counter32;
          units "Packets";
          description
           "The total number of packets sent by all currently
            and previously active and IPsec Phase-1 
            Tunnels.";
          smiv2:max-access "read-only";
          smiv2:oid "1.3.6.1.4.1.9.9.171.1.2.5.1.12";
        }

        leaf cikePhase1GWOutDropPkts {
          type yang:counter32;
          units "Packets";
          description
           "The total number of packets which were dropped
            during send processing by all currently 
            and previously
            active IPsec Phase-1 IKE Tunnels.";
          smiv2:max-access "read-only";
          smiv2:oid "1.3.6.1.4.1.9.9.171.1.2.5.1.13";
        }

        leaf cikePhase1GWOutNotifys {
          type yang:counter32;
          units "Notification Payloads";
          description
           "The total number of notifys sent by all currently
            and previously active IPsec Phase-1 IKE Tunnels.";
          smiv2:max-access "read-only";
          smiv2:oid "1.3.6.1.4.1.9.9.171.1.2.5.1.14";
        }

        leaf cikePhase1GWOutP2Exchgs {
          type yang:counter32;
          units "SA Payloads";
          description
           "The total number of IPsec Phase-2 exchanges
            which were sent by all currently and previously 
            active IPsec Phase-1 IKE Tunnels.";
          smiv2:max-access "read-only";
          smiv2:oid "1.3.6.1.4.1.9.9.171.1.2.5.1.15";
        }

        leaf cikePhase1GWOutP2ExchgInvalids {
          type yang:counter32;
          units "SA Payloads";
          description
           "The total number of IPsec Phase-2 exchanges
            which were sent and found to be invalid by 
            all currently and previously active IPsec Phase-1 
            Tunnels.";
          smiv2:max-access "read-only";
          smiv2:oid "1.3.6.1.4.1.9.9.171.1.2.5.1.16";
        }

        leaf cikePhase1GWOutP2ExchgRejects {
          type yang:counter32;
          units "SA Payloads";
          description
           "The total number of IPsec Phase-2 exchanges
            which were sent and rejected by all currently and
            previously active IPsec Phase-1 IKE Tunnels.";
          smiv2:max-access "read-only";
          smiv2:oid "1.3.6.1.4.1.9.9.171.1.2.5.1.17";
        }

        leaf cikePhase1GWOutP2SaDelRequests {
          type yang:counter32;
          units "Notification Payloads";
          description
           "The total number of IPsec Phase-2 SA
            delete requests sent by all currently and 
            previously active IPsec Phase-1 IKE Tunnels.";
          smiv2:max-access "read-only";
          smiv2:oid "1.3.6.1.4.1.9.9.171.1.2.5.1.18";
        }

        leaf cikePhase1GWInitTunnels {
          type yang:counter32;
          units "SAs";
          description
           "The total number of IPsec Phase-1 IKE
            Tunnels which were locally initiated.";
          smiv2:max-access "read-only";
          smiv2:oid "1.3.6.1.4.1.9.9.171.1.2.5.1.19";
        }

        leaf cikePhase1GWInitTunnelFails {
          type yang:counter32;
          units "SAs";
          description
           "The total number of IPsec Phase-1 IKE Tunnels
            which were locally initiated and failed to activate.";
          smiv2:max-access "read-only";
          smiv2:oid "1.3.6.1.4.1.9.9.171.1.2.5.1.20";
        }

        leaf cikePhase1GWRespTunnelFails {
          type yang:counter32;
          units "SAs";
          description
           "The total number of IPsec Phase-1 IKE Tunnels
            which were remotely initiated and failed to activate.";
          smiv2:max-access "read-only";
          smiv2:oid "1.3.6.1.4.1.9.9.171.1.2.5.1.21";
        }

        leaf cikePhase1GWSysCapFails {
          type yang:counter32;
          units "Failures";
          description
           "The total number of system capacity failures
            which occurred during processing of all current 
            and previously active IPsec Phase-1 IKE Tunnels.";
          smiv2:max-access "read-only";
          smiv2:oid "1.3.6.1.4.1.9.9.171.1.2.5.1.22";
        }

        leaf cikePhase1GWAuthFails {
          type yang:counter32;
          units "Failures";
          description
           "The total number of authentications which ended
            in failure by all current and previous IPsec Phase-1
            IKE Tunnels.";
          smiv2:max-access "read-only";
          smiv2:oid "1.3.6.1.4.1.9.9.171.1.2.5.1.23";
        }

        leaf cikePhase1GWDecryptFails {
          type yang:counter32;
          units "Failures";
          description
           "The total number of decryptions which ended
            in failure by all current and previous IPsec Phase-1
            IKE Tunnels.";
          smiv2:max-access "read-only";
          smiv2:oid "1.3.6.1.4.1.9.9.171.1.2.5.1.24";
        }

        leaf cikePhase1GWHashValidFails {
          type yang:counter32;
          units "Failures";
          description
           "The total number of hash validations which ended
            in failure by all current and previous IPsec Phase-1
            IKE Tunnels.";
          smiv2:max-access "read-only";
          smiv2:oid "1.3.6.1.4.1.9.9.171.1.2.5.1.25";
        }

        leaf cikePhase1GWNoSaFails {
          type yang:counter32;
          units "Failures";
          description
           "The total number of non-existent 'Security Association'
            failures occurred during processing of current and 
            previous IPsec Phase-1 IKE Tunnels.";
          smiv2:max-access "read-only";
          smiv2:oid "1.3.6.1.4.1.9.9.171.1.2.5.1.26";
        }
      }
    }

    container cipSecTunnelTable {
      description
       "The IPsec Phase-2 Tunnel Table.
        There is one entry in this table for 
        each active IPsec Phase-2 Tunnel.";
      smiv2:oid "1.3.6.1.4.1.9.9.171.1.3.2";

      list cipSecTunnelEntry {
        key "cipSecTunIndex";
        description
         "Each entry contains the attributes
          associated with an active IPsec Phase-2 Tunnel.";
        smiv2:oid "1.3.6.1.4.1.9.9.171.1.3.2.1";

        leaf cipSecTunIndex {
          type int32 {
            range "1..2147483647";
          }
          description
           "The index of the IPsec Phase-2 Tunnel Table.
            The value of the index is a number which begins 
            at one and is incremented with each tunnel that 
            is created. The value of this object will wrap 
            at 2,147,483,647.";
          smiv2:max-access "not-accessible";
          smiv2:oid "1.3.6.1.4.1.9.9.171.1.3.2.1.1";
        }

        leaf cipSecTunIkeTunnelIndex {
          type int32 {
            range "1..2147483647";
          }
          description
           "The index of the associated IPsec Phase-1
            IKE Tunnel.
             (cikeTunIndex in the cikeTunnelTable)";
          smiv2:max-access "read-only";
          smiv2:oid "1.3.6.1.4.1.9.9.171.1.3.2.1.2";
        }

        leaf cipSecTunIkeTunnelAlive {
          type boolean;
          description
           "An indicator which specifies whether or not the
            IPsec Phase-1 IKE Tunnel currently exists.";
          smiv2:max-access "read-only";
          smiv2:oid "1.3.6.1.4.1.9.9.171.1.3.2.1.3";
        }

        leaf cipSecTunLocalAddr {
          type CISCO-IPSEC-FLOW-MONITOR-MIB:IPSIpAddress;
          description
           "The IP address of the local endpoint for the IPsec
            Phase-2 Tunnel.";
          smiv2:max-access "read-only";
          smiv2:oid "1.3.6.1.4.1.9.9.171.1.3.2.1.4";
        }

        leaf cipSecTunRemoteAddr {
          type CISCO-IPSEC-FLOW-MONITOR-MIB:IPSIpAddress;
          description
           "The IP address of the remote endpoint for the IPsec
            Phase-2 Tunnel.";
          smiv2:max-access "read-only";
          smiv2:oid "1.3.6.1.4.1.9.9.171.1.3.2.1.5";
        }

        leaf cipSecTunKeyType {
          type CISCO-IPSEC-FLOW-MONITOR-MIB:KeyType;
          description
           "The type of key used by the IPsec Phase-2 Tunnel.";
          smiv2:max-access "read-only";
          smiv2:oid "1.3.6.1.4.1.9.9.171.1.3.2.1.6";
        }

        leaf cipSecTunEncapMode {
          type CISCO-IPSEC-FLOW-MONITOR-MIB:EncapMode;
          description
           "The encapsulation mode used by the
            IPsec Phase-2 Tunnel.";
          smiv2:max-access "read-only";
          smiv2:oid "1.3.6.1.4.1.9.9.171.1.3.2.1.7";
        }

        leaf cipSecTunLifeSize {
          type int32 {
            range "1..2147483647";
          }
          units "KBytes";
          description
           "The negotiated LifeSize of the
            IPsec Phase-2 Tunnel in kilobytes.";
          smiv2:max-access "read-only";
          smiv2:oid "1.3.6.1.4.1.9.9.171.1.3.2.1.8";
        }

        leaf cipSecTunLifeTime {
          type int32 {
            range "1..2147483647";
          }
          units "Seconds";
          description
           "The negotiated LifeTime of the
            IPsec Phase-2 Tunnel in seconds.";
          smiv2:max-access "read-only";
          smiv2:oid "1.3.6.1.4.1.9.9.171.1.3.2.1.9";
        }

        leaf cipSecTunActiveTime {
          type snmpv2-tc:TimeInterval;
          description
           "The length of time the IPsec Phase-2
            Tunnel has been
             active in hundredths of seconds.";
          smiv2:max-access "read-only";
          smiv2:oid "1.3.6.1.4.1.9.9.171.1.3.2.1.10";
        }

        leaf cipSecTunSaLifeSizeThreshold {
          type int32 {
            range "1..2147483647";
          }
          units "KBytes";
          description
           "The security association LifeSize refresh
            threshold in kilobytes.";
          smiv2:max-access "read-only";
          smiv2:oid "1.3.6.1.4.1.9.9.171.1.3.2.1.11";
        }

        leaf cipSecTunSaLifeTimeThreshold {
          type int32 {
            range "1..2147483647";
          }
          units "Seconds";
          description
           "The security association LifeTime refresh
            threshold in seconds.";
          smiv2:max-access "read-only";
          smiv2:oid "1.3.6.1.4.1.9.9.171.1.3.2.1.12";
        }

        leaf cipSecTunTotalRefreshes {
          type yang:counter32;
          units "QM Exchanges";
          description
           "The total number of security
            association refreshes performed.";
          smiv2:max-access "read-only";
          smiv2:oid "1.3.6.1.4.1.9.9.171.1.3.2.1.13";
        }

        leaf cipSecTunExpiredSaInstances {
          type yang:counter32;
          units "SAs";
          description
           "The total number of security associations
            which have expired.";
          smiv2:max-access "read-only";
          smiv2:oid "1.3.6.1.4.1.9.9.171.1.3.2.1.14";
        }

        leaf cipSecTunCurrentSaInstances {
          type yang:gauge32;
          description
           "The number of security associations
            which are currently active or expiring.";
          smiv2:max-access "read-only";
          smiv2:oid "1.3.6.1.4.1.9.9.171.1.3.2.1.15";
        }

        leaf cipSecTunInSaDiffHellmanGrp {
          type CISCO-IPSEC-FLOW-MONITOR-MIB:DiffHellmanGrp;
          description
           "The Diffie Hellman Group used
            by the inbound security association of the 
            IPsec Phase-2 Tunnel.";
          smiv2:max-access "read-only";
          smiv2:oid "1.3.6.1.4.1.9.9.171.1.3.2.1.16";
        }

        leaf cipSecTunInSaEncryptAlgo {
          type CISCO-IPSEC-FLOW-MONITOR-MIB:EncryptAlgo;
          description
           "The encryption algorithm used by the inbound security
            association of the IPsec Phase-2 Tunnel.";
          smiv2:max-access "read-only";
          smiv2:oid "1.3.6.1.4.1.9.9.171.1.3.2.1.17";
        }

        leaf cipSecTunInSaAhAuthAlgo {
          type CISCO-IPSEC-FLOW-MONITOR-MIB:AuthAlgo;
          description
           "The authentication algorithm used by the inbound
            authentication header (AH) security association of
            the IPsec Phase-2 Tunnel.";
          smiv2:max-access "read-only";
          smiv2:oid "1.3.6.1.4.1.9.9.171.1.3.2.1.18";
        }

        leaf cipSecTunInSaEspAuthAlgo {
          type CISCO-IPSEC-FLOW-MONITOR-MIB:AuthAlgo;
          description
           "The authentication algorithm used by the inbound
            encapsulation security protocol (ESP) security 
            association of the IPsec Phase-2 Tunnel.";
          smiv2:max-access "read-only";
          smiv2:oid "1.3.6.1.4.1.9.9.171.1.3.2.1.19";
        }

        leaf cipSecTunInSaDecompAlgo {
          type CISCO-IPSEC-FLOW-MONITOR-MIB:CompAlgo;
          description
           "The decompression algorithm used by the inbound
            security association of the IPsec Phase-2 Tunnel.";
          smiv2:max-access "read-only";
          smiv2:oid "1.3.6.1.4.1.9.9.171.1.3.2.1.20";
        }

        leaf cipSecTunOutSaDiffHellmanGrp {
          type CISCO-IPSEC-FLOW-MONITOR-MIB:DiffHellmanGrp;
          description
           "The Diffie Hellman Group used by the outbound security
            association of the IPsec Phase-2 Tunnel.";
          smiv2:max-access "read-only";
          smiv2:oid "1.3.6.1.4.1.9.9.171.1.3.2.1.21";
        }

        leaf cipSecTunOutSaEncryptAlgo {
          type CISCO-IPSEC-FLOW-MONITOR-MIB:EncryptAlgo;
          description
           "The encryption algorithm used by the outbound security
            association of the IPsec Phase-2 Tunnel.";
          smiv2:max-access "read-only";
          smiv2:oid "1.3.6.1.4.1.9.9.171.1.3.2.1.22";
        }

        leaf cipSecTunOutSaAhAuthAlgo {
          type CISCO-IPSEC-FLOW-MONITOR-MIB:AuthAlgo;
          description
           "The authentication algorithm used by the outbound
            authentication header (AH) security association of
            the IPsec Phase-2 Tunnel.";
          smiv2:max-access "read-only";
          smiv2:oid "1.3.6.1.4.1.9.9.171.1.3.2.1.23";
        }

        leaf cipSecTunOutSaEspAuthAlgo {
          type CISCO-IPSEC-FLOW-MONITOR-MIB:AuthAlgo;
          description
           "The authentication algorithm used by the inbound
            encapsulation security protocol (ESP) 
            security association of the IPsec Phase-2 Tunnel.";
          smiv2:max-access "read-only";
          smiv2:oid "1.3.6.1.4.1.9.9.171.1.3.2.1.24";
        }

        leaf cipSecTunOutSaCompAlgo {
          type CISCO-IPSEC-FLOW-MONITOR-MIB:CompAlgo;
          description
           "The compression algorithm used by the inbound
            security association of the IPsec Phase-2 Tunnel.";
          smiv2:max-access "read-only";
          smiv2:oid "1.3.6.1.4.1.9.9.171.1.3.2.1.25";
        }

        leaf cipSecTunInOctets {
          type yang:counter32;
          units "Octets";
          description
           "The total number of octets received by this IPsec
            Phase-2 Tunnel.  This value is accumulated
            BEFORE determining whether or not the packet should be
            decompressed.  See also cipSecTunInOctWraps for the
            number of times this counter has wrapped.";
          smiv2:max-access "read-only";
          smiv2:oid "1.3.6.1.4.1.9.9.171.1.3.2.1.26";
        }

        leaf cipSecTunHcInOctets {
          type yang:counter64;
          units "Octets";
          description
           "A high capacity count of the total number of octets
            received by this IPsec Phase-2 Tunnel.  This value is
            accumulated BEFORE determining whether or not the packet
            should be decompressed.";
          smiv2:max-access "read-only";
          smiv2:oid "1.3.6.1.4.1.9.9.171.1.3.2.1.27";
        }

        leaf cipSecTunInOctWraps {
          type yang:counter32;
          units "Integral units";
          description
           "The number of times the octets received counter
            (cipSecTunInOctets) has wrapped.";
          smiv2:max-access "read-only";
          smiv2:oid "1.3.6.1.4.1.9.9.171.1.3.2.1.28";
        }

        leaf cipSecTunInDecompOctets {
          type yang:counter32;
          units "Octets";
          description
           "The total number of decompressed octets received
            by this IPsec Phase-2 Tunnel. This value is 
            accumulated AFTER the packet is decompressed. 
            If compression is not being
             used, this value will match the value of 
             cipSecTunInOctets.  See also cipSecTunInDecompOctWraps 
             for the number of times
             this counter has wrapped.";
          smiv2:max-access "read-only";
          smiv2:oid "1.3.6.1.4.1.9.9.171.1.3.2.1.29";
        }

        leaf cipSecTunHcInDecompOctets {
          type yang:counter64;
          description
           "A high capacity count of the total number of decompressed
            octets received by this IPsec Phase-2 Tunnel.  This value
            is accumulated AFTER the packet is decompressed. If
            compression is not being used, this value will match the
            value of cipSecTunHcInOctets.";
          smiv2:max-access "read-only";
          smiv2:oid "1.3.6.1.4.1.9.9.171.1.3.2.1.30";
        }

        leaf cipSecTunInDecompOctWraps {
          type yang:counter32;
          units "Integral units";
          description
           "The number of times the decompressed
            octets received counter
             (cipSecTunInDecompOctets) has wrapped.";
          smiv2:max-access "read-only";
          smiv2:oid "1.3.6.1.4.1.9.9.171.1.3.2.1.31";
        }

        leaf cipSecTunInPkts {
          type yang:counter32;
          units "Packets";
          description
           "The total number of packets received
            by this IPsec Phase-2 Tunnel.";
          smiv2:max-access "read-only";
          smiv2:oid "1.3.6.1.4.1.9.9.171.1.3.2.1.32";
        }

        leaf cipSecTunInDropPkts {
          type yang:counter32;
          units "Packets";
          description
           "The total number of packets dropped
            during receive processing by this IPsec Phase-2 
            Tunnel. This count does NOT include
             packets dropped due to Anti-Replay processing.";
          smiv2:max-access "read-only";
          smiv2:oid "1.3.6.1.4.1.9.9.171.1.3.2.1.33";
        }

        leaf cipSecTunInReplayDropPkts {
          type yang:counter32;
          units "Packets";
          description
           "The total number of packets dropped during
            receive processing due to Anti-Replay processing 
            by this IPsec Phase-2 Tunnel.";
          smiv2:max-access "read-only";
          smiv2:oid "1.3.6.1.4.1.9.9.171.1.3.2.1.34";
        }

        leaf cipSecTunInAuths {
          type yang:counter32;
          units "Events";
          description
           "The total number of inbound
            authentication's performed by this 
            IPsec Phase-2 Tunnel.";
          smiv2:max-access "read-only";
          smiv2:oid "1.3.6.1.4.1.9.9.171.1.3.2.1.35";
        }

        leaf cipSecTunInAuthFails {
          type yang:counter32;
          units "Failures";
          description
           "The total number of inbound authentication's
            which ended in
             failure by this IPsec Phase-2 Tunnel .";
          smiv2:max-access "read-only";
          smiv2:oid "1.3.6.1.4.1.9.9.171.1.3.2.1.36";
        }

        leaf cipSecTunInDecrypts {
          type yang:counter32;
          units "Packets";
          description
           "The total number of inbound decryption's performed
            by this IPsec Phase-2 Tunnel.";
          smiv2:max-access "read-only";
          smiv2:oid "1.3.6.1.4.1.9.9.171.1.3.2.1.37";
        }

        leaf cipSecTunInDecryptFails {
          type yang:counter32;
          units "Failures";
          description
           "The total number of inbound decryption's
            which ended in failure
             by this IPsec Phase-2 Tunnel.";
          smiv2:max-access "read-only";
          smiv2:oid "1.3.6.1.4.1.9.9.171.1.3.2.1.38";
        }

        leaf cipSecTunOutOctets {
          type yang:counter32;
          units "Octets";
          description
           "The total number of octets sent by this IPsec
            Phase-2 Tunnel.  This value is accumulated
            AFTER determining whether or not the packet should 
            be compressed.  See also cipSecTunOutOctWraps for
            the number of times this counter has wrapped.";
          smiv2:max-access "read-only";
          smiv2:oid "1.3.6.1.4.1.9.9.171.1.3.2.1.39";
        }

        leaf cipSecTunHcOutOctets {
          type yang:counter64;
          description
           "A high capacity count of the total number of octets
            sent by this IPsec Phase-2 Tunnel.  This value is
            accumulated AFTER determining whether or not the 
            packet
            should be compressed.";
          smiv2:max-access "read-only";
          smiv2:oid "1.3.6.1.4.1.9.9.171.1.3.2.1.40";
        }

        leaf cipSecTunOutOctWraps {
          type yang:counter32;
          units "Integral units";
          description
           "The number of times the out octets counter
            (cipSecTunOutOctets) has wrapped.";
          smiv2:max-access "read-only";
          smiv2:oid "1.3.6.1.4.1.9.9.171.1.3.2.1.41";
        }

        leaf cipSecTunOutUncompOctets {
          type yang:counter32;
          units "Octets";
          description
           "The total number of uncompressed octets sent
            by this IPsec Phase-2 Tunnel.  This value 
            is accumulated BEFORE the packet is compressed. 
            If compression is not being used, this value 
            will match the value of cipSecTunOutOctets.
             See also cipSecTunOutDecompOctWraps for the 
             number of times this counter has wrapped.";
          smiv2:max-access "read-only";
          smiv2:oid "1.3.6.1.4.1.9.9.171.1.3.2.1.42";
        }

        leaf cipSecTunHcOutUncompOctets {
          type yang:counter64;
          description
           "A high capacity count of the total number
            of uncompressed octets sent by this IPsec 
            Phase-2 Tunnel.  This value is accumulated BEFORE 
            the packet is compressed. If compression
             is not being used, this value will match the value
             of cipSecTunHcOutOctets.";
          smiv2:max-access "read-only";
          smiv2:oid "1.3.6.1.4.1.9.9.171.1.3.2.1.43";
        }

        leaf cipSecTunOutUncompOctWraps {
          type yang:counter32;
          units "Integral units";
          description
           "The number of times the uncompressed octets sent
            counter (cipSecTunOutUncompOctets) has wrapped.";
          smiv2:max-access "read-only";
          smiv2:oid "1.3.6.1.4.1.9.9.171.1.3.2.1.44";
        }

        leaf cipSecTunOutPkts {
          type yang:counter32;
          units "Packets";
          description
           "The total number of packets sent by this
            IPsec Phase-2 Tunnel.";
          smiv2:max-access "read-only";
          smiv2:oid "1.3.6.1.4.1.9.9.171.1.3.2.1.45";
        }

        leaf cipSecTunOutDropPkts {
          type yang:counter32;
          units "Packets";
          description
           "The total number of packets dropped during
            send processing by this IPsec Phase-2 Tunnel.";
          smiv2:max-access "read-only";
          smiv2:oid "1.3.6.1.4.1.9.9.171.1.3.2.1.46";
        }

        leaf cipSecTunOutAuths {
          type yang:counter32;
          units "Events";
          description
           "The total number of outbound authentication's performed
            by this IPsec Phase-2 Tunnel.";
          smiv2:max-access "read-only";
          smiv2:oid "1.3.6.1.4.1.9.9.171.1.3.2.1.47";
        }

        leaf cipSecTunOutAuthFails {
          type yang:counter32;
          units "Failures";
          description
           "The total number of outbound
            authentication's which ended in failure 
            by this IPsec Phase-2 Tunnel.";
          smiv2:max-access "read-only";
          smiv2:oid "1.3.6.1.4.1.9.9.171.1.3.2.1.48";
        }

        leaf cipSecTunOutEncrypts {
          type yang:counter32;
          units "Packets";
          description
           "The total number of outbound encryption's performed
            by this IPsec Phase-2 Tunnel.";
          smiv2:max-access "read-only";
          smiv2:oid "1.3.6.1.4.1.9.9.171.1.3.2.1.49";
        }

        leaf cipSecTunOutEncryptFails {
          type yang:counter32;
          units "Failures";
          description
           "The total number of outbound encryption's
            which ended in failure by this IPsec Phase-2 Tunnel.";
          smiv2:max-access "read-only";
          smiv2:oid "1.3.6.1.4.1.9.9.171.1.3.2.1.50";
        }

        leaf cipSecTunStatus {
          type CISCO-IPSEC-FLOW-MONITOR-MIB:TunnelStatus;
          description
           "The status of the MIB table row.
            
            This object can be used to bring the tunnel down
            by setting value of this object to destroy(2).
            When the value is set to destroy(2), the SA
            bundle is destroyed and this row is deleted
            from this table.
            
            When this MIB value is queried, the value of
            active(1) is always returned, if the instance 
            exists.
            
            This object cannot be used to create a MIB 
            table row.";
          smiv2:max-access "read-write";
          smiv2:oid "1.3.6.1.4.1.9.9.171.1.3.2.1.51";
        }
      }
    }

    container cipSecEndPtTable {
      description
       "The IPsec Phase-2 Tunnel Endpoint Table.
        This table contains an entry for each 
        active endpoint associated with an IPsec
         Phase-2 Tunnel.";
      smiv2:oid "1.3.6.1.4.1.9.9.171.1.3.3";

      list cipSecEndPtEntry {
        key "cipSecTunIndex cipSecEndPtIndex";
        description
         "An IPsec Phase-2 Tunnel Endpoint entry.";
        smiv2:oid "1.3.6.1.4.1.9.9.171.1.3.3.1";

        leaf cipSecTunIndex {
          type leafref {
            path "/CISCO-IPSEC-FLOW-MONITOR-MIB:CISCO-IPSEC-FLOW-MONITOR-MIB/CISCO-IPSEC-FLOW-MONITOR-MIB:cipSecTunnelTable/CISCO-IPSEC-FLOW-MONITOR-MIB:cipSecTunnelEntry/CISCO-IPSEC-FLOW-MONITOR-MIB:cipSecTunIndex";
          }
        }

        leaf cipSecEndPtIndex {
          type int32 {
            range "1..2147483647";
          }
          description
           "The number of the Endpoint associated with the
            IPsec Phase-2 Tunnel Table.  The value of this
            index is a number which begins at one and 
            is incremented with each Endpoint associated 
            with an IPsec Phase-2 Tunnel.
            The value of this object will wrap at 2,147,483,647.";
          smiv2:max-access "not-accessible";
          smiv2:oid "1.3.6.1.4.1.9.9.171.1.3.3.1.1";
        }

        leaf cipSecEndPtLocalName {
          type snmpv2-tc:DisplayString;
          description
           "The DNS name of the local Endpoint.";
          smiv2:max-access "read-only";
          smiv2:oid "1.3.6.1.4.1.9.9.171.1.3.3.1.2";
        }

        leaf cipSecEndPtLocalType {
          type CISCO-IPSEC-FLOW-MONITOR-MIB:EndPtType;
          description
           "The type of identity for the local Endpoint.
            Possible values are:
            1) a single IP address, or
            2) an IP address range, or
            3) an IP subnet.";
          smiv2:max-access "read-only";
          smiv2:oid "1.3.6.1.4.1.9.9.171.1.3.3.1.3";
        }

        leaf cipSecEndPtLocalAddr1 {
          type CISCO-IPSEC-FLOW-MONITOR-MIB:IPSIpAddress;
          description
           "The local Endpoint's first IP address specification.
            
            If the local Endpoint type is single IP address, 
            then this is the value of the IP address.
            
            If the local Endpoint type is IP subnet, then this
            is the value of the subnet.
            
            If the local Endpoint type is IP address range, 
            then this is the value of beginning IP address 
            of the range.";
          smiv2:max-access "read-only";
          smiv2:oid "1.3.6.1.4.1.9.9.171.1.3.3.1.4";
        }

        leaf cipSecEndPtLocalAddr2 {
          type CISCO-IPSEC-FLOW-MONITOR-MIB:IPSIpAddress;
          description
           "The local Endpoint's second IP address specification.
            
            If the local Endpoint type is single IP address, 
            then this is the value of the IP address.
            
            If the local Endpoint type is IP subnet, then this
            is the value of the subnet mask.
            
            If the local Endpoint type is IP address range, 
            then this is the value of ending IP address 
            of the range.";
          smiv2:max-access "read-only";
          smiv2:oid "1.3.6.1.4.1.9.9.171.1.3.3.1.5";
        }

        leaf cipSecEndPtLocalProtocol {
          type int32 {
            range "0..255";
          }
          description
           "The protocol number of the local Endpoint's traffic.";
          smiv2:max-access "read-only";
          smiv2:oid "1.3.6.1.4.1.9.9.171.1.3.3.1.6";
        }

        leaf cipSecEndPtLocalPort {
          type int32 {
            range "0..65535";
          }
          description
           "The port number of the local Endpoint's traffic.";
          smiv2:max-access "read-only";
          smiv2:oid "1.3.6.1.4.1.9.9.171.1.3.3.1.7";
        }

        leaf cipSecEndPtRemoteName {
          type snmpv2-tc:DisplayString;
          description
           "The DNS name of the remote Endpoint.";
          smiv2:max-access "read-only";
          smiv2:oid "1.3.6.1.4.1.9.9.171.1.3.3.1.8";
        }

        leaf cipSecEndPtRemoteType {
          type CISCO-IPSEC-FLOW-MONITOR-MIB:EndPtType;
          description
           "The type of identity for the remote Endpoint.
            Possible values are:
            1) a single IP address, or
            2) an IP address range, or
            3) an IP subnet.";
          smiv2:max-access "read-only";
          smiv2:oid "1.3.6.1.4.1.9.9.171.1.3.3.1.9";
        }

        leaf cipSecEndPtRemoteAddr1 {
          type CISCO-IPSEC-FLOW-MONITOR-MIB:IPSIpAddress;
          description
           "The remote Endpoint's first IP address specification.
            
            If the remote Endpoint type is single IP address, 
            then this is the value of the IP address.
            
            If the remote Endpoint type is IP subnet, then this
            is the value of the subnet.
            
            If the remote Endpoint type is IP address range, 
            then this is the value of beginning IP address 
            of the range.";
          smiv2:max-access "read-only";
          smiv2:oid "1.3.6.1.4.1.9.9.171.1.3.3.1.10";
        }

        leaf cipSecEndPtRemoteAddr2 {
          type CISCO-IPSEC-FLOW-MONITOR-MIB:IPSIpAddress;
          description
           "The remote Endpoint's second IP address specification.
            
            If the remote Endpoint type is single IP address, 
            then this is the value of the IP address.
            
            If the remote Endpoint type is IP subnet, then this
            is the value of the subnet mask.
            
            If the remote Endpoint type is IP address range, 
            then this is the value of ending IP address of 
            the range.";
          smiv2:max-access "read-only";
          smiv2:oid "1.3.6.1.4.1.9.9.171.1.3.3.1.11";
        }

        leaf cipSecEndPtRemoteProtocol {
          type int32 {
            range "0..255";
          }
          description
           "The protocol number of the remote Endpoint's traffic.";
          smiv2:max-access "read-only";
          smiv2:oid "1.3.6.1.4.1.9.9.171.1.3.3.1.12";
        }

        leaf cipSecEndPtRemotePort {
          type int32 {
            range "0..65535";
          }
          description
           "The port number of the remote Endpoint's traffic.";
          smiv2:max-access "read-only";
          smiv2:oid "1.3.6.1.4.1.9.9.171.1.3.3.1.13";
        }
      }
    }

    container cipSecSpiTable {
      description
       "The IPsec Phase-2 Security Protection Index Table.
        This table contains an entry for each active 
        and expiring security
         association.";
      smiv2:oid "1.3.6.1.4.1.9.9.171.1.3.4";

      list cipSecSpiEntry {
        key "cipSecTunIndex cipSecSpiIndex";
        description
         "Each entry contains the attributes associated with
          active and expiring IPsec Phase-2 
          security associations.";
        smiv2:oid "1.3.6.1.4.1.9.9.171.1.3.4.1";

        leaf cipSecTunIndex {
          type leafref {
            path "/CISCO-IPSEC-FLOW-MONITOR-MIB:CISCO-IPSEC-FLOW-MONITOR-MIB/CISCO-IPSEC-FLOW-MONITOR-MIB:cipSecTunnelTable/CISCO-IPSEC-FLOW-MONITOR-MIB:cipSecTunnelEntry/CISCO-IPSEC-FLOW-MONITOR-MIB:cipSecTunIndex";
          }
        }

        leaf cipSecSpiIndex {
          type int32 {
            range "1..2147483647";
          }
          description
           "The number of the SPI associated with the
            Phase-2 Tunnel Table.  The value of this 
            index is a number which begins at one and is 
            incremented with each SPI associated with an 
            IPsec Phase-2 Tunnel.  The value of this 
            object will wrap at 2,147,483,647.";
          smiv2:max-access "not-accessible";
          smiv2:oid "1.3.6.1.4.1.9.9.171.1.3.4.1.1";
        }

        leaf cipSecSpiDirection {
          type enumeration {
            enum "in" {
              value "1";
            }
            enum "out" {
              value "2";
            }
          }
          description
           "The direction of the SPI.";
          smiv2:max-access "read-only";
          smiv2:oid "1.3.6.1.4.1.9.9.171.1.3.4.1.2";
        }

        leaf cipSecSpiValue {
          type uint32 {
            range "1..4294967295";
          }
          description
           "The value of the SPI.";
          smiv2:max-access "read-only";
          smiv2:oid "1.3.6.1.4.1.9.9.171.1.3.4.1.3";
        }

        leaf cipSecSpiProtocol {
          type enumeration {
            enum "ah" {
              value "1";
            }
            enum "esp" {
              value "2";
            }
            enum "ipcomp" {
              value "3";
            }
          }
          description
           "The protocol of the SPI.";
          smiv2:max-access "read-only";
          smiv2:oid "1.3.6.1.4.1.9.9.171.1.3.4.1.4";
        }

        leaf cipSecSpiStatus {
          type enumeration {
            enum "active" {
              value "1";
            }
            enum "expiring" {
              value "2";
            }
          }
          description
           "The status of the SPI.";
          smiv2:max-access "read-only";
          smiv2:oid "1.3.6.1.4.1.9.9.171.1.3.4.1.5";
        }
      }
    }

    container cipSecPhase2GWStatsTable {
      description
       "Phase-2 IPsec stats information is included in this table.
        Each entry is related to a specific gateway which is 
        identified by 'cmgwIndex'";
      smiv2:oid "1.3.6.1.4.1.9.9.171.1.3.5";

      list cipSecPhase2GWStatsEntry {
        key "cmgwIndex";
        description
         "Each entry contains the attributes of an Phase-2 IPsec stats
          information for the related gateway.
          
          There is only one entry for each gateway. The entry 
          is created when a gateway up and cannot be deleted.";
        smiv2:oid "1.3.6.1.4.1.9.9.171.1.3.5.1";

        leaf cmgwIndex {
          type leafref {
            path "/cisco-media:CISCO-MEDIA-GATEWAY-MIB/cisco-media:cMediaGwTable/cisco-media:cMediaGwEntry/cisco-media:cmgwIndex";
          }
        }

        leaf cipSecPhase2GWActiveTunnels {
          type yang:gauge32;
          description
           "The total number of currently active
            IPsec Phase-2 Tunnels.";
          smiv2:max-access "read-only";
          smiv2:oid "1.3.6.1.4.1.9.9.171.1.3.5.1.1";
        }

        leaf cipSecPhase2GWPreviousTunnels {
          type yang:counter32;
          units "Phase-2 Tunnels";
          description
           "The total number of previously active
            IPsec Phase-2 Tunnels.";
          smiv2:max-access "read-only";
          smiv2:oid "1.3.6.1.4.1.9.9.171.1.3.5.1.2";
        }

        leaf cipSecPhase2GWInOctets {
          type yang:counter32;
          units "Octets";
          description
           "The total number of octets received by all
            current and previous IPsec Phase-2 Tunnels. 
            This value is accumulated BEFORE determining 
            whether or not the packet should be decompressed. 
            See also cipSecGlobalInOctWraps for the number
            of times this counter has wrapped.";
          smiv2:max-access "read-only";
          smiv2:oid "1.3.6.1.4.1.9.9.171.1.3.5.1.3";
        }

        leaf cipSecPhase2GWInOctWraps {
          type yang:counter32;
          units "Integral units";
          description
           "The number of times the global octets received
            counter (cipSecGlobalInOctets) has wrapped.";
          smiv2:max-access "read-only";
          smiv2:oid "1.3.6.1.4.1.9.9.171.1.3.5.1.4";
        }

        leaf cipSecPhase2GWInDecompOctets {
          type yang:counter32;
          units "Octets";
          description
           "The total number of decompressed octets received
            by all current and previous IPsec Phase-2 Tunnels.  
            This value is accumulated AFTER the packet is 
            decompressed. If compression is not being used, 
            this value will match the value of cipSecGlobalInOctets. 
            See also cipSecGlobalInDecompOctWraps
            for the number of times this counter has wrapped.";
          smiv2:max-access "read-only";
          smiv2:oid "1.3.6.1.4.1.9.9.171.1.3.5.1.5";
        }

        leaf cipSecPhase2GWInDecompOctWraps {
          type yang:counter32;
          units "Integral units";
          description
           "The number of times the global decompressed
            octets received counter (cipSecGlobalInDecompOctets) 
            has wrapped.";
          smiv2:max-access "read-only";
          smiv2:oid "1.3.6.1.4.1.9.9.171.1.3.5.1.6";
        }

        leaf cipSecPhase2GWInPkts {
          type yang:counter32;
          units "Packets";
          description
           "The total number of packets received
            by all current and previous IPsec Phase-2 Tunnels.";
          smiv2:max-access "read-only";
          smiv2:oid "1.3.6.1.4.1.9.9.171.1.3.5.1.7";
        }

        leaf cipSecPhase2GWInDrops {
          type yang:counter32;
          units "Packets";
          description
           "The total number of packets dropped
            during receive processing by all current and previous 
            IPsec Phase-2 Tunnels. This count does NOT include 
            packets dropped due to Anti-Replay processing.";
          smiv2:max-access "read-only";
          smiv2:oid "1.3.6.1.4.1.9.9.171.1.3.5.1.8";
        }

        leaf cipSecPhase2GWInReplayDrops {
          type yang:counter32;
          units "Packets";
          description
           "The total number of packets dropped during
            receive processing due to Anti-Replay 
            processing by all current and previous IPsec
            Phase-2 Tunnels.";
          smiv2:max-access "read-only";
          smiv2:oid "1.3.6.1.4.1.9.9.171.1.3.5.1.9";
        }

        leaf cipSecPhase2GWInAuths {
          type yang:counter32;
          units "Events";
          description
           "The total number of inbound authentication's
            performed by all current and previous IPsec 
            Phase-2 Tunnels.";
          smiv2:max-access "read-only";
          smiv2:oid "1.3.6.1.4.1.9.9.171.1.3.5.1.10";
        }

        leaf cipSecPhase2GWInAuthFails {
          type yang:counter32;
          units "Failures";
          description
           "The total number of inbound authentication's
            which ended in failure by all current and previous 
            IPsec Phase-2 Tunnels.";
          smiv2:max-access "read-only";
          smiv2:oid "1.3.6.1.4.1.9.9.171.1.3.5.1.11";
        }

        leaf cipSecPhase2GWInDecrypts {
          type yang:counter32;
          units "Packets";
          description
           "The total number of inbound decryption's
            performed by all current and previous IPsec 
            Phase-2 Tunnels.";
          smiv2:max-access "read-only";
          smiv2:oid "1.3.6.1.4.1.9.9.171.1.3.5.1.12";
        }

        leaf cipSecPhase2GWInDecryptFails {
          type yang:counter32;
          units "Packets";
          description
           "The total number of inbound decryption's
            which ended in failure by all current and 
            previous IPsec Phase-2 Tunnels.";
          smiv2:max-access "read-only";
          smiv2:oid "1.3.6.1.4.1.9.9.171.1.3.5.1.13";
        }

        leaf cipSecPhase2GWOutOctets {
          type yang:counter32;
          units "Octets";
          description
           "The total number of octets sent by all
            current and previous IPsec Phase-2 Tunnels.  
            This value is accumulated AFTER determining 
            whether or not the packet should be compressed.  
            See also cipSecGlobalOutOctWraps for the
            number of times this counter has wrapped.";
          smiv2:max-access "read-only";
          smiv2:oid "1.3.6.1.4.1.9.9.171.1.3.5.1.14";
        }

        leaf cipSecPhase2GWOutOctWraps {
          type yang:counter32;
          units "Integral units";
          description
           "The number of times the global octets sent counter
            (cipSecGlobalOutOctets) has wrapped.";
          smiv2:max-access "read-only";
          smiv2:oid "1.3.6.1.4.1.9.9.171.1.3.5.1.15";
        }

        leaf cipSecPhase2GWOutUncompOctets {
          type yang:counter32;
          units "Octets";
          description
           "The total number of uncompressed octets sent
            by all current and previous IPsec Phase-2 Tunnels.  
            This value is accumulated BEFORE the packet is 
            compressed. If compression is not being used, this 
            value will match the value of cipSecGlobalOutOctets. 
            See also cipSecGlobalOutDecompOctWraps for the number 
            of times this counter has wrapped.";
          smiv2:max-access "read-only";
          smiv2:oid "1.3.6.1.4.1.9.9.171.1.3.5.1.16";
        }

        leaf cipSecPhase2GWOutUncompOctWraps {
          type yang:counter32;
          units "Integral units";
          description
           "The number of times the global uncompressed
            octets sent counter (cipSecGlobalOutUncompOctets) 
            has wrapped.";
          smiv2:max-access "read-only";
          smiv2:oid "1.3.6.1.4.1.9.9.171.1.3.5.1.17";
        }

        leaf cipSecPhase2GWOutPkts {
          type yang:counter32;
          units "Packets";
          description
           "The total number of packets sent by all
            current and previous IPsec Phase-2 
            Tunnels.";
          smiv2:max-access "read-only";
          smiv2:oid "1.3.6.1.4.1.9.9.171.1.3.5.1.18";
        }

        leaf cipSecPhase2GWOutDrops {
          type yang:counter32;
          units "Packets";
          description
           "The total number of packets dropped during send
            processing by all current and previous IPsec 
            Phase-2 Tunnels.";
          smiv2:max-access "read-only";
          smiv2:oid "1.3.6.1.4.1.9.9.171.1.3.5.1.19";
        }

        leaf cipSecPhase2GWOutAuths {
          type yang:counter32;
          units "Events";
          description
           "The total number of outbound authentication's
            performed by all current and previous IPsec 
            Phase-2 Tunnels.";
          smiv2:max-access "read-only";
          smiv2:oid "1.3.6.1.4.1.9.9.171.1.3.5.1.20";
        }

        leaf cipSecPhase2GWOutAuthFails {
          type yang:counter32;
          units "Failures";
          description
           "The total number of outbound authentication's
            which ended in failure
            by all current and previous IPsec Phase-2 Tunnels.";
          smiv2:max-access "read-only";
          smiv2:oid "1.3.6.1.4.1.9.9.171.1.3.5.1.21";
        }

        leaf cipSecPhase2GWOutEncrypts {
          type yang:counter32;
          units "Packets";
          description
           "The total number of outbound encryption's performed
            by all current and previous IPsec Phase-2 Tunnels.";
          smiv2:max-access "read-only";
          smiv2:oid "1.3.6.1.4.1.9.9.171.1.3.5.1.22";
        }

        leaf cipSecPhase2GWOutEncryptFails {
          type yang:counter32;
          units "Failures";
          description
           "The total number of outbound encryption's
            which ended in failure by all current and 
            previous IPsec Phase-2 Tunnels.";
          smiv2:max-access "read-only";
          smiv2:oid "1.3.6.1.4.1.9.9.171.1.3.5.1.23";
        }

        leaf cipSecPhase2GWProtocolUseFails {
          type yang:counter32;
          units "Failures";
          description
           "The total number of protocol use failures
            which occurred during processing of all current 
            and previously active IPsec Phase-2 Tunnels.";
          smiv2:max-access "read-only";
          smiv2:oid "1.3.6.1.4.1.9.9.171.1.3.5.1.24";
        }

        leaf cipSecPhase2GWNoSaFails {
          type yang:counter32;
          units "Failures";
          description
           "The total number of non-existent
            Security Association in failures which occurred 
            during processing of all current
            and previous IPsec Phase-2 Tunnels.";
          smiv2:max-access "read-only";
          smiv2:oid "1.3.6.1.4.1.9.9.171.1.3.5.1.25";
        }

        leaf cipSecPhase2GWSysCapFails {
          type yang:counter32;
          units "Failures";
          description
           "The total number of system capacity failures
            which occurred during processing of all current 
            and previously active IPsec Phase-2 Tunnels.";
          smiv2:max-access "read-only";
          smiv2:oid "1.3.6.1.4.1.9.9.171.1.3.5.1.26";
        }
      }
    }

    container cikeTunnelHistTable {
      description
       "The IPsec Phase-1 Internet Key Exchange Tunnel
        History Table.  This table is implemented as a 
        sliding window in which only the last n entries 
        are maintained.  The maximum number of entries
         is specified by the cipSecHistTableSize object.";
      smiv2:oid "1.3.6.1.4.1.9.9.171.1.4.2.1";

      list cikeTunnelHistEntry {
        key "cikeTunHistIndex";
        description
         "Each entry contains the attributes
          associated with a previously active IPsec 
          Phase-1 IKE Tunnel.";
        smiv2:oid "1.3.6.1.4.1.9.9.171.1.4.2.1.1";

        leaf cikeTunHistIndex {
          type int32 {
            range "1..2147483647";
          }
          description
           "The index of the IPsec Phase-1 IKE Tunnel History
            Table.  The value of the index is a number which 
            begins at one and is incremented with each 
            tunnel that ends. The value of this object 
            will wrap at 2,147,483,647.";
          smiv2:max-access "not-accessible";
          smiv2:oid "1.3.6.1.4.1.9.9.171.1.4.2.1.1.1";
        }

        leaf cikeTunHistTermReason {
          type enumeration {
            enum "other" {
              value "1";
            }
            enum "normal" {
              value "2";
            }
            enum "operRequest" {
              value "3";
            }
            enum "peerDelRequest" {
              value "4";
            }
            enum "peerLost" {
              value "5";
            }
            enum "localFailure" {
              value "6";
            }
            enum "checkPointReg" {
              value "7";
            }
          }
          description
           "The reason the IPsec Phase-1 IKE Tunnel was terminated.
            Possible reasons include:
            1 = other
            2 = normal termination
            3 = operator request
            4 = peer delete request was received
            5 = contact with peer was lost
            6 = local failure occurred.
            7 = operator initiated check point request";
          smiv2:max-access "read-only";
          smiv2:oid "1.3.6.1.4.1.9.9.171.1.4.2.1.1.2";
        }

        leaf cikeTunHistActiveIndex {
          type int32 {
            range "1..2147483647";
          }
          description
           "The index of the previously active IPsec
            Phase-1 IKE Tunnel.";
          smiv2:max-access "read-only";
          smiv2:oid "1.3.6.1.4.1.9.9.171.1.4.2.1.1.3";
        }

        leaf cikeTunHistPeerLocalType {
          type CISCO-IPSEC-FLOW-MONITOR-MIB:IkePeerType;
          description
           "The type of local peer identity.  The local peer
            may be identified by:
             1. an IP address, or
             2. a host name.";
          smiv2:max-access "read-only";
          smiv2:oid "1.3.6.1.4.1.9.9.171.1.4.2.1.1.4";
        }

        leaf cikeTunHistPeerLocalValue {
          type snmpv2-tc:DisplayString;
          description
           "The value of the local peer identity.
            
            If the local peer type is an IP Address, then this
            is the IP Address used to identify the local peer.
            
            If the local peer type is a host name, then this is
            the host name used to identify the local peer.";
          smiv2:max-access "read-only";
          smiv2:oid "1.3.6.1.4.1.9.9.171.1.4.2.1.1.5";
        }

        leaf cikeTunHistPeerIntIndex {
          type int32 {
            range "1..2147483647";
          }
          description
           "The internal index of the local-remote peer
            association.  This internal index is used to 
            uniquely identify multiple associations between 
            the local and remote peer.";
          smiv2:max-access "read-only";
          smiv2:oid "1.3.6.1.4.1.9.9.171.1.4.2.1.1.6";
        }

        leaf cikeTunHistPeerRemoteType {
          type CISCO-IPSEC-FLOW-MONITOR-MIB:IkePeerType;
          description
           "The type of remote peer identity.  The remote
            peer may be identified by:
             1. an IP address, or
             2. a host name.";
          smiv2:max-access "read-only";
          smiv2:oid "1.3.6.1.4.1.9.9.171.1.4.2.1.1.7";
        }

        leaf cikeTunHistPeerRemoteValue {
          type snmpv2-tc:DisplayString;
          description
           "The value of the remote peer identity.
            
            If the remote peer type is an IP Address, then this
            is the IP Address used to identify the remote peer.
            
            If the remote peer type is a host name, then this is
            the host name used to identify the remote peer.";
          smiv2:max-access "read-only";
          smiv2:oid "1.3.6.1.4.1.9.9.171.1.4.2.1.1.8";
        }

        leaf cikeTunHistLocalAddr {
          type CISCO-IPSEC-FLOW-MONITOR-MIB:IPSIpAddress;
          description
           "The IP address of the local endpoint for the IPsec
            Phase-1 IKE Tunnel.";
          smiv2:max-access "read-only";
          smiv2:oid "1.3.6.1.4.1.9.9.171.1.4.2.1.1.9";
        }

        leaf cikeTunHistLocalName {
          type snmpv2-tc:DisplayString;
          description
           "The DNS name of the local IP address for
            the IPsec Phase-1 IKE Tunnel. If the DNS 
            name associated with the local tunnel endpoint 
            is not known, then the value of this
             object will be a NULL string.";
          smiv2:max-access "read-only";
          smiv2:oid "1.3.6.1.4.1.9.9.171.1.4.2.1.1.10";
        }

        leaf cikeTunHistRemoteAddr {
          type CISCO-IPSEC-FLOW-MONITOR-MIB:IPSIpAddress;
          description
           "The IP address of the remote endpoint for the IPsec
            Phase-1 IKE Tunnel.";
          smiv2:max-access "read-only";
          smiv2:oid "1.3.6.1.4.1.9.9.171.1.4.2.1.1.11";
        }

        leaf cikeTunHistRemoteName {
          type snmpv2-tc:DisplayString;
          description
           "The DNS name of the remote IP address of IPsec Phase-1
            IKE Tunnel. If the DNS name associated with the remote
            tunnel endpoint is not known, then the value of this
            object will be a NULL string.";
          smiv2:max-access "read-only";
          smiv2:oid "1.3.6.1.4.1.9.9.171.1.4.2.1.1.12";
        }

        leaf cikeTunHistNegoMode {
          type CISCO-IPSEC-FLOW-MONITOR-MIB:IkeNegoMode;
          description
           "The negotiation mode of the IPsec Phase-1 IKE Tunnel.";
          smiv2:max-access "read-only";
          smiv2:oid "1.3.6.1.4.1.9.9.171.1.4.2.1.1.13";
        }

        leaf cikeTunHistDiffHellmanGrp {
          type CISCO-IPSEC-FLOW-MONITOR-MIB:DiffHellmanGrp;
          description
           "The Diffie Hellman Group used in IPsec Phase-1 IKE
            negotiations.";
          smiv2:max-access "read-only";
          smiv2:oid "1.3.6.1.4.1.9.9.171.1.4.2.1.1.14";
        }

        leaf cikeTunHistEncryptAlgo {
          type CISCO-IPSEC-FLOW-MONITOR-MIB:EncryptAlgo;
          description
           "The encryption algorithm used in IPsec Phase-1 IKE
            negotiations.";
          smiv2:max-access "read-only";
          smiv2:oid "1.3.6.1.4.1.9.9.171.1.4.2.1.1.15";
        }

        leaf cikeTunHistHashAlgo {
          type CISCO-IPSEC-FLOW-MONITOR-MIB:IkeHashAlgo;
          description
           "The hash algorithm used in IPsec Phase-1 IKE
            negotiations.";
          smiv2:max-access "read-only";
          smiv2:oid "1.3.6.1.4.1.9.9.171.1.4.2.1.1.16";
        }

        leaf cikeTunHistAuthMethod {
          type CISCO-IPSEC-FLOW-MONITOR-MIB:IkeAuthMethod;
          description
           "The authentication method used in IPsec Phase-1 IKE
            negotiations.";
          smiv2:max-access "read-only";
          smiv2:oid "1.3.6.1.4.1.9.9.171.1.4.2.1.1.17";
        }

        leaf cikeTunHistLifeTime {
          type int32 {
            range "1..2147483647";
          }
          description
           "The negotiated LifeTime of the IPsec Phase-1 IKE Tunnel
            in seconds.";
          smiv2:max-access "read-only";
          smiv2:oid "1.3.6.1.4.1.9.9.171.1.4.2.1.1.18";
        }

        leaf cikeTunHistStartTime {
          type yang:timestamp;
          description
           "The value of sysUpTime in hundredths of seconds
            when the IPsec Phase-1 IKE tunnel was started.";
          smiv2:max-access "read-only";
          smiv2:oid "1.3.6.1.4.1.9.9.171.1.4.2.1.1.19";
        }

        leaf cikeTunHistActiveTime {
          type snmpv2-tc:TimeInterval;
          description
           "The length of time the IPsec Phase-1 IKE tunnel was been
            active in hundredths of seconds.";
          smiv2:max-access "read-only";
          smiv2:oid "1.3.6.1.4.1.9.9.171.1.4.2.1.1.20";
        }

        leaf cikeTunHistTotalRefreshes {
          type yang:counter32;
          units "QM Exchanges";
          description
           "The total number of security associations
            refreshes performed.";
          smiv2:max-access "read-only";
          smiv2:oid "1.3.6.1.4.1.9.9.171.1.4.2.1.1.21";
        }

        leaf cikeTunHistTotalSas {
          type yang:counter32;
          units "SAs";
          description
           "The total number of security associations
            used during the
             life of the IPsec Phase-1 IKE Tunnel.";
          smiv2:max-access "read-only";
          smiv2:oid "1.3.6.1.4.1.9.9.171.1.4.2.1.1.22";
        }

        leaf cikeTunHistInOctets {
          type yang:counter32;
          units "Octets";
          description
           "The total number of octets
            received by this IPsec Phase-1
             IKE Tunnel.";
          smiv2:max-access "read-only";
          smiv2:oid "1.3.6.1.4.1.9.9.171.1.4.2.1.1.23";
        }

        leaf cikeTunHistInPkts {
          type yang:counter32;
          units "Packets";
          description
           "The total number of packets received
            by this IPsec Phase-1
             IKE Tunnel.";
          smiv2:max-access "read-only";
          smiv2:oid "1.3.6.1.4.1.9.9.171.1.4.2.1.1.24";
        }

        leaf cikeTunHistInDropPkts {
          type yang:counter32;
          units "Packets";
          description
           "The total number of packets dropped
            by this IPsec Phase-1
             IKE Tunnel during receive processing.";
          smiv2:max-access "read-only";
          smiv2:oid "1.3.6.1.4.1.9.9.171.1.4.2.1.1.25";
        }

        leaf cikeTunHistInNotifys {
          type yang:counter32;
          units "Notification Payloads";
          description
           "The total number of notifys received
            by this IPsec Phase-1
             IKE Tunnel.";
          smiv2:max-access "read-only";
          smiv2:oid "1.3.6.1.4.1.9.9.171.1.4.2.1.1.26";
        }

        leaf cikeTunHistInP2Exchgs {
          type yang:counter32;
          units "SA Payloads";
          description
           "The total number of IPsec Phase-2
            exchanges received by
             this IPsec Phase-1 IKE Tunnel.";
          smiv2:max-access "read-only";
          smiv2:oid "1.3.6.1.4.1.9.9.171.1.4.2.1.1.27";
        }

        leaf cikeTunHistInP2ExchgInvalids {
          type yang:counter32;
          units "SA Payloads";
          description
           "The total number of IPsec Phase-2
            exchanges received and
             found to be invalid by this IPsec Phase-1 IKE Tunnel.";
          smiv2:max-access "read-only";
          smiv2:oid "1.3.6.1.4.1.9.9.171.1.4.2.1.1.28";
        }

        leaf cikeTunHistInP2ExchgRejects {
          type yang:counter32;
          units "SA Payloads";
          description
           "The total number of IPsec Phase-2
            exchanges received and
             rejected by this IPsec Phase-1 IKE Tunnel.";
          smiv2:max-access "read-only";
          smiv2:oid "1.3.6.1.4.1.9.9.171.1.4.2.1.1.29";
        }

        leaf cikeTunHistInP2SaDelRequests {
          type yang:counter32;
          units "Notification Payloads";
          description
           "The total number of IPsec Phase-2 security association
            delete requests received by this IPsec 
            Phase-1 IKE Tunnel.";
          smiv2:max-access "read-only";
          smiv2:oid "1.3.6.1.4.1.9.9.171.1.4.2.1.1.30";
        }

        leaf cikeTunHistOutOctets {
          type yang:counter32;
          units "Octets";
          description
           "The total number of octets sent by this IPsec Phase-1
            IKE Tunnel.";
          smiv2:max-access "read-only";
          smiv2:oid "1.3.6.1.4.1.9.9.171.1.4.2.1.1.31";
        }

        leaf cikeTunHistOutPkts {
          type yang:counter32;
          units "Packets";
          description
           "The total number of packets sent by this IPsec Phase-1
            IKE Tunnel.";
          smiv2:max-access "read-only";
          smiv2:oid "1.3.6.1.4.1.9.9.171.1.4.2.1.1.32";
        }

        leaf cikeTunHistOutDropPkts {
          type yang:counter32;
          units "Packets";
          description
           "The total number of packets dropped
            by this IPsec Phase-1
             IKE Tunnel during send processing.";
          smiv2:max-access "read-only";
          smiv2:oid "1.3.6.1.4.1.9.9.171.1.4.2.1.1.33";
        }

        leaf cikeTunHistOutNotifys {
          type yang:counter32;
          units "Notification Payloads";
          description
           "The total number of notifys sent by this IPsec Phase-1
            IKE Tunnel.";
          smiv2:max-access "read-only";
          smiv2:oid "1.3.6.1.4.1.9.9.171.1.4.2.1.1.34";
        }

        leaf cikeTunHistOutP2Exchgs {
          type yang:counter32;
          units "SA Payloads";
          description
           "The total number of IPsec Phase-2 exchanges sent by
            this IPsec Phase-1 IKE Tunnel.";
          smiv2:max-access "read-only";
          smiv2:oid "1.3.6.1.4.1.9.9.171.1.4.2.1.1.35";
        }

        leaf cikeTunHistOutP2ExchgInvalids {
          type yang:counter32;
          units "SA Payloads";
          description
           "The total number of IPsec Phase-2 exchanges sent and
            found to be invalid by this IPsec Phase-1 IKE Tunnel.";
          smiv2:max-access "read-only";
          smiv2:oid "1.3.6.1.4.1.9.9.171.1.4.2.1.1.36";
        }

        leaf cikeTunHistOutP2ExchgRejects {
          type yang:counter32;
          units "SA Payloads";
          description
           "The total number of IPsec Phase-2 exchanges sent and
            rejected by this IPsec Phase-1 IKE Tunnel.";
          smiv2:max-access "read-only";
          smiv2:oid "1.3.6.1.4.1.9.9.171.1.4.2.1.1.37";
        }

        leaf cikeTunHistOutP2SaDelRequests {
          type yang:counter32;
          units "Notification Payloads";
          description
           "The total number of IPsec Phase-2 security association
            delete requests sent by this IPsec Phase-1 IKE Tunnel.";
          smiv2:max-access "read-only";
          smiv2:oid "1.3.6.1.4.1.9.9.171.1.4.2.1.1.38";
        }
      }
    }

    container cipSecTunnelHistTable {
      description
       "The IPsec Phase-2 Tunnel History Table.
        This table is implemented as a sliding 
        window in which only the
        last n entries are maintained.  The maximum number 
        of entries
        is specified by the cipSecHistTableSize object.";
      smiv2:oid "1.3.6.1.4.1.9.9.171.1.4.3.1";

      list cipSecTunnelHistEntry {
        key "cipSecTunHistIndex";
        description
         "Each entry contains the attributes associated with
          a previously active IPsec Phase-2 Tunnel.";
        smiv2:oid "1.3.6.1.4.1.9.9.171.1.4.3.1.1";

        leaf cipSecTunHistIndex {
          type int32 {
            range "1..2147483647";
          }
          description
           "The index of the IPsec Phase-2 Tunnel History Table.
            The value of the index is a number which 
            begins at one and is incremented with each tunnel 
            that ends. The value
            of this object will wrap at 2,147,483,647.";
          smiv2:max-access "not-accessible";
          smiv2:oid "1.3.6.1.4.1.9.9.171.1.4.3.1.1.1";
        }

        leaf cipSecTunHistTermReason {
          type enumeration {
            enum "other" {
              value "1";
            }
            enum "normal" {
              value "2";
            }
            enum "operRequest" {
              value "3";
            }
            enum "peerDelRequest" {
              value "4";
            }
            enum "peerLost" {
              value "5";
            }
            enum "seqNumRollOver" {
              value "6";
            }
            enum "checkPointReq" {
              value "7";
            }
          }
          description
           "The reason the IPsec Phase-2 Tunnel was terminated.
            Possible reasons include:
            1 = other
            2 = normal termination
            3 = operator request
            4 = peer delete request was received
            5 = contact with peer was lost
            6 = local failure occurred
            7 = operator initiated check point request";
          smiv2:max-access "read-only";
          smiv2:oid "1.3.6.1.4.1.9.9.171.1.4.3.1.1.2";
        }

        leaf cipSecTunHistActiveIndex {
          type int32 {
            range "1..2147483647";
          }
          description
           "The index of the previously active
            IPsec Phase-2 Tunnel.";
          smiv2:max-access "read-only";
          smiv2:oid "1.3.6.1.4.1.9.9.171.1.4.3.1.1.3";
        }

        leaf cipSecTunHistIkeTunnelIndex {
          type int32 {
            range "1..2147483647";
          }
          description
           "The index of the associated IPsec Phase-1 Tunnel
            (cikeTunIndex in the cikeTunnelTable).";
          smiv2:max-access "read-only";
          smiv2:oid "1.3.6.1.4.1.9.9.171.1.4.3.1.1.4";
        }

        leaf cipSecTunHistLocalAddr {
          type CISCO-IPSEC-FLOW-MONITOR-MIB:IPSIpAddress;
          description
           "The IP address of the local endpoint for the IPsec
            Phase-2 Tunnel.";
          smiv2:max-access "read-only";
          smiv2:oid "1.3.6.1.4.1.9.9.171.1.4.3.1.1.5";
        }

        leaf cipSecTunHistRemoteAddr {
          type CISCO-IPSEC-FLOW-MONITOR-MIB:IPSIpAddress;
          description
           "The IP address of the remote endpoint for the IPsec
            Phase-2 Tunnel.";
          smiv2:max-access "read-only";
          smiv2:oid "1.3.6.1.4.1.9.9.171.1.4.3.1.1.6";
        }

        leaf cipSecTunHistKeyType {
          type CISCO-IPSEC-FLOW-MONITOR-MIB:KeyType;
          description
           "The type of key used by the IPsec Phase-2 Tunnel.";
          smiv2:max-access "read-only";
          smiv2:oid "1.3.6.1.4.1.9.9.171.1.4.3.1.1.7";
        }

        leaf cipSecTunHistEncapMode {
          type CISCO-IPSEC-FLOW-MONITOR-MIB:EncapMode;
          description
           "The encapsulation mode used by the
            IPsec Phase-2 Tunnel.";
          smiv2:max-access "read-only";
          smiv2:oid "1.3.6.1.4.1.9.9.171.1.4.3.1.1.8";
        }

        leaf cipSecTunHistLifeSize {
          type int32 {
            range "1..2147483647";
          }
          units "KBytes";
          description
           "The negotiated LifeSize of the IPsec Phase-2 Tunnel in
            kilobytes.";
          smiv2:max-access "read-only";
          smiv2:oid "1.3.6.1.4.1.9.9.171.1.4.3.1.1.9";
        }

        leaf cipSecTunHistLifeTime {
          type int32 {
            range "1..2147483647";
          }
          units "Seconds";
          description
           "The negotiated LifeTime of the IPsec Phase-2 Tunnel in
            seconds.";
          smiv2:max-access "read-only";
          smiv2:oid "1.3.6.1.4.1.9.9.171.1.4.3.1.1.10";
        }

        leaf cipSecTunHistStartTime {
          type yang:timestamp;
          description
           "The value of sysUpTime in hundredths of seconds
            when the IPsec Phase-2 Tunnel was started.";
          smiv2:max-access "read-only";
          smiv2:oid "1.3.6.1.4.1.9.9.171.1.4.3.1.1.11";
        }

        leaf cipSecTunHistActiveTime {
          type snmpv2-tc:TimeInterval;
          description
           "The length of time the IPsec Phase-2 Tunnel has been
            active in hundredths of seconds.";
          smiv2:max-access "read-only";
          smiv2:oid "1.3.6.1.4.1.9.9.171.1.4.3.1.1.12";
        }

        leaf cipSecTunHistTotalRefreshes {
          type yang:counter32;
          units "QM Exchanges";
          description
           "The total number of security association refreshes
            performed.";
          smiv2:max-access "read-only";
          smiv2:oid "1.3.6.1.4.1.9.9.171.1.4.3.1.1.13";
        }

        leaf cipSecTunHistTotalSas {
          type yang:counter32;
          units "SAs";
          description
           "The total number of security associations used
            during the
             life of the IPsec Phase-2 Tunnel.";
          smiv2:max-access "read-only";
          smiv2:oid "1.3.6.1.4.1.9.9.171.1.4.3.1.1.14";
        }

        leaf cipSecTunHistInSaDiffHellmanGrp {
          type CISCO-IPSEC-FLOW-MONITOR-MIB:DiffHellmanGrp;
          description
           "The Diffie Hellman Group used by the inbound security
            association of the IPsec Phase-2 Tunnel.";
          smiv2:max-access "read-only";
          smiv2:oid "1.3.6.1.4.1.9.9.171.1.4.3.1.1.15";
        }

        leaf cipSecTunHistInSaEncryptAlgo {
          type CISCO-IPSEC-FLOW-MONITOR-MIB:EncryptAlgo;
          description
           "The encryption algorithm used by the inbound security
            association of the IPsec Phase-2 Tunnel.";
          smiv2:max-access "read-only";
          smiv2:oid "1.3.6.1.4.1.9.9.171.1.4.3.1.1.16";
        }

        leaf cipSecTunHistInSaAhAuthAlgo {
          type CISCO-IPSEC-FLOW-MONITOR-MIB:AuthAlgo;
          description
           "The authentication algorithm used by the inbound
            authentication header (AH) security association of
            the IPsec Phase-2 Tunnel.";
          smiv2:max-access "read-only";
          smiv2:oid "1.3.6.1.4.1.9.9.171.1.4.3.1.1.17";
        }

        leaf cipSecTunHistInSaEspAuthAlgo {
          type CISCO-IPSEC-FLOW-MONITOR-MIB:AuthAlgo;
          description
           "The authentication algorithm used by the inbound
            encapsulation security protocol (ESP) 
            security association of
            the IPsec Phase-2 Tunnel.";
          smiv2:max-access "read-only";
          smiv2:oid "1.3.6.1.4.1.9.9.171.1.4.3.1.1.18";
        }

        leaf cipSecTunHistInSaDecompAlgo {
          type CISCO-IPSEC-FLOW-MONITOR-MIB:CompAlgo;
          description
           "The decompression algorithm used by the inbound
            security association of the IPsec Phase-2 Tunnel.";
          smiv2:max-access "read-only";
          smiv2:oid "1.3.6.1.4.1.9.9.171.1.4.3.1.1.19";
        }

        leaf cipSecTunHistOutSaDiffHellmanGrp {
          type CISCO-IPSEC-FLOW-MONITOR-MIB:DiffHellmanGrp;
          description
           "The Diffie Hellman Group used by the outbound security
            association of the IPsec Phase-2 Tunnel.";
          smiv2:max-access "read-only";
          smiv2:oid "1.3.6.1.4.1.9.9.171.1.4.3.1.1.20";
        }

        leaf cipSecTunHistOutSaEncryptAlgo {
          type CISCO-IPSEC-FLOW-MONITOR-MIB:EncryptAlgo;
          description
           "The encryption algorithm used by the outbound security
            association of the IPsec Phase-2 Tunnel.";
          smiv2:max-access "read-only";
          smiv2:oid "1.3.6.1.4.1.9.9.171.1.4.3.1.1.21";
        }

        leaf cipSecTunHistOutSaAhAuthAlgo {
          type CISCO-IPSEC-FLOW-MONITOR-MIB:AuthAlgo;
          description
           "The authentication algorithm used by the outbound
            authentication header (AH) security association of
            the IPsec Phase-2 Tunnel.";
          smiv2:max-access "read-only";
          smiv2:oid "1.3.6.1.4.1.9.9.171.1.4.3.1.1.22";
        }

        leaf cipSecTunHistOutSaEspAuthAlgo {
          type CISCO-IPSEC-FLOW-MONITOR-MIB:AuthAlgo;
          description
           "The authentication algorithm used by the inbound
            encapsulation security protocol (ESP) 
            security association of the IPsec Phase-2 Tunnel.";
          smiv2:max-access "read-only";
          smiv2:oid "1.3.6.1.4.1.9.9.171.1.4.3.1.1.23";
        }

        leaf cipSecTunHistOutSaCompAlgo {
          type CISCO-IPSEC-FLOW-MONITOR-MIB:CompAlgo;
          description
           "The compression algorithm used by the inbound
            security association of the IPsec Phase-2 Tunnel.";
          smiv2:max-access "read-only";
          smiv2:oid "1.3.6.1.4.1.9.9.171.1.4.3.1.1.24";
        }

        leaf cipSecTunHistInOctets {
          type yang:counter32;
          units "Octets";
          description
           "The total number of octets received by this IPsec
            Phase-2 Tunnel.  This value is accumulated
            BEFORE determining whether or not the packet should 
            be decompressed.  See also cipSecTunInOctWraps for 
            the number of times this counter has wrapped.";
          smiv2:max-access "read-only";
          smiv2:oid "1.3.6.1.4.1.9.9.171.1.4.3.1.1.25";
        }

        leaf cipSecTunHistHcInOctets {
          type yang:counter64;
          description
           "A high capacity count of the total number of octets
            received by this IPsec Phase-2 Tunnel.  This value is
            accumulated BEFORE determining whether or not 
            the packet should be decompressed.";
          smiv2:max-access "read-only";
          smiv2:oid "1.3.6.1.4.1.9.9.171.1.4.3.1.1.26";
        }

        leaf cipSecTunHistInOctWraps {
          type yang:counter32;
          units "Integral units";
          description
           "The number of times the octets received counter
            (cipSecTunInOctets) has wrapped.";
          smiv2:max-access "read-only";
          smiv2:oid "1.3.6.1.4.1.9.9.171.1.4.3.1.1.27";
        }

        leaf cipSecTunHistInDecompOctets {
          type yang:counter32;
          units "Octets";
          description
           "The total number of decompressed octets received by this
            IPsec Phase-2 Tunnel.  This value is accumulated AFTER
            the packet is decompressed. If compression is not being
            used, this value will match the value of cipSecTunHistInOctets.
            See also cipSecTunInDecompOctWraps for the number of times
            this counter has wrapped.";
          smiv2:max-access "read-only";
          smiv2:oid "1.3.6.1.4.1.9.9.171.1.4.3.1.1.28";
        }

        leaf cipSecTunHistHcInDecompOctets {
          type yang:counter64;
          description
           "A high capacity count of the total number of decompressed
            octets received by this IPsec Phase-2 Tunnel.  This value
            is accumulated AFTER the packet is decompressed. If
            compression is not being used, this value will match the
            value of cipSecTunHistHcInOctets.";
          smiv2:max-access "read-only";
          smiv2:oid "1.3.6.1.4.1.9.9.171.1.4.3.1.1.29";
        }

        leaf cipSecTunHistInDecompOctWraps {
          type yang:counter32;
          units "Integral units";
          description
           "The number of times the decompressed octets
            received counter (cipSecTunInDecompOctets) has wrapped.";
          smiv2:max-access "read-only";
          smiv2:oid "1.3.6.1.4.1.9.9.171.1.4.3.1.1.30";
        }

        leaf cipSecTunHistInPkts {
          type yang:counter32;
          units "Packets";
          description
           "The total number of packets received by this
            IPsec Phase-2 Tunnel.";
          smiv2:max-access "read-only";
          smiv2:oid "1.3.6.1.4.1.9.9.171.1.4.3.1.1.31";
        }

        leaf cipSecTunHistInDropPkts {
          type yang:counter32;
          units "Packets";
          description
           "The total number of packets dropped during
            receive processing by this IPsec Phase-2 Tunnel. 
            This count does NOT include packets
             dropped due to Anti-Replay processing.";
          smiv2:max-access "read-only";
          smiv2:oid "1.3.6.1.4.1.9.9.171.1.4.3.1.1.32";
        }

        leaf cipSecTunHistInReplayDropPkts {
          type yang:counter32;
          units "Packets";
          description
           "The total number of packets dropped during
            receive processing due to Anti-Replay processing 
            by this IPsec Phase-2 Tunnel.";
          smiv2:max-access "read-only";
          smiv2:oid "1.3.6.1.4.1.9.9.171.1.4.3.1.1.33";
        }

        leaf cipSecTunHistInAuths {
          type yang:counter32;
          units "Events";
          description
           "The total number of inbound authentication's
            performed
             by this IPsec Phase-2 Tunnel.";
          smiv2:max-access "read-only";
          smiv2:oid "1.3.6.1.4.1.9.9.171.1.4.3.1.1.34";
        }

        leaf cipSecTunHistInAuthFails {
          type yang:counter32;
          units "Failures";
          description
           "The total number of inbound authentication's
            which ended in
             failure by this IPsec Phase-2 Tunnel .";
          smiv2:max-access "read-only";
          smiv2:oid "1.3.6.1.4.1.9.9.171.1.4.3.1.1.35";
        }

        leaf cipSecTunHistInDecrypts {
          type yang:counter32;
          units "Packets";
          description
           "The total number of inbound decryption's performed
            by this IPsec Phase-2 Tunnel.";
          smiv2:max-access "read-only";
          smiv2:oid "1.3.6.1.4.1.9.9.171.1.4.3.1.1.36";
        }

        leaf cipSecTunHistInDecryptFails {
          type yang:counter32;
          units "Failures";
          description
           "The total number of inbound decryption's
            which ended in failure
             by this IPsec Phase-2 Tunnel.";
          smiv2:max-access "read-only";
          smiv2:oid "1.3.6.1.4.1.9.9.171.1.4.3.1.1.37";
        }

        leaf cipSecTunHistOutOctets {
          type yang:counter32;
          units "Octets";
          description
           "The total number of octets sent by this IPsec
            Phase-2 Tunnel.  This value is accumulated
            AFTER determining whether or not the 
            packet should be
            compressed.  See also cipSecTunOutOctWraps for the
            number of times this counter has wrapped.";
          smiv2:max-access "read-only";
          smiv2:oid "1.3.6.1.4.1.9.9.171.1.4.3.1.1.38";
        }

        leaf cipSecTunHistHcOutOctets {
          type yang:counter64;
          description
           "A high capacity count of the total number of octets
            sent by this IPsec Phase-2 Tunnel.  This value 
            is accumulated AFTER determining whether or not 
            the packet should be
            compressed.";
          smiv2:max-access "read-only";
          smiv2:oid "1.3.6.1.4.1.9.9.171.1.4.3.1.1.39";
        }

        leaf cipSecTunHistOutOctWraps {
          type yang:counter32;
          units "Integral units";
          description
           "The number of times the octets sent counter
            (cipSecTunOutOctets) has wrapped.";
          smiv2:max-access "read-only";
          smiv2:oid "1.3.6.1.4.1.9.9.171.1.4.3.1.1.40";
        }

        leaf cipSecTunHistOutUncompOctets {
          type yang:counter32;
          units "Octets";
          description
           "The total number of uncompressed octets sent by this
            IPsec Phase-2 Tunnel.  This value is accumulated BEFORE
            the packet is compressed. If compression is not being
            used, this value will match the value of 
            cipSecTunHistOutOctets.  See also 
            cipSecTunOutDecompOctWraps for the number of times
            this counter has wrapped.";
          smiv2:max-access "read-only";
          smiv2:oid "1.3.6.1.4.1.9.9.171.1.4.3.1.1.41";
        }

        leaf cipSecTunHistHcOutUncompOctets {
          type yang:counter64;
          units "Octets";
          description
           "A high capacity count of the total
            number of uncompressed octets sent by this 
            IPsec Phase-2 Tunnel.  This value is accumulated 
            BEFORE the packet is compressed. If compression
            is not being used, this value will match the value of
            cipSecTunHistHcOutOctets.";
          smiv2:max-access "read-only";
          smiv2:oid "1.3.6.1.4.1.9.9.171.1.4.3.1.1.42";
        }

        leaf cipSecTunHistOutUncompOctWraps {
          type yang:counter32;
          units "Integral units";
          description
           "The number of times the uncompressed octets sent counter
            (cipSecTunOutUncompOctets) has wrapped.";
          smiv2:max-access "read-only";
          smiv2:oid "1.3.6.1.4.1.9.9.171.1.4.3.1.1.43";
        }

        leaf cipSecTunHistOutPkts {
          type yang:counter32;
          units "Packets";
          description
           "The total number of packets sent by this
            IPsec Phase-2 Tunnel.";
          smiv2:max-access "read-only";
          smiv2:oid "1.3.6.1.4.1.9.9.171.1.4.3.1.1.44";
        }

        leaf cipSecTunHistOutDropPkts {
          type yang:counter32;
          units "Packets";
          description
           "The total number of packets dropped
            during send processing
             by this IPsec Phase-2 Tunnel.";
          smiv2:max-access "read-only";
          smiv2:oid "1.3.6.1.4.1.9.9.171.1.4.3.1.1.45";
        }

        leaf cipSecTunHistOutAuths {
          type yang:counter32;
          units "Events";
          description
           "The total number of outbound authentication's performed
            by this IPsec Phase-2 Tunnel.";
          smiv2:max-access "read-only";
          smiv2:oid "1.3.6.1.4.1.9.9.171.1.4.3.1.1.46";
        }

        leaf cipSecTunHistOutAuthFails {
          type yang:counter32;
          units "Failures";
          description
           "The total number of outbound authentication's
            which ended in
             failure by this IPsec Phase-2 Tunnel.";
          smiv2:max-access "read-only";
          smiv2:oid "1.3.6.1.4.1.9.9.171.1.4.3.1.1.47";
        }

        leaf cipSecTunHistOutEncrypts {
          type yang:counter32;
          units "Packets";
          description
           "The total number of outbound encryption's performed
            by this IPsec Phase-2 Tunnel.";
          smiv2:max-access "read-only";
          smiv2:oid "1.3.6.1.4.1.9.9.171.1.4.3.1.1.48";
        }

        leaf cipSecTunHistOutEncryptFails {
          type yang:counter32;
          units "Failures";
          description
           "The total number of outbound encryption's
            which ended in failure
             by this IPsec Phase-2 Tunnel.";
          smiv2:max-access "read-only";
          smiv2:oid "1.3.6.1.4.1.9.9.171.1.4.3.1.1.49";
        }
      }
    }

    container cipSecEndPtHistTable {
      description
       "The IPsec Phase-2 Tunnel Endpoint History Table.
        This table is implemented as a 
        sliding window in which only the
        last n entries are maintained.  
        The maximum number of entries
        is specified by the cipSecHistTableSize object.";
      smiv2:oid "1.3.6.1.4.1.9.9.171.1.4.3.2";

      list cipSecEndPtHistEntry {
        key "cipSecEndPtHistIndex";
        description
         "Each entry contains the attributes associated with
          a previously active IPsec Phase-2 Tunnel Endpoint.";
        smiv2:oid "1.3.6.1.4.1.9.9.171.1.4.3.2.1";

        leaf cipSecEndPtHistIndex {
          type int32 {
            range "1..2147483647";
          }
          description
           "The number of the previously active
            Endpoint associated
             with a IPsec Phase-2 Tunnel Table.  The value 
             of this index is a number which begins at 
             one and is incremented with each Endpoint 
             associated with an IPsec Phase-2 Tunnel.
             The value of this object will wrap at 2,147,483,647.";
          smiv2:max-access "not-accessible";
          smiv2:oid "1.3.6.1.4.1.9.9.171.1.4.3.2.1.1";
        }

        leaf cipSecEndPtHistTunIndex {
          type int32 {
            range "1..2147483647";
          }
          description
           "The index  of the previously active IPsec
            Phase-2 Tunnel Table.";
          smiv2:max-access "read-only";
          smiv2:oid "1.3.6.1.4.1.9.9.171.1.4.3.2.1.2";
        }

        leaf cipSecEndPtHistActiveIndex {
          type int32 {
            range "1..2147483647";
          }
          description
           "The index  of the previously active Endpoint.";
          smiv2:max-access "read-only";
          smiv2:oid "1.3.6.1.4.1.9.9.171.1.4.3.2.1.3";
        }

        leaf cipSecEndPtHistLocalName {
          type snmpv2-tc:DisplayString;
          description
           "The DNS name of the local Endpoint.";
          smiv2:max-access "read-only";
          smiv2:oid "1.3.6.1.4.1.9.9.171.1.4.3.2.1.4";
        }

        leaf cipSecEndPtHistLocalType {
          type CISCO-IPSEC-FLOW-MONITOR-MIB:EndPtType;
          description
           "The type of identity for the local Endpoint.
            Possible values are:
            1) a single IP address, or
            2) an IP address range, or
            3) an IP subnet.";
          smiv2:max-access "read-only";
          smiv2:oid "1.3.6.1.4.1.9.9.171.1.4.3.2.1.5";
        }

        leaf cipSecEndPtHistLocalAddr1 {
          type CISCO-IPSEC-FLOW-MONITOR-MIB:IPSIpAddress;
          description
           "The local Endpoint's first IP address specification.
            
            If the local Endpoint type is single IP address, 
            then this is the value of the IP address.
            
            If the local Endpoint type is IP subnet, then this
            is the value of the subnet.
            
            If the local Endpoint type is IP address range, 
            then this is the value of beginning IP address of 
            the range.";
          smiv2:max-access "read-only";
          smiv2:oid "1.3.6.1.4.1.9.9.171.1.4.3.2.1.6";
        }

        leaf cipSecEndPtHistLocalAddr2 {
          type CISCO-IPSEC-FLOW-MONITOR-MIB:IPSIpAddress;
          description
           "The local Endpoint's second IP address specification.
            
            If the local Endpoint type is single IP address, 
            then this is the value of the IP address.
            
            If the local Endpoint type is IP subnet, then this
            is the value of the subnet mask.
            
            If the local Endpoint type is IP address range, 
            then this
            is the value of ending IP address of the range.";
          smiv2:max-access "read-only";
          smiv2:oid "1.3.6.1.4.1.9.9.171.1.4.3.2.1.7";
        }

        leaf cipSecEndPtHistLocalProtocol {
          type int32 {
            range "0..255";
          }
          description
           "The protocol number of the local Endpoint's traffic.";
          smiv2:max-access "read-only";
          smiv2:oid "1.3.6.1.4.1.9.9.171.1.4.3.2.1.8";
        }

        leaf cipSecEndPtHistLocalPort {
          type int32 {
            range "0..65535";
          }
          description
           "The port number of the local Endpoint's traffic.";
          smiv2:max-access "read-only";
          smiv2:oid "1.3.6.1.4.1.9.9.171.1.4.3.2.1.9";
        }

        leaf cipSecEndPtHistRemoteName {
          type snmpv2-tc:DisplayString;
          description
           "The DNS name of the remote Endpoint.";
          smiv2:max-access "read-only";
          smiv2:oid "1.3.6.1.4.1.9.9.171.1.4.3.2.1.10";
        }

        leaf cipSecEndPtHistRemoteType {
          type CISCO-IPSEC-FLOW-MONITOR-MIB:EndPtType;
          description
           "The type of identity for the remote Endpoint.
            Possible values are:
            1) a single IP address, or
            2) an IP address range, or
            3) an IP subnet.";
          smiv2:max-access "read-only";
          smiv2:oid "1.3.6.1.4.1.9.9.171.1.4.3.2.1.11";
        }

        leaf cipSecEndPtHistRemoteAddr1 {
          type CISCO-IPSEC-FLOW-MONITOR-MIB:IPSIpAddress;
          description
           "The remote Endpoint's first IP address specification.
            
            If the remote Endpoint type is single IP address, 
            then this
            is the value of the IP address.
            
            If the remote Endpoint type is IP subnet, then this
            is the value of the subnet.
            
            If the remote Endpoint type is IP address range, 
            then this
            is the value of beginning IP address of the range.";
          smiv2:max-access "read-only";
          smiv2:oid "1.3.6.1.4.1.9.9.171.1.4.3.2.1.12";
        }

        leaf cipSecEndPtHistRemoteAddr2 {
          type CISCO-IPSEC-FLOW-MONITOR-MIB:IPSIpAddress;
          description
           "The remote Endpoint's second IP address specification.
            
            If the remote Endpoint type is single IP address, 
            then this
            is the value of the IP address.
            
            If the remote Endpoint type is IP subnet, then this
            is the value of the subnet mask.
            
            If the remote Endpoint type is IP address range, 
            then this
            is the value of ending IP address of the range.";
          smiv2:max-access "read-only";
          smiv2:oid "1.3.6.1.4.1.9.9.171.1.4.3.2.1.13";
        }

        leaf cipSecEndPtHistRemoteProtocol {
          type int32 {
            range "0..255";
          }
          description
           "The protocol number of the remote Endpoint's traffic.";
          smiv2:max-access "read-only";
          smiv2:oid "1.3.6.1.4.1.9.9.171.1.4.3.2.1.14";
        }

        leaf cipSecEndPtHistRemotePort {
          type int32 {
            range "0..65535";
          }
          description
           "The port number of the remote Endpoint's traffic.";
          smiv2:max-access "read-only";
          smiv2:oid "1.3.6.1.4.1.9.9.171.1.4.3.2.1.15";
        }
      }
    }

    container cikeFailTable {
      description
       "The IPsec Phase-1 Failure Table.
        This table is implemented as a sliding 
        window in which only the last n entries are 
        maintained.  The maximum number of entries
        is specified by the cipSecFailTableSize object.";
      smiv2:oid "1.3.6.1.4.1.9.9.171.1.5.2.1";

      list cikeFailEntry {
        key "cikeFailIndex";
        description
         "Each entry contains the attributes associated
          with
           an IPsec Phase-1 failure.";
        smiv2:oid "1.3.6.1.4.1.9.9.171.1.5.2.1.1";

        leaf cikeFailIndex {
          type int32 {
            range "1..2147483647";
          }
          description
           "The IPsec Phase-1 Failure Table index.
            The value of the index is a number which 
            begins at one and is incremented with each 
            IPsec Phase-1 failure. The value
            of this object will wrap at 2,147,483,647.";
          smiv2:max-access "not-accessible";
          smiv2:oid "1.3.6.1.4.1.9.9.171.1.5.2.1.1.1";
        }

        leaf cikeFailReason {
          type enumeration {
            enum "other" {
              value "1";
            }
            enum "peerDelRequest" {
              value "2";
            }
            enum "peerLost" {
              value "3";
            }
            enum "localFailure" {
              value "4";
            }
            enum "authFailure" {
              value "5";
            }
            enum "hashValidation" {
              value "6";
            }
            enum "encryptFailure" {
              value "7";
            }
            enum "internalError" {
              value "8";
            }
            enum "sysCapExceeded" {
              value "9";
            }
            enum "proposalFailure" {
              value "10";
            }
            enum "peerCertUnavailable" {
              value "11";
            }
            enum "peerCertNotValid" {
              value "12";
            }
            enum "localCertExpired" {
              value "13";
            }
            enum "crlFailure" {
              value "14";
            }
            enum "peerEncodingError" {
              value "15";
            }
            enum "nonExistentSa" {
              value "16";
            }
            enum "operRequest" {
              value "17";
            }
          }
          description
           "The reason for the failure.  Possible reasons include:
            1 = other
            2 = peer delete request was received
            3 = contact with peer was lost
            4 = local failure occurred
            5 = authentication failure
            6 = hash validation failure
            7 = encryption failure
            8 = internal error occurred
            9 = system capacity failure
            10 = proposal failure
            11 = peer's certificate is unavailable
            12 = peer's certificate was found invalid
            13 = local certificate expired
            14 = certificate revoke list (crl) failure
            15 = peer encoding error
            16 = non-existent security association
            17 = operator requested termination.";
          smiv2:max-access "read-only";
          smiv2:oid "1.3.6.1.4.1.9.9.171.1.5.2.1.1.2";
        }

        leaf cikeFailTime {
          type yang:timestamp;
          description
           "The value of sysUpTime in hundredths of seconds
            at the time of the failure.";
          smiv2:max-access "read-only";
          smiv2:oid "1.3.6.1.4.1.9.9.171.1.5.2.1.1.3";
        }

        leaf cikeFailLocalType {
          type CISCO-IPSEC-FLOW-MONITOR-MIB:IkePeerType;
          description
           "The type of local peer identity.  The local peer
            may be identified by:
             1. an IP address, or
             2. a host name.";
          smiv2:max-access "read-only";
          smiv2:oid "1.3.6.1.4.1.9.9.171.1.5.2.1.1.4";
        }

        leaf cikeFailLocalValue {
          type snmpv2-tc:DisplayString;
          description
           "The value of the local peer identity.
            
            If the local peer type is an IP Address, then this
            is the IP Address used to identify the local peer.
            
            If the local peer type is a host name, then this is
            the host name used to identify the local peer.";
          smiv2:max-access "read-only";
          smiv2:oid "1.3.6.1.4.1.9.9.171.1.5.2.1.1.5";
        }

        leaf cikeFailRemoteType {
          type CISCO-IPSEC-FLOW-MONITOR-MIB:IkePeerType;
          description
           "The type of remote peer identity.  The remote
            peer may be identified by:
             1. an IP address, or
             2. a host name.";
          smiv2:max-access "read-only";
          smiv2:oid "1.3.6.1.4.1.9.9.171.1.5.2.1.1.6";
        }

        leaf cikeFailRemoteValue {
          type snmpv2-tc:DisplayString;
          description
           "The value of the remote peer identity.
            
            If the remote peer type is an IP Address, then this
            is the IP Address used to identify the remote peer.
            
            If the remote peer type is a host name, then this is
            the host name used to identify the remote peer.";
          smiv2:max-access "read-only";
          smiv2:oid "1.3.6.1.4.1.9.9.171.1.5.2.1.1.7";
        }

        leaf cikeFailLocalAddr {
          type CISCO-IPSEC-FLOW-MONITOR-MIB:IPSIpAddress;
          description
           "The IP address of the local peer.";
          smiv2:max-access "read-only";
          smiv2:oid "1.3.6.1.4.1.9.9.171.1.5.2.1.1.8";
        }

        leaf cikeFailRemoteAddr {
          type CISCO-IPSEC-FLOW-MONITOR-MIB:IPSIpAddress;
          description
           "The IP address of the remote peer.";
          smiv2:max-access "read-only";
          smiv2:oid "1.3.6.1.4.1.9.9.171.1.5.2.1.1.9";
        }
      }
    }

    container cipSecFailTable {
      description
       "The IPsec Phase-2 Failure Table.
        This table is implemented as a sliding window 
        in which only the last n entries are maintained.  
        The maximum number of entries
        is specified by the cipSecFailTableSize object.";
      smiv2:oid "1.3.6.1.4.1.9.9.171.1.5.3.1";

      list cipSecFailEntry {
        key "cipSecFailIndex";
        description
         "Each entry contains the attributes associated with
          an IPsec Phase-1 failure.";
        smiv2:oid "1.3.6.1.4.1.9.9.171.1.5.3.1.1";

        leaf cipSecFailIndex {
          type int32 {
            range "1..2147483647";
          }
          description
           "The IPsec Phase-2 Failure Table index.
            The value of the index is a number which 
            begins at one and is incremented with each 
            IPsec Phase-1 failure. The value
            of this object will wrap at 2,147,483,647.";
          smiv2:max-access "not-accessible";
          smiv2:oid "1.3.6.1.4.1.9.9.171.1.5.3.1.1.1";
        }

        leaf cipSecFailReason {
          type enumeration {
            enum "other" {
              value "1";
            }
            enum "internalError" {
              value "2";
            }
            enum "peerEncodingError" {
              value "3";
            }
            enum "proposalFailure" {
              value "4";
            }
            enum "protocolUseFail" {
              value "5";
            }
            enum "nonExistentSa" {
              value "6";
            }
            enum "decryptFailure" {
              value "7";
            }
            enum "encryptFailure" {
              value "8";
            }
            enum "inAuthFailure" {
              value "9";
            }
            enum "outAuthFailure" {
              value "10";
            }
            enum "compression" {
              value "11";
            }
            enum "sysCapExceeded" {
              value "12";
            }
            enum "peerDelRequest" {
              value "13";
            }
            enum "peerLost" {
              value "14";
            }
            enum "seqNumRollOver" {
              value "15";
            }
            enum "operRequest" {
              value "16";
            }
          }
          description
           "The reason for the failure.  Possible reasons
            include:
              1 = other
              2 = internal error occurred
              3 = peer encoding error
              4 = proposal failure
              5 = protocol use failure
              6 = non-existent security association
              7 = decryption failure
              8 = encryption failure
              9 = inbound authentication failure
             10 = outbound authentication failure
             11 = compression failure
             12 = system capacity failure
             13 = peer delete request was received
             14 = contact with peer was lost
             15 = sequence number rolled over
             16 = operator requested termination.";
          smiv2:max-access "read-only";
          smiv2:oid "1.3.6.1.4.1.9.9.171.1.5.3.1.1.2";
        }

        leaf cipSecFailTime {
          type yang:timestamp;
          description
           "The value of sysUpTime in hundredths of seconds
            at the time of the failure.";
          smiv2:max-access "read-only";
          smiv2:oid "1.3.6.1.4.1.9.9.171.1.5.3.1.1.3";
        }

        leaf cipSecFailTunnelIndex {
          type int32 {
            range "1..2147483647";
          }
          description
           "The Phase-2 Tunnel index (cipSecTunIndex).";
          smiv2:max-access "read-only";
          smiv2:oid "1.3.6.1.4.1.9.9.171.1.5.3.1.1.4";
        }

        leaf cipSecFailSaSpi {
          type int32 {
            range "0..2147483647";
          }
          description
           "The security association SPI value.";
          smiv2:max-access "read-only";
          smiv2:oid "1.3.6.1.4.1.9.9.171.1.5.3.1.1.5";
        }

        leaf cipSecFailPktSrcAddr {
          type CISCO-IPSEC-FLOW-MONITOR-MIB:IPSIpAddress;
          description
           "The packet's source IP address.";
          smiv2:max-access "read-only";
          smiv2:oid "1.3.6.1.4.1.9.9.171.1.5.3.1.1.6";
        }

        leaf cipSecFailPktDstAddr {
          type CISCO-IPSEC-FLOW-MONITOR-MIB:IPSIpAddress;
          description
           "The packet's destination IP address.";
          smiv2:max-access "read-only";
          smiv2:oid "1.3.6.1.4.1.9.9.171.1.5.3.1.1.7";
        }
      }
    }
  }

  notification cikeTunnelStart {
    description
     "This notification is generated when an IPsec Phase-1
      IKE Tunnel becomes active.";
    smiv2:oid "1.3.6.1.4.1.9.9.171.2.0.1";

    container object-1 {

      leaf cikePeerLocalType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalType";
        }
      }

      leaf cikePeerLocalValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalValue";
        }
      }

      leaf cikePeerRemoteType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteType";
        }
      }

      leaf cikePeerRemoteValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteValue";
        }
      }

      leaf cikePeerIntIndex {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerIntIndex";
        }
      }

      leaf cikePeerLocalAddr {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalAddr";
        }
      }
    }

    container object-2 {

      leaf cikePeerLocalType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalType";
        }
      }

      leaf cikePeerLocalValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalValue";
        }
      }

      leaf cikePeerRemoteType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteType";
        }
      }

      leaf cikePeerRemoteValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteValue";
        }
      }

      leaf cikePeerIntIndex {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerIntIndex";
        }
      }

      leaf cikePeerRemoteAddr {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteAddr";
        }
      }
    }

    container object-3 {

      leaf cikeTunIndex {
        type leafref {
          path "/CISCO-IPSEC-FLOW-MONITOR-MIB:CISCO-IPSEC-FLOW-MONITOR-MIB/CISCO-IPSEC-FLOW-MONITOR-MIB:cikeTunnelTable/CISCO-IPSEC-FLOW-MONITOR-MIB:cikeTunnelEntry/CISCO-IPSEC-FLOW-MONITOR-MIB:cikeTunIndex";
        }
      }

      leaf cikeTunLifeTime {
        type leafref {
          path "/CISCO-IPSEC-FLOW-MONITOR-MIB:CISCO-IPSEC-FLOW-MONITOR-MIB/CISCO-IPSEC-FLOW-MONITOR-MIB:cikeTunnelTable/CISCO-IPSEC-FLOW-MONITOR-MIB:cikeTunnelEntry/CISCO-IPSEC-FLOW-MONITOR-MIB:cikeTunLifeTime";
        }
      }
    }
  }

  notification cikeTunnelStop {
    description
     "This notification is generated when an IPsec Phase-1
      IKE Tunnel becomes inactive.";
    smiv2:oid "1.3.6.1.4.1.9.9.171.2.0.2";

    container object-1 {

      leaf cikePeerLocalType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalType";
        }
      }

      leaf cikePeerLocalValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalValue";
        }
      }

      leaf cikePeerRemoteType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteType";
        }
      }

      leaf cikePeerRemoteValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteValue";
        }
      }

      leaf cikePeerIntIndex {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerIntIndex";
        }
      }

      leaf cikePeerLocalAddr {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalAddr";
        }
      }
    }

    container object-2 {

      leaf cikePeerLocalType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalType";
        }
      }

      leaf cikePeerLocalValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalValue";
        }
      }

      leaf cikePeerRemoteType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteType";
        }
      }

      leaf cikePeerRemoteValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteValue";
        }
      }

      leaf cikePeerIntIndex {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerIntIndex";
        }
      }

      leaf cikePeerRemoteAddr {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteAddr";
        }
      }
    }

    container object-3 {

      leaf cikeTunIndex {
        type leafref {
          path "/CISCO-IPSEC-FLOW-MONITOR-MIB:CISCO-IPSEC-FLOW-MONITOR-MIB/CISCO-IPSEC-FLOW-MONITOR-MIB:cikeTunnelTable/CISCO-IPSEC-FLOW-MONITOR-MIB:cikeTunnelEntry/CISCO-IPSEC-FLOW-MONITOR-MIB:cikeTunIndex";
        }
      }

      leaf cikeTunActiveTime {
        type leafref {
          path "/CISCO-IPSEC-FLOW-MONITOR-MIB:CISCO-IPSEC-FLOW-MONITOR-MIB/CISCO-IPSEC-FLOW-MONITOR-MIB:cikeTunnelTable/CISCO-IPSEC-FLOW-MONITOR-MIB:cikeTunnelEntry/CISCO-IPSEC-FLOW-MONITOR-MIB:cikeTunActiveTime";
        }
      }
    }
  }

  notification cikeSysFailure {
    description
     "This notification is generated when the processing for
      an IPsec Phase-1 IKE Tunnel experiences an internal
      or system capacity error.";
    smiv2:oid "1.3.6.1.4.1.9.9.171.2.0.3";

    container object-1 {

      leaf cikePeerLocalType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalType";
        }
      }

      leaf cikePeerLocalValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalValue";
        }
      }

      leaf cikePeerRemoteType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteType";
        }
      }

      leaf cikePeerRemoteValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteValue";
        }
      }

      leaf cikePeerIntIndex {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerIntIndex";
        }
      }

      leaf cikePeerLocalAddr {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalAddr";
        }
      }
    }

    container object-2 {

      leaf cikePeerLocalType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalType";
        }
      }

      leaf cikePeerLocalValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalValue";
        }
      }

      leaf cikePeerRemoteType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteType";
        }
      }

      leaf cikePeerRemoteValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteValue";
        }
      }

      leaf cikePeerIntIndex {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerIntIndex";
        }
      }

      leaf cikePeerRemoteAddr {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteAddr";
        }
      }
    }
  }

  notification cikeCertCrlFailure {
    description
     "This notification is generated when the processing for
      an IPsec Phase-1 IKE Tunnel experiences a Certificate
      or a Certificate Revoke List (CRL) related error.";
    smiv2:oid "1.3.6.1.4.1.9.9.171.2.0.4";

    container object-1 {

      leaf cikePeerLocalType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalType";
        }
      }

      leaf cikePeerLocalValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalValue";
        }
      }

      leaf cikePeerRemoteType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteType";
        }
      }

      leaf cikePeerRemoteValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteValue";
        }
      }

      leaf cikePeerIntIndex {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerIntIndex";
        }
      }

      leaf cikePeerLocalAddr {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalAddr";
        }
      }
    }

    container object-2 {

      leaf cikePeerLocalType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalType";
        }
      }

      leaf cikePeerLocalValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalValue";
        }
      }

      leaf cikePeerRemoteType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteType";
        }
      }

      leaf cikePeerRemoteValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteValue";
        }
      }

      leaf cikePeerIntIndex {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerIntIndex";
        }
      }

      leaf cikePeerRemoteAddr {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteAddr";
        }
      }
    }
  }

  notification cikeProtocolFailure {
    description
     "This notification is generated when the processing for
      an IPsec Phase-1 IKE Tunnel experiences a protocol
      related error.";
    smiv2:oid "1.3.6.1.4.1.9.9.171.2.0.5";

    container object-1 {

      leaf cikePeerLocalType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalType";
        }
      }

      leaf cikePeerLocalValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalValue";
        }
      }

      leaf cikePeerRemoteType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteType";
        }
      }

      leaf cikePeerRemoteValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteValue";
        }
      }

      leaf cikePeerIntIndex {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerIntIndex";
        }
      }

      leaf cikePeerLocalAddr {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalAddr";
        }
      }
    }

    container object-2 {

      leaf cikePeerLocalType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalType";
        }
      }

      leaf cikePeerLocalValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalValue";
        }
      }

      leaf cikePeerRemoteType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteType";
        }
      }

      leaf cikePeerRemoteValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteValue";
        }
      }

      leaf cikePeerIntIndex {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerIntIndex";
        }
      }

      leaf cikePeerRemoteAddr {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteAddr";
        }
      }
    }
  }

  notification cikeNoSa {
    description
     "This notification is generated when the processing for
      an IPsec Phase-1 IKE Tunnel experiences a non-existent
      security association error.";
    smiv2:oid "1.3.6.1.4.1.9.9.171.2.0.6";

    container object-1 {

      leaf cikePeerLocalType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalType";
        }
      }

      leaf cikePeerLocalValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalValue";
        }
      }

      leaf cikePeerRemoteType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteType";
        }
      }

      leaf cikePeerRemoteValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteValue";
        }
      }

      leaf cikePeerIntIndex {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerIntIndex";
        }
      }

      leaf cikePeerLocalAddr {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalAddr";
        }
      }
    }

    container object-2 {

      leaf cikePeerLocalType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalType";
        }
      }

      leaf cikePeerLocalValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalValue";
        }
      }

      leaf cikePeerRemoteType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteType";
        }
      }

      leaf cikePeerRemoteValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteValue";
        }
      }

      leaf cikePeerIntIndex {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerIntIndex";
        }
      }

      leaf cikePeerRemoteAddr {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteAddr";
        }
      }
    }
  }

  notification cipSecTunnelStart {
    description
     "This notification is generated when an IPsec Phase-2
      Tunnel becomes active.";
    smiv2:oid "1.3.6.1.4.1.9.9.171.2.0.7";

    container object-1 {

      leaf cipSecTunIndex {
        type leafref {
          path "/CISCO-IPSEC-FLOW-MONITOR-MIB:CISCO-IPSEC-FLOW-MONITOR-MIB/CISCO-IPSEC-FLOW-MONITOR-MIB:cipSecTunnelTable/CISCO-IPSEC-FLOW-MONITOR-MIB:cipSecTunnelEntry/CISCO-IPSEC-FLOW-MONITOR-MIB:cipSecTunIndex";
        }
      }

      leaf cipSecTunLifeTime {
        type leafref {
          path "/CISCO-IPSEC-FLOW-MONITOR-MIB:CISCO-IPSEC-FLOW-MONITOR-MIB/CISCO-IPSEC-FLOW-MONITOR-MIB:cipSecTunnelTable/CISCO-IPSEC-FLOW-MONITOR-MIB:cipSecTunnelEntry/CISCO-IPSEC-FLOW-MONITOR-MIB:cipSecTunLifeTime";
        }
      }
    }

    container object-2 {

      leaf cipSecTunIndex {
        type leafref {
          path "/CISCO-IPSEC-FLOW-MONITOR-MIB:CISCO-IPSEC-FLOW-MONITOR-MIB/CISCO-IPSEC-FLOW-MONITOR-MIB:cipSecTunnelTable/CISCO-IPSEC-FLOW-MONITOR-MIB:cipSecTunnelEntry/CISCO-IPSEC-FLOW-MONITOR-MIB:cipSecTunIndex";
        }
      }

      leaf cipSecTunLifeSize {
        type leafref {
          path "/CISCO-IPSEC-FLOW-MONITOR-MIB:CISCO-IPSEC-FLOW-MONITOR-MIB/CISCO-IPSEC-FLOW-MONITOR-MIB:cipSecTunnelTable/CISCO-IPSEC-FLOW-MONITOR-MIB:cipSecTunnelEntry/CISCO-IPSEC-FLOW-MONITOR-MIB:cipSecTunLifeSize";
        }
      }
    }
  }

  notification cipSecTunnelStop {
    description
     "This notification is generated when an IPsec Phase-2
      Tunnel becomes inactive.";
    smiv2:oid "1.3.6.1.4.1.9.9.171.2.0.8";

    container object-1 {

      leaf cipSecTunIndex {
        type leafref {
          path "/CISCO-IPSEC-FLOW-MONITOR-MIB:CISCO-IPSEC-FLOW-MONITOR-MIB/CISCO-IPSEC-FLOW-MONITOR-MIB:cipSecTunnelTable/CISCO-IPSEC-FLOW-MONITOR-MIB:cipSecTunnelEntry/CISCO-IPSEC-FLOW-MONITOR-MIB:cipSecTunIndex";
        }
      }

      leaf cipSecTunActiveTime {
        type leafref {
          path "/CISCO-IPSEC-FLOW-MONITOR-MIB:CISCO-IPSEC-FLOW-MONITOR-MIB/CISCO-IPSEC-FLOW-MONITOR-MIB:cipSecTunnelTable/CISCO-IPSEC-FLOW-MONITOR-MIB:cipSecTunnelEntry/CISCO-IPSEC-FLOW-MONITOR-MIB:cipSecTunActiveTime";
        }
      }
    }
  }

  notification cipSecSysFailure {
    description
     "This notification is generated when the processing for
      an IPsec Phase-2 Tunnel experiences an internal
      or system capacity error.";
    smiv2:oid "1.3.6.1.4.1.9.9.171.2.0.9";

    container object-1 {

      leaf cikePeerLocalType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalType";
        }
      }

      leaf cikePeerLocalValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalValue";
        }
      }

      leaf cikePeerRemoteType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteType";
        }
      }

      leaf cikePeerRemoteValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteValue";
        }
      }

      leaf cikePeerIntIndex {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerIntIndex";
        }
      }

      leaf cikePeerLocalAddr {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalAddr";
        }
      }
    }

    container object-2 {

      leaf cikePeerLocalType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalType";
        }
      }

      leaf cikePeerLocalValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalValue";
        }
      }

      leaf cikePeerRemoteType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteType";
        }
      }

      leaf cikePeerRemoteValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteValue";
        }
      }

      leaf cikePeerIntIndex {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerIntIndex";
        }
      }

      leaf cikePeerRemoteAddr {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteAddr";
        }
      }
    }

    container object-3 {

      leaf cipSecTunIndex {
        type leafref {
          path "/CISCO-IPSEC-FLOW-MONITOR-MIB:CISCO-IPSEC-FLOW-MONITOR-MIB/CISCO-IPSEC-FLOW-MONITOR-MIB:cipSecTunnelTable/CISCO-IPSEC-FLOW-MONITOR-MIB:cipSecTunnelEntry/CISCO-IPSEC-FLOW-MONITOR-MIB:cipSecTunIndex";
        }
      }

      leaf cipSecTunActiveTime {
        type leafref {
          path "/CISCO-IPSEC-FLOW-MONITOR-MIB:CISCO-IPSEC-FLOW-MONITOR-MIB/CISCO-IPSEC-FLOW-MONITOR-MIB:cipSecTunnelTable/CISCO-IPSEC-FLOW-MONITOR-MIB:cipSecTunnelEntry/CISCO-IPSEC-FLOW-MONITOR-MIB:cipSecTunActiveTime";
        }
      }
    }

    container object-4 {

      leaf cipSecTunIndex {
        type leafref {
          path "/CISCO-IPSEC-FLOW-MONITOR-MIB:CISCO-IPSEC-FLOW-MONITOR-MIB/CISCO-IPSEC-FLOW-MONITOR-MIB:cipSecTunnelTable/CISCO-IPSEC-FLOW-MONITOR-MIB:cipSecTunnelEntry/CISCO-IPSEC-FLOW-MONITOR-MIB:cipSecTunIndex";
        }
      }

      leaf cipSecSpiIndex {
        type leafref {
          path "/CISCO-IPSEC-FLOW-MONITOR-MIB:CISCO-IPSEC-FLOW-MONITOR-MIB/CISCO-IPSEC-FLOW-MONITOR-MIB:cipSecSpiTable/CISCO-IPSEC-FLOW-MONITOR-MIB:cipSecSpiEntry/CISCO-IPSEC-FLOW-MONITOR-MIB:cipSecSpiIndex";
        }
      }

      leaf cipSecSpiProtocol {
        type leafref {
          path "/CISCO-IPSEC-FLOW-MONITOR-MIB:CISCO-IPSEC-FLOW-MONITOR-MIB/CISCO-IPSEC-FLOW-MONITOR-MIB:cipSecSpiTable/CISCO-IPSEC-FLOW-MONITOR-MIB:cipSecSpiEntry/CISCO-IPSEC-FLOW-MONITOR-MIB:cipSecSpiProtocol";
        }
      }
    }
  }

  notification cipSecSetUpFailure {
    description
     "This notification is generated when the setup for
      an IPsec Phase-2 Tunnel fails.";
    smiv2:oid "1.3.6.1.4.1.9.9.171.2.0.10";

    container object-1 {

      leaf cikePeerLocalType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalType";
        }
      }

      leaf cikePeerLocalValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalValue";
        }
      }

      leaf cikePeerRemoteType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteType";
        }
      }

      leaf cikePeerRemoteValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteValue";
        }
      }

      leaf cikePeerIntIndex {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerIntIndex";
        }
      }

      leaf cikePeerLocalAddr {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalAddr";
        }
      }
    }

    container object-2 {

      leaf cikePeerLocalType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalType";
        }
      }

      leaf cikePeerLocalValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerLocalValue";
        }
      }

      leaf cikePeerRemoteType {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteType";
        }
      }

      leaf cikePeerRemoteValue {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteValue";
        }
      }

      leaf cikePeerIntIndex {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerIntIndex";
        }
      }

      leaf cikePeerRemoteAddr {
        type leafref {
          path "/CISCO-IPSEC-FLOW-MONITOR-MIB:CISCO-IPSEC-FLOW-MONITOR-MIB/CISCO-IPSEC-FLOW-MONITOR-MIB:cikePeerTable/CISCO-IPSEC-FLOW-MONITOR-MIB:cikePeerEntry/CISCO-IPSEC-FLOW-MONITOR-MIB:cikePeerRemoteAddr";
        }
      }
    }
  }

  notification cipSecEarlyTunTerm {
    description
     "This notification is generated when an an IPsec Phase-2
      Tunnel is terminated earily or before expected.";
    smiv2:oid "1.3.6.1.4.1.9.9.171.2.0.11";

    container object-1 {

      leaf cipSecTunIndex {
        type leafref {
          path "/CISCO-IPSEC-FLOW-MONITOR-MIB:CISCO-IPSEC-FLOW-MONITOR-MIB/CISCO-IPSEC-FLOW-MONITOR-MIB:cipSecTunnelTable/CISCO-IPSEC-FLOW-MONITOR-MIB:cipSecTunnelEntry/CISCO-IPSEC-FLOW-MONITOR-MIB:cipSecTunIndex";
        }
      }

      leaf cipSecTunActiveTime {
        type leafref {
          path "/CISCO-IPSEC-FLOW-MONITOR-MIB:CISCO-IPSEC-FLOW-MONITOR-MIB/CISCO-IPSEC-FLOW-MONITOR-MIB:cipSecTunnelTable/CISCO-IPSEC-FLOW-MONITOR-MIB:cipSecTunnelEntry/CISCO-IPSEC-FLOW-MONITOR-MIB:cipSecTunActiveTime";
        }
      }
    }

    container object-2 {

      leaf cipSecTunIndex {
        type leafref {
          path "/CISCO-IPSEC-FLOW-MONITOR-MIB:CISCO-IPSEC-FLOW-MONITOR-MIB/CISCO-IPSEC-FLOW-MONITOR-MIB:cipSecTunnelTable/CISCO-IPSEC-FLOW-MONITOR-MIB:cipSecTunnelEntry/CISCO-IPSEC-FLOW-MONITOR-MIB:cipSecTunIndex";
        }
      }

      leaf cipSecSpiIndex {
        type leafref {
          path "/CISCO-IPSEC-FLOW-MONITOR-MIB:CISCO-IPSEC-FLOW-MONITOR-MIB/CISCO-IPSEC-FLOW-MONITOR-MIB:cipSecSpiTable/CISCO-IPSEC-FLOW-MONITOR-MIB:cipSecSpiEntry/CISCO-IPSEC-FLOW-MONITOR-MIB:cipSecSpiIndex";
        }
      }

      leaf cipSecSpiProtocol {
        type leafref {
          path "/CISCO-IPSEC-FLOW-MONITOR-MIB:CISCO-IPSEC-FLOW-MONITOR-MIB/CISCO-IPSEC-FLOW-MONITOR-MIB:cipSecSpiTable/CISCO-IPSEC-FLOW-MONITOR-MIB:cipSecSpiEntry/CISCO-IPSEC-FLOW-MONITOR-MIB:cipSecSpiProtocol";
        }
      }
    }
  }

  notification cipSecProtocolFailure {
    description
     "This notification is generated when the processing for
      an IPsec Phase-2 Tunnel experiences a protocol
      related error.";
    smiv2:oid "1.3.6.1.4.1.9.9.171.2.0.12";

    container object-1 {

      leaf cipSecTunIndex {
        type leafref {
          path "/CISCO-IPSEC-FLOW-MONITOR-MIB:CISCO-IPSEC-FLOW-MONITOR-MIB/CISCO-IPSEC-FLOW-MONITOR-MIB:cipSecTunnelTable/CISCO-IPSEC-FLOW-MONITOR-MIB:cipSecTunnelEntry/CISCO-IPSEC-FLOW-MONITOR-MIB:cipSecTunIndex";
        }
      }

      leaf cipSecTunActiveTime {
        type leafref {
          path "/CISCO-IPSEC-FLOW-MONITOR-MIB:CISCO-IPSEC-FLOW-MONITOR-MIB/CISCO-IPSEC-FLOW-MONITOR-MIB:cipSecTunnelTable/CISCO-IPSEC-FLOW-MONITOR-MIB:cipSecTunnelEntry/CISCO-IPSEC-FLOW-MONITOR-MIB:cipSecTunActiveTime";
        }
      }
    }

    container object-2 {

      leaf cipSecTunIndex {
        type leafref {
          path "/CISCO-IPSEC-FLOW-MONITOR-MIB:CISCO-IPSEC-FLOW-MONITOR-MIB/CISCO-IPSEC-FLOW-MONITOR-MIB:cipSecTunnelTable/CISCO-IPSEC-FLOW-MONITOR-MIB:cipSecTunnelEntry/CISCO-IPSEC-FLOW-MONITOR-MIB:cipSecTunIndex";
        }
      }

      leaf cipSecSpiIndex {
        type leafref {
          path "/CISCO-IPSEC-FLOW-MONITOR-MIB:CISCO-IPSEC-FLOW-MONITOR-MIB/CISCO-IPSEC-FLOW-MONITOR-MIB:cipSecSpiTable/CISCO-IPSEC-FLOW-MONITOR-MIB:cipSecSpiEntry/CISCO-IPSEC-FLOW-MONITOR-MIB:cipSecSpiIndex";
        }
      }

      leaf cipSecSpiProtocol {
        type leafref {
          path "/CISCO-IPSEC-FLOW-MONITOR-MIB:CISCO-IPSEC-FLOW-MONITOR-MIB/CISCO-IPSEC-FLOW-MONITOR-MIB:cipSecSpiTable/CISCO-IPSEC-FLOW-MONITOR-MIB:cipSecSpiEntry/CISCO-IPSEC-FLOW-MONITOR-MIB:cipSecSpiProtocol";
        }
      }
    }
  }

  notification cipSecNoSa {
    description
     "This notification is generated when the processing for
      an IPsec Phase-2 Tunnel experiences a non-existent
      security association error.";
    smiv2:oid "1.3.6.1.4.1.9.9.171.2.0.13";
  }

  smiv2:alias "ciscoIpSecFlowMonitorMIB" {
    smiv2:oid "1.3.6.1.4.1.9.9.171";
  }

  smiv2:alias "cipSecMIBObjects" {
    smiv2:oid "1.3.6.1.4.1.9.9.171.1";
  }

  smiv2:alias "cipSecLevels" {
    smiv2:oid "1.3.6.1.4.1.9.9.171.1.1";
  }

  smiv2:alias "cipSecPhaseOne" {
    smiv2:oid "1.3.6.1.4.1.9.9.171.1.2";
  }

  smiv2:alias "cikeGlobalStats" {
    smiv2:oid "1.3.6.1.4.1.9.9.171.1.2.1";
  }

  smiv2:alias "cipSecPhaseTwo" {
    smiv2:oid "1.3.6.1.4.1.9.9.171.1.3";
  }

  smiv2:alias "cipSecGlobalStats" {
    smiv2:oid "1.3.6.1.4.1.9.9.171.1.3.1";
  }

  smiv2:alias "cipSecHistory" {
    smiv2:oid "1.3.6.1.4.1.9.9.171.1.4";
  }

  smiv2:alias "cipSecHistGlobal" {
    smiv2:oid "1.3.6.1.4.1.9.9.171.1.4.1";
  }

  smiv2:alias "cipSecHistGlobalCntl" {
    smiv2:oid "1.3.6.1.4.1.9.9.171.1.4.1.1";
  }

  smiv2:alias "cipSecHistPhaseOne" {
    smiv2:oid "1.3.6.1.4.1.9.9.171.1.4.2";
  }

  smiv2:alias "cipSecHistPhaseTwo" {
    smiv2:oid "1.3.6.1.4.1.9.9.171.1.4.3";
  }

  smiv2:alias "cipSecFailures" {
    smiv2:oid "1.3.6.1.4.1.9.9.171.1.5";
  }

  smiv2:alias "cipSecFailGlobal" {
    smiv2:oid "1.3.6.1.4.1.9.9.171.1.5.1";
  }

  smiv2:alias "cipSecFailGlobalCntl" {
    smiv2:oid "1.3.6.1.4.1.9.9.171.1.5.1.1";
  }

  smiv2:alias "cipSecFailPhaseOne" {
    smiv2:oid "1.3.6.1.4.1.9.9.171.1.5.2";
  }

  smiv2:alias "cipSecFailPhaseTwo" {
    smiv2:oid "1.3.6.1.4.1.9.9.171.1.5.3";
  }

  smiv2:alias "cipSecTrapCntl" {
    smiv2:oid "1.3.6.1.4.1.9.9.171.1.6";
  }

  smiv2:alias "cipSecMIBNotificationPrefix" {
    smiv2:oid "1.3.6.1.4.1.9.9.171.2";
  }

  smiv2:alias "cipSecMIBNotifications" {
    smiv2:oid "1.3.6.1.4.1.9.9.171.2.0";
  }

  smiv2:alias "cipSecMIBConformance" {
    smiv2:oid "1.3.6.1.4.1.9.9.171.3";
  }

  smiv2:alias "cipSecMIBGroups" {
    smiv2:oid "1.3.6.1.4.1.9.9.171.3.1";
  }

  smiv2:alias "cipSecMIBCompliances" {
    smiv2:oid "1.3.6.1.4.1.9.9.171.3.2";
  }

}
