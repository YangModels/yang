/*
 * Generated by confdc --mib2yang-std
 * Source: mgmt/dmi/model/common/mib-source/CISCO-ENVMON-MIB.mib
 */
/*
 * This YANG module has been generated by smidump 0.5.0:
 *
 *      smidump -f yang CISCO-ENVMON-MIB
 *
 * Do not edit. Edit the source file instead!
 */

module CISCO-ENVMON-MIB {

  namespace "urn:ietf:params:xml:ns:yang:smiv2:CISCO-ENVMON-MIB";
  prefix CISCO-ENVMON-MIB;

  import SNMPv2-TC {
    prefix "snmpv2-tc";
  }

  import ietf-yang-smiv2 {
    prefix "smiv2";
  }

  import ietf-yang-types {
    prefix "yang";
  }

  organization
   "Cisco Systems, Inc.";

  contact
   "       Cisco Systems
    Customer Service
    
    Postal: 170 W Tasman Drive
    San Jose, CA  95134
    USA
    
    Tel: +1 800 553-NETS
    
    E-mail: cs-snmp@cisco.com";

  description
   "The MIB module to describe the status of the Environmental
    Monitor on those devices which support one.";

  revision 2003-12-01 {
    description
     "Added c37xx (13) and other (14) as values for 
      ciscoEnvMonPresent";
  }

  revision 2003-11-25 {
    description
     "Added ciscoEnvMonMIBMiscNotifGroup.";
  }

  revision 2002-10-15 {
    description
     "Added c7600(12) as values for ciscoEnvMonPresent";
  }

  revision 2002-07-17 {
    description
     "Added optional groups ciscoEnvMonEnableStatChangeGroup
      and ciscoEnvMonStatChangeNotifGroup.";
  }

  revision 2002-02-04 {
    description
     "Added osr7600(11) as values 
      for ciscoEnvMonPresent";
  }

  revision 2001-08-30 {
    description
     "Added c10000(10) as values for ciscoEnvMonPresent";
  }

  revision 2001-08-16 {
    description
     "Added cat4000(9) as values for ciscoEnvMonPresent";
  }

  revision 2001-05-07 {
    description
     "Added cat6000(7),ubr7200(8) 
      as values for ciscoEnvMonPresent";
  }

  revision 2000-01-31 {
    description
     "Add notFunctioning to CiscoEnvMonState.";
  }

  revision 1998-10-22 {
    description
     "Renamed enumerated value internalRPS(5) as 
      internalRedundant(5) and added description for
      ciscoEnvMonSupplySource enumerated values.";
  }

  revision 1998-08-05 {
    description
     "Add enumerated value internalRPS(5) to 
      ciscoEnvMonSupplySource.";
  }

  revision 1996-11-12 {
    description
     "Add monitoring support for c3600 series router";
  }

  revision 1995-08-15 {
    description
     "Specify a correct (non-negative) range for several
      index objects.";
  }

  revision 1995-03-13 {
    description
     "Miscellaneous changes including monitoring support
      for c7000 series redundant power supplies.";
  }

  typedef CiscoEnvMonState {
    type enumeration {
      enum "normal" {
        value "1";
      }
      enum "warning" {
        value "2";
      }
      enum "critical" {
        value "3";
      }
      enum "shutdown" {
        value "4";
      }
      enum "notPresent" {
        value "5";
      }
      enum "notFunctioning" {
        value "6";
      }
    }
    description
     "Represents the state of a device being monitored.
      Valid values are:
      
      normal(1):         the environment is good, such as low
                         temperature.
      
      warning(2):        the environment is bad, such as temperature
                         above normal operation range but not too
                         high.
      
      critical(3):       the environment is very bad, such as
                         temperature much higher than normal
                         operation limit.
      
      shutdown(4):       the environment is the worst, the system
                         should be shutdown immediately.
      
      notPresent(5):     the environmental monitor is not present,
                         such as temperature sensors do not exist.
      
      notFunctioning(6): the environmental monitor does not 
                         function properly, such as a temperature
                         sensor generates a abnormal data like
                         1000 C.";
  }

  typedef CiscoSignedGauge {
    type int32;
    description
     "Represents the current value of an entity, as a signed 
      integer.";
  }


  container CISCO-ENVMON-MIB {
    config false;

    container ciscoEnvMonObjects {
      smiv2:oid "1.3.6.1.4.1.9.9.13.1";

      leaf ciscoEnvMonPresent {
        type enumeration {
          enum "oldAgs" {
            value "1";
          }
          enum "ags" {
            value "2";
          }
          enum "c7000" {
            value "3";
          }
          enum "ci" {
            value "4";
          }
          enum "cAccessMon" {
            value "6";
          }
          enum "cat6000" {
            value "7";
          }
          enum "ubr7200" {
            value "8";
          }
          enum "cat4000" {
            value "9";
          }
          enum "c10000" {
            value "10";
          }
          enum "osr7600" {
            value "11";
          }
          enum "c7600" {
            value "12";
          }
          enum "c37xx" {
            value "13";
          }
          enum "other" {
            value "14";
          }
        }
        description
         "The type of environmental monitor located in the chassis.
          An oldAgs environmental monitor card is identical to an ags
          environmental card except that it is not capable of supplying
          data, and hence no instance of the remaining objects in this
          MIB will be returned in response to an SNMP query.  Note that
          only a firmware upgrade is required to convert an oldAgs into
          an ags card.";
        smiv2:max-access "read-only";
        smiv2:oid "1.3.6.1.4.1.9.9.13.1.1";
      }

      leaf ciscoEnvMonAlarmContacts {
        type bits {
          bit minorVisual {
            position "0";
          }
          bit majorVisual {
            position "1";
          }
          bit criticalVisual {
            position "2";
          }
          bit minorAudible {
            position "3";
          }
          bit majorAudible {
            position "4";
          }
          bit criticalAudible {
            position "5";
          }
          bit input {
            position "6";
          }
        }
        description
         "Each bit is set to reflect the respective
          alarm being set.  The bit will be cleared
          when the respective alarm is cleared.";
        smiv2:max-access "read-only";
        smiv2:oid "1.3.6.1.4.1.9.9.13.1.6";
      }
    }

    container ciscoEnvMonMIBNotificationEnables {
      smiv2:oid "1.3.6.1.4.1.9.9.13.2";

      leaf ciscoEnvMonEnableShutdownNotification {
        type boolean;
        description
         "This variable  indicates  whether  the  system
          produces the ciscoEnvMonShutdownNotification.  A false 
          value will prevent shutdown notifications 
          from being generated by this system.";
        smiv2:defval "false";
        smiv2:max-access "read-write";
        smiv2:oid "1.3.6.1.4.1.9.9.13.2.1";
      }

      leaf ciscoEnvMonEnableVoltageNotification {
        type boolean;
        status deprecated;
        description
         "This variable  indicates  whether  the  system
          produces the ciscoEnvMonVoltageNotification. A false 
          value will prevent voltage notifications from being 
          generated by this system. This object is deprecated
          in favour of ciscoEnvMonEnableStatChangeNotif.";
        smiv2:defval "false";
        smiv2:max-access "read-write";
        smiv2:oid "1.3.6.1.4.1.9.9.13.2.2";
      }

      leaf ciscoEnvMonEnableTemperatureNotification {
        type boolean;
        status deprecated;
        description
         "This variable  indicates  whether  the  system
          produces the ciscoEnvMonTemperatureNotification.
          A false value prevents temperature notifications 
          from being sent by  this entity. This object is 
          deprecated in favour of 
          ciscoEnvMonEnableStatChangeNotif.";
        smiv2:defval "false";
        smiv2:max-access "read-write";
        smiv2:oid "1.3.6.1.4.1.9.9.13.2.3";
      }

      leaf ciscoEnvMonEnableFanNotification {
        type boolean;
        status deprecated;
        description
         "This variable  indicates  whether  the  system
          produces the ciscoEnvMonFanNotification.
          A false value prevents fan notifications 
          from being sent by  this entity. This object is 
          deprecated in favour of 
          ciscoEnvMonEnableStatChangeNotif.";
        smiv2:defval "false";
        smiv2:max-access "read-write";
        smiv2:oid "1.3.6.1.4.1.9.9.13.2.4";
      }

      leaf ciscoEnvMonEnableRedundantSupplyNotification {
        type boolean;
        status deprecated;
        description
         "This variable  indicates  whether  the  system
          produces the ciscoEnvMonRedundantSupplyNotification. 
          A false value prevents redundant supply notifications
          from being generated by this system. This object is
          deprecated in favour of 
          ciscoEnvMonEnableStatChangeNotif.";
        smiv2:defval "false";
        smiv2:max-access "read-write";
        smiv2:oid "1.3.6.1.4.1.9.9.13.2.5";
      }

      leaf ciscoEnvMonEnableStatChangeNotif {
        type boolean;
        description
         "This variable indicates whether the system
          produces the ciscoEnvMonVoltStatusChangeNotif,
          ciscoEnvMonTempStatusChangeNotif, 
          ciscoEnvMonFanStatusChangeNotif and  
          ciscoEnvMonSuppStatusChangeNotif. A false value will 
          prevent these notifications from being generated by 
          this system.";
        smiv2:defval "false";
        smiv2:max-access "read-write";
        smiv2:oid "1.3.6.1.4.1.9.9.13.2.6";
      }
    }

    container ciscoEnvMonVoltageStatusTable {
      description
       "The table of voltage status maintained by the environmental
        monitor.";
      smiv2:oid "1.3.6.1.4.1.9.9.13.1.2";

      list ciscoEnvMonVoltageStatusEntry {
        key "ciscoEnvMonVoltageStatusIndex";
        description
         "An entry in the voltage status table, representing the status
          of the associated testpoint maintained by the environmental
          monitor.";
        smiv2:oid "1.3.6.1.4.1.9.9.13.1.2.1";

        leaf ciscoEnvMonVoltageStatusIndex {
          type int32 {
            range "0..2147483647";
          }
          description
           "Unique index for the testpoint being instrumented.
            This index is for SNMP purposes only, and has no
            intrinsic meaning.";
          smiv2:max-access "not-accessible";
          smiv2:oid "1.3.6.1.4.1.9.9.13.1.2.1.1";
        }

        leaf ciscoEnvMonVoltageStatusDescr {
          type snmpv2-tc:DisplayString {
            length "0..32";
          }
          description
           "Textual description of the testpoint being instrumented.
            This description is a short textual label, suitable as a
            human-sensible identification for the rest of the
            information in the entry.";
          smiv2:max-access "read-only";
          smiv2:oid "1.3.6.1.4.1.9.9.13.1.2.1.2";
        }

        leaf ciscoEnvMonVoltageStatusValue {
          type CISCO-ENVMON-MIB:CiscoSignedGauge;
          units "millivolts";
          description
           "The current measurement of the testpoint being instrumented.";
          smiv2:max-access "read-only";
          smiv2:oid "1.3.6.1.4.1.9.9.13.1.2.1.3";
        }

        leaf ciscoEnvMonVoltageThresholdLow {
          type int32;
          units "millivolts";
          description
           "The lowest value that the associated instance of the object
            ciscoEnvMonVoltageStatusValue may obtain before an emergency
            shutdown of the managed device is initiated.";
          smiv2:max-access "read-only";
          smiv2:oid "1.3.6.1.4.1.9.9.13.1.2.1.4";
        }

        leaf ciscoEnvMonVoltageThresholdHigh {
          type int32;
          units "millivolts";
          description
           "The highest value that the associated instance of the object
            ciscoEnvMonVoltageStatusValue may obtain before an emergency
            shutdown of the managed device is initiated.";
          smiv2:max-access "read-only";
          smiv2:oid "1.3.6.1.4.1.9.9.13.1.2.1.5";
        }

        leaf ciscoEnvMonVoltageLastShutdown {
          type int32;
          units "millivolts";
          description
           "The value of the associated instance of the object
            ciscoEnvMonVoltageStatusValue at the time an emergency
            shutdown of the managed device was last initiated.  This
            value is stored in non-volatile RAM and hence is able to
            survive the shutdown.";
          smiv2:max-access "read-only";
          smiv2:oid "1.3.6.1.4.1.9.9.13.1.2.1.6";
        }

        leaf ciscoEnvMonVoltageState {
          type CISCO-ENVMON-MIB:CiscoEnvMonState;
          description
           "The current state of the testpoint being instrumented.";
          smiv2:max-access "read-only";
          smiv2:oid "1.3.6.1.4.1.9.9.13.1.2.1.7";
        }
      }
    }

    container ciscoEnvMonTemperatureStatusTable {
      description
       "The table of ambient temperature status maintained by the
        environmental monitor.";
      smiv2:oid "1.3.6.1.4.1.9.9.13.1.3";

      list ciscoEnvMonTemperatureStatusEntry {
        key "ciscoEnvMonTemperatureStatusIndex";
        description
         "An entry in the ambient temperature status table, representing
          the status of the associated testpoint maintained by the
          environmental monitor.";
        smiv2:oid "1.3.6.1.4.1.9.9.13.1.3.1";

        leaf ciscoEnvMonTemperatureStatusIndex {
          type int32 {
            range "0..2147483647";
          }
          description
           "Unique index for the testpoint being instrumented.
            This index is for SNMP purposes only, and has no
            intrinsic meaning.";
          smiv2:max-access "not-accessible";
          smiv2:oid "1.3.6.1.4.1.9.9.13.1.3.1.1";
        }

        leaf ciscoEnvMonTemperatureStatusDescr {
          type snmpv2-tc:DisplayString {
            length "0..32";
          }
          description
           "Textual description of the testpoint being instrumented.
            This description is a short textual label, suitable as a
            human-sensible identification for the rest of the
            information in the entry.";
          smiv2:max-access "read-only";
          smiv2:oid "1.3.6.1.4.1.9.9.13.1.3.1.2";
        }

        leaf ciscoEnvMonTemperatureStatusValue {
          type yang:gauge32;
          units "degrees Celsius";
          description
           "The current measurement of the testpoint being instrumented.";
          smiv2:max-access "read-only";
          smiv2:oid "1.3.6.1.4.1.9.9.13.1.3.1.3";
        }

        leaf ciscoEnvMonTemperatureThreshold {
          type int32;
          units "degrees Celsius";
          description
           "The highest value that the associated instance of the
            object ciscoEnvMonTemperatureStatusValue may obtain
            before an emergency shutdown of the managed device is
            initiated.";
          smiv2:max-access "read-only";
          smiv2:oid "1.3.6.1.4.1.9.9.13.1.3.1.4";
        }

        leaf ciscoEnvMonTemperatureLastShutdown {
          type int32;
          units "degrees Celsius";
          description
           "The value of the associated instance of the object
            ciscoEnvMonTemperatureStatusValue at the time an emergency
            shutdown of the managed device was last initiated.  This
            value is stored in non-volatile RAM and hence is able to
            survive the shutdown.";
          smiv2:max-access "read-only";
          smiv2:oid "1.3.6.1.4.1.9.9.13.1.3.1.5";
        }

        leaf ciscoEnvMonTemperatureState {
          type CISCO-ENVMON-MIB:CiscoEnvMonState;
          description
           "The current state of the testpoint being instrumented.";
          smiv2:max-access "read-only";
          smiv2:oid "1.3.6.1.4.1.9.9.13.1.3.1.6";
        }
      }
    }

    container ciscoEnvMonFanStatusTable {
      description
       "The table of fan status maintained by the environmental
        monitor.";
      smiv2:oid "1.3.6.1.4.1.9.9.13.1.4";

      list ciscoEnvMonFanStatusEntry {
        key "ciscoEnvMonFanStatusIndex";
        description
         "An entry in the fan status table, representing the status of
          the associated fan maintained by the environmental monitor.";
        smiv2:oid "1.3.6.1.4.1.9.9.13.1.4.1";

        leaf ciscoEnvMonFanStatusIndex {
          type int32 {
            range "0..2147483647";
          }
          description
           "Unique index for the fan being instrumented.
            This index is for SNMP purposes only, and has no
            intrinsic meaning.";
          smiv2:max-access "not-accessible";
          smiv2:oid "1.3.6.1.4.1.9.9.13.1.4.1.1";
        }

        leaf ciscoEnvMonFanStatusDescr {
          type snmpv2-tc:DisplayString {
            length "0..32";
          }
          description
           "Textual description of the fan being instrumented.
            This description is a short textual label, suitable as a
            human-sensible identification for the rest of the
            information in the entry.";
          smiv2:max-access "read-only";
          smiv2:oid "1.3.6.1.4.1.9.9.13.1.4.1.2";
        }

        leaf ciscoEnvMonFanState {
          type CISCO-ENVMON-MIB:CiscoEnvMonState;
          description
           "The current state of the fan being instrumented.";
          smiv2:max-access "read-only";
          smiv2:oid "1.3.6.1.4.1.9.9.13.1.4.1.3";
        }
      }
    }

    container ciscoEnvMonSupplyStatusTable {
      description
       "The table of power supply status maintained by the
        environmental monitor card.";
      smiv2:oid "1.3.6.1.4.1.9.9.13.1.5";

      list ciscoEnvMonSupplyStatusEntry {
        key "ciscoEnvMonSupplyStatusIndex";
        description
         "An entry in the power supply status table, representing the
          status of the associated power supply maintained by the
          environmental monitor card.";
        smiv2:oid "1.3.6.1.4.1.9.9.13.1.5.1";

        leaf ciscoEnvMonSupplyStatusIndex {
          type int32 {
            range "0..2147483647";
          }
          description
           "Unique index for the power supply being instrumented.
            This index is for SNMP purposes only, and has no
            intrinsic meaning.";
          smiv2:max-access "not-accessible";
          smiv2:oid "1.3.6.1.4.1.9.9.13.1.5.1.1";
        }

        leaf ciscoEnvMonSupplyStatusDescr {
          type snmpv2-tc:DisplayString {
            length "0..32";
          }
          description
           "Textual description of the power supply being instrumented.
            This description is a short textual label, suitable as a
            human-sensible identification for the rest of the
            information in the entry.";
          smiv2:max-access "read-only";
          smiv2:oid "1.3.6.1.4.1.9.9.13.1.5.1.2";
        }

        leaf ciscoEnvMonSupplyState {
          type CISCO-ENVMON-MIB:CiscoEnvMonState;
          description
           "The current state of the power supply being instrumented.";
          smiv2:max-access "read-only";
          smiv2:oid "1.3.6.1.4.1.9.9.13.1.5.1.3";
        }

        leaf ciscoEnvMonSupplySource {
          type enumeration {
            enum "unknown" {
              value "1";
            }
            enum "ac" {
              value "2";
            }
            enum "dc" {
              value "3";
            }
            enum "externalPowerSupply" {
              value "4";
            }
            enum "internalRedundant" {
              value "5";
            }
          }
          description
           "The power supply source.
            unknown - Power supply source unknown
            ac      - AC power supply
            dc      - DC power supply
            externalPowerSupply - External power supply
            internalRedundant - Internal redundant power supply ";
          smiv2:max-access "read-only";
          smiv2:oid "1.3.6.1.4.1.9.9.13.1.5.1.4";
        }
      }
    }
  }

  notification ciscoEnvMonShutdownNotification {
    description
     "A ciscoEnvMonShutdownNotification is sent if the environmental
      monitor detects a testpoint reaching a critical state
      and is about to initiate a shutdown.  This notification 
      contains no objects so that it may be encoded and sent in the
      shortest amount of time possible.  Even so, management
      applications should not rely on receiving such a notification
      as it may not be sent before the shutdown completes.";
    smiv2:oid "1.3.6.1.4.1.9.9.13.3.0.1";
  }

  notification ciscoEnvMonVoltageNotification {
    status deprecated;
    description
     "A ciscoEnvMonVoltageNotification is sent if the voltage 
      measured at a given testpoint is outside the normal range 
      for the testpoint (i.e. is at the warning, critical, or
      shutdown stage).  Since such a notification is usually 
      generated before the shutdown state is reached, it can 
      convey more data and has a better chance of being sent 
      than does the ciscoEnvMonShutdownNotification.
      This notification is deprecated in favour of
      ciscoEnvMonVoltStatusChangeNotif.";
    smiv2:oid "1.3.6.1.4.1.9.9.13.3.0.2";

    container object-1 {

      leaf ciscoEnvMonVoltageStatusIndex {
        type leafref {
          path "/CISCO-ENVMON-MIB:CISCO-ENVMON-MIB/CISCO-ENVMON-MIB:ciscoEnvMonVoltageStatusTable/CISCO-ENVMON-MIB:ciscoEnvMonVoltageStatusEntry/CISCO-ENVMON-MIB:ciscoEnvMonVoltageStatusIndex";
        }
      }

      leaf ciscoEnvMonVoltageStatusDescr {
        type leafref {
          path "/CISCO-ENVMON-MIB:CISCO-ENVMON-MIB/CISCO-ENVMON-MIB:ciscoEnvMonVoltageStatusTable/CISCO-ENVMON-MIB:ciscoEnvMonVoltageStatusEntry/CISCO-ENVMON-MIB:ciscoEnvMonVoltageStatusDescr";
        }
      }
    }

    container object-2 {

      leaf ciscoEnvMonVoltageStatusIndex {
        type leafref {
          path "/CISCO-ENVMON-MIB:CISCO-ENVMON-MIB/CISCO-ENVMON-MIB:ciscoEnvMonVoltageStatusTable/CISCO-ENVMON-MIB:ciscoEnvMonVoltageStatusEntry/CISCO-ENVMON-MIB:ciscoEnvMonVoltageStatusIndex";
        }
      }

      leaf ciscoEnvMonVoltageStatusValue {
        type leafref {
          path "/CISCO-ENVMON-MIB:CISCO-ENVMON-MIB/CISCO-ENVMON-MIB:ciscoEnvMonVoltageStatusTable/CISCO-ENVMON-MIB:ciscoEnvMonVoltageStatusEntry/CISCO-ENVMON-MIB:ciscoEnvMonVoltageStatusValue";
        }
      }
    }

    container object-3 {

      leaf ciscoEnvMonVoltageStatusIndex {
        type leafref {
          path "/CISCO-ENVMON-MIB:CISCO-ENVMON-MIB/CISCO-ENVMON-MIB:ciscoEnvMonVoltageStatusTable/CISCO-ENVMON-MIB:ciscoEnvMonVoltageStatusEntry/CISCO-ENVMON-MIB:ciscoEnvMonVoltageStatusIndex";
        }
      }

      leaf ciscoEnvMonVoltageState {
        type leafref {
          path "/CISCO-ENVMON-MIB:CISCO-ENVMON-MIB/CISCO-ENVMON-MIB:ciscoEnvMonVoltageStatusTable/CISCO-ENVMON-MIB:ciscoEnvMonVoltageStatusEntry/CISCO-ENVMON-MIB:ciscoEnvMonVoltageState";
        }
      }
    }
  }

  notification ciscoEnvMonTemperatureNotification {
    status deprecated;
    description
     "A ciscoEnvMonTemperatureNotification is sent if the 
      temperature measured at a given testpoint is outside 
      the normal range for the testpoint (i.e. is at the warning, 
      critical, or shutdown stage).  Since such a Notification 
      is usually generated before the shutdown state is reached,
      it can convey more data and has a better chance of being
      sent than does the ciscoEnvMonShutdownNotification.
      This notification is deprecated in favour of 
      ciscoEnvMonTempStatusChangeNotif.";
    smiv2:oid "1.3.6.1.4.1.9.9.13.3.0.3";

    container object-1 {

      leaf ciscoEnvMonTemperatureStatusIndex {
        type leafref {
          path "/CISCO-ENVMON-MIB:CISCO-ENVMON-MIB/CISCO-ENVMON-MIB:ciscoEnvMonTemperatureStatusTable/CISCO-ENVMON-MIB:ciscoEnvMonTemperatureStatusEntry/CISCO-ENVMON-MIB:ciscoEnvMonTemperatureStatusIndex";
        }
      }

      leaf ciscoEnvMonTemperatureStatusDescr {
        type leafref {
          path "/CISCO-ENVMON-MIB:CISCO-ENVMON-MIB/CISCO-ENVMON-MIB:ciscoEnvMonTemperatureStatusTable/CISCO-ENVMON-MIB:ciscoEnvMonTemperatureStatusEntry/CISCO-ENVMON-MIB:ciscoEnvMonTemperatureStatusDescr";
        }
      }
    }

    container object-2 {

      leaf ciscoEnvMonTemperatureStatusIndex {
        type leafref {
          path "/CISCO-ENVMON-MIB:CISCO-ENVMON-MIB/CISCO-ENVMON-MIB:ciscoEnvMonTemperatureStatusTable/CISCO-ENVMON-MIB:ciscoEnvMonTemperatureStatusEntry/CISCO-ENVMON-MIB:ciscoEnvMonTemperatureStatusIndex";
        }
      }

      leaf ciscoEnvMonTemperatureStatusValue {
        type leafref {
          path "/CISCO-ENVMON-MIB:CISCO-ENVMON-MIB/CISCO-ENVMON-MIB:ciscoEnvMonTemperatureStatusTable/CISCO-ENVMON-MIB:ciscoEnvMonTemperatureStatusEntry/CISCO-ENVMON-MIB:ciscoEnvMonTemperatureStatusValue";
        }
      }
    }

    container object-3 {

      leaf ciscoEnvMonTemperatureStatusIndex {
        type leafref {
          path "/CISCO-ENVMON-MIB:CISCO-ENVMON-MIB/CISCO-ENVMON-MIB:ciscoEnvMonTemperatureStatusTable/CISCO-ENVMON-MIB:ciscoEnvMonTemperatureStatusEntry/CISCO-ENVMON-MIB:ciscoEnvMonTemperatureStatusIndex";
        }
      }

      leaf ciscoEnvMonTemperatureState {
        type leafref {
          path "/CISCO-ENVMON-MIB:CISCO-ENVMON-MIB/CISCO-ENVMON-MIB:ciscoEnvMonTemperatureStatusTable/CISCO-ENVMON-MIB:ciscoEnvMonTemperatureStatusEntry/CISCO-ENVMON-MIB:ciscoEnvMonTemperatureState";
        }
      }
    }
  }

  notification ciscoEnvMonFanNotification {
    status deprecated;
    description
     "A ciscoEnvMonFanNotification is sent if any one of
      the fans in the fan array (where extant) fails. 
      Since such a notification is usually generated before 
      the shutdown state is reached, it can convey more 
      data and has a better chance of being sent
      than does the ciscoEnvMonShutdownNotification.
      This notification is deprecated in favour of
      ciscoEnvMonFanStatusChangeNotif.";
    smiv2:oid "1.3.6.1.4.1.9.9.13.3.0.4";

    container object-1 {

      leaf ciscoEnvMonFanStatusIndex {
        type leafref {
          path "/CISCO-ENVMON-MIB:CISCO-ENVMON-MIB/CISCO-ENVMON-MIB:ciscoEnvMonFanStatusTable/CISCO-ENVMON-MIB:ciscoEnvMonFanStatusEntry/CISCO-ENVMON-MIB:ciscoEnvMonFanStatusIndex";
        }
      }

      leaf ciscoEnvMonFanStatusDescr {
        type leafref {
          path "/CISCO-ENVMON-MIB:CISCO-ENVMON-MIB/CISCO-ENVMON-MIB:ciscoEnvMonFanStatusTable/CISCO-ENVMON-MIB:ciscoEnvMonFanStatusEntry/CISCO-ENVMON-MIB:ciscoEnvMonFanStatusDescr";
        }
      }
    }

    container object-2 {

      leaf ciscoEnvMonFanStatusIndex {
        type leafref {
          path "/CISCO-ENVMON-MIB:CISCO-ENVMON-MIB/CISCO-ENVMON-MIB:ciscoEnvMonFanStatusTable/CISCO-ENVMON-MIB:ciscoEnvMonFanStatusEntry/CISCO-ENVMON-MIB:ciscoEnvMonFanStatusIndex";
        }
      }

      leaf ciscoEnvMonFanState {
        type leafref {
          path "/CISCO-ENVMON-MIB:CISCO-ENVMON-MIB/CISCO-ENVMON-MIB:ciscoEnvMonFanStatusTable/CISCO-ENVMON-MIB:ciscoEnvMonFanStatusEntry/CISCO-ENVMON-MIB:ciscoEnvMonFanState";
        }
      }
    }
  }

  notification ciscoEnvMonRedundantSupplyNotification {
    status deprecated;
    description
     "A ciscoEnvMonRedundantSupplyNotification is sent if
      the redundant power supply (where extant) fails. 
      Since such a notification is usually generated before 
      the shutdown state is reached, it can convey more 
      data and has a better chance of being sent
      than does the ciscoEnvMonShutdownNotification.
      This notification is deprecated in favour of 
      ciscoEnvMonSuppStatusChangeNotif.";
    smiv2:oid "1.3.6.1.4.1.9.9.13.3.0.5";

    container object-1 {

      leaf ciscoEnvMonSupplyStatusIndex {
        type leafref {
          path "/CISCO-ENVMON-MIB:CISCO-ENVMON-MIB/CISCO-ENVMON-MIB:ciscoEnvMonSupplyStatusTable/CISCO-ENVMON-MIB:ciscoEnvMonSupplyStatusEntry/CISCO-ENVMON-MIB:ciscoEnvMonSupplyStatusIndex";
        }
      }

      leaf ciscoEnvMonSupplyStatusDescr {
        type leafref {
          path "/CISCO-ENVMON-MIB:CISCO-ENVMON-MIB/CISCO-ENVMON-MIB:ciscoEnvMonSupplyStatusTable/CISCO-ENVMON-MIB:ciscoEnvMonSupplyStatusEntry/CISCO-ENVMON-MIB:ciscoEnvMonSupplyStatusDescr";
        }
      }
    }

    container object-2 {

      leaf ciscoEnvMonSupplyStatusIndex {
        type leafref {
          path "/CISCO-ENVMON-MIB:CISCO-ENVMON-MIB/CISCO-ENVMON-MIB:ciscoEnvMonSupplyStatusTable/CISCO-ENVMON-MIB:ciscoEnvMonSupplyStatusEntry/CISCO-ENVMON-MIB:ciscoEnvMonSupplyStatusIndex";
        }
      }

      leaf ciscoEnvMonSupplyState {
        type leafref {
          path "/CISCO-ENVMON-MIB:CISCO-ENVMON-MIB/CISCO-ENVMON-MIB:ciscoEnvMonSupplyStatusTable/CISCO-ENVMON-MIB:ciscoEnvMonSupplyStatusEntry/CISCO-ENVMON-MIB:ciscoEnvMonSupplyState";
        }
      }
    }
  }

  notification ciscoEnvMonVoltStatusChangeNotif {
    description
     "A ciscoEnvMonVoltStatusChangeNotif is sent if there is 
      change in the state of a device being monitored
      by ciscoEnvMonVoltageState.";
    smiv2:oid "1.3.6.1.4.1.9.9.13.3.0.6";

    container object-1 {

      leaf ciscoEnvMonVoltageStatusIndex {
        type leafref {
          path "/CISCO-ENVMON-MIB:CISCO-ENVMON-MIB/CISCO-ENVMON-MIB:ciscoEnvMonVoltageStatusTable/CISCO-ENVMON-MIB:ciscoEnvMonVoltageStatusEntry/CISCO-ENVMON-MIB:ciscoEnvMonVoltageStatusIndex";
        }
      }

      leaf ciscoEnvMonVoltageStatusDescr {
        type leafref {
          path "/CISCO-ENVMON-MIB:CISCO-ENVMON-MIB/CISCO-ENVMON-MIB:ciscoEnvMonVoltageStatusTable/CISCO-ENVMON-MIB:ciscoEnvMonVoltageStatusEntry/CISCO-ENVMON-MIB:ciscoEnvMonVoltageStatusDescr";
        }
      }
    }

    container object-2 {

      leaf ciscoEnvMonVoltageStatusIndex {
        type leafref {
          path "/CISCO-ENVMON-MIB:CISCO-ENVMON-MIB/CISCO-ENVMON-MIB:ciscoEnvMonVoltageStatusTable/CISCO-ENVMON-MIB:ciscoEnvMonVoltageStatusEntry/CISCO-ENVMON-MIB:ciscoEnvMonVoltageStatusIndex";
        }
      }

      leaf ciscoEnvMonVoltageStatusValue {
        type leafref {
          path "/CISCO-ENVMON-MIB:CISCO-ENVMON-MIB/CISCO-ENVMON-MIB:ciscoEnvMonVoltageStatusTable/CISCO-ENVMON-MIB:ciscoEnvMonVoltageStatusEntry/CISCO-ENVMON-MIB:ciscoEnvMonVoltageStatusValue";
        }
      }
    }

    container object-3 {

      leaf ciscoEnvMonVoltageStatusIndex {
        type leafref {
          path "/CISCO-ENVMON-MIB:CISCO-ENVMON-MIB/CISCO-ENVMON-MIB:ciscoEnvMonVoltageStatusTable/CISCO-ENVMON-MIB:ciscoEnvMonVoltageStatusEntry/CISCO-ENVMON-MIB:ciscoEnvMonVoltageStatusIndex";
        }
      }

      leaf ciscoEnvMonVoltageState {
        type leafref {
          path "/CISCO-ENVMON-MIB:CISCO-ENVMON-MIB/CISCO-ENVMON-MIB:ciscoEnvMonVoltageStatusTable/CISCO-ENVMON-MIB:ciscoEnvMonVoltageStatusEntry/CISCO-ENVMON-MIB:ciscoEnvMonVoltageState";
        }
      }
    }
  }

  notification ciscoEnvMonTempStatusChangeNotif {
    description
     "A ciscoEnvMonTempStatusChangeNotif is sent if there 
      is change in the state of a device being monitored
      by ciscoEnvMonTemperatureState.";
    smiv2:oid "1.3.6.1.4.1.9.9.13.3.0.7";

    container object-1 {

      leaf ciscoEnvMonTemperatureStatusIndex {
        type leafref {
          path "/CISCO-ENVMON-MIB:CISCO-ENVMON-MIB/CISCO-ENVMON-MIB:ciscoEnvMonTemperatureStatusTable/CISCO-ENVMON-MIB:ciscoEnvMonTemperatureStatusEntry/CISCO-ENVMON-MIB:ciscoEnvMonTemperatureStatusIndex";
        }
      }

      leaf ciscoEnvMonTemperatureStatusDescr {
        type leafref {
          path "/CISCO-ENVMON-MIB:CISCO-ENVMON-MIB/CISCO-ENVMON-MIB:ciscoEnvMonTemperatureStatusTable/CISCO-ENVMON-MIB:ciscoEnvMonTemperatureStatusEntry/CISCO-ENVMON-MIB:ciscoEnvMonTemperatureStatusDescr";
        }
      }
    }

    container object-2 {

      leaf ciscoEnvMonTemperatureStatusIndex {
        type leafref {
          path "/CISCO-ENVMON-MIB:CISCO-ENVMON-MIB/CISCO-ENVMON-MIB:ciscoEnvMonTemperatureStatusTable/CISCO-ENVMON-MIB:ciscoEnvMonTemperatureStatusEntry/CISCO-ENVMON-MIB:ciscoEnvMonTemperatureStatusIndex";
        }
      }

      leaf ciscoEnvMonTemperatureStatusValue {
        type leafref {
          path "/CISCO-ENVMON-MIB:CISCO-ENVMON-MIB/CISCO-ENVMON-MIB:ciscoEnvMonTemperatureStatusTable/CISCO-ENVMON-MIB:ciscoEnvMonTemperatureStatusEntry/CISCO-ENVMON-MIB:ciscoEnvMonTemperatureStatusValue";
        }
      }
    }

    container object-3 {

      leaf ciscoEnvMonTemperatureStatusIndex {
        type leafref {
          path "/CISCO-ENVMON-MIB:CISCO-ENVMON-MIB/CISCO-ENVMON-MIB:ciscoEnvMonTemperatureStatusTable/CISCO-ENVMON-MIB:ciscoEnvMonTemperatureStatusEntry/CISCO-ENVMON-MIB:ciscoEnvMonTemperatureStatusIndex";
        }
      }

      leaf ciscoEnvMonTemperatureState {
        type leafref {
          path "/CISCO-ENVMON-MIB:CISCO-ENVMON-MIB/CISCO-ENVMON-MIB:ciscoEnvMonTemperatureStatusTable/CISCO-ENVMON-MIB:ciscoEnvMonTemperatureStatusEntry/CISCO-ENVMON-MIB:ciscoEnvMonTemperatureState";
        }
      }
    }
  }

  notification ciscoEnvMonFanStatusChangeNotif {
    description
     "A ciscoEnvMonFanStatusChangeNotif is sent if there 
      is change in the state of a device being monitored
      by ciscoEnvMonFanState.";
    smiv2:oid "1.3.6.1.4.1.9.9.13.3.0.8";

    container object-1 {

      leaf ciscoEnvMonFanStatusIndex {
        type leafref {
          path "/CISCO-ENVMON-MIB:CISCO-ENVMON-MIB/CISCO-ENVMON-MIB:ciscoEnvMonFanStatusTable/CISCO-ENVMON-MIB:ciscoEnvMonFanStatusEntry/CISCO-ENVMON-MIB:ciscoEnvMonFanStatusIndex";
        }
      }

      leaf ciscoEnvMonFanStatusDescr {
        type leafref {
          path "/CISCO-ENVMON-MIB:CISCO-ENVMON-MIB/CISCO-ENVMON-MIB:ciscoEnvMonFanStatusTable/CISCO-ENVMON-MIB:ciscoEnvMonFanStatusEntry/CISCO-ENVMON-MIB:ciscoEnvMonFanStatusDescr";
        }
      }
    }

    container object-2 {

      leaf ciscoEnvMonFanStatusIndex {
        type leafref {
          path "/CISCO-ENVMON-MIB:CISCO-ENVMON-MIB/CISCO-ENVMON-MIB:ciscoEnvMonFanStatusTable/CISCO-ENVMON-MIB:ciscoEnvMonFanStatusEntry/CISCO-ENVMON-MIB:ciscoEnvMonFanStatusIndex";
        }
      }

      leaf ciscoEnvMonFanState {
        type leafref {
          path "/CISCO-ENVMON-MIB:CISCO-ENVMON-MIB/CISCO-ENVMON-MIB:ciscoEnvMonFanStatusTable/CISCO-ENVMON-MIB:ciscoEnvMonFanStatusEntry/CISCO-ENVMON-MIB:ciscoEnvMonFanState";
        }
      }
    }
  }

  notification ciscoEnvMonSuppStatusChangeNotif {
    description
     "A ciscoEnvMonSupplyStatChangeNotif is sent if there 
      is change in the state of a device being monitored
      by ciscoEnvMonSupplyState.";
    smiv2:oid "1.3.6.1.4.1.9.9.13.3.0.9";

    container object-1 {

      leaf ciscoEnvMonSupplyStatusIndex {
        type leafref {
          path "/CISCO-ENVMON-MIB:CISCO-ENVMON-MIB/CISCO-ENVMON-MIB:ciscoEnvMonSupplyStatusTable/CISCO-ENVMON-MIB:ciscoEnvMonSupplyStatusEntry/CISCO-ENVMON-MIB:ciscoEnvMonSupplyStatusIndex";
        }
      }

      leaf ciscoEnvMonSupplyStatusDescr {
        type leafref {
          path "/CISCO-ENVMON-MIB:CISCO-ENVMON-MIB/CISCO-ENVMON-MIB:ciscoEnvMonSupplyStatusTable/CISCO-ENVMON-MIB:ciscoEnvMonSupplyStatusEntry/CISCO-ENVMON-MIB:ciscoEnvMonSupplyStatusDescr";
        }
      }
    }

    container object-2 {

      leaf ciscoEnvMonSupplyStatusIndex {
        type leafref {
          path "/CISCO-ENVMON-MIB:CISCO-ENVMON-MIB/CISCO-ENVMON-MIB:ciscoEnvMonSupplyStatusTable/CISCO-ENVMON-MIB:ciscoEnvMonSupplyStatusEntry/CISCO-ENVMON-MIB:ciscoEnvMonSupplyStatusIndex";
        }
      }

      leaf ciscoEnvMonSupplyState {
        type leafref {
          path "/CISCO-ENVMON-MIB:CISCO-ENVMON-MIB/CISCO-ENVMON-MIB:ciscoEnvMonSupplyStatusTable/CISCO-ENVMON-MIB:ciscoEnvMonSupplyStatusEntry/CISCO-ENVMON-MIB:ciscoEnvMonSupplyState";
        }
      }
    }
  }

  smiv2:alias "ciscoEnvMonMIB" {
    smiv2:oid "1.3.6.1.4.1.9.9.13";
  }

  smiv2:alias "ciscoEnvMonObjects" {
    smiv2:oid "1.3.6.1.4.1.9.9.13.1";
  }

  smiv2:alias "ciscoEnvMonMIBNotificationEnables" {
    smiv2:oid "1.3.6.1.4.1.9.9.13.2";
  }

  smiv2:alias "ciscoEnvMonMIBNotificationPrefix" {
    smiv2:oid "1.3.6.1.4.1.9.9.13.3";
  }

  smiv2:alias "ciscoEnvMonMIBNotifications" {
    smiv2:oid "1.3.6.1.4.1.9.9.13.3.0";
  }

  smiv2:alias "ciscoEnvMonMIBConformance" {
    smiv2:oid "1.3.6.1.4.1.9.9.13.4";
  }

  smiv2:alias "ciscoEnvMonMIBCompliances" {
    smiv2:oid "1.3.6.1.4.1.9.9.13.4.1";
  }

  smiv2:alias "ciscoEnvMonMIBGroups" {
    smiv2:oid "1.3.6.1.4.1.9.9.13.4.2";
  }

}
