/*
 * Generated by confdc --mib2yang-std
 * Source: mgmt/dmi/model/common/mib-source/CISCO-TC.mib
 */
/*
 * This YANG module has been generated by smidump 0.5.0:
 *
 *      smidump -f yang CISCO-TC
 *
 * Do not edit. Edit the source file instead!
 */

module CISCO-TC {

  namespace "urn:ietf:params:xml:ns:yang:smiv2:CISCO-TC";
  prefix CISCO-TC;

  import ietf-yang-smiv2 {
    prefix "smiv2";
  }

  import ietf-yang-types {
    prefix "yang";
  }

  organization
   "Cisco Systems, Inc.";

  contact
   "Cisco Systems
    Customer Service
    
    Postal: 170 W Tasman Drive
    San Jose, CA  95134
    USA
    
    Tel: +1 800 553-NETS
    
    E-mail: cs-snmp@cisco.com";

  description
   "This module defines textual conventions used throughout
    cisco enterprise mibs.";

  revision 2011-11-11 {
    description
     "Added CiscoEntityIndexList TC.";
  }

  revision 2011-06-17 {
    description
     "-Added the following enums for FcIfOperStatusReason:
      fcRedirectIsolation,
      portActLicenseNotAvailable,
      sdmIsolation,
      fcidAllocationFailed,
      unavailableNPVUpstreamPort,
      unavailableNPVPrefUpstreamPort,
      sfpReadError,
      stickyDownOnLinkFailure,
      tooManyLinkFlapsErr,
      unidirectionalUDLD,
      txRxLoopUDLD,
      neighborMismatchUDLD,
      authzPending,
      hotStdbyInBundle,
      incompleteConfig,
      incompleteTunnelCfg,
      hwProgrammingFailed,
      tunnelDstUnreachable,
      suspendByMtu,
      sfpInvalid,
      sfpAbsent,
      portCapabilitiesUnknown,
      channelErrDisabled,
      vrfMismatch,
      vrfForwardReferencing,
      dupTunnelConfigDetected,
      primaryVLANDown,
      vrfUnusable,
      errDisableHandShkFailure,
      errDisabledBPDUGuard,
      dot1xSecViolationErrDisabled,
      emptyEchoUDLD,
      vfTaggingCapErr,
      portDisabled,
      tunnelModeNotConfigured,
      tunnelSrcNotConfigured,
      tunnelDstNotConfigured,
      tunnelUnableToResolveSrcIP
      tunnelUnableToResolveDstIP,
      tunnelVrfDown,
      sifAdminDown,
      phyIntfDown,
      ifSifLimitExceeded,
      sifHoldDown,
      noFcoe,
      dcxCompatMismatch,
      isolateBundleLimitExceeded,
      sifNotBound,
      errDisabledLacpMiscfg,
      satFabricIfDown,
      invalidSatFabricIf,
      noRemoteChassis,
      vicEnableNotReceived,
      vicDisableReceived,
      vlanVsanMappingNotEnabled,
      stpNotFwdingInFcoeMappedVlan,
      moduleOffline,
      udldAggModeLinkFailure,
      stpInconsVpcPeerDisabled,
      setPortStateFailed,
      suspendedByVpc,
      vpcCfgInProgress,
      vpcPeerLinkDown,
      vpcNoRspFromPeer,
      protoPortSuspend,
      tunnelSrcDown,
      cdpInfoUnavailable,
      fexSfpInvalid,
      errDisabledIpConflict,
      fcotClkRateMismatch,
      portGuardTrustSecViolation,
      sdpTimeout,
      satIncompatTopo,
      waitForFlogi,
      satNotConfigured,
      npivNotEnabledInUpstream,
      vsanMismatchWithUpstreamSwPort,
      portGuardBitErrRate,
      portGuardSigLoss,
      portGuardSyncLoss,
      portGuardLinkReset,
      portGuardCreditLoss,
      bitErrorRate,
      signalLoss,
      syncLoss,
      linkReset,
      creditLoss,
      ipQosMgrPolicyAppFailure,
      pauseRateLimitErrDisabled,
      lstGrpUplinkDown,
      stickyDnLinkFailure,
      routerMacFailure,
      dcxMultipleMsapIds,
      dcxHundredPdusRcvdNoAck,
      enmSatIncompatibleUplink,
      enmLoopDetected,
      nonStickyExternallyDisabled,
      subGroupIdNotAssigned,
      vemUnlicensed,
      profileNotFound,
      nonExistentVlan,
      vlanInvalidType,
      vlanDown,
      vpcPeerUpgrade,
      ipQosDcbxpCompatFailure,
      nonCiscoHbaVfTag,
      domainIdConfigMismatch,
      sfpSpeedMismatch,
      xcvrInitializing,
      xcvrAbsent,
      xcvrInvalid,
      vfcBindingInvalid,
      vlanNotFcoeEnabled,
      pvlanNativeVlanErr,
      ethL2VlanDown,
      ethIntfInvalidBinding,
      pmonFailure,
      l3NotReady,
      speedMismatch,
      flowControlMismatch,
      vdcMode,
      suspendedDueToMinLinks,
      enmPinFailLinkDown,
      inactiveM1PortFpathActiveVlan,
      parentPortDown,
      moduleRemoved,
      corePortMct,
      nonCorePortMct,
      ficonInorderNotActive,
      invalidEncapsulation,
      modemLineDeasserted,
      ipSecHndshkInProgress,
      sfpEthCompliantErr,
      cellularModemUnattached,
      outOfGlblRxBuffers,
      sfpFcCompliantErr,
      ethIntfNotLicensed,
      domainIdsInvalid,
      fabricNameInvalid.";
  }

  revision 2010-02-24 {
    description
     "Added CiscoURLStringOrEmpty textual convention.";
  }

  revision 2009-06-18 {
    description
     "Added the new textual convention CiscoVrfName";
  }

  revision 2009-03-10 {
    description
     "Added the new textual convention CiscoInterfaceIndexList";
  }

  revision 2009-02-26 {
    description
     "Added the new textual convention Cisco2KVlanList";
  }

  revision 2008-04-02 {
    description
     "Added the new textual convention CiscoBridgeDomain.";
  }

  revision 2007-02-15 {
    description
     "Added following textual conventions:
      CiscoVlanList,
      CiscoCosList, 
      CiscoPbbServiceIdentifier";
  }

  revision 2006-07-06 {
    description
     "Added the following enums to IfOperStatusReason:
      - elpFailureAllZeroPeerWWNRcvd,
      - preferredPathIsolation.";
  }

  revision 2006-04-13 {
    description
     "Added enumeration to IfOperStatusReason from 113-131
      ('dpvmVsanSuspended' to 'domainOther').";
  }

  revision 2005-06-24 {
    description
     "Added CvE164Address textual convention.";
  }

  revision 2005-06-16 {
    description
     "Added following textual conventions:
      CiscoURLString
      CiscoHTTPResponseStatusCode
      EntLogicalIndexOrZero.";
  }

  revision 2004-10-11 {
    description
     "Added IfOperStatusReason textual convention.";
  }

  revision 2004-06-08 {
    description
     "Added CiscoPortListRange textual convention.";
  }

  revision 2004-04-14 {
    description
     "Added CiscoPortList textual convention.
      Removed Unsigned32 textual convention.";
  }

  revision 2002-12-18 {
    description
     "Changed MilliSeconds TC to CiscoMilliSeconds as it was
      overlapping with the one in a standard MIB.";
  }

  revision 2002-12-12 {
    description
     "Added the 'http' enumeration to CiscoNetworkProtocol.";
  }

  revision 2002-12-02 {
    description
     "Added Unsigned64 textual convention.";
  }

  revision 2002-09-22 {
    description
     "Added ListIndex, ListIndexOrZero, TimeIntervalSec,
      TimeintervalMin, MicroSeconds and MicroSeconds TC from 
      Andiamo's TC MIB .";
  }

  revision 2002-09-17 {
    description
     "Added ConfigIterator & BulkConfigResult textual
      convention for bulk provisioning.
      Added CountryCodeITU textual convention for ITU-T defined
      country codes for non-standard facilities.";
  }

  revision 2002-04-16 {
    description
     "Added PerfHighIntervalCount TEXTUAL-CONVENTION.";
  }

  revision 2001-07-07 {
    description
     "Added enumerations to CiscoNetworkProtocol";
  }

  revision 2001-01-18 {
    description
     "Added CiscoAlarmSeverity textual convention.
      Changed SAPType display hint to d.  Changed
      INTEGER to Integer32 in CiscoPort and
      CiscoIpProtocol TCs.  Changed SnmpAdminString
      to OCTET STRING in CiscoLocationSpecifier.
      Removed IMPORTs for ciscoProducts and
      SnmpAdminString.";
  }

  revision 2000-11-21 {
    description
     "Added CiscoLocationClass, CiscoLocationSpecifier
      CiscoInetAddressMask, CiscoAbsZeroBasedCounter32, 
      CiscoSnapShotAbsCounter32 textual conventions.";
  }

  revision 1998-10-28 {
    description
     "Added CiscoRowOperStatus, EntPhysicalIndexOrZero,
      Port and IpProtocol textual conventions.";
  }

  revision 1997-03-13 {
    description
     "Added SAPType, CountryCode textual convention.";
  }

  revision 1996-08-14 {
    description
     "Added InterfaceIndexOrZero textual convention.";
  }

  revision 1996-07-08 {
    description
     "Added new CiscoNetworkProtocol enumerations.";
  }

  revision 1996-02-22 {
    description
     "Added Unsigned32 textual conventions.";
  }

  revision 1995-06-07 {
    description
     "Miscellaneous updates/corrections, including making
      CiscoNetworkProtocol enumerations contiguous.";
  }

  typedef Layer2Cos {
    type int32 {
      range "0..7";
    }
    description
     "An integer that is in the range of the layer 2 CoS values. It
      corresponds to the IEEE 802.1P CoS value which defines eight
      (2^3) user priority levels.
      Note: the IEEE 802.1P has been merged into IEEE 802.1D.";
    reference
     "IEEE 802.1D, 2004 Edition, Annex G User priorities and traffic
      classes.";
  }

  typedef CiscoNetworkProtocol {
    type enumeration {
      enum "ip" {
        value "1";
      }
      enum "decnet" {
        value "2";
      }
      enum "pup" {
        value "3";
      }
      enum "chaos" {
        value "4";
      }
      enum "xns" {
        value "5";
      }
      enum "x121" {
        value "6";
      }
      enum "appletalk" {
        value "7";
      }
      enum "clns" {
        value "8";
      }
      enum "lat" {
        value "9";
      }
      enum "vines" {
        value "10";
      }
      enum "cons" {
        value "11";
      }
      enum "apollo" {
        value "12";
      }
      enum "stun" {
        value "13";
      }
      enum "novell" {
        value "14";
      }
      enum "qllc" {
        value "15";
      }
      enum "snapshot" {
        value "16";
      }
      enum "atmIlmi" {
        value "17";
      }
      enum "bstun" {
        value "18";
      }
      enum "x25pvc" {
        value "19";
      }
      enum "ipv6" {
        value "20";
      }
      enum "cdm" {
        value "21";
      }
      enum "nbf" {
        value "22";
      }
      enum "bpxIgx" {
        value "23";
      }
      enum "clnsPfx" {
        value "24";
      }
      enum "http" {
        value "25";
      }
      enum "unknown" {
        value "65535";
      }
    }
    description
     "Represents the different types of network layer protocols.";
  }

  typedef CiscoNetworkAddress {
    type binary;
    description
     "Represents a network layer address.  The length and format of
      the address is protocol dependent as follows:
      ip        4 octets
      decnet    2 octets
      pup       obsolete
      chaos     2 octets
      xns       10 octets
                first 4 octets are the net number
                last 6 octets are the host number
      x121    
      appletalk 3 octets
                first 2 octets are the net number
                last octet is the host number
      clns
      lat
      vines     6 octets
                first 4 octets are the net number
                last 2 octets are the host number
      cons
      apollo    10 octets
                first 4 octets are the net number
                last 6 octets are the host number
      stun      8 octets
      novell    10 octets
                first 4 octets are the net number
                last 6 octets are the host number
      qllc      6 octets
      bstun     1 octet - bi-sync serial tunnel 
      snapshot  1 octet
      atmIlmi   4 octets
      x25 pvc   2 octets (12 bits)
      ipv6      16 octets
      cdm
      nbf
      bgpIgx
      clnsPfx  upto 20 octets
      http     upto 70 octets
               first 4 octets are the IPv4 host 
               address
               next 2 octets are the TCP port 
               number
               remaining(1 upto 64) octets are 
               the URI";
  }

  typedef Unsigned64 {
    type yang:counter64;
    description
     "An unsigned 64 bit integer. We use SYNTAX Counter64 for the
      encoding rules.";
  }

  typedef InterfaceIndexOrZero {
    type int32 {
      range "0..2147483647";
    }
    description
     "Either the value 0, or the ifIndex value of an
      interface in the ifTable.";
  }

  typedef SAPType {
    type int32 {
      range "0..254";
    }
    description
     "Service Access Point - is a term that denotes the means
      by which a user entity in layer n+1 accesses a service
      of a provider entity in layer n.";
  }

  typedef CountryCode {
    type binary {
      length "0|2";
    }
    description
     "Represents a case-insensitive 2-letter country code taken
      from ISO-3166. Unrecognized countries are represented as 
      empty string.";
  }

  typedef CountryCodeITU {
    type uint32 {
      range "0..255";
    }
    description
     "This textual convention represents a country or area code for
      non-standard facilities in telematic services.";
    reference
     "ITU-T T.35 - Section 3.1 Country Code";
  }

  typedef EntPhysicalIndexOrZero {
    type int32 {
      range "0..2147483647";
    }
    description
     "This textual convention is an extension of entPhysicalIndex.
      If non-zero, the object is an entPhysicalIndex. If zero, no
      appropriate entPhysicalIndex exists. Any additional semantics
      are object specific.";
  }

  typedef CiscoRowOperStatus {
    type enumeration {
      enum "active" {
        value "1";
      }
      enum "activeDependencies" {
        value "2";
      }
      enum "inactiveDependency" {
        value "3";
      }
      enum "missingDependency" {
        value "4";
      }
    }
    description
     "Represents the operational status of an table entry.
      This textual convention allows explicitly representing
      the states of rows dependent on rows in other tables.
      
      active(1) -
          Indicates this entry's RowStatus is active
          and the RowStatus for each dependency is active.
      
      activeDependencies(2) -
          Indicates that the RowStatus for each dependency
          is active, but the entry's RowStatus is not active.
      
      inactiveDependency(3) -
          Indicates that the RowStatus for at least one
          dependency is not active.
      
      missingDependency(4) -
          Indicates that at least one dependency does
          not exist in it's table.";
  }

  typedef CiscoPort {
    type int32 {
      range "0..65535";
    }
    description
     "The TCP or UDP port number range.";
    reference
     "Transmission Control Protocol. J. Postel. RFC793,
      User Datagram Protocol. J. Postel. RFC768";
  }

  typedef CiscoIpProtocol {
    type int32 {
      range "0..255";
    }
    description
     "IP protocol number range.";
    reference
     "Internet Protocol. J. Postel. RFC791";
  }

  typedef CiscoLocationClass {
    type enumeration {
      enum "chassis" {
        value "1";
      }
      enum "shelf" {
        value "2";
      }
      enum "slot" {
        value "3";
      }
      enum "subSlot" {
        value "4";
      }
      enum "port" {
        value "5";
      }
      enum "subPort" {
        value "6";
      }
      enum "channel" {
        value "7";
      }
      enum "subChannel" {
        value "8";
      }
    }
    description
     "An enumerated value which provides an indication of
      the general location type of a particular physical and/or
      logical interface.
      chassis - a system framework for mounting one or more 
                shelves/slots/cards.
      shelf - a cabinet that holds one or more slots.
      slot -  card or subSlot holder.
      subSlot - daughter-card holder.
      port - a physical port (e.g., a DS1 or DS3 physical port).
      subPort - a logical port on a physical port (e.g., a DS1 
                subPort on a DS3 physical port).
      channel - a logical interface (e.g., a DS0 channel, signaling
                channel, ATM port, other virtual interfaces).
      subChannel - a sub-channel on a logical interface.";
  }

  typedef CiscoLocationSpecifier {
    type binary {
      length "0..255";
    }
    description
     "Use this TC to define objects that indicate the
      physical entity and/or logical interface location 
      of a managed entity on a managed device. In SNMP, a 
      standard mechanism for indicating the physical location
      of entities is via the ENTITY-MIB. However, that approach
      is not satisfactory in some cases because:
      
      1. The entity requiring a location-based naming may be 
         associated with an entity which can not be represented 
         as a physical entity in the ENTITY-MIB,
      2. NMS applications may desire a more direct 
         name/representation of a physical entity than is 
         available via the ENTITY-MIB, e.g., a physical entity
         which is named via a hierarchy of levels in the ENTITY-MIB.
      
      The value of an object defined using this TC is an ASCII 
      string consisting of zero or more elements separated by 
      commas. Each element is of the form  = . 
      
      An example of this syntax is 'slot=5,port=3'.
      
      The syntax of the string is formally specified using
      ABNF notation (with one exception, noted below), as
      follows:                 
      
      location-specifier =  elem *(',' elem) 
                     ; subject to 
                     ; size restriction specified in the SYNTAX
                     ; clause below
      
      elem    =   loctype '=' number
      
      number  = %x00-FFFFFFFF / %d0-4294967295
      
      loctype = 1*32VCHAR 
      
      It is recommended that loctype use one of the enumerated
      labels defined for CiscoLocationClass.
      
      (NOTE: To conform to ABNF notation as defined in RFC2234, 
       substitute the single-quote symbol with a double-quote 
       symbol in the above rules.)
      
      A zero length of CiscoLocationSpecifier is object-specific
      and must be defined as part of the description of any object
      which uses this syntax.";
    reference
     "RFC2234, Augmented BNF for syntax specifications: ABNF";
  }

  typedef CiscoInetAddressMask {
    type uint32 {
      range "0..128";
    }
    description
     "Denotes a generic Internet subnet address mask.
      The Internet subnet address mask is represented as the
      number of contiguous 1-bit from MSB (most significant bit)
      of the Internet subnet address mask.
      A CiscoInetAddressMask value is always interpreted within
      the context of an InetAddressType value. The 
      InetAddressType only object or InetAddressType with
      InetAddress objects which define the context must be
      registered immediately before the object which uses the
      CiscoInetAddressMask textual convention.  In other words,
      the object identifiers for the InetAddressType object and
      the CiscoInetAddressMask object MUST have the same length
      and the last sub-identifier of the InetAddressType object
      MUST be 1 less than the last sub-identifier of the 
      CiscoInetAddressMask object and MUST be 2 less than the
      last sub-identifier of the CiscoInetAddressMask object if
      an InetAddress object is defined between InetAddressType
      and CiscoInetAddressMask objects.
      The maximum value of the CiscoInetAddressMask TC is 32 for
      the value 'ipv4(1)' in InetAddressType object and 128 for
      the value 'ipv6(2)' in InetAddressType object.
      The value zero is object-specific and must therefore be
      defined as part of the description of any object which
      uses this syntax.  Examples of the usage of zero might
      include situations where Internet subnet mask was unknown,
      or when none subnet masks need to be referenced.";
    reference
     "RFC2851, Textual Conventions for Internet Network Addresses.";
  }

  typedef CiscoAbsZeroBasedCounter32 {
    type yang:gauge32;
    description
     "This TC describes an object which counts events with the
      following semantics: objects of this type will be set to
      zero(0) on creation and will thereafter count appropriate
      events, it locks at the maximum value of 4,294,967,295 if
      the counter overflows.
      This TC may be used only in situations where wrapping is
      not possible or extremely unlikely situation.";
  }

  typedef CiscoSnapShotAbsCounter32 {
    type uint32;
    description
     "This TC describes an object which stores a snap-shot value
      with the following semantics: objects of this type will
      take a snap-shot value from their associated
      CiscoAbsZeroBasedCounter32 type objects on creation.";
  }

  typedef CiscoAlarmSeverity {
    type enumeration {
      enum "cleared" {
        value "1";
      }
      enum "indeterminate" {
        value "2";
      }
      enum "critical" {
        value "3";
      }
      enum "major" {
        value "4";
      }
      enum "minor" {
        value "5";
      }
      enum "warning" {
        value "6";
      }
      enum "info" {
        value "7";
      }
    }
    description
     "Represents the perceived alarm severity associated
      with a service or safety affecting condition and/or
      event.  These are based on ITU severities, except
      that info(7) is added.
      
          cleared(1) -
              Indicates a previous alarm condition has been
              cleared.  It is not required (unless specifically
              stated elsewhere on a case by case basis) that an
              alarm condition that has been cleared will produce
              a notification or other event containing an
              alarm severity with this value.
      
          indeterminate(2) -
              Indicates that the severity level cannot be
              determined. 
      
          critical(3) -
              Indicates that a service or safety affecting
              condition has occurred and an immediate
              corrective action is required.
      
          major(4) -
              Indicates that a service affecting condition has
              occurred and an urgent corrective action is
              required.
      
          minor(5) -
              Indicates the existence of a non-service affecting
              condition and that corrective action should be
              taken in order to prevent a more serious (for
              example, service or safety affecting) condition.
      
          warning(6) -
              Indicates the detection of a potential or impending
              service or safety affecting condition, before any
              significant effects have been felt.
      
          info(7) -
              Indicates an alarm condition that does not
              meet any other severity definition.  This can
              include important, but non-urgent, notices or
              informational events.";
    reference
     "ITU-X.733";
  }

  typedef PerfHighIntervalCount {
    type yang:counter64;
    description
     "A 64 bit counter associated with a
      performance measurement in a previous
      15 minute measurement interval. In the
      case where the agent has no valid data
      available for a particular interval the
      corresponding object instance is not
      available and upon a retrieval request
      a corresponding error message shall be
      returned to indicate that this instance
      does not exist (for example, a noSuchName
      error for SNMPv1 and a noSuchInstance for
      SNMPv2 GET operation).
      In a system supporting
      a history of n intervals with
      IntervalCount(1) and IntervalCount(n) the
      most and least recent intervals
      respectively, the following applies at
      the end of a 15 minute interval:
          - discard the value of IntervalCount(n)
          - the value of IntervalCount(i) becomes that
            of IntervalCount(i-1) for n >= i > 1
          - the value of IntervalCount(1) becomes that
            of CurrentCount
          - the TotalCount, if supported, is adjusted.
      
      This definition is based on CounterBasedGauge64 TEXTUAL
      CONVENTION  defined in RFC2856. The PerfHighIntervalCount
      type represents a non-negative
      integer, which may increase or decrease, but shall never
      exceed a maximum value, nor fall below a minimum value. The
      maximum value can not be greater than 2^64-1
      (18446744073709551615 decimal), and the minimum value can
      not be smaller than 0.  The value of a PerfHighIntervalCount,
      has its maximum value whenever the information being modeled
      is greater than or equal to its maximum value, and has its
      minimum value whenever the information being modeled is
      smaller than or equal to its minimum value.  If the
      information being modeled subsequently decreases below
      (increases above) the maximum (minimum) value, the
      PerfHighIntervalCount also decreases (increases).
      
      Note that this TC is not strictly supported in SMIv2,
      because the 'always increasing' and 'counter wrap' semantics
      associated with the Counter64 base type are not preserved.
      It is possible that management applications which rely
      solely upon the (Counter64) ASN.1 tag to determine object
      semantics will mistakenly operate upon objects of this type
      as they would for Counter64 objects.
      
      This textual convention represents a limited and short-term
      solution, and may be deprecated as a long term solution is
      defined and deployed to replace it.";
    reference
     "RFC 2856(HCNUM-TC MIB).
      RFC 2493(PerfHist-TC-MIB).";
  }

  typedef ConfigIterator {
    type uint32 {
      range "1..4294967295";
    }
    description
     "This object type is a control object type which applies to
      writable objects in the same SNMP PDU related to the
      same table containing those objects. It controls an 
      operation which repeatedly applies the specified 
      configuration data to more than one rows in a table. 
      The operation starts from the row specified by the index 
      of the instance and repeats for the number of rows as 
      the value of the object. 
      
      ConfigIterator object needs to be accompanied by one set of
      writable objects which are of the same instance to apply to.
      
      For example, a SNMP PDU contains 
         { objectA.10 = 1, 
           objectB.10 = 'E1',
           objectC.10 = 44,
           objectRepetition.10 = 100 }
      
      The SYNTAX of objectRepetition is ConfigIterator.
      This will apply value 1 to objectA, value 'E1' to objectB,
      value 44 to objectC in the table starting from row 10 
      repeatedly for 100 rows.
      
      The iteration is based on the number of rows, not based on
      the value of the index. For sparse tables, the index 10, 
      20, 30, 110, and 120 counts for 5 rows, the operation will 
      go beyond index 100 in the previous SNMP PDU example.
      
      The iteration will stop prematurely when it comes to the 
      following situations:
      (1) When the number of the rows in the table is less than
          the designated row indicated by the ConfigIterator 
          object. 
      (2) When it encounters the first error in any row, the 
          operation won't continue to next row.
      
      The operation of ConfigIterator object applies only to
      the writable objects having the same index as the
      ConfigIterator object in one SNMP PDU.
      
      For example, a SNMP PDU contains
         { objectD.5 = 38,
           objectE.6 = 'T1',
           objectF.5 = 'false',
           objectIterator.5 = 10 }
      
      The SYNTAX of objectIterator is ConfigIterator.
      This will apply value 38 to objectD, value 'false' to 
      objectF in the table starting from row 5 repeatedly 
      for 10 rows. Since the object objectE.6 has different
      index (6) from the index of objectIterator, the 
      repetition won't be applied to it. However the value 
      of objectE in the row 6 will be set to 'T1' according
      to regular SNMP SET orperation. 
      
      If there is row overlapping of the iteration in a SNMP PDU,
      it will be operated as they are in two different SNMP PDUs.
      
      For example, a SNMP PDU contains
         { objectD.5 = 38,
           objectD.6 = 40,
           objectE.6 = 'T1',
           objectF.5 = 'false',
           objectIterator.5 = 10
           objectIterator.6 = 10 }
      
      This will apply value 38 to objectD, value 'false' to 
      objectF starting from row 5 repeatedly for 10 rows, and
      apply value 40 to objectD, value 'T1' to objectE starting
      from row 6 repeatedly for 10 rows. The final value of 
      objectD.6 can be 38 or 40, it depends on the SNMP stack of
      the system starts SNMP SET for the row 5 before the row 6 
      or the other way around.
      
      The object defined as ConfigIterator will be set to value 1 
      after the iteration operation is kick-off regardless the 
      system has completed the operation to the designated rows 
      or not. Therefore retrieving the value of this object 
      is meaningless. It acts as the one time operation for 
      bulk configuration.
      
      The object defined as ConfigIterator has no meaning by itself,
      it has to be combined with one or more than one writable 
      objects from the same table and within the same SNMP PDU
      for the repetition operation.
      
      For example, a SNMP PDU contains
         { objectG.2 = 49,
           objectH.2 = 'AE'h
           objectIterator.4 = 20 }
      
      The SYNTAX of objectIterator is ConfigIterator. Since
      there are no objects having the same index as the index
      of objectIterator in the PDU, the result of this SNMP 
      operation will set value 49 to objectG and value 0xAE 
      to objectH of the row 2 only as regular SNMP SET operation.
      
      The index of the instance indicates the starting row for the
      iteration. 
      The order of the iteration depends, for instance, on: 
      (1) physical hardware position, or
      (2) logical index.
      
      It depends on the characters of the table which contains
      the ConfigIterator object.
      
      Iteration can be done through some or all the components
      of the index for a table. The description of the iterator
      object in that table should describe which part of the 
      index the iteration is applied to.
      
      The operation for this object type is based on the best
      effort. When the agent receives a SNMP PDU containing this 
      data type, the return status of the SNMP request reflects 
      only the result of the SET operation has applied to the 
      starting row. It may return a SNMP response with SUCCESS 
      status regardless the number of rows for the data actually 
      been deployed later on. Therefore it is possible the data 
      might not be completely deployed to the number of rows
      designated by the ConfigIterator and the operation stops 
      prematurely due to an error it first encounters after 
      n rows (n < the value of ConfigIterator object).
      
      Usually the error report mechanism for this type of operation
      is accomplished by combining this type of object with the
      other two objects in the same table:
      
      (1) An OwnerString object
      (2) An object indicates the result of the operation.
      
      When issuing this bulk configuration request, the SNMP 
      manager should provide its identifier in (1) object.
      After issuing the request, it should check the value of (1) 
      object if it is the same with it own name.
      If they are the same, then the value of the object presents
      in (2) is the result from the previous operation from this
      manager. Otherwise, another SNMP manager might issue
      the bulk configuration to the same table before the previous
      bulk operation has been completed. These two objects will 
      represent the last bulk operation in the table.";
  }

  typedef BulkConfigResult {
    type binary {
      length "0..255";
    }
    description
     "This textual convention defines the format of the
      displayable textual result from the bulk configuration
      operation specified as ConfigIterator type.
      
      The format should be: 
      'COMPLETION=          error occured>/,
       ERROR=/:
       '
      
      For example:
      'COMPLETION=22/100,ERROR=38/44:Invalid Ds1 line coding 
       for the line type'";
  }

  typedef ListIndex {
    type int32 {
      range "1..2147483647";
    }
    description
     "A unique value greater than zero, for each of the
      list that is defined. The object using this 
      convention should give all the object specific 
      details including the list type.";
  }

  typedef ListIndexOrZero {
    type int32 {
      range "0..2147483647";
    }
    description
     "This textual convention is an extension of the
      ListIndex. In addition to the ListIndex range, 
      this also includes 0 in its range of values. 
      This value could be object specific and 
      should be given the description of that object. 
      In most cases, a value 0 means that the it does 
      not represent any lists.";
  }

  typedef TimeIntervalSec {
    type uint32;
    description
     "A period of time, measured in units of 1 second.";
  }

  typedef TimeIntervalMin {
    type uint32;
    description
     "A period of time, measured in units of 1 minute.";
  }

  typedef CiscoMilliSeconds {
    type uint32;
    description
     "Represents time unit value in milliseconds.";
  }

  typedef MicroSeconds {
    type uint32;
    description
     "Represents time unit value in microseconds.";
  }

  typedef CiscoPortList {
    type binary {
      length "0..256";
    }
    description
     "Each octet within this value specifies a set of eight
      ports. The object defined by this textual convention
      can specify a port range of 2k ports in its description.
      Example: 1 - 2048, 2049 - 4096, etc. The first octet 
      represents the first 8 ports of the range of ports
      specified by the object, the second octet represents 
      the next 8 ports, etc. When a port range is not
      specified, a default port range of '1 - 2048' is assumed.
      
      Within each octet, the most significant bit represents
      the lowest numbered port, and the least significant bit
      represents the highest numbered port. Thus, each port
      of the bridge is represented by a single bit within the
      value of this object.  If that bit has a value of '1'
      then that port is included in the set of ports; the port
      is not included if its bit has a value of '0'.
      
      Note that if the length of this string is less than
      256 octets, any 'missing' octets are assumed to contain
      the value zero. An NMS may omit any zero-valued octets
      from the end of this string in order to reduce SetPDU size,
      and the agent may also omit zero-valued trailing octets,
      to reduce the size of GetResponse PDUs.";
  }

  typedef CiscoPortListRange {
    type enumeration {
      enum "oneto2k" {
        value "1";
      }
      enum "twoKto4K" {
        value "2";
      }
      enum "fourKto6K" {
        value "3";
      }
      enum "sixKto8K" {
        value "4";
      }
      enum "eightKto10K" {
        value "5";
      }
      enum "tenKto12K" {
        value "6";
      }
      enum "twelveKto14K" {
        value "7";
      }
      enum "fourteenKto16K" {
        value "8";
      }
    }
    description
     "Indicates the port range.
      
      oneto2K(1) indicates that the port number range is
      from 1 to 2048.
      
      twoKto4K(2) indicates that the port number range is
      from 2049 to 4096.
      
      fourKto6K(3) indicates that the port number range is
      from 4097 to 6144.
      
      sixKto8K(4) indicates that the port number range is
      from 6145 to 8192.
      
      eightKto10K(5) indicates that the port number range is
      from 8193 to 10240.
      
      tenKto12K(6) indicates that the port number range is
      from 10241 to 12288.
      
      twelveKto14K(7) indicates that the port number range is
      from 12289 to 14336.
      
      fourteenKto16K(8) indicates that the port number range is
      from 14337 to 16384.
      
      When an object is defined with this textual convention,
      it must be accompanied by an object of CiscoPortList
      syntax.";
  }

  typedef IfOperStatusReason {
    type enumeration {
      enum "other" {
        value "1";
      }
      enum "none" {
        value "2";
      }
      enum "hwFailure" {
        value "3";
      }
      enum "loopbackDiagFailure" {
        value "4";
      }
      enum "errorDisabled" {
        value "5";
      }
      enum "swFailure" {
        value "6";
      }
      enum "linkFailure" {
        value "7";
      }
      enum "offline" {
        value "8";
      }
      enum "nonParticipating" {
        value "9";
      }
      enum "initializing" {
        value "10";
      }
      enum "vsanInactive" {
        value "11";
      }
      enum "adminDown" {
        value "12";
      }
      enum "channelAdminDown" {
        value "13";
      }
      enum "channelOperSuspended" {
        value "14";
      }
      enum "channelConfigurationInProgress" {
        value "15";
      }
      enum "rcfInProgress" {
        value "16";
      }
      enum "elpFailureIsolation" {
        value "17";
      }
      enum "escFailureIsolation" {
        value "18";
      }
      enum "domainOverlapIsolation" {
        value "19";
      }
      enum "domainAddrAssignFailureIsolation" {
        value "20";
      }
      enum "domainOtherSideEportIsolation" {
        value "21";
      }
      enum "domainInvalidRcfReceived" {
        value "22";
      }
      enum "domainManagerDisabled" {
        value "23";
      }
      enum "zoneMergeFailureIsolation" {
        value "24";
      }
      enum "vsanMismatchIsolation" {
        value "25";
      }
      enum "parentDown" {
        value "26";
      }
      enum "srcPortNotBound" {
        value "27";
      }
      enum "interfaceRemoved" {
        value "28";
      }
      enum "fcotNotPresent" {
        value "29";
      }
      enum "fcotVendorNotSupported" {
        value "30";
      }
      enum "incompatibleAdminMode" {
        value "31";
      }
      enum "incompatibleAdminSpeed" {
        value "32";
      }
      enum "suspendedByMode" {
        value "33";
      }
      enum "suspendedBySpeed" {
        value "34";
      }
      enum "suspendedByWWN" {
        value "35";
      }
      enum "domainMaxReTxFailure" {
        value "36";
      }
      enum "eppFailure" {
        value "37";
      }
      enum "portVsanMismatchIsolation" {
        value "38";
      }
      enum "loopbackIsolation" {
        value "39";
      }
      enum "upgradeInProgress" {
        value "40";
      }
      enum "incompatibleAdminRxBbCredit" {
        value "41";
      }
      enum "incompatibleAdminRxBufferSize" {
        value "42";
      }
      enum "portChannelMembersDown" {
        value "43";
      }
      enum "zoneRemoteNoRespIsolation" {
        value "44";
      }
      enum "firstPortUpAsEport" {
        value "45";
      }
      enum "firstPortNotUp" {
        value "46";
      }
      enum "peerFCIPPortClosedConnection" {
        value "47";
      }
      enum "peerFCIPPortResetConnection" {
        value "48";
      }
      enum "fcipPortMaxReTx" {
        value "49";
      }
      enum "fcipPortKeepAliveTimerExpire" {
        value "50";
      }
      enum "fcipPortPersistTimerExpire" {
        value "51";
      }
      enum "fcipPortSrcLinkDown" {
        value "52";
      }
      enum "fcipPortSrcAdminDown" {
        value "53";
      }
      enum "fcipPortAdminCfgChange" {
        value "54";
      }
      enum "fcipSrcPortRemoved" {
        value "55";
      }
      enum "fcipSrcModuleNotOnline" {
        value "56";
      }
      enum "invalidConfig" {
        value "57";
      }
      enum "portBindFailure" {
        value "58";
      }
      enum "portFabricBindFailure" {
        value "59";
      }
      enum "noCommonVsanIsolation" {
        value "60";
      }
      enum "ficonVsanDown" {
        value "61";
      }
      enum "invalidAttachment" {
        value "62";
      }
      enum "portBlocked" {
        value "63";
      }
      enum "incomAdminRxBbCreditPerBuf" {
        value "64";
      }
      enum "tooManyInvalidFlogis" {
        value "65";
      }
      enum "deniedDueToPortBinding" {
        value "66";
      }
      enum "elpFailureRevMismatch" {
        value "67";
      }
      enum "elpFailureClassFParamErr" {
        value "68";
      }
      enum "elpFailureClassNParamErr" {
        value "69";
      }
      enum "elpFailureUnknownFlowCtlCode" {
        value "70";
      }
      enum "elpFailureInvalidFlowCtlParam" {
        value "71";
      }
      enum "elpFailureInvalidPortName" {
        value "72";
      }
      enum "elpFailureInvalidSwitchName" {
        value "73";
      }
      enum "elpFailureRatovEdtovMismatch" {
        value "74";
      }
      enum "elpFailureLoopbackDetected" {
        value "75";
      }
      enum "elpFailureInvalidTxBbCredit" {
        value "76";
      }
      enum "elpFailureInvalidPayloadSize" {
        value "77";
      }
      enum "bundleMisCfg" {
        value "78";
      }
      enum "bitErrRuntimeThreshExceeded" {
        value "79";
      }
      enum "linkFailLinkReset" {
        value "80";
      }
      enum "linkFailPortInitFail" {
        value "81";
      }
      enum "linkFailPortUnusable" {
        value "82";
      }
      enum "linkFailLossOfSignal" {
        value "83";
      }
      enum "linkFailLossOfSync" {
        value "84";
      }
      enum "linkFailNosRcvd" {
        value "85";
      }
      enum "linkFailOLSRcvd" {
        value "86";
      }
      enum "linkFailDebounceTimeout" {
        value "87";
      }
      enum "linkFailLrRcvd" {
        value "88";
      }
      enum "linkFailCreditLoss" {
        value "89";
      }
      enum "linkFailRxQOverflow" {
        value "90";
      }
      enum "linkFailTooManyInterrupts" {
        value "91";
      }
      enum "linkFailLipRcvdBb" {
        value "92";
      }
      enum "linkFailBbCreditLoss" {
        value "93";
      }
      enum "linkFailOpenPrimSignalTimeout" {
        value "94";
      }
      enum "linkFailOpenPrimSignalReturned" {
        value "95";
      }
      enum "linkFailLipF8Rcvd" {
        value "96";
      }
      enum "linkFailLineCardPortShutdown" {
        value "97";
      }
      enum "fcspAuthenfailure" {
        value "98";
      }
      enum "fcotChecksumError" {
        value "99";
      }
      enum "ohmsExtLoopbackTest" {
        value "100";
      }
      enum "invalidFabricBindExchange" {
        value "101";
      }
      enum "tovMismatch" {
        value "102";
      }
      enum "ficonNotEnabled" {
        value "103";
      }
      enum "ficonNoPortNumber" {
        value "104";
      }
      enum "ficonBeingEnabled" {
        value "105";
      }
      enum "ePortProhibited" {
        value "106";
      }
      enum "portGracefulShutdown" {
        value "107";
      }
      enum "trunkNotFullyActive" {
        value "108";
      }
      enum "fabricBindingSwitchWwnNotFound" {
        value "109";
      }
      enum "fabricBindingDomainInvalid" {
        value "110";
      }
      enum "fabricBindingDbMismatch" {
        value "111";
      }
      enum "fabricBindingNoRspFromPeer" {
        value "112";
      }
      enum "dpvmVsanSuspended" {
        value "113";
      }
      enum "dpvmVsanNotFound" {
        value "114";
      }
      enum "trackedPortDown" {
        value "115";
      }
      enum "ecSuspendedOnLoop" {
        value "116";
      }
      enum "isolateBundleMisCfg" {
        value "117";
      }
      enum "noPeerBundleSupport" {
        value "118";
      }
      enum "portBringupIsolation" {
        value "119";
      }
      enum "domainNotAllowedIsolated" {
        value "120";
      }
      enum "virtualIvrDomainOverlapIsolation" {
        value "121";
      }
      enum "outOfService" {
        value "122";
      }
      enum "portAuthFailed" {
        value "123";
      }
      enum "bundleStandby" {
        value "124";
      }
      enum "portConnectorTypeErr" {
        value "125";
      }
      enum "errorDisabledReInitLmtReached" {
        value "126";
      }
      enum "ficonDupPortNum" {
        value "127";
      }
      enum "localRcf" {
        value "128";
      }
      enum "twoSwitchesWithSameWWN" {
        value "129";
      }
      enum "invalidOtherSidePrincEFPReqRecd" {
        value "130";
      }
      enum "domainOther" {
        value "131";
      }
      enum "elpFailureAllZeroPeerWWNRcvd" {
        value "132";
      }
      enum "preferredPathIsolation" {
        value "133";
      }
      enum "fcRedirectIsolation" {
        value "134";
      }
      enum "portActLicenseNotAvailable" {
        value "135";
      }
      enum "sdmIsolation" {
        value "136";
      }
      enum "fcidAllocationFailed" {
        value "137";
      }
      enum "externallyDisabled" {
        value "138";
      }
      enum "unavailableNPVUpstreamPort" {
        value "139";
      }
      enum "unavailableNPVPrefUpstreamPort" {
        value "140";
      }
      enum "sfpReadError" {
        value "141";
      }
      enum "stickyDownOnLinkFailure" {
        value "142";
      }
      enum "tooManyLinkFlapsErr" {
        value "143";
      }
      enum "unidirectionalUDLD" {
        value "144";
      }
      enum "txRxLoopUDLD" {
        value "145";
      }
      enum "neighborMismatchUDLD" {
        value "146";
      }
      enum "authzPending" {
        value "147";
      }
      enum "hotStdbyInBundle" {
        value "148";
      }
      enum "incompleteConfig" {
        value "149";
      }
      enum "incompleteTunnelCfg" {
        value "150";
      }
      enum "hwProgrammingFailed" {
        value "151";
      }
      enum "tunnelDstUnreachable" {
        value "152";
      }
      enum "suspendByMtu" {
        value "153";
      }
      enum "sfpInvalid" {
        value "154";
      }
      enum "sfpAbsent" {
        value "155";
      }
      enum "portCapabilitiesUnknown" {
        value "156";
      }
      enum "channelErrDisabled" {
        value "157";
      }
      enum "vrfMismatch" {
        value "158";
      }
      enum "vrfForwardReferencing" {
        value "159";
      }
      enum "dupTunnelConfigDetected" {
        value "160";
      }
      enum "primaryVLANDown" {
        value "161";
      }
      enum "vrfUnusable" {
        value "162";
      }
      enum "errDisableHandShkFailure" {
        value "163";
      }
      enum "errDisabledBPDUGuard" {
        value "164";
      }
      enum "dot1xSecViolationErrDisabled" {
        value "165";
      }
      enum "emptyEchoUDLD" {
        value "166";
      }
      enum "vfTaggingCapErr" {
        value "167";
      }
      enum "portDisabled" {
        value "168";
      }
      enum "tunnelModeNotConfigured" {
        value "169";
      }
      enum "tunnelSrcNotConfigured" {
        value "170";
      }
      enum "tunnelDstNotConfigured" {
        value "171";
      }
      enum "tunnelUnableToResolveSrcIP" {
        value "172";
      }
      enum "tunnelUnableToResolveDstIP" {
        value "173";
      }
      enum "tunnelVrfDown" {
        value "174";
      }
      enum "sifAdminDown" {
        value "175";
      }
      enum "phyIntfDown" {
        value "176";
      }
      enum "ifSifLimitExceeded" {
        value "177";
      }
      enum "sifHoldDown" {
        value "178";
      }
      enum "noFcoe" {
        value "179";
      }
      enum "dcxCompatMismatch" {
        value "180";
      }
      enum "isolateBundleLimitExceeded" {
        value "181";
      }
      enum "sifNotBound" {
        value "182";
      }
      enum "errDisabledLacpMiscfg" {
        value "183";
      }
      enum "satFabricIfDown" {
        value "184";
      }
      enum "invalidSatFabricIf" {
        value "185";
      }
      enum "noRemoteChassis" {
        value "186";
      }
      enum "vicEnableNotReceived" {
        value "187";
      }
      enum "vicDisableReceived" {
        value "188";
      }
      enum "vlanVsanMappingNotEnabled" {
        value "189";
      }
      enum "stpNotFwdingInFcoeMappedVlan" {
        value "190";
      }
      enum "moduleOffline" {
        value "191";
      }
      enum "udldAggModeLinkFailure" {
        value "192";
      }
      enum "stpInconsVpcPeerDisabled" {
        value "193";
      }
      enum "setPortStateFailed" {
        value "194";
      }
      enum "suspendedByVpc" {
        value "195";
      }
      enum "vpcCfgInProgress" {
        value "196";
      }
      enum "vpcPeerLinkDown" {
        value "197";
      }
      enum "vpcNoRspFromPeer" {
        value "198";
      }
      enum "protoPortSuspend" {
        value "199";
      }
      enum "tunnelSrcDown" {
        value "200";
      }
      enum "cdpInfoUnavailable" {
        value "201";
      }
      enum "fexSfpInvalid" {
        value "202";
      }
      enum "errDisabledIpConflict" {
        value "203";
      }
      enum "fcotClkRateMismatch" {
        value "204";
      }
      enum "portGuardTrustSecViolation" {
        value "205";
      }
      enum "sdpTimeout" {
        value "206";
      }
      enum "satIncompatTopo" {
        value "207";
      }
      enum "waitForFlogi" {
        value "208";
      }
      enum "satNotConfigured" {
        value "209";
      }
      enum "npivNotEnabledInUpstream" {
        value "210";
      }
      enum "vsanMismatchWithUpstreamSwPort" {
        value "211";
      }
      enum "portGuardBitErrRate" {
        value "212";
      }
      enum "portGuardSigLoss" {
        value "213";
      }
      enum "portGuardSyncLoss" {
        value "214";
      }
      enum "portGuardLinkReset" {
        value "215";
      }
      enum "portGuardCreditLoss" {
        value "216";
      }
      enum "ipQosMgrPolicyAppFailure" {
        value "217";
      }
      enum "pauseRateLimitErrDisabled" {
        value "218";
      }
      enum "lstGrpUplinkDown" {
        value "219";
      }
      enum "stickyDnLinkFailure" {
        value "220";
      }
      enum "routerMacFailure" {
        value "221";
      }
      enum "dcxMultipleMsapIds" {
        value "222";
      }
      enum "dcxHundredPdusRcvdNoAck" {
        value "223";
      }
      enum "enmSatIncompatibleUplink" {
        value "224";
      }
      enum "enmLoopDetected" {
        value "225";
      }
      enum "nonStickyExternallyDisabled" {
        value "226";
      }
      enum "subGroupIdNotAssigned" {
        value "227";
      }
      enum "vemUnlicensed" {
        value "228";
      }
      enum "profileNotFound" {
        value "229";
      }
      enum "nonExistentVlan" {
        value "230";
      }
      enum "vlanInvalidType" {
        value "231";
      }
      enum "vlanDown" {
        value "232";
      }
      enum "vpcPeerUpgrade" {
        value "233";
      }
      enum "ipQosDcbxpCompatFailure" {
        value "234";
      }
      enum "nonCiscoHbaVfTag" {
        value "235";
      }
      enum "domainIdConfigMismatch" {
        value "236";
      }
      enum "sfpSpeedMismatch" {
        value "237";
      }
      enum "xcvrInitializing" {
        value "238";
      }
      enum "xcvrAbsent" {
        value "239";
      }
      enum "xcvrInvalid" {
        value "240";
      }
      enum "vfcBindingInvalid" {
        value "241";
      }
      enum "vlanNotFcoeEnabled" {
        value "242";
      }
      enum "pvlanNativeVlanErr" {
        value "243";
      }
      enum "ethL2VlanDown" {
        value "244";
      }
      enum "ethIntfInvalidBinding" {
        value "245";
      }
      enum "pmonFailure" {
        value "246";
      }
      enum "l3NotReady" {
        value "247";
      }
      enum "speedMismatch" {
        value "248";
      }
      enum "flowControlMismatch" {
        value "249";
      }
      enum "vdcMode" {
        value "250";
      }
      enum "suspendedDueToMinLinks" {
        value "251";
      }
      enum "enmPinFailLinkDown" {
        value "252";
      }
      enum "inactiveM1PortFpathActiveVlan" {
        value "253";
      }
      enum "parentPortDown" {
        value "254";
      }
      enum "moduleRemoved" {
        value "255";
      }
      enum "corePortMct" {
        value "256";
      }
      enum "nonCorePortMct" {
        value "257";
      }
      enum "ficonInorderNotActive" {
        value "258";
      }
      enum "invalidEncapsulation" {
        value "259";
      }
      enum "modemLineDeasserted" {
        value "260";
      }
      enum "ipSecHndshkInProgress" {
        value "261";
      }
      enum "sfpEthCompliantErr" {
        value "262";
      }
      enum "cellularModemUnattached" {
        value "263";
      }
      enum "outOfGlblRxBuffers" {
        value "264";
      }
      enum "sfpFcCompliantErr" {
        value "265";
      }
      enum "ethIntfNotLicensed" {
        value "266";
      }
      enum "domainIdsInvalid" {
        value "267";
      }
      enum "fabricNameInvalid" {
        value "268";
      }
    }
    description
     "The cause of current operational state of the
      interface.
      
      GLOSSARY:
      
              BB        - Buffer-to-Buffer.
      
      BB_Credit - Buffer-to-Buffer credit, a link level flow
                  control mechanism.
      
      B_Port    - A Fibre Channel, Bridging port.
      
      BPDU      - Bridge Protocol Data Unit.
      
      CDP       - Cisco Discovery Protocol.
      
      Class F   - A connectionless service with notification on 
                  non-delivery between E_Ports, used for control, 
                  coordination, and configuration of the Fabric.
      
      Class N   - Refers to any class of service (different types
                  of frame delivery services) other than Class F.
      
      E_D_TOV   - Error Detect Timeout Value.
      
      ENM       - Egress Non-Multicast.
      
      ELP       - Exchange Link Parameter.
      
      E-mode    - A fibre channel port providing E_Port 
                  functionality. 
      
      E_Port    - A Fabric Expansion Port.  
      
      EPP       - Exchange Peer Parameters.
      
      ESC       - Exchange Switch Capabilities.
      
      Fabric    - The set of physically connected fibre channel
                  switches.
      
      FEX       - Fabric EXtender.
      
      FC-FS     - Fibre Channel Framing and Signaling.
      
      FCIP      - Fibre Channel over IP protocol.
      
      FCID      - Fibre Channel Domain ID.
      
      FCOE      - Fibre Channel Over Ethernet.
      
      FCOT      - Fibre channel optical transmitter.
      
      FC-PH     - The Fibre Channel Physical and Signaling 
                  standard.
      
      FCSP      - Fibre Channel Security Protocol. 
      
      Fibre Channel - The primary protocol for building SANs. 
      
      FICON     - An I\O protocol used between IBM (and compatible) 
                  mainframes and storage.
      
      FLOGI     - Fabric Login, used by a node port to establish a
                  session with the fabric.
      
      GBIC      - Gigabit Interface Converter; a removable 
                  transceiver module permitting Fibre Channel and 
                  Gigabit Ethernet physical-layer transport.
      
      Interconnect_Ports - Switch Ports that assume either the
                  E_Port or B_Port mode are generally referred to 
                  as Interconnect_Ports.
      
      LACP      - Link Access Control Protocol.
      
      LIP       - Loop Initialization Primitive sequence.
      
      LR        - Link Reset, the FC-PH defined primitive sequence 
                  used to initiate a link reset.
      
      MTU       - Maximun transmission unit. 
      
      NOS       - Not Operational Sequence, the FC-PH defined 
                  primitive sequence to indicate that the 
                  transmitting port has detected a link failure (or)
                  offline condition.
      
      VIC       - Virtual Interface Card.
      
      VPC       - Virtual Port Channel.
      
      NPIV      - N Port Identifier Virtualization.
      
      NPV       - NPort Virtualizer.
      
      Nx_Port   - A Fiber Channel Node Port. 
      
      OLS       - Offline Sequence, the FC-PH defined primitive 
                  sequence to indicate that the port is entering
                  into offline state.
      
      OHMS      - Online Health Management System.
      
      PMON      - Port Monitor.
      
      R_A_TOV   - Resource Allocation Timeout Value.
      
      RCF       - Reconfigure Fabric. 
      
      Rxbbcredit - Receive BB credit value configured for 
                   a FC interface.
      
      SAN       - Storage Area Network; a network linking computing 
                  devices to disk or tape arrays and other devices 
                  over Fibre Channel.
      
      SIF       - Service Information Field.
      
      SDM       - Security Device Manager.
      
      SDP       - Secure Device Provisioning.
      
      SFP       - Small Formfactor Pluggable.
      
      TE_Port   - Trunking E_Port.
      
      TOV       - Time out value.
      
      UDLD      - Uni Directional Link Detection.
      
      VDC       - Virtual Device Context.
      
      VEM       - Virtual Ethernet Module.
      
      VFC       - Virtual Fibre Channel.
      
      VRF       - VPN Routing and Forwarding.
      
      VSAN      - Virtual Storage Area Network.
      
      WWN       - World Wide Name.
      
      xE_Port   - A Fiber channel port that can assume either 
                  E_Port or TE_Port mode.
      
      The enumerated values which provides the cause of the current
      operational state of the interface are,
      
         'other(1)' - reasons other than defined here.
      
         'none(2)' - no failure.
      
         'hwFailure(3)' - hardware failure.  
      
         'loopbackDiagFailure(4)' - loopback diagnostics failure.
      
         'errorDisabled(5)' - the port is not operational due to 
             some error conditions that require administrative 
             attention.
      
         'swFailure(6)' - software failure.
      
         'linkFailure(7)' - physical link failure.
      
         'offline(8)' -  physical link is in offline state as 
             defined in the FC-FS standards.
      
         'nonParticipating(9)' - during loop initialization, the 
             port is not allowed to participate in loop operations.
      
         'initializing(10)' - port is being initialized. 
      
         'vsanInactive(11)'- port VSAN is inactive. The port becomes 
             operational again when the port VSAN is active. 
      
         'adminDown(12)' - ifAdminStatus is 'down'.
      
         'channelAdminDown(13)' - this port is a member of a port 
             channel and that port channel's ifAdminStatus is 
             'down'. 
      
         'channelOperSuspended(14)' - this port is a member of a 
             port channel and its operational parameters are 
             incompatible with the port channel parameters.  
      
         'channelConfigurationInProgress(15)' - this port is 
             undergoing a port channel configuration.
      
         'rcfInProgress(16)' - an isolated xE_port is transmitting 
             an reconfigure fabric, requesting a disruptive 
             reconfiguration in an attempt to build a single, 
             non-isolated fabric. Only the Interconnect_Ports can 
             become isolated. 
      
         'elpFailureIsolation(17)' - during a port initialization 
             the prospective Interconnect_Ports find incompatible 
             link parameters.
      
         'escFailureIsolation(18) - during a port initialization the 
             prospective Interconnect_Ports are unable to proceed 
             with initialization as a result of ESC.
      
         'domainOverlapIsolation(19)' - there is a overlap in 
             domains while attempting to connect two existing 
             fabrics.
      
         'domainAddrAssignFailureIsolation(20)' - the elected 
             principal switch is not capable of performing domain 
             address manager functions so no Nx_port traffic can be 
             forwarded across switches, hence all Interconnect_Ports 
             in the switch are isolated.
      
         'domainOtherSideEportIsolation(21)' - the peer E_port is 
             isolated.
      
         'domainInvalidRcfReceived(22)' - invalid RCF received.
      
         'domainManagerDisabled(23) - domain manager is disabled.
      
         'zoneMergeFailureIsolation(24)' - the two Interconnect_Ports 
             cannot merge zoning configuration after having exchanged 
             merging request for zoning.
      
         'vsanMismatchIsolation(25)' - this VSAN is not configured 
             on both sides of a trunk port.
      
         'parentDown(26)' - the physical port to which this interface 
             is bound is down.
      
         'srcPortNotBound(27)'- no source port is specified for this 
             interface.
      
         'interfaceRemoved(28)' - interface is being removed.
      
         'fcotNotPresent(29)' - FCOT (GBIC) not present.
      
         'fcotVendorNotSupported(30)' - FCOT (GBIC) vendor is not 
             supported. 
      
         'incompatibleAdminMode(31)' - port administrative mode is 
             incompatible with port capabilities. 
      
         'incompatibleAdminSpeed(32)' - port speed is incompatible 
             with port capabilities. 
      
         'suspendedByMode(33)' - port that belongs to a port channel
             is suspended due to incompatible operational mode.
      
         'suspendedBySpeed(34)' - port that belongs to a port channel
             is suspended due to incompatible operational speed.
      
         'suspendedByWwn(35)' - port that belongs to a port channel 
             is suspended due to incompatible remote switch WWN.
      
         'domainMaxReTxFailure(36)' - domain manager failure after 
             maximum retries.
      
         'eppFailure(37)' - trunk negotiation protocol failure after 
             maximum retries.
      
         'portVsanMismatchIsolation(38)' - an attempt is made to 
             connect two switches using non-trunking ports having 
             different port VSANs. 
      
         'loopbackIsolation(39)' - port is connected to another port 
             in the same switch.
      
         'upgradeInProgress(40)' - linecard upgrade in progress.
      
         'incompatibleAdminRxBbCredit(41)' - receive BB credit is 
             incompatible.
      
         'incompatibleAdminRxBufferSize(42)' - receive buffer size 
             is incompatible.
      
         'portChannelMembersDown(43)' - no operational members.
      
         'zoneRemoteNoRespIsolation(44)' - isolation due to remote 
             zone server not responding.
      
         'firstPortUpAsEport(45)' - in a over subscribed line card, 
             when the first port in a group is up in E-mode, other 
             ports in that group cannot be brought up.
      
         'firstPortNotUp(46)' - in a over subscribed line card, 
             first port cannot be brought up in E-mode when the 
             other ports in the group are up.
      
         'peerFcipPortClosedConnection(47)' - port went down because 
             peer FCIP port closed TCP connection.    
      
         'peerFcipPortResetConnection(48)' - port went down because 
             the TCP connection was reset by the peer FCIP port.
      
         'fcipPortMaxReTx(49)' - FCIP port went down due to maximum 
             TCP re-transmissions reached the configured limit.
      
         'fcipPortKeepAliveTimerExpire(50)' - FCIP port went down 
             due to TCP keep alive timer expired.
      
         'fcipPortPersistTimerExpire(51)' - FCIP port went down due 
             to TCP persist timer expired.
      
         'fcipPortSrcLinkDown(52)' - FCIP port went down due to 
             Ethernet link down.
      
         'fcipPortSrcAdminDown(53)' - FCIP port went down because 
             the source Ethernet link was administratively shutdown.
      
         'fcipPortAdminCfgChange(54)' - FCIP port went down due to 
             configuration change. 
      
         'fcipSrcPortRemoved(55)' - FCIP port went down due to source 
             port removal.
      
         'fcipSrcModuleNotOnline(56)' - FCIP port went down due to 
             source module not online.
      
         'invalidConfig(57)' - this port has a misconfiguration with 
             respect to port channels.
      
         'portBindFailure(58)' - port got isolated due to port bind 
             failure.  
      
         'portFabricBindFailure(59)' - port got isolated due to 
             fabric bind failure.    
      
         'noCommonVsanIsolation(60)' - trunk is isolated because 
             there are no common VSANs with peer.
      
         'ficonVsanDown (61)' - FICON VSAN down.
      
         'invalidAttachment (62)' -  invalid attachment.
      
         'portBlocked (63)' - port blocked due to FICON. 
      
         'incomAdminRxBbCreditPerBuf (64)' - disabled due to 
             incompatible administrative port rxbbcredit, 
             performance buffers.
      
         'tooManyInvalidFlogis (65)' - suspended due to too many 
             invalid FLOGIs. 
      
         'deniedDueToPortBinding (66)' - suspended due to port 
             binding.
      
         'elpFailureRevMismatch (67)' - isolated for ELP failure due 
             to revision mismatch.
      
         'elpFailureClassFParamErr (68)' - isolated for ELP failure 
             due to Class F parameter error.
      
         'elpFailureClassNParamErr (69)' - isolated for ELP failure 
             due to Class N parameter error.
      
         'elpFailureUnknownFlowCtlCode (70)' - isolated for ELP 
             failure due to invalid flow control code.
      
         'elpFailureInvalidFlowCtlParam (71)' - isolated for ELP 
             failure due to invalid flow control parameter.
      
         'elpFailureInvalidPortName(72)' - isolated for ELP failure 
             due to invalid port name.
      
         'elpFailureInvalidSwitchName (73)' - isolated for ELP 
             failure due to invalid switch name.
      
         'elpFailureRatovEdtovMismatch (74)' - isolated for ELP 
             failure due to R_A_TOV or E_D_TOV mismatch.
      
         'elpFailureLoopbackDetected (75)' - isolated for ELP 
             failure due to loopback detected.
      
         'elpFailureInvalidTxBbCredit (76)' - isolated for ELP 
             failure due to invalid transmit BB credit.
      
         'elpFailureInvalidPayloadSize (77)' - isolated for ELP 
             failure due to invalid payload size.
      
         'bundleMisCfg (78)' - misconfiguration in port channel 
             membership detected.
      
         'bitErrRuntimeThreshExceeded (79)' - bit error rate too 
             high. It has exceeded the run time threshold.
      
         'linkFailLinkReset (80)' - link failure due to link reset.
      
         'linkFailPortInitFail (81)' - link failure due to port 
             initialization failure.
      
         'linkFailPortUnusable (82)' - link failure due to port 
             unusable.
      
         'linkFailLossOfSignal (83)' - link failure due to loss of 
             signal. 
      
         'linkFailLossOfSync (84)' - link failure due to loss of 
             sync.
      
         'linkFailNosRcvd (85)' - link failure due to non-operational 
             sequences received.
      
         'linkFailOLSRcvd (86)' - link failure due to offline 
             sequences received.
      
         'linkFailDebounceTimeout (87)' - link failure due to 
             re-negotiation failed.
      
         'linkFailLrRcvd (88)' - link failure when link reset(LR) 
             operation fails due to non-empty receive queue.  
      
         'linkFailCreditLoss (89)' - link failure due to excessive 
             credit loss indications.
      
         'linkFailRxQOverflow (90)' - link failure due to receive 
             queue overflow.
      
         'linkFailTooManyInterrupts (91)' - link failure due to 
             excessive port interrupts.
      
         'linkFailLipRcvdBb (92)' - link failure when loop 
             initialization(LIP) operation fails due to non empty 
             receive queue.
      
         'linkFailBbCreditLoss (93)' - link failure when link 
             reset(LR) operation fails due to queue not empty.
      
         'linkFailOpenPrimSignalTimeout (94)' - link failure due to
             open primitive signal timeout while receive queue
             not empty.
      
         'linkFailOpenPrimSignalReturned (95)' - link failure due to
             open primitive signal returned while receive queue 
             not empty. 
      
         'linkFailLipF8Rcvd (96)' - link failure due to F8 LIP 
             received.
      
         'linkFailLineCardPortShutdown (97)' - link failure due to 
             port shutdown.
      
         'fcspAuthenFailure (98)' - fibre channel security protocol 
             authorization fail.
      
         'fcotChecksumError (99)' - FCOT SPROM checksum error. 
      
         'ohmsExtLoopbackTest (100)' - link suspended due to external 
             loopback diagnostics failure.
      
         'invalidFabricBindExchange (101)' - invalid fabric binding 
             exchange.
      
         'tovMismatch (102)' - link isolation due to TOV mismatch.
      
         'ficonNotEnabled (103)' - FICON not enabled.
      
         'ficonNoPortNumber (104)' - no FICON port number.
      
         'ficonBeingEnabled (105)' - FICON is being enabled.
      
         'ePortProhibited (106)' - port down because FICON prohibit 
             mask in place for E/TE port.
      
         'portGracefulShutdown (107)' - port has been shutdown 
             gracefully.
      
         'trunkNotFullyActive (108)' - some of the VSANs which are 
             common with the peer are not up.
      
         'fabricBindingSwitchWwnNotFound (109)' - peer switch WWN not 
             found in fabric binding active database.
      
         'fabricBindingDomainInvalid (110)' - peer domain ID is 
             invalid in fabric binding active database.
      
         'fabricBindingDbMismatch (111)' - fabric binding active 
             database mismatch with peer. 
      
         'fabricBindingNoRspFromPeer (112)' - fabric binding no 
             response from peer.
      
         'dpvmVsanSuspended (113)' - dpvm vsan is suspended.
      
         'dpvmVsanNotFound (114)' - dpvm vsan not found.
      
         'trackedPortDown (115)' - port down because tracked
             port is down.
      
         'ecSuspendedOnLoop (116)' - port suspended because extended
             BB credits are configured on loop port.
      
         'isolateBundleMisCfg (117)' - port isolated due to bundle
             mis-configuration.
      
         'noPeerBundleSupport (118)' - peer port does not support
             bundle.
      
         'portBringupIsolation (119)' - trunk port isolated during 
             bringup time.
      
         'domainNotAllowedIsolated (120)' - port isolated due to
             domain not allowed.
      
         'virtualIvrDomainOverlapIsolation (121)' - port isolated
                    due to virtual IVR domain overlap.
      
         'outOfService (122)' - port is in out of service state.
      
         'portAuthFailed (123)' - port has encountered an 802.1x 
          authentication failure.
      
         'bundleStandby (124)' - port cannot be brought up in 
                 a bundle, since the bundle has max members.
      
         'portConnectorTypeErr (125)' - Error in the port connector 
          type (SFP).
      
         'errorDisabledReInitLmtReached (126)' - the port is not 
          operational after trying to initialize the port multiple 
          times due to some erorrs.
      
         'ficonDupPortNum (127)' - the ficon vsan has a duplicate 
          port number.
      
         'localRcf (128)' - fcdomain applied a locally disruptive
          reconfiguration (the local domain became invalid; no 
          RCF frames have been sent outside the local switch).
      
          'twoSwitchesWithSameWWN (129)' - merge attempt between
          VSANs containing the same WWN. If the user attempts to 
          merge two different VSANs and both have at least one 
          switch with the same WWN then the link in between the 
          VSANs is isolated.
      
          'invalidOtherSidePrincEFPReqRecd (130)' - EFP request frame
          indicating a principal switch other than the locally 
          known one.
      
          'domainOther (131)' - other domain manager reasons not 
          defined here.
      
          'elpFailureAllZeroPeerWWNRcvd (132)' - isolated for ELP 
          failure due to peer WWN is received with all zeros.
      
          'preferredPathIsolation (133)' - port isolated due to
           preferred path not able to program the routes.
      
          'fcRedirectIsolation (134)' - port isolated due to
                  FC Redirect not being able to program routes.
      
           'portActLicenseNotAvailable (135)' - port not brought up
              due to lack of port activation licenses.
      
           'sdmIsolation (136)' - port isolated due to SDM 
              (Security Device Manager) not being
              able to program routes.
      
           'fcidAllocationFailed (137)' - port down due to failure
              in FCID (Fibre Channel Domain ID) allocation.   
      
           'externallyDisabled (138)' - port externally disabled.
      
           'unavailableNPVUpstreamPort (139)' - NPV 
                   (NPort Virtualizer) upstream port not available.
      
           'unavailableNPVPrefUpstreamPort (140)' - NPV 
              (NPort Virtualizer) preferred 
              upstream port not available.
      
           'sfpReadError (141)' - the port is not operational due to 
                   SFP (Small Formfactor Pluggable) read error.
      
           'stickyDownOnLinkFailure (142)' - the port is 
                   not operational due to link failure 
                   in the sticky down mode.
      
           'tooManyLinkFlapsErr (143)' - too many link flaps 
                   on the port in a short interval.
      
           'unidirectionalUDLD (144)' - unidirectional UDLD 
              (Uni Directional Link Detection) detected.
      
           'txRxLoopUDLD (145)' - UDLD (Uni Directional 
                   Link Detection) Tx Rx loop.
      
           'neighborMismatchUDLD (146)' - UDLD 
              (Uni Directional Link Detection) neighbor mismatch.
      
           'authzPending (147)' - authorization pending.
      
           'hotStdbyInBundle (148)' - hot standby in bundle.
      
           'incompleteConfig (149)' - all parameters on the port 
                            have not been configured.
      
           'incompleteTunnelCfg (150)' - incomplete tunnel config.
      
           'hwProgrammingFailed (151)' - hardware programming failed.
      
           'tunnelDstUnreachable (152)' - no route to 
                   tunnel destination address.
      
           'suspendByMtu (153)' - MTU allocation failed.
      
           'sfpInvalid (154)' - SFP (Small Formfactor Pluggable) 
              is not Cisco certified.
      
           'sfpAbsent (155)' - SFP (Small Formfactor 
                   Pluggable) is absent.
      
          'portCapabilitiesUnknown (156)' - the capabilities of the 
                  port are unknown.
      
           'channelErrDisabled (157)' - the port-channel to which 
                   the port belongs is in error disabled state.
      
           'vrfMismatch (158)' - Mismatch in source and transport VRF
                      (VPN Routing and Forwarding).
      
           'vrfForwardReferencing (159)' - Forward referencing 
                   transport VRF (VPN Routing and Forwarding).
      
           'dupTunnelConfigDetected (160)' - two tunnel interfaces 
                   with same configuration is not allowed.
      
           'primaryVLANDown (161)' - primary VLAN is in down state.
      
           'vrfUnusable (162)' - VRF (VPN Routing and Forwarding) 
                  is unusable.
      
           'errDisableHandShkFailure (163)' - port is not operational 
                           due to an internal handshake failure.
      
           'errDisabledBPDUGuard (164)' - BPDUGuard 
           (Bridge Protocol Data Unit) triggered 
           error disable on the port.
      
           'dot1xSecViolationErrDisabled (165)' - error disabled 
                 due to dot1x security violation.
      
           'emptyEchoUDLD (166)' - UDLD (Uni Directional 
                   Link Detection) empty echo.
      
           'vfTaggingCapErr (167)' - VF Tagging capability 
                   mismatch error.
      
           'portDisabled (168)' - Port disabled.
      
           'tunnelModeNotConfigured (169)' - Tunnel Mode is not 
                           configured.
      
           'tunnelSrcNotConfigured (170)' - Tunnel Source is not 
                           configured. 
      
           'tunnelDstNotConfigured (171)' - Tunnel Destination 
                           is not configured.
      
           'tunnelUnableToResolveSrcIP (172)' - Unable to resolve 
                           tunnel source IP address. 
      
           'tunnelUnableToResolveDstIP (173)' - Unable to resolve 
                           tunnel destination IP address.
      
           'tunnelVrfDown (174)' - Tunnel VRF down.
      
           'sifAdminDown (175)' - SIF (Service Information Field) 
              is admin down.
      
           'phyIntfDown (176)' - Physical interface is down.
      
           'ifSifLimitExceeded (177)' - Interface SIF 
           (Service Information Field)limit is exceeded.
      
           'sifHoldDown (178)' - SIF (Service Information Field) 
                   hold down.
      
           'noFcoe (179)' - No FCOE (Fibre Channel Over Ethernet) 
              configuration.
      
           'dcxCompatMismatch (180)' - DCX Compatibility Mismatch.
      
           'isolateBundleLimitExceeded (181)' - Isolation due to 
                       bundle limit exceeded.
      
           'sifNotBound (182)' - SIF (ervice Information Field) 
                   is not bound.
      
           'errDisabledLacpMiscfg (183)' - Error Disabled due to 
                   LACP (Link Access Control Protocol) misconfig.
      
           'satFabricIfDown (184)' - Satellite fabric interface down.
      
           'invalidSatFabricIf (185)' - Invalid satellite fabric 
                           interface.
      
           'noRemoteChassis (186)' - No remote chassis.
      
           'vicEnableNotReceived (187)' - VIC enable not received.
      
           'vicDisableReceived (188)' - VIC disable received.
      
           'vlanVsanMappingNotEnabled (189)' - VLAN VSAN mapping not 
                           enabled.
      
           'stpNotFwdingInFcoeMappedVlan (190)' - STP not forwarding 
                           in FCOE Mapped Vlan.
      
           'moduleOffline (191)' - Module Offline.
      
           'udldAggModeLinkFailure (192)' - UDLD (Uni Directional Link
              Detection) aggresive mode link failure.
      
           'stpInconsVpcPeerDisabled (193)' - STP inconsistent 
                   VPC (Virtual Port Channel) peer disabled. 
      
           'setPortStateFailed (194)' - Set port state failed.
      
           'suspendedByVpc (195)' - Suspended by VPC 
                   (Virtual Port Channel).
      
           'vpcCfgInProgress (196)' - VPC (Virtual Port Channel)
               configuration in progress.
      
           'vpcPeerLinkDown (197)' - VPC (Virtual Port Channel)
               peer link down.
      
           'vpcNoRspFromPeer (198)' - VPC (Virtual Port Channel) 
              no response from peer.
      
           'protoPortSuspend (199)' - Proto port suspend.
      
           'tunnelSrcDown (200)' - Tunnel source down.
      
           'cdpInfoUnavailable (201)' - CDP 
           (Cisco Discovery Protocol) information unavailable.
      
           'fexSfpInvalid (202)' - FEX (Fabric Extender) 
           SFP (Small Formfactor Pluggable) invalid.
      
           'errDisabledIpConflict (203)' - Error Disabled due to IP
                            conflict.
      
           'fcotClkRateMismatch (204)' - FCOT CLK rate mismatch.
      
           'portGuardTrustSecViolation (205)' - Error disabled due 
               to port guard (Cisco Trusted Security Violation).
      
           'sdpTimeout (206)' - SDP (Secure Device Provisioning)
                    timeout.
      
           'satIncompatTopo (207)' - Satellite incompatible topology.
      
           'waitForFlogi (208)' - Wait for FLOGI.
      
           'satNotConfigured (209)' - Satellite not configured.
      
           'npivNotEnabledInUpstream (210)' - NPIV (N Port Identifier
              Virtualization) not enabled in upstream.
      
           'vsanMismatchWithUpstreamSwPort (211)' - VSAN 
                   mismatch with upstream switch port.
      
           'portGuardBitErrRate (212)' - Error disabled due to port 
                           guard (Bit Error Rate).
      
           'portGuardSigLoss (213)' - Error disabled due to 
                   port guard (Signal Loss).
      
           'portGuardSyncLoss (214)' - Error disabled due to port 
                           guard (Sync Loss).
      
           'portGuardLinkReset (215)' - Error disabled due to port
                           guard (Link Reset).
      
           'portGuardCreditLoss (216)' - Error disabled due to port
                           guard (Credit Loss).
      
           'ipQosMgrPolicyAppFailure (217)' - IP QOS Manager policy 
                        application failure.
      
           'pauseRateLimitErrDisabled (218)' - Port error disabled due
                                      to pause rate limit condition.
      
           'lstGrpUplinkDown (219)' - EthPM LSTGRP downstream link 
                           down due to upstream link down.
      
           'stickyDnLinkFailure (220)' - Port kept in error disabled
                                       state due to Link Failure.
      
           'routerMacFailure (221)' - Router MAC failure.
      
           'dcxMultipleMsapIds (222)' - Port error disabled due to
                                      multiple MSAP IDs (DCX).
      
           'dcxHundredPdusRcvdNoAck (223)' - Hundred PDUs received 
                           without ACK (DCX).
      
           'enmSatIncompatibleUplink (224)' - Satellite Incompatible 
                           Uplink.
      
           'enmLoopDetected (225)' - Loop Detected (ENM).
      
           'nonStickyExternallyDisabled (226)' - Disabled by VPD 
                           Manager with shut/no shut allowed.
      
           'nonStickyExternallyDisabled (227)' - Sub-group ID 
                           not assigned.
      
           'vemUnlicensed (228)' - VEM Unlicensed.
      
           'profileNotFound (229)' - Profile not found.
      
           'nonExistentVlan (230)' - VLAN does not exist.
      
           'vlanInvalidType (231)' - Invalid VLAN type.
      
           'vlanDown (232)' - VLAN down.
      
           'vpcPeerUpgrade (233)' - VPC Peer Upgrade.
      
           'ipQosDcbxpCompatFailure (234)' - IPQOS DCBXP compatibility
                         failure.
      
           'nonCiscoHbaVfTag (235)' - Error Disabled due to Non-Cisco 
                           HBA VF Tag.
      
           'domainIdConfigMismatch (236)' - Domain ID config mismatch.
      
           'sfpSpeedMismatch (237)' - SFP (Small Formfactor Pluggable)
               speed mismatch.
           'xcvrInitializing (238)' - Transceiver initializing.
      
           'xcvrAbsent (239)' - Transceiver absent.
      
           'xcvrInvalid (240)' - Transceiver invalid.
      
           'vfcBindingInvalid (241)' - Invalid VFC Binding.
      
           'vlanNotFcoeEnabled (242)' - VLAN down due to FCOE 
                           disabled.
      
           'pvlanNativeVlanErr (243)' - Private VLAN 
                           Native VLAN error.
      
           'ethL2VlanDown (244)' - Ethernet L2 VLAN down.
      
           'ethIntfInvalidBinding (245)' - Invalid Binding 
                   to Ethernet Interface.
      
           'pmonFailure (246)' - PMON Failure.
      
           'l3NotReady (247)' - L3 not ready.
      
           'speedMismatch (248)' - Speed Mismatch.
      
           'flowControlMismatch (249)' - Flow Control Mismatch.
      
           'vdcMode (250)' - VDC mode 
      
           'suspendedDueToMinLinks (251)' - Suspended due 
                           to Min Links.
      
           'enmPinFailLinkDown (252)' - ENM Pin Fail Link Down.
      
           'inactiveM1PortFpathActiveVlan (253)' - Inactive M1 Port
                                  F Path Active VLAN.
      
           'parentPortDown (254)' - Parent Port Down.
      
           'moduleRemoved (255)' - Module Removed.
      
           'corePortMct (256)' - Core Port MCT.
      
           'nonCorePortMct (257)' - Non Core port MCT.
      
           'ficonInorderNotActive (258)'- FICON Inorder Not Active.
      
           'invalidEncapsulation (259)' - Invalid Encapsulation.
      
           'modemLineDeasserted (260)' - Modem line Deasserted.
      
           'ipSecHndshkInProgress (261)' - IP Sec Handshake in 
                                   progress.
      
           'sfpEthCompliantErr (262)' - Sfp Ethernet compliant error.
      
           'cellularModemUnattached (263)' - Cellular Modem 
                           unattached.
      
           'outOfGlblRxBuffers (264)' - Out of Global Rx Buffers.
      
           'sfpFcCompliantErr (265)' - Sfp Fc compliant Error.
      
           'ethIntfNotLicensed (266)' - Ethernet Interface Not 
                                           Licensed.
      
           'domainIdsInvalid (267)' - Domain IDs Invalid.
      
           'fabricNameInvalid (268)' - Fabric Name Invalid.";
  }

  typedef EntLogicalIndexOrZero {
    type int32 {
      range "0..2147483647";
    }
    description
     "This textual convention is an extension of entLogicalIndex.
      If non-zero, the semantic is same as entLogicalIndex object.
      If zero, no appropriate entLogicalIndex exists.  Any additional 
      semantics must be defined as part of the description of any 
      object which uses this syntax.";
  }

  typedef CiscoURLString {
    type binary {
      length "1..255";
    }
    description
     "This textual convention defines the URL string.
      The  Universal Resource Locator(URL). The URL strings
      are compact string representation for a resource
      available via internet. This is the address location 
      of the page to load. The string should represent a
      fully qualifying string with the format 
      'protocol:/server/page'. In general the string should 
      point to any value that can be saved/loaded.
      Any limitation for the URL must be defined as part of
      the description of any object which uses this syntax.";
    reference
     "Uniform Resource Locators. RFC 1738.";
  }

  typedef CiscoURLStringOrEmpty {
    type binary {
      length "0..255";
    }
    description
     "This textual convention is an extension of CiscoURLString.
      This extension permits the additional value of empty (zero
      length) string.  The description of any object which uses this
      syntax must specifically describe the meaning of empty string
      value.";
    reference
     "Uniform Resource Locators. RFC 1738.";
  }

  typedef CiscoHTTPResponseStatusCode {
    type uint32 {
      range "100..599";
    }
    description
     "This corresponds to the HTTP Status code.
      The Status-Code element in HTTP response is 
      a 3-digit integer result code of the attempt
      to understand and satisfy the HTTP request
      The Status-Code is intended for use by automata.
      
      The first digit of the Status-Code defines the class of 
      response.  The last two digits do not have any 
      categorization role. There are 5 values for the first digit:
      
       - 1xx: Informational - Request received, continuing process
      
       - 2xx: Success - The action was successfully received,
              understood, and accepted
      
       - 3xx: Redirection - Further action must be taken in order 
              to complete the request
      
       - 4xx: Client Error - The request contains bad syntax 
              or cannot be fulfilled
      
       - 5xx: Server Error - The server failed to fulfill an 
              apparently valid request.";
    reference
     "RFC 2616 Section 6.1.1 Status Code and Reason Phrase.";
  }

  typedef CvE164Address {
    type binary {
      length "1..128";
    }
    description
     "A UTF-8 string limited to the character set defined for
      E.164, '0123456789*#,'.
      Note that  represents the double quote which
      cannot be contained in a SMI description clause.
           OR
      An IA5String limited to the character set '0123456789*#,.'";
    reference
     "ITU-T E.164, Q.931 chapter 4.5.10
      ITU-H H.225.0 Annex H";
  }

  typedef CiscoVlanList {
    type binary {
      length "0..128";
    }
    description
     "Each octet within this value specifies a set of eight
      VLANs. The object defined by this textual convention
      can specify a VLAN range of 1k VLANs in its description.
      Example: 0 - 1023, 1024 - 2047, etc. The first octet
      represents the first 8 VLANs of the range of VLANs
      specified by the object, the second octet represents
      the next 8 VLANs, etc. When a VLAN range is not
      specified, a default VLAN range of '0 - 1023' is assumed.
      
      Within each octet, the most significant bit represents
      the lowest numbered VLAN, and the least significant bit
      represents the highest numbered VLAN. Thus, each VLAN
      of the device is represented by a single bit within the
      value of this object.  If that bit has a value of '1'
      then that VLAN is included in the set of VLANs; the VLAN
      is not included if its bit has a value of '0'.
      
      Note that if the length of this string is less than
      128 octets, any 'missing' octets are assumed to contain
      the value zero. An NMS may omit any zero-valued octets
      from the end of this string in order to reduce SetPDU size,
      and the agent may also omit zero-valued trailing octets,
      to reduce the size of GetResponse PDUs.";
  }

  typedef CiscoCosList {
    type bits {
      bit cos0 {
        position "0";
      }
      bit cos1 {
        position "1";
      }
      bit cos2 {
        position "2";
      }
      bit cos3 {
        position "3";
      }
      bit cos4 {
        position "4";
      }
      bit cos5 {
        position "5";
      }
      bit cos6 {
        position "6";
      }
      bit cos7 {
        position "7";
      }
    }
    description
     "Each bit represents a CoS value (0 through 7).";
  }

  typedef CiscoPbbServiceIdentifier {
    type uint32 {
      range "1..16777216";
    }
    description
     "An integer-value which identifies the service instance of
      the Provider Backbone Bridge frame.";
    reference
     "IEEE P802.1ah/D3.3 chapter 9.8, December 2006";
  }

  typedef CiscoBridgeDomain {
    type uint32 {
      range "1..65535";
    }
    description
     "An object with this syntax contains a bridge domain number
      which is used to distinguish between multiple bridge domains. A
      bridge domain represents a set of (logical) Ethernet segments
      which are interconnected by 802.1D bridges. 802.1Q allows for a
      maximum of 4095 VLANs within a bridge domain. Some devices can
      be connected to multiple bridge domains, e.g., routers with
      some of their interfaces in one bridge domain and other
      interfaces in other bridge domain. In such devices, the
      combination of bridge-domain-number and VLAN-id can be used to
      uniquely identify any VLAN across all interfaces.";
  }

  typedef Cisco2KVlanList {
    type binary {
      length "0..256";
    }
    description
     "Each octet within this value specifies a set of eight VLANs.
      The object defined by this textual convention can specify a VLAN
      range of 2k VLANs in its description. Example: 0 - 2047, 2048 -
      4095, etc. The first octet represents the first 8 VLANs of the
      range of VLANs specified by the object, the second octet
      represents the next 8 VLANs, etc.
      
      Within each octet, the most significant bit represents the
      lowest numbered VLAN, and the least significant bit represents
      the highest numbered VLAN. Thus, each VLAN of the device is
      represented by a single bit within the value of this object. If
      that bit has a value of '1' then that VLAN is included in the
      set of VLANs; the VLAN is not included if its bit has a value of
      '0'.
      
      Note that if the length of this string is less than 256 octets,
      any 'missing' octets are assumed to contain the value zero. An
      NMS may omit any zero-valued octets from the end of this string
      in order to reduce SetPDU size, and the agent may also omit
      zero-valued trailing octets, to reduce the size of GetResponse
      PDUs.";
  }

  typedef CiscoInterfaceIndexList {
    type binary {
      length "0..256";
    }
    description
     "This textual convention contains a list of ifIndex values.
      
      Each ifIndex value is represented by four octets.
      Every set of four octets represents a value of an instance
      of ifIndex object, defined in IF-MIB, corresponding to a
      particular interface.
      
      For example, the first octet to the fourth octet represent a 
      value of the instance of ifIndex object for the first 
      interface in the list.  The fifth octet to the eighth octet 
      represent a value of the instance of ifIndex object for
      the second interface in the list.
      
      Up to 64 interfaces can be represented by this textual 
      convention.";
  }

  typedef CiscoVrfName {
    type binary {
      length "0..32";
    }
    description
     "The name of the Virtual Private Network Routing and
      Forwarding (VRF) domain.
      
      Semantics of a zero length CiscoVrfName are object-specific
      and must be defined as part of the description of any object
      which uses this syntax.";
  }

  typedef CiscoEntityIndexList {
    type binary {
      length "0..256";
    }
    description
     "This text convention contains a list of entPhysicalIndex
      values.
      
      Each entPhysicalIndex value is represented by four
      octets. Every set of four octets represents a value of an
      instance of entPhysicalIndex object, defined in ENTITY-MIB,
      corresponding to a particular physical entity.
      
      For example, the first octet to the fourth octet
      represents a value of the instance of entPhysicalIndex object
      for the first physical entity in the list. The fifth octet to
      the eighth octet represents a value of the instance of
      entPhysicalIndex object for the second physical entity in the
      list.
      
      Up to 64 physical entities can be represented by this
      textual convention.";
  }

  smiv2:alias "ciscoTextualConventions" {
    smiv2:oid "1.3.6.1.4.1.9.12.1";
  }

}
