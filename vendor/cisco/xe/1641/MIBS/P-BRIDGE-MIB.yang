/*
 * Generated by confdc --mib2yang-std
 * Source: mgmt/dmi/model/common/mib-source/P-BRIDGE-MIB.mib
 */
/*
 * This YANG module has been generated by smidump 0.5.0:
 *
 *      smidump -f yang P-BRIDGE-MIB
 *
 * Do not edit. Edit the source file instead!
 */

module P-BRIDGE-MIB {

  namespace "urn:ietf:params:xml:ns:yang:smiv2:P-BRIDGE-MIB";
  prefix P-BRIDGE-MIB;

  import BRIDGE-MIB {
    prefix "bridge-mib";
  }

  import SNMPv2-TC {
    prefix "snmpv2-tc";
  }

  import ietf-yang-smiv2 {
    prefix "smiv2";
  }

  import ietf-yang-types {
    prefix "yang";
  }

  organization
   "IETF Bridge MIB Working Group";

  contact
   "Email:  bridge-mib@ietf.org
    ietfmibs@ops.ietf.org
    
    David Levi
    Postal: Nortel Networks
    4655 Great America Parkway
    Santa Clara, CA 95054
    USA
    Phone: +1 865 686 0432
    Email: dlevi@nortel.com
    
    David Harrington
    Postal: Effective Software
    50 Harding Rd.
    Portsmouth, NH 03801
    USA
    Phone: +1 603 436 8634
    Email: ietfdbh@comcast.net
    
    Les Bell
    Postal: Hemel Hempstead, Herts. HP2 7YU
    UK
    Email: elbell@ntlworld.com
    
    Vivian Ngai
    
    Email: vivian_ngai@acm.org
    
    Andrew Smith
    Postal: Beijing Harbour Networks
    Jiuling Building
    21 North Xisanhuan Ave.
    Beijing, 100089
    PRC
    Fax: +1 415 345 1827
    Email: ah_smith@acm.org
    
    Paul Langille
    Postal: Newbridge Networks
    5 Corporate Drive
    Andover, MA 01810
    USA
    Phone: +1 978 691 4665
    Email: langille@newbridge.com
    
    Anil Rijhsinghani
    Postal: Accton Technology Corporation
    5 Mount Royal Ave
    Marlboro, MA 01752
    USA
    Phone:
    Email: anil@accton.com
    
    Keith McCloghrie
    Postal: Cisco Systems, Inc.
    170 West Tasman Drive
    San Jose, CA 95134-1706
    USA
    Phone: +1 408 526 5260
    Email: kzm@cisco.com";

  description
   "The Bridge MIB Extension module for managing Priority
    and Multicast Filtering, defined by IEEE 802.1D-1998,
    including Restricted Group Registration defined by
    IEEE 802.1t-2001.
    
    Copyright (C) The Internet Society (2006).  This version of
    this MIB module is part of RFC 4363; See the RFC itself for
    full legal notices.";

  revision 2006-01-09 {
    description
     "Added dot1dPortRestrictedGroupRegistration.
      Deprecated pBridgePortGmrpGroup and pBridgeCompliance
      and added pBridgePortGmrpGroup2 and pBridgeCompliance2.";
  }

  revision 1999-08-25 {
    description
     "The Bridge MIB Extension module for managing Priority
      and Multicast Filtering, defined by IEEE 802.1D-1998.
      
      Initial version, published as RFC 2674.";
  }

  typedef EnabledStatus {
    type enumeration {
      enum "enabled" {
        value "1";
      }
      enum "disabled" {
        value "2";
      }
    }
    description
     "A simple status value for the object.";
  }


  container P-BRIDGE-MIB {
    config false;

    container dot1dExtBase {
      smiv2:oid "1.3.6.1.2.1.17.6.1.1";

      leaf dot1dDeviceCapabilities {
        type bits {
          bit dot1dExtendedFilteringServices {
            position "0";
          }
          bit dot1dTrafficClasses {
            position "1";
          }
          bit dot1qStaticEntryIndividualPort {
            position "2";
          }
          bit dot1qIVLCapable {
            position "3";
          }
          bit dot1qSVLCapable {
            position "4";
          }
          bit dot1qHybridCapable {
            position "5";
          }
          bit dot1qConfigurablePvidTagging {
            position "6";
          }
          bit dot1dLocalVlanCapable {
            position "7";
          }
        }
        description
         "Indicates the optional parts of IEEE 802.1D and 802.1Q
          that are implemented by this device and are manageable
          through this MIB.  Capabilities that are allowed on a
          per-port basis are indicated in dot1dPortCapabilities.
          
          dot1dExtendedFilteringServices(0),
                                -- can perform filtering of
                                -- individual multicast addresses
                                -- controlled by GMRP.
          dot1dTrafficClasses(1),
                                -- can map user priority to
                                -- multiple traffic classes.
          dot1qStaticEntryIndividualPort(2),
                                -- dot1qStaticUnicastReceivePort &
                                -- dot1qStaticMulticastReceivePort
                                -- can represent non-zero entries.
          dot1qIVLCapable(3),   -- Independent VLAN Learning (IVL).
          dot1qSVLCapable(4),   -- Shared VLAN Learning (SVL).
          dot1qHybridCapable(5),
                                -- both IVL & SVL simultaneously.
          dot1qConfigurablePvidTagging(6),
                                -- whether the implementation
                                -- supports the ability to
                                -- override the default PVID
                                -- setting and its egress status
                                -- (VLAN-Tagged or Untagged) on
                                -- each port.
          dot1dLocalVlanCapable(7)
                                -- can support multiple local
                                -- bridges, outside of the scope
                                -- of 802.1Q defined VLANs.";
        reference
         "ISO/IEC 15802-3 Section 5.2,
          IEEE 802.1Q/D11 Section 5.2, 12.10.1.1.3/b/2";
        smiv2:max-access "read-only";
        smiv2:oid "1.3.6.1.2.1.17.6.1.1.1";
      }

      leaf dot1dTrafficClassesEnabled {
        type boolean;
        description
         "The value true(1) indicates that Traffic Classes are
          enabled on this bridge.  When false(2), the bridge
          operates with a single priority level for all traffic.
          
          The value of this object MUST be retained across
          reinitializations of the management system.";
        smiv2:defval "true";
        smiv2:max-access "read-write";
        smiv2:oid "1.3.6.1.2.1.17.6.1.1.2";
      }

      leaf dot1dGmrpStatus {
        type P-BRIDGE-MIB:EnabledStatus;
        description
         "The administrative status requested by management for
          GMRP.  The value enabled(1) indicates that GMRP should
          be enabled on this device, in all VLANs, on all ports
          for which it has not been specifically disabled.  When
          disabled(2), GMRP is disabled, in all VLANs and on all
          ports, and all GMRP packets will be forwarded
          transparently.  This object affects both Applicant and
          Registrar state machines.  A transition from disabled(2)
          to enabled(1) will cause a reset of all GMRP state
          machines on all ports.
          
          The value of this object MUST be retained across
          reinitializations of the management system.";
        smiv2:defval "enabled";
        smiv2:max-access "read-write";
        smiv2:oid "1.3.6.1.2.1.17.6.1.1.3";
      }
    }

    container dot1dTpHCPortTable {
      description
       "A table that contains information about every high-
        capacity port that is associated with this transparent
        bridge.";
      smiv2:oid "1.3.6.1.2.1.17.4.5";

      list dot1dTpHCPortEntry {
        key "dot1dTpPort";
        description
         "Statistics information for each high-capacity port of a
          transparent bridge.";
        smiv2:oid "1.3.6.1.2.1.17.4.5.1";

        leaf dot1dTpPort {
          type leafref {
            path "/bridge-mib:BRIDGE-MIB/bridge-mib:dot1dTpPortTable/bridge-mib:dot1dTpPortEntry/bridge-mib:dot1dTpPort";
          }
        }

        leaf dot1dTpHCPortInFrames {
          type yang:counter64;
          description
           "The number of frames that have been received by this
            port from its segment.  Note that a frame received on
            the interface corresponding to this port is only counted
            by this object if and only if it is for a protocol being
            processed by the local bridging function, including
            bridge management frames.";
          reference
           "ISO/IEC 15802-3 Section 14.6.1.1.3";
          smiv2:max-access "read-only";
          smiv2:oid "1.3.6.1.2.1.17.4.5.1.1";
        }

        leaf dot1dTpHCPortOutFrames {
          type yang:counter64;
          description
           "The number of frames that have been transmitted by this
            port to its segment.  Note that a frame transmitted on
            the interface corresponding to this port is only counted
            by this object if and only if it is for a protocol being
            processed by the local bridging function, including
            bridge management frames.";
          reference
           "ISO/IEC 15802-3 Section 14.6.1.1.3";
          smiv2:max-access "read-only";
          smiv2:oid "1.3.6.1.2.1.17.4.5.1.2";
        }

        leaf dot1dTpHCPortInDiscards {
          type yang:counter64;
          description
           "Count of valid frames that have been received by this
            port from its segment that were discarded (i.e.,
            filtered) by the Forwarding Process.";
          reference
           "ISO/IEC 15802-3 Section 14.6.1.1.3";
          smiv2:max-access "read-only";
          smiv2:oid "1.3.6.1.2.1.17.4.5.1.3";
        }
      }
    }

    container dot1dTpPortOverflowTable {
      description
       "A table that contains the most-significant bits of
        statistics counters for ports that are associated with this
        transparent bridge that are on high-capacity interfaces, as
        defined in the conformance clauses for this table.  This table
        is provided as a way to read 64-bit counters for agents that
        support only SNMPv1.
        
        Note that the reporting of most-significant and
        least-significant counter bits separately runs the risk of
        missing an overflow of the lower bits in the interval between
        sampling.  The manager must be aware of this possibility, even
        within the same varbindlist, when interpreting the results of
        a request or asynchronous notification.";
      smiv2:oid "1.3.6.1.2.1.17.4.6";

      list dot1dTpPortOverflowEntry {
        key "dot1dTpPort";
        description
         "The most significant bits of statistics counters for a high-
          capacity interface of a transparent bridge.  Each object is
          associated with a corresponding object in dot1dTpPortTable
          that indicates the least significant bits of the counter.";
        smiv2:oid "1.3.6.1.2.1.17.4.6.1";

        leaf dot1dTpPort {
          type leafref {
            path "/bridge-mib:BRIDGE-MIB/bridge-mib:dot1dTpPortTable/bridge-mib:dot1dTpPortEntry/bridge-mib:dot1dTpPort";
          }
        }

        leaf dot1dTpPortInOverflowFrames {
          type yang:counter32;
          description
           "The number of times the associated dot1dTpPortInFrames
            counter has overflowed.";
          reference
           "ISO/IEC 15802-3 Section 14.6.1.1.3";
          smiv2:max-access "read-only";
          smiv2:oid "1.3.6.1.2.1.17.4.6.1.1";
        }

        leaf dot1dTpPortOutOverflowFrames {
          type yang:counter32;
          description
           "The number of times the associated dot1dTpPortOutFrames
            counter has overflowed.";
          reference
           "ISO/IEC 15802-3 Section 14.6.1.1.3";
          smiv2:max-access "read-only";
          smiv2:oid "1.3.6.1.2.1.17.4.6.1.2";
        }

        leaf dot1dTpPortInOverflowDiscards {
          type yang:counter32;
          description
           "The number of times the associated
            dot1dTpPortInDiscards counter has overflowed.";
          reference
           "ISO/IEC 15802-3 Section 14.6.1.1.3";
          smiv2:max-access "read-only";
          smiv2:oid "1.3.6.1.2.1.17.4.6.1.3";
        }
      }
    }

    container dot1dUserPriorityRegenTable {
      description
       "A list of Regenerated User Priorities for each received
        User Priority on each port of a bridge.  The Regenerated
        User Priority value may be used to index the Traffic
        Class Table for each input port.  This only has effect
        on media that support native User Priority.  The default
        values for Regenerated User Priorities are the same as
        the User Priorities.";
      reference
       "ISO/IEC 15802-3 Section 6.4";
      smiv2:oid "1.3.6.1.2.1.17.6.1.2.2";

      list dot1dUserPriorityRegenEntry {
        key "dot1dBasePort dot1dUserPriority";
        description
         "A mapping of incoming User Priority to a Regenerated
          User Priority.";
        smiv2:oid "1.3.6.1.2.1.17.6.1.2.2.1";

        leaf dot1dBasePort {
          type leafref {
            path "/bridge-mib:BRIDGE-MIB/bridge-mib:dot1dBasePortTable/bridge-mib:dot1dBasePortEntry/bridge-mib:dot1dBasePort";
          }
        }

        leaf dot1dUserPriority {
          type int32 {
            range "0..7";
          }
          description
           "The User Priority for a frame received on this port.";
          smiv2:max-access "not-accessible";
          smiv2:oid "1.3.6.1.2.1.17.6.1.2.2.1.1";
        }

        leaf dot1dRegenUserPriority {
          type int32 {
            range "0..7";
          }
          description
           "The Regenerated User Priority that the incoming User
            
            Priority is mapped to for this port.
            
            The value of this object MUST be retained across
            reinitializations of the management system.";
          smiv2:max-access "read-write";
          smiv2:oid "1.3.6.1.2.1.17.6.1.2.2.1.2";
        }
      }
    }

    container dot1dTrafficClassTable {
      description
       "A table mapping evaluated User Priority to Traffic
        Class, for forwarding by the bridge.  Traffic class is a
        number in the range (0..(dot1dPortNumTrafficClasses-1)).";
      reference
       "ISO/IEC 15802-3 Table 7-2";
      smiv2:oid "1.3.6.1.2.1.17.6.1.2.3";

      list dot1dTrafficClassEntry {
        key "dot1dBasePort dot1dTrafficClassPriority";
        description
         "User Priority to Traffic Class mapping.";
        smiv2:oid "1.3.6.1.2.1.17.6.1.2.3.1";

        leaf dot1dBasePort {
          type leafref {
            path "/bridge-mib:BRIDGE-MIB/bridge-mib:dot1dBasePortTable/bridge-mib:dot1dBasePortEntry/bridge-mib:dot1dBasePort";
          }
        }

        leaf dot1dTrafficClassPriority {
          type int32 {
            range "0..7";
          }
          description
           "The Priority value determined for the received frame.
            This value is equivalent to the priority indicated in
            the tagged frame received, or one of the evaluated
            priorities, determined according to the media-type.
            
            For untagged frames received from Ethernet media, this
            value is equal to the dot1dPortDefaultUserPriority value
            for the ingress port.
            
            For untagged frames received from non-Ethernet media,
            this value is equal to the dot1dRegenUserPriority value
            for the ingress port and media-specific user priority.";
          smiv2:max-access "not-accessible";
          smiv2:oid "1.3.6.1.2.1.17.6.1.2.3.1.1";
        }

        leaf dot1dTrafficClass {
          type int32 {
            range "0..7";
          }
          description
           "The Traffic Class the received frame is mapped to.
            
            The value of this object MUST be retained across
            reinitializations of the management system.";
          smiv2:max-access "read-write";
          smiv2:oid "1.3.6.1.2.1.17.6.1.2.3.1.2";
        }
      }
    }

    container dot1dPortOutboundAccessPriorityTable {
      description
       "A table mapping Regenerated User Priority to Outbound
        Access Priority.  This is a fixed mapping for all port
        types, with two options for 802.5 Token Ring.";
      reference
       "ISO/IEC 15802-3 Table 7-3";
      smiv2:oid "1.3.6.1.2.1.17.6.1.2.4";

      list dot1dPortOutboundAccessPriorityEntry {
        key "dot1dBasePort dot1dRegenUserPriority";
        description
         "Regenerated User Priority to Outbound Access Priority
          mapping.";
        smiv2:oid "1.3.6.1.2.1.17.6.1.2.4.1";

        leaf dot1dBasePort {
          type leafref {
            path "/bridge-mib:BRIDGE-MIB/bridge-mib:dot1dBasePortTable/bridge-mib:dot1dBasePortEntry/bridge-mib:dot1dBasePort";
          }
        }

        leaf dot1dRegenUserPriority {
          type leafref {
            path "/P-BRIDGE-MIB:P-BRIDGE-MIB/P-BRIDGE-MIB:dot1dUserPriorityRegenTable/P-BRIDGE-MIB:dot1dUserPriorityRegenEntry/P-BRIDGE-MIB:dot1dRegenUserPriority";
          }
        }

        leaf dot1dPortOutboundAccessPriority {
          type int32 {
            range "0..7";
          }
          description
           "The Outbound Access Priority the received frame is
            mapped to.";
          smiv2:max-access "read-only";
          smiv2:oid "1.3.6.1.2.1.17.6.1.2.4.1.1";
        }
      }
    }
  }

  smiv2:alias "dot1dPortCapabilitiesTable" {
    description
     "A table that contains capabilities information about
      every port that is associated with this bridge.";
    smiv2:oid "1.3.6.1.2.1.17.6.1.1.4";
  }

  smiv2:alias "dot1dPortCapabilitiesEntry" {
    description
     "A set of capabilities information about this port
      indexed by dot1dBasePort.";
    smiv2:oid "1.3.6.1.2.1.17.6.1.1.4.1";
  }

  augment "/bridge-mib:BRIDGE-MIB/bridge-mib:dot1dBasePortTable/bridge-mib:dot1dBasePortEntry" {
    description
     "A set of capabilities information about this port
      indexed by dot1dBasePort.";
    smiv2:oid "1.3.6.1.2.1.17.6.1.1.4.1";

    leaf dot1dPortCapabilities {
      type bits {
        bit dot1qDot1qTagging {
          position "0";
        }
        bit dot1qConfigurableAcceptableFrameTypes {
          position "1";
        }
        bit dot1qIngressFiltering {
          position "2";
        }
      }
      description
       "Indicates the parts of IEEE 802.1D and 802.1Q that are
        optional on a per-port basis, that are implemented by
        this device, and that are manageable through this MIB.
        
        dot1qDot1qTagging(0), -- supports 802.1Q VLAN tagging of
                              -- frames and GVRP.
        dot1qConfigurableAcceptableFrameTypes(1),
                              -- allows modified values of
                              -- dot1qPortAcceptableFrameTypes.
        dot1qIngressFiltering(2)
                              -- supports the discarding of any
                              -- frame received on a Port whose
                              -- VLAN classification does not
                              -- include that Port in its Member
                              -- set.";
      reference
       "ISO/IEC 15802-3 Section 5.2,
        IEEE 802.1Q/D11 Section 5.2";
      smiv2:max-access "read-only";
      smiv2:oid "1.3.6.1.2.1.17.6.1.1.4.1.1";
    }
  }

  smiv2:alias "dot1dPortPriorityTable" {
    description
     "A table that contains information about every port that
      is associated with this transparent bridge.";
    smiv2:oid "1.3.6.1.2.1.17.6.1.2.1";
  }

  smiv2:alias "dot1dPortPriorityEntry" {
    description
     "A list of Default User Priorities for each port of a
      transparent bridge.  This is indexed by dot1dBasePort.";
    smiv2:oid "1.3.6.1.2.1.17.6.1.2.1.1";
  }

  augment "/bridge-mib:BRIDGE-MIB/bridge-mib:dot1dBasePortTable/bridge-mib:dot1dBasePortEntry" {
    description
     "A list of Default User Priorities for each port of a
      transparent bridge.  This is indexed by dot1dBasePort.";
    smiv2:oid "1.3.6.1.2.1.17.6.1.2.1.1";

    leaf dot1dPortDefaultUserPriority {
      type int32 {
        range "0..7";
      }
      description
       "The default ingress User Priority for this port.  This
        only has effect on media, such as Ethernet, that do not
        support native User Priority.
        
        The value of this object MUST be retained across
        reinitializations of the management system.";
      smiv2:max-access "read-write";
      smiv2:oid "1.3.6.1.2.1.17.6.1.2.1.1.1";
    }

    leaf dot1dPortNumTrafficClasses {
      type int32 {
        range "1..8";
      }
      description
       "The number of egress traffic classes supported on this
        port.  This object may optionally be read-only.
        
        The value of this object MUST be retained across
        reinitializations of the management system.";
      smiv2:max-access "read-write";
      smiv2:oid "1.3.6.1.2.1.17.6.1.2.1.1.2";
    }
  }

  smiv2:alias "dot1dPortGarpTable" {
    description
     "A table of GARP control information about every bridge
      port.  This is indexed by dot1dBasePort.";
    smiv2:oid "1.3.6.1.2.1.17.6.1.3.1";
  }

  smiv2:alias "dot1dPortGarpEntry" {
    description
     "GARP control information for a bridge port.";
    smiv2:oid "1.3.6.1.2.1.17.6.1.3.1.1";
  }

  augment "/bridge-mib:BRIDGE-MIB/bridge-mib:dot1dBasePortTable/bridge-mib:dot1dBasePortEntry" {
    description
     "GARP control information for a bridge port.";
    smiv2:oid "1.3.6.1.2.1.17.6.1.3.1.1";

    leaf dot1dPortGarpJoinTime {
      type snmpv2-tc:TimeInterval;
      description
       "The GARP Join time, in centiseconds.
        
        The value of this object MUST be retained across
        reinitializations of the management system.";
      smiv2:defval "20";
      smiv2:max-access "read-write";
      smiv2:oid "1.3.6.1.2.1.17.6.1.3.1.1.1";
    }

    leaf dot1dPortGarpLeaveTime {
      type snmpv2-tc:TimeInterval;
      description
       "The GARP Leave time, in centiseconds.
        
        The value of this object MUST be retained across
        reinitializations of the management system.";
      smiv2:defval "60";
      smiv2:max-access "read-write";
      smiv2:oid "1.3.6.1.2.1.17.6.1.3.1.1.2";
    }

    leaf dot1dPortGarpLeaveAllTime {
      type snmpv2-tc:TimeInterval;
      description
       "The GARP LeaveAll time, in centiseconds.
        
        The value of this object MUST be retained across
        reinitializations of the management system.";
      smiv2:defval "1000";
      smiv2:max-access "read-write";
      smiv2:oid "1.3.6.1.2.1.17.6.1.3.1.1.3";
    }
  }

  smiv2:alias "dot1dPortGmrpTable" {
    description
     "A table of GMRP control and status information about
      every bridge port.  Augments the dot1dBasePortTable.";
    smiv2:oid "1.3.6.1.2.1.17.6.1.4.1";
  }

  smiv2:alias "dot1dPortGmrpEntry" {
    description
     "GMRP control and status information for a bridge port.";
    smiv2:oid "1.3.6.1.2.1.17.6.1.4.1.1";
  }

  augment "/bridge-mib:BRIDGE-MIB/bridge-mib:dot1dBasePortTable/bridge-mib:dot1dBasePortEntry" {
    description
     "GMRP control and status information for a bridge port.";
    smiv2:oid "1.3.6.1.2.1.17.6.1.4.1.1";

    leaf dot1dPortGmrpStatus {
      type P-BRIDGE-MIB:EnabledStatus;
      description
       "The administrative state of GMRP operation on this port.  The
        value enabled(1) indicates that GMRP is enabled on this port
        in all VLANs as long as dot1dGmrpStatus is also enabled(1).
        A value of disabled(2) indicates that GMRP is disabled on
        this port in all VLANs: any GMRP packets received will
        be silently discarded, and no GMRP registrations will be
        propagated from other ports.  Setting this to a value of
        enabled(1) will be stored by the agent but will only take
        effect on the GMRP protocol operation if dot1dGmrpStatus
        also indicates the value enabled(1).  This object affects
        all GMRP Applicant and Registrar state machines on this
        port.  A transition from disabled(2) to enabled(1) will
        cause a reset of all GMRP state machines on this port.
        
        The value of this object MUST be retained across
        reinitializations of the management system.";
      smiv2:defval "enabled";
      smiv2:max-access "read-write";
      smiv2:oid "1.3.6.1.2.1.17.6.1.4.1.1.1";
    }

    leaf dot1dPortGmrpFailedRegistrations {
      type yang:counter32;
      description
       "The total number of failed GMRP registrations, for any
        reason, in all VLANs, on this port.";
      smiv2:max-access "read-only";
      smiv2:oid "1.3.6.1.2.1.17.6.1.4.1.1.2";
    }

    leaf dot1dPortGmrpLastPduOrigin {
      type yang:mac-address;
      description
       "The Source MAC Address of the last GMRP message
        received on this port.";
      smiv2:max-access "read-only";
      smiv2:oid "1.3.6.1.2.1.17.6.1.4.1.1.3";
    }

    leaf dot1dPortRestrictedGroupRegistration {
      type boolean;
      description
       "The state of Restricted Group Registration on this port.
        If the value of this control is true(1), then creation
        of a new dynamic entry is permitted only if there is a
        Static Filtering Entry for the VLAN concerned, in which
        the Registrar Administrative Control value is Normal
        Registration.
        
        The value of this object MUST be retained across
        reinitializations of the management system.";
      reference
       "IEEE 802.1t clause 10.3.2.3, 14.10.1.3.";
      smiv2:defval "false";
      smiv2:max-access "read-write";
      smiv2:oid "1.3.6.1.2.1.17.6.1.4.1.1.4";
    }
  }

  smiv2:alias "pBridgeMIB" {
    smiv2:oid "1.3.6.1.2.1.17.6";
  }

  smiv2:alias "pBridgeMIBObjects" {
    smiv2:oid "1.3.6.1.2.1.17.6.1";
  }

  smiv2:alias "dot1dExtBase" {
    smiv2:oid "1.3.6.1.2.1.17.6.1.1";
  }

  smiv2:alias "dot1dPriority" {
    smiv2:oid "1.3.6.1.2.1.17.6.1.2";
  }

  smiv2:alias "dot1dGarp" {
    smiv2:oid "1.3.6.1.2.1.17.6.1.3";
  }

  smiv2:alias "dot1dGmrp" {
    smiv2:oid "1.3.6.1.2.1.17.6.1.4";
  }

  smiv2:alias "pBridgeConformance" {
    smiv2:oid "1.3.6.1.2.1.17.6.2";
  }

  smiv2:alias "pBridgeGroups" {
    smiv2:oid "1.3.6.1.2.1.17.6.2.1";
  }

  smiv2:alias "pBridgeCompliances" {
    smiv2:oid "1.3.6.1.2.1.17.6.2.2";
  }

}
