/*-------------------------------------------------------------------
 *  cisco-qos-common.yang - common units for qos actions 
 * 
 *  April 2015, Xia Wu   
 *                                           
 *  Copyright (c) 2015 by Cisco Systems, Inc.
 *  All rights reserved.                     
 *-------------------------------------------------------------------
 */
module cisco-qos-common {
    yang-version 1;
    namespace "urn:cisco:params:xml:ns:yang:cisco-qos-common";

    prefix qos;

    import ietf-diffserv-classifier {
        prefix class;
    }
    
    import policy-types { 
        prefix c3pl;
    }
    
    import policy-attr {
        prefix c3pl-attr;
    }
    
    import ietf-inet-types {
        prefix inet;
    }
  
    import ietf-diffserv-action {
        prefix action;
    }

    organization "Cisco Systems";
    contact
    "Editor:   Xia Wu
               <mailto:xiaw2@cisco.com>";
    description
    "This module contains YANG definitions for
    common units for qos
     
    Copyright (c) 2015 by Cisco Systems, Inc.
    All rights reserved.";
    
    revision 2015-05-09 {
        description "first revision";
        reference "ietf-diffserv-action.yang";
    }

    typedef thresh-unit {
        type enumeration {
            enum default;
            enum bytes;
            enum sec;
            enum packets;
            enum cells;
            enum percent;
        }

        description "Unit for threshold";
    }

    typedef percent-value-1to100 {
        type uint8 {
            range "1..100";
        }

        description "Percent range from 1 to 100";
    }

    typedef match-type {
       type identityref {
        base class:filter-type;
       }
       
       description "match type";
    }
    typedef dscp {
        type inet:dscp;
        description "dscp value";
    }
    
    grouping COS-RANGE {
        uses c3pl-attr:cos-cfg;
        description "cos value range";
    }

    grouping DSCP-RANGE {
        uses c3pl-attr:dscp-cfg;
        description "dscp value range";
    }

    grouping DISC-CLASS-RANGE {
        leaf disc-class-min { 
            type c3pl:discard-class-type;
            description "Minimum value for discard class in the range";
        }  
        leaf disc-class-max { 
            type c3pl:discard-class-type;
            description "Maximum value for discard class in the range";
        }  
        description "Discard class value range";
    }

    grouping QOS-GRP-RANGE {
        uses c3pl-attr:qos-group-cfg;
        description "qos group value range";
    }

    grouping PREC-RANGE {
        leaf prec-min { 
            type c3pl:prec-val-type;//ip-prec-type;
            description "Minimum value for precedence in the range";
        }  
        
        leaf prec-max { 
            type c3pl:prec-val-type;//ip-prec-type;
            description "Maximum value for precedence in the range";
        }  
        description "Precendence value range";
    }

    grouping MPLS-EXP-RANGE {
       uses c3pl-attr:mpls-exp-cfg;
       description "mpls exp value range";
    }

    grouping DEI-RANGE {
        leaf dei-min { 
            type c3pl:dei-type;
            description "Minimum value for dei in the range";
        }
        leaf dei-max { 
            type c3pl:dei-type;
            description "Maximum value for dei in the range";
        }
        description "Dei value range";
    }

    grouping CLP-VAL {
        leaf clp-val {
            type boolean;
            description "Is clp enbaled or not";
        }
        description "CLP vlaue";
    }


    grouping RATE-OPER {
        leaf rate {
            type uint64;
            units "bits-per-second";
            description "Rate value";
        }

        uses RATE-UNIT;
        description "Rate value and units operator";
    }

    grouping RATE-UNIT {
        leaf rate-metric {
            type c3pl:metric;
            default none;
            description "Metric";
        }
        leaf rate-units {
            type c3pl:rate-unit;
            description "Rate basic units";
        }
        
        description "Rate units";
    } 
    
    
    grouping BURST-OPER {
        uses action:burst {
            augment "burst-type/size" {
                description "burst size units";
                uses BURST-SIZE-UNIT;
            }
            augment "burst-type/interval" {
                description "burst interval units";
                uses BURST-INTERVAL-UNIT;
            }
        }
        description "Burst value and units operator";
    } 

    grouping BURST-SIZE-UNIT {
        leaf burst-size-units {
            type enumeration {
                enum none;
                enum bytes;
                enum packets;
                enum percent;//for IOS-XE adaptive shaper
            }
            description "Burst size basic units";
        }

        leaf burst-size-metric {
            type c3pl:metric;
            description "Units metric";
        }    
        description "Burst size units";        
    }
    
    grouping BURST-INTERVAL-UNIT {
        leaf burst-interval-units {
            type enumeration {
                enum none;
                enum sec;
            }
            description "Burst interval basic units";
        }
        
        leaf burst-interval-metric {
            type c3pl:metric;
            description "Units metric";
        }
        description "Burst intevral units";
    }

    grouping THRESH-SIZE-UNIT {
        leaf thresh-size-metric   { 
            type c3pl:metric ; 
            description "Threshold units metric";
        } 

        leaf thresh-size-units   { 
            type thresh-unit; 
            description "Threshold size basic units";
        } 
        description "Threshold size units";
    }

    grouping THRESH-INTERVAL-UNIT {
        leaf thresh-interval-metric   { 
            type c3pl:metric ; 
            description "Threshold units metric";
        } 

        leaf thresh-interval-units   { 
            type thresh-unit; 
            description "Threshold intveral basic units";
        } 
        description "Threshold intveral units";
    }
    
    grouping  THRESHOLD   { 
        uses action:threshold {
            augment  "threshold/threshold-type/size"   { 
                description "Threshold size units";
                uses THRESH-SIZE-UNIT;
            }  
            augment  "threshold/threshold-type/interval" { 
                description "Threshold interval units";
                uses THRESH-INTERVAL-UNIT;
            }     
        }
        description "Threshold operators";
    }  
}
