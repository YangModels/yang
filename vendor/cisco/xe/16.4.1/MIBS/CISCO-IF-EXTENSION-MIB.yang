/*
 * Generated by confdc --mib2yang-std
 * Source: mgmt/dmi/model/common/mib-source/CISCO-IF-EXTENSION-MIB.mib
 */
/*
 * This YANG module has been generated by smidump 0.5.0:
 *
 *      smidump -f yang CISCO-IF-EXTENSION-MIB
 *
 * Do not edit. Edit the source file instead!
 */

module CISCO-IF-EXTENSION-MIB {

  namespace "urn:ietf:params:xml:ns:yang:smiv2:CISCO-IF-EXTENSION-MIB";
  prefix CISCO-IF-EXTENSION-MIB;

  import CISCO-TC {
    prefix "cisco-tc";
  }

  import ENTITY-MIB {
    prefix "entity-mib";
  }

  import IF-MIB {
    prefix "if-mib";
  }

  import SNMP-FRAMEWORK-MIB {
    prefix "snmp-framework";
  }

  import SNMPv2-TC {
    prefix "snmpv2-tc";
  }

  import ietf-yang-smiv2 {
    prefix "smiv2";
  }

  import ietf-yang-types {
    prefix "yang";
  }

  organization
   "Cisco Systems, Inc.";

  contact
   "Cisco Systems
    Customer Service
    
    Postal: 170 West Tasman Drive
    San Jose, CA  95134
    USA
    
    Tel: +1 800 553-NETS
    
    E-mail: cs-core-mibs@cisco.com,
    cs-lan-switch-snmp@cisco.com";

  description
   "A MIB module for extending the IF-MIB (RFC2863)
    to add objects which provide additional information
    about interfaces not available in other MIBS.
    This MIB replaces the OLD-CISCO-INTERFACES-MIB.
    
    GLOSSARY :
    
    Virtual Switch - A physical switch partitioned into 
            multiple logical switches.
    
    Interface Sharing - An interface can be shared among 
            multiple virtual switches.
    
    Speed Group - An interface is capable of operating in any one of
    the speed range depending on the capability of the hardware.
    
    Virtual Link (VL) - Virtual Link is a logical connectivity 
        between two end points. A physical interface can 
        have multiple Virtual Links.
    
    No Drop Virtual Link - According to 802.3 standard, 
        No drop specifies lossless service on a virtual link.
    
    Drop Virtual Link - According to 802.3 standard,
        Traffic drop may occur on this virtual Link.";

  revision 2013-03-13 {
    description
     "Added new object cieIfTransceiverFrequencyConfig,
      cieIfFillPatternConfig, cieIfIgnoreBitErrorsConfig and
      cieIfIgnoreInterruptThresholdConfig to cieIfInterfaceTable.
      - Added a new group 
         ciscoIfExtensionTableIntfGroup3SupR02
      - Deprecated ciscoIfExtensionMIBCompliance13
      - Added ciscoIfExtensionMIBCompliance14.";
  }

  revision 2012-09-05 {
    description
     "Added new object cieLinkUpDownConfig.
      - Added a new group cieLinkUpDownNotifConfigGroup.
      - Deprecated cieLinkUpDownEnable.
      - Deprecated cieStandardLinkUpDownVarbinds.
      - Deprecated ciscoIfExtensionMIBCompliance13.
      - Added ciscoIfExtensionMIBCompliance14.";
  }

  revision 2011-06-27 {
    description
     "Added new object cieIfSharedConfig and
      cieIfSpeedGroupConfig to cieIfInterfaceTable.
      Add cieIfVlStatsTable.
      - Added a new group 
      ciscoIfExtensionTableIntfGroup3SupR01 and 
      cieIfVlStatsGroup
      - Deprecated ciscoIfExtensionMIBCompliance12
      - Added ciscoIfExtensionMIBCompliance13.";
  }

  revision 2009-02-26 {
    description
     "Added Textual Convention InterfaceOwnershipList
      - Added new object cieInterfaceOwnershipBitmap
      - Added new group cieIfStatusListGroupSup1
      - Deprecated ciscoIfExtensionMIBCompliance11
      - Added ciscoIfExtensionMIBCompliance12";
  }

  revision 2008-12-09 {
    description
     "Added new object cieIfOwner to
      cieIfInterfaceTable.
      - Added a new group 
      ciscoIfExtensionTableIntfGroup3
      - Deprecated ciscoIfExtensionTableIntfGroup2
      - Deprecated ciscoIfExtensionMIBCompliance10
      - Added ciscoIfExtensionMIBCompliance11";
  }

  revision 2008-10-06 {
    description
     "Added a new textual Convention IfIndexPersistenceState.
      - Added scalar object cieIfIndexGlobalPersistence to
        ciscoIfExtSystemConfig. 
      - Deprecated scalar object cieIfIndexPersistence to
        ciscoIfExtSystemConfig.
      - Added a new object cieIfIndexPersistenceControl in 
        cieIfIndexPersistenceTable.
      - Deprecated an object cieIfIndexPersistenceEnabled in 
        cieIfIndexPersistenceTable.
      - Added a new group cieIfIndexPersistenceControlGroup.
      - Deprecated the group cieIfIndexPersistenceGroup.
      - Added ciscoIfExtensionMIBCompliance10
      - Deprecated ciscoIfExtensionMIBCompliance9";
  }

  revision 2008-07-31 {
    description
     "Added cieIfOperStatusCause to the objects in the
      notification cieDelayedLinkUpDownNotif.";
  }

  revision 2008-07-08 {
    description
     "Added notification cieDelayedLinkUpDownNotif
      - Added scalar objects cieDelayedLinkUpDownNotifEnable and 
        cieDelayedLinkUpDownNotifDelay to ciscoIfExtSystemConfig.
      - Added the following groups:
                cieDelayedLinkUpDownNotifNotifGroup
                cieDelayedLinkUpDownNotifNotifEnableGroup
      - Deprecated ciscoIfExtensionMIBCompliance7
      - Added ciscoIfExtensionMIBCompliance8.";
  }

  revision 2008-06-23 {
    description
     "Added scalar object cieIfIndexPersistence to
      ciscoIfExtSystemConfig.
      - Added a new Table cieIfIndexPersistenceTable. 
      - Added a new object cieIfIndexPersistenceEnabled in 
      cieIfIndexPersistenceTable.
      - Added a new group cieIfIndexPersistenceGroup.
      - Deprecated ciscoIfExtensionMIBCompliance7
      - Added ciscoIfExtensionMIBCompliance8";
  }

  revision 2007-07-23 {
    description
     "Added cieIfInterval in cieIfUtilTable. Changed
      the description of objects in cieIfUtilTable.
      Added ciscoIfExtUtilIntervalGroup.";
  }

  revision 2006-11-01 {
    description
     "Add support for asymetrical interfaces speeds.
      
      - Added following objects in cieIfInterfaceTable 
        cieIfSpeedReceive 
        cieIfHighSpeedReceive 
      - Added ciscoIfExtensionAsymmetricalSpeedGroup OBJECT-GROUP 
      - Added ciscoIfExtensionMIBCompliance6 MODULE-COMPLIANCE";
  }

  revision 2005-04-28 {
    description
     "Added:
      - cieLinkUp & cieLinkDown notifications.
      - object to control sending: only standard 
        linkUp/linkDown OR only cieLinkUp/cieLinkDown
        OR both.
      - object to control sending only standard defined
        varbinds in linkUp/linkDown OR additional varbinds
        in addition to standard defined.";
  }

  revision 2005-01-25 {
    description
     "Updated the description of cieIfDot1dBaseMappingEntry.";
  }

  revision 2004-09-08 {
    description
     "Added new objects 'cieIfOperStatusCause' and
      'cieIfOperStatusCauseDescr' in cieIfInterfaceTable.
      Added a new table 'cieIfStatusListTable'.";
  }

  revision 2003-11-14 {
    description
     "Added new objects cieIfName and cieIfIndex for the
      'ifName' to 'ifIndex' mapping.  Deprecated the
      ciscoIfExtensionMIBCompliance2 compliance.
      Added ciscoIfExtensionMIBCompliance3 and
      ciscoIfExtIfNameMappingGroup.";
  }

  revision 2003-08-12 {
    description
     "Added ciscoIfExtDot1dBaseMappingGroup.";
  }

  revision 2003-07-17 {
    description
     "Added ciscoIfExtUtilizationGroup.";
  }

  revision 2003-06-25 {
    description
     "Added the object cieSystemMtu and
      ciscoIfExtSystemGroup.
      Added ciscoIfExtDot1qCustomEtherType and
      ciscoIfExtDot1qEtherTypeGroup.";
  }

  revision 2002-10-12 {
    description
     "Added the objects cieIfDhcpMode, cieIfMtu,
      cieIfContextName to cieIfInterfaceTable.
      Deprecated the ciscoIfExtensionMIBCompliance
      compliance.  Added ciscoIfExtensionMIBCompliance1.
      Added ciscoIfExtensionTableIntfGroup1.";
  }

  revision 2002-07-24 {
    description
     "Initial version of the MIB module.";
  }

  typedef InterfaceIndexList {
    type binary {
      length "0..256";
    }
    description
     "This textual convention defines the 'ifIndex' for a
      set of 64 interfaces in a module.
      
      Each 4 bytes within the value of an object of this
      type is combined together to represent the interface
      index of a particular port in the module (i.e., each
      4 byte group represents the 'ifIndex' of an interface).
      
      The first 4 bytes (byte 1, byte 2, byte 3 and byte 4)
      combined represent the 'ifIndex' of an interface.
      While the second 4 bytes (byte 5, byte 6, byte 7 and
      byte 8) represent the 'ifIndex' for the next interface
      in the module, and so on.
      
      If there are only 'n' interfaces in a set of 64
      interfaces in the module, then bytes after the '4n'
      byte in this object are irrelevant.";
  }

  typedef InterfaceOperModeList {
    type binary {
      length "0..64";
    }
    description
     "This textual convention defines the operational mode
      for a set of 64 interfaces in a module.
      
      The operational mode of an interface is represented
      by the value defined in the textual convention
      'InterfaceOperMode' (defined in CISCO-ST-TC).
      
      Each 'byte' within the value of an object of this
      type, specifies the operational mode of an interface
      in the module.
      
      The first byte (byte 1) represents the operational
      mode of an interface in the module, whose 'ifIndex'
      is represented by the corresponding instance of
      'cieInterfacesIndex' object in its first 4 bytes.
      
      The second byte (byte 2) represents the operational
      mode of an interface in the module, whose 'ifIndex'
      is represented by the corresponding instance of
      'cieInterfacesIndex' object in its second 4 bytes.
      
      If there are only 'n' interfaces in a set of 64
      interfaces in the module, then bytes after the 'n'
      byte in this object are irrelevant.";
  }

  typedef InterfaceOperCauseList {
    type binary {
      length "0..128";
    }
    description
     "This textual convention defines the operational
      status cause for a set of 64 interfaces in a module.
      
      The operational status cause of an interface is
      represented by the value defined in the textual
      convention 'IfOperStatusReason' (defined in CISCO-TC).
      
      Each 2 bytes within the value of an object of this
      type is combined together to represent the operational
      status cause of a particular interface in the module
      (i.e., each 2 byte group represents the
      'cieIfOperStatusCause' of an interface).
      
      The first 2 bytes (byte 1 and byte 2) of this object,
      represents the operational status cause of an
      interface in the module, whose 'ifIndex' is
      represented by the corresponding instance of
      'cieInterfacesIndex' object in its first 4 bytes.
      
      The next 2 bytes (byte 3 and byte 4) of this object,
      represents the operational status cause of an
      interface in the module, whose 'ifIndex' is
      represented by the corresponding instance of
      'cieInterfacesIndex' object in the next 4 bytes
      respectively.
      
      If there are only 'n' interfaces in a set of 64
      interfaces in the module, then bytes after the
      '2n' byte in this object are irrelevant.";
  }

  typedef InterfaceOwnershipList {
    type binary {
      length "0..8";
    }
    description
     "This textual convention defines the status for a set of
      64 interfaces in a module regarding whether or not each 
      interface is administratively assigned a name of the current 
      owner of the interface resource as per the object cieIfOwner,
      defined on that interface. 
      
      Each 'bit' within the value of an object of this type, 
      specifies whether the corresponding interface on the module 
      has been administratively assigned a name of the current
      owner of the interface resource. In other words, each bit 
      represents whether the corresponding interface is 'owned' 
      or not. This bit is set to 1 if the interface is owned. 
      It is 0 otherwise.
      
      The first bit (bit 1) in byte 1 represents whether the 
      interface, whose 'ifIndex' is represented by the corresponding 
      instance of 'cieInterfacesIndex' object in its first 4 bytes, 
      is owned or not.
      
      The second byte (byte 2) in byte 2 represents whether the 
      interface, whose 'ifIndex' is represented by the corresponding 
      instance of 'cieInterfacesIndex' object in its second 4 bytes, 
      is owned or not.
      
      If there are only 'n' interfaces in a set of 64 interfaces in 
      the module, then bits after the 'n' bit in this object are 
      irrelevant and set to 0.";
  }

  typedef IfIndexPersistenceState {
    type enumeration {
      enum "disable" {
        value "1";
      }
      enum "enable" {
        value "2";
      }
      enum "global" {
        value "3";
      }
    }
    description
     "This textual convention is used to define the state of ifIndex
      Persistence for both global as well as interface level.
      
      The global object, cieIfIndexGlobalPersistence can have two
      state of ifIndex Persistence i.e. either enable or disable. At
      interface level, the object cieIfIndexPersistenceControl can
      take all the three values enable/disable/global.";
  }


  container CISCO-IF-EXTENSION-MIB {
    config false;

    container ciscoIfExtSystemConfig {
      smiv2:oid "1.3.6.1.4.1.9.9.276.1.2";

      leaf cieSystemMtu {
        type int32;
        description
         "Global system MTU in octets.
          This object specifies the MTU on all interfaces.
          However, the value specified by cieIfMtu
          takes precedence for an interface, which means
          that the interface's MTU uses the value
          specified by cieIfMtu, if it is configured.";
        smiv2:defval "1500";
        smiv2:max-access "read-write";
        smiv2:oid "1.3.6.1.4.1.9.9.276.1.2.1";
      }

      leaf cieLinkUpDownEnable {
        type bits {
          bit standard {
            position "0";
          }
          bit cisco {
            position "1";
          }
        }
        status deprecated;
        description
         "Indicates whether cieLinkUp/cieLinkDown
          or standard mib-II defined linkUp/Down or
          both, notifications should be generated
          for the interfaces in the system.
          
          'standard'  - only generate standard defined
                        mib-II linkUp/linkDown notification
                        if 'ifLinkUpDownTrapEnable' for 
                        the interface is 'enabled'.
          'cisco'     - only generate cieLinkUp/cieLinkDown
                        notifications for an interface if
                        the 'ifLinkUpDownTrapEnable' for the
                        interface is 'enabled'.
          
          If both bits are selected then linkUp/linkDown and
          cieLinkUp/cieLinkDown are both generated for an 
          interface if the 'ifLinkUpDownTrapEnable' for the
          interface is 'enabled'.";
        smiv2:defval "{standard}";
        smiv2:max-access "read-write";
        smiv2:oid "1.3.6.1.4.1.9.9.276.1.2.2";
      }

      leaf cieStandardLinkUpDownVarbinds {
        type enumeration {
          enum "standard" {
            value "1";
          }
          enum "additional" {
            value "2";
          }
          enum "other" {
            value "3";
          }
        }
        status deprecated;
        description
         "Indicates whether to send the extra
          varbinds in addition to the varbinds defined 
          in linkUp/linkDown notifications.
          
          'standard'   - only send the varbinds defined in
                         the standard linkUp/linkDown
                         notification.  
          'additional' - send the extra varbinds in addition 
                         to the defined ones.
          'other'      - any other config not covered by the above.
                         This value is read-only.";
        smiv2:defval "additional";
        smiv2:max-access "read-write";
        smiv2:oid "1.3.6.1.4.1.9.9.276.1.2.3";
      }

      leaf cieIfIndexPersistence {
        type boolean;
        status deprecated;
        description
         "This object specifies whether ifIndex values persist across
          reinitialization of the device.
          
          ifIndex persistence means that the mapping between the ifDescr
          object values and the ifIndex object values will be retained
          across reboots.
          
          Applications such as device inventory, billing, and fault
          detection depend on the maintenance of the correspondence
          between particular ifIndex values and their interfaces. During
          reboot or insertion of a new card, the data to correlate the
          interfaces to the ifIndex may become invalid in absence of
          ifIndex persistence feature.
          
          ifIndex persistence for an interface ensures ifIndex value for
          the interface will remain the same after a system reboot.
          Hence, this feature allows users to avoid the workarounds
          required for consistent interface identification across
          reinitialization.
          
          Due to change in syntax, this object is deprecated by
          cieIfIndexGlobalPersistence.";
        smiv2:defval "false";
        smiv2:max-access "read-write";
        smiv2:oid "1.3.6.1.4.1.9.9.276.1.2.4";
      }

      leaf cieDelayedLinkUpDownNotifEnable {
        type boolean;
        description
         "This object specifies whether the system generates a
          cieDelayedLinkUpDownNotif notification.";
        smiv2:defval "false";
        smiv2:max-access "read-write";
        smiv2:oid "1.3.6.1.4.1.9.9.276.1.2.6";
      }

      leaf cieDelayedLinkUpDownNotifDelay {
        type uint32 {
          range "1..60";
        }
        units "minutes";
        description
         "This object specifies the interval of time an interface's
          operational status must remain stable following a transition
          before the system will generate a cieDelayedLinkUpDownNotif.";
        smiv2:defval "4";
        smiv2:max-access "read-write";
        smiv2:oid "1.3.6.1.4.1.9.9.276.1.2.7";
      }

      leaf cieIfIndexGlobalPersistence {
        type CISCO-IF-EXTENSION-MIB:IfIndexPersistenceState;
        description
         "This object specifies whether ifIndex values persist across
          reinitialization of the device.
          
          ifIndex persistence means that the mapping between the ifDescr
          object values and the ifIndex object values will be retained
          across reboots.
          
          Applications such as device inventory, billing, and fault
          detection depend on the maintenance of the correspondence
          between particular ifIndex values and their interfaces. During
          reboot or insertion of a new card, the data to correlate the
          interfaces to the ifIndex may become invalid in absence of
          ifIndex persistence feature.
          
          ifIndex persistence for an interface ensures ifIndex value for
          the interface will remain the same after a system reboot. Hence,
          this feature allows users to avoid the workarounds required for
          consistent interface identification across reinitialization.
          
          The allowed values for this object are either enable or disable.
          global value is not allowed.";
        smiv2:defval "disable";
        smiv2:max-access "read-write";
        smiv2:oid "1.3.6.1.4.1.9.9.276.1.2.8";
      }

      leaf cieLinkUpDownConfig {
        type bits {
          bit standardLinkUp {
            position "0";
          }
          bit standardLinkDown {
            position "1";
          }
          bit additionalLinkUp {
            position "2";
          }
          bit additionalLinkDown {
            position "3";
          }
          bit ciscoLinkUp {
            position "4";
          }
          bit ciscoLinkDown {
            position "5";
          }
        }
        description
         "This object specifies whether standard mib-II defined linkUp/
          linkDown, extended linkUp/linkDown (with extra varbinds in
          addition to the varbinds defined in linkUp/linkDown) or
          cieLinkUp/cieLinkDown notifications should be generated for
          the interfaces in the system.
          
          'standardLinkUp'     - generate standard defined mib-II 
                                 linkUp notification if 
                                 'ifLinkUpDownTrapEnable' for the 
                                 interface is 'enabled'.
          'standardLinkDown'   - generate standard defined mib-II 
                                 linkDown notification if 
                                 'ifLinkUpDownTrapEnable' for the 
                                 interface is 'enabled'.  
          'additionalLinkUp'   - generate linkUp notification with
                                 additional varbinds if 
                                 'ifLinkUpDownTrapEnable' for the 
                                 interface is 'enabled'.  
          'additionalLinkDown' - generate linkDown notification with
                                 additional varbinds if 
                                 'ifLinkUpDownTrapEnable' for the 
                                 interface is 'enabled'.
          'ciscoLinkUp'        - generate cieLinkUp notification
                                 if the 'ifLinkUpDownTrapEnable' for the
                                 interface is 'enabled'.
          'ciscoLinkDown'      - generate cieLinkDown notification
                                 if the 'ifLinkUpDownTrapEnable' for the
                                 interface is 'enabled'.
          
          If multiple bits are set then multiple notifications will
          be generated for an interface if the 'ifLinkUpDownTrapEnable' 
          for the interface is 'enabled'.";
        smiv2:max-access "read-write";
        smiv2:oid "1.3.6.1.4.1.9.9.276.1.2.9";
      }
    }

    container cieIfPacketStatsTable {
      description
       "This  table contains interface packet
        statistics which are not available in 
        IF-MIB(RFC2863). 
        
        As an example, some interfaces to which
        objects in this table are applicable are
        as follows :
        
                o Ethernet
                o FastEthernet
                o ATM
                o BRI
                o Sonet
                o GigabitEthernet
        
        Some objects defined in this table may be 
        applicable to physical interfaces only.
        As a result, this table may be sparse for
        some logical interfaces.";
      smiv2:oid "1.3.6.1.4.1.9.9.276.1.1.1";

      list cieIfPacketStatsEntry {
        key "ifIndex";
        description
         "An entry into the cieIfPacketStatsTable.";
        smiv2:oid "1.3.6.1.4.1.9.9.276.1.1.1.1";

        leaf ifIndex {
          type leafref {
            path "/if-mib:IF-MIB/if-mib:ifTable/if-mib:ifEntry/if-mib:ifIndex";
          }
        }

        leaf cieIfLastInTime {
          type yang:gauge32;
          units "milliseconds";
          description
           "This object represents the elapsed time in
            milliseconds since last protocol input 
            packet was received.
            
            Discontinuities in the value of this variable
            can occur at re-initialization of the
            management system, and at other times as 
            indicated by the values of 
            cieIfPacketDiscontinuityTime.";
          smiv2:max-access "read-only";
          smiv2:oid "1.3.6.1.4.1.9.9.276.1.1.1.1.1";
        }

        leaf cieIfLastOutTime {
          type yang:gauge32;
          units "milliseconds";
          description
           "This object represents the elapsed time in
            milliseconds since last protocol  output 
            packet was transmitted.
            
            Discontinuities in the value of this variable
            can occur at re-initialization of the
            management system, and at other times as 
            indicated by the values of 
            cieIfPacketDiscontinuityTime.";
          smiv2:max-access "read-only";
          smiv2:oid "1.3.6.1.4.1.9.9.276.1.1.1.1.2";
        }

        leaf cieIfLastOutHangTime {
          type yang:gauge32;
          units "milliseconds";
          description
           "This object represents the elapsed time in
            milliseconds since last protocol    output
            packet could not be successfully transmitted.
            
            Discontinuities in the value of this variable
            can occur at re-initialization of the
            management system, and at other times as 
            indicated by the values of 
            cieIfPacketDiscontinuityTime.";
          smiv2:max-access "read-only";
          smiv2:oid "1.3.6.1.4.1.9.9.276.1.1.1.1.3";
        }

        leaf cieIfInRuntsErrs {
          type yang:counter32;
          description
           "The number of packets input on a particular
            physical interface which were dropped as
            they were smaller than the minimum allowable 
            physical media limit.
            
            Discontinuities in the value of this variable
            can occur at re-initialization of the
            management system, and at other times as 
            indicated by the values of 
            cieIfPacketDiscontinuityTime.";
          smiv2:max-access "read-only";
          smiv2:oid "1.3.6.1.4.1.9.9.276.1.1.1.1.4";
        }

        leaf cieIfInGiantsErrs {
          type yang:counter32;
          description
           "The number of input packets on a particular
            physical interface which were dropped as 
            they were larger than the ifMtu (largest 
            permitted  size of a packet which can be 
            sent/received on an interface).
            
            Discontinuities in the value of this variable
            can occur at re-initialization of the
            management system, and at other times as 
            indicated by the values of 
            cieIfPacketDiscontinuityTime.";
          smiv2:max-access "read-only";
          smiv2:oid "1.3.6.1.4.1.9.9.276.1.1.1.1.5";
        }

        leaf cieIfInFramingErrs {
          type yang:counter32;
          description
           "The number of input packets on a physical
            interface which were misaligned or had
            framing errors. This happens when the 
            format of the incoming packet on a physical
            interface is incorrect.
            
            Discontinuities in the value of this variable
            can occur at re-initialization of the
            management system, and at other times as 
            indicated by the values of 
            cieIfPacketDiscontinuityTime.";
          smiv2:max-access "read-only";
          smiv2:oid "1.3.6.1.4.1.9.9.276.1.1.1.1.6";
        }

        leaf cieIfInOverrunErrs {
          type yang:counter32;
          description
           "The number of input packets which arrived
            on a particular physical interface which 
            were too quick for the hardware to receive
            and hence the receiver ran out of buffers.
            
            Discontinuities in the value of this variable
            can occur at re-initialization of the
            management system, and at other times as 
            indicated by the values of 
            cieIfPacketDiscontinuityTime.";
          smiv2:max-access "read-only";
          smiv2:oid "1.3.6.1.4.1.9.9.276.1.1.1.1.7";
        }

        leaf cieIfInIgnored {
          type yang:counter32;
          description
           "The number of input packets which were simply
            ignored by this physical interface due to 
            insufficient resources to handle the incoming
            packets.
            
            For example, this could indicate that the input
            receive buffers are not available or that the
            receiver lost a packet.
            
            Discontinuities in the value of this variable
            can occur at re-initialization of the
            management system, and at other times as 
            indicated by the values of 
            cieIfPacketDiscontinuityTime.";
          smiv2:max-access "read-only";
          smiv2:oid "1.3.6.1.4.1.9.9.276.1.1.1.1.8";
        }

        leaf cieIfInAbortErrs {
          type yang:counter32;
          description
           "Number of input packets which were dropped
            because the receiver aborted.
            
            Examples of this could be when an abort
            sequence aborted the input frame or when
            there is a collision in an ethernet segment.
            
            Discontinuities in the value of this variable
            can occur at re-initialization of the
            management system, and at other times as 
            indicated by the values of 
            cieIfPacketDiscontinuityTime.";
          smiv2:max-access "read-only";
          smiv2:oid "1.3.6.1.4.1.9.9.276.1.1.1.1.9";
        }

        leaf cieIfInputQueueDrops {
          type yang:counter32;
          description
           "The number of input packets which were
            dropped.
            
            Some reasons why this object could be 
            incremented are:
            
            o  Input queue is full.
            o  Errors at the receiver hardware 
               while receiving the packet.
            
            Discontinuities in the value of this variable
            can occur at re-initialization of the
            management system, and at other times as 
            indicated by the values of 
            cieIfPacketDiscontinuityTime.";
          smiv2:max-access "read-only";
          smiv2:oid "1.3.6.1.4.1.9.9.276.1.1.1.1.10";
        }

        leaf cieIfOutputQueueDrops {
          type yang:counter32;
          description
           "This object indicates the  number of output
            packets dropped by the interface even though
            no error had been detected to prevent them
            being transmitted. 
            
            The packet could be dropped for many reasons,
            which could range from the interface being
            down to errors in the format of the packet.
            
            Discontinuities in the value of this variable
            can occur at re-initialization of the
            management system, and at other times as 
            indicated by the values of 
            cieIfPacketDiscontinuityTime.";
          smiv2:max-access "read-only";
          smiv2:oid "1.3.6.1.4.1.9.9.276.1.1.1.1.11";
        }

        leaf cieIfPacketDiscontinuityTime {
          type yang:timestamp;
          description
           "The value of sysUpTime on the most recent
            occasion at which this interface's  counters
            suffered a discontinuity. 
            
            If no such discontinuities have occurred 
            since the last re-initialization of the 
            local management subsystem, then this 
            object contains a value of zero.";
          smiv2:max-access "read-only";
          smiv2:oid "1.3.6.1.4.1.9.9.276.1.1.1.1.12";
        }
      }
    }

    container cieIfInterfaceTable {
      description
       "This  table contains objects which provide
        more information about interface  
        properties not available in IF-MIB
        (RFC 2863).
        
        Some objects defined in this table may be
        applicable to physical interfaces only.
        As a result, this table may be sparse for
        logical interfaces.";
      smiv2:oid "1.3.6.1.4.1.9.9.276.1.1.2";

      list cieIfInterfaceEntry {
        key "ifIndex";
        description
         "An entry into the cieIfInterfaceTable.";
        smiv2:oid "1.3.6.1.4.1.9.9.276.1.1.2.1";

        leaf ifIndex {
          type leafref {
            path "/if-mib:IF-MIB/if-mib:ifTable/if-mib:ifEntry/if-mib:ifIndex";
          }
        }

        leaf cieIfResetCount {
          type yang:counter32;
          description
           "The number of times the interface was
            internally reset and brought up.
            
            Some of the actions which can cause this
            counter to increment are :
            
            o  Bringing an interface up using the 
               interface CLI command.
            
            o  Clearing the interface with the exec
               CLI command.
            
            o  Bringing the interface up via SNMP.
            
            Discontinuities in the value of this variable
            can occur at re-initialization of the
            management system, and at other times as 
            indicated by the values of 
            cieIfInterfaceDiscontinuityTime.";
          smiv2:max-access "read-only";
          smiv2:oid "1.3.6.1.4.1.9.9.276.1.1.2.1.1";
        }

        leaf cieIfKeepAliveEnabled {
          type boolean;
          description
           "A keepalive is a small, layer-2 message
            that is transmitted by a network device 
            to let directly-connected network devices
            know of its presence.
            
            This object returns 'true' if keepalives
            are enabled on this interface. If keepalives
            are not enabled, 'false' is returned.
            
            Setting this object to TRUE or FALSE enables
            or disables (respectively) keepalive on this 
            interface.";
          smiv2:max-access "read-write";
          smiv2:oid "1.3.6.1.4.1.9.9.276.1.1.2.1.2";
        }

        leaf cieIfStateChangeReason {
          type snmp-framework:SnmpAdminString;
          description
           "This object displays a human-readable
            textual string which describes the 
            cause of the last state change of the 
            interface.
            
            Examples of the values this object
            can take are:
            
            o  'Lost Carrier'
            o  'administratively down'
            o  'up'
            o  'down'";
          smiv2:max-access "read-only";
          smiv2:oid "1.3.6.1.4.1.9.9.276.1.1.2.1.3";
        }

        leaf cieIfCarrierTransitionCount {
          type yang:counter32;
          description
           "Number of times interface saw the carrier
            signal transition.
            
            For example, if a T1 line is unplugged, 
            then framer will detect the loss of signal 
            (LOS) on the line  and will count it as a
            transition.
            
            Discontinuities in the value of this variable
            can occur at re-initialization of the
            management system, and at other times as 
            indicated by the values of 
            cieIfInterfaceDiscontinuityTime.";
          smiv2:max-access "read-only";
          smiv2:oid "1.3.6.1.4.1.9.9.276.1.1.2.1.4";
        }

        leaf cieIfInterfaceDiscontinuityTime {
          type yang:timestamp;
          description
           "The value of sysUpTime on the most recent
            occasion at which this interface's  counters 
            suffered  a discontinuity. 
            
            If no such discontinuities have occurred 
            since the last re-initialization of the 
            local management subsystem, then this 
            object contains a value of zero.";
          smiv2:max-access "read-only";
          smiv2:oid "1.3.6.1.4.1.9.9.276.1.1.2.1.5";
        }

        leaf cieIfDhcpMode {
          type boolean;
          description
           "The DHCP mode configured by the
            administrator.
            If 'true' the DHCP is enabled. In which
            case an IP address is requested in DHCP.
            This is in addition to any that are 
            configured by the administrator in
            'ciiIPAddressTable' or 'ciiIPIfAddressTable'
            in CISCO-IP-IF-MIB.
            If 'false' the DHCP is disabled. In which
            case all IP addresses are configured by the
            administrator in 'ciiIPAddressTable' or 
            'ciiIPIfAddressTable'.
            For interfaces, for which DHCP cannot be or
            is not supported, then this object has the
            value 'false'.";
          smiv2:defval "false";
          smiv2:max-access "read-write";
          smiv2:oid "1.3.6.1.4.1.9.9.276.1.1.2.1.6";
        }

        leaf cieIfMtu {
          type int32 {
            range "40..2147483647";
          }
          description
           "The MTU configured by the administrator.
            This object is exactly same as 'ifMtu' in 
            ifTable from IF-MIB for the same ifIndex
            value , except that it is configurable by the
            administrator. For more description of this
            object refer to 'ifMtu' in IF-MIB.";
          smiv2:defval "1500";
          smiv2:max-access "read-write";
          smiv2:oid "1.3.6.1.4.1.9.9.276.1.1.2.1.7";
        }

        leaf cieIfContextName {
          type binary {
            length "0..32";
          }
          description
           "The ContextName denotes the interface
            'context' and is used to logically separate
            the MIB management.
            RFC 2571 and RFC 2737 describe this approach.
            When the agent supports a different SNMP 
            context, as detailed in RFC 2571 and 
            RFC 2737, for different interfaces, then the
            value of this object specifies the context
            name used for this interface.";
          smiv2:defval "";
          smiv2:max-access "read-only";
          smiv2:oid "1.3.6.1.4.1.9.9.276.1.1.2.1.8";
        }

        leaf cieIfOperStatusCause {
          type cisco-tc:IfOperStatusReason;
          description
           "This object represents the detailed
            operational cause reason for the current 
            operational state of the interface. 
            The current operational state of the interface 
            is given by the 'ifOperStatus' defined 
            in IF-MIB. 
            
            The corresponding instance of 
            'cieIfOperStatusCauseDescr' must be used to 
            get the information about the operational 
            cause value mentioned in this object.
            
            For interfaces whose 'ifOperStatus' is 'down' 
            the objects 'cieIfOperStatusCause' and 
            'cieIfOperStatusCauseDescr' together provides 
            the information about the operational cause 
            reason and the description of the cause. 
            
            The value of this object will be 'none' for
            all the 'ifOperStatus' values except for 
            'down'. Its value will be one status cause 
            defined in the 'IfOperStatusReason' textual 
            convention if 'ifOperStatus' is 'down'. 
            
            The value of this object will be 'other' 
            if the operational status cause is not one 
            defined in 'IfOperStatusReason'.";
          smiv2:max-access "read-only";
          smiv2:oid "1.3.6.1.4.1.9.9.276.1.1.2.1.9";
        }

        leaf cieIfOperStatusCauseDescr {
          type snmp-framework:SnmpAdminString;
          description
           "The description for the cause of current
            operational state of the interface, given 
            by the object 'cieIfOperStatusCause'.
            
            For an interface whose 'ifOperStatus' is not
            'down' the value of this object will be 
            'none'.";
          smiv2:max-access "read-only";
          smiv2:oid "1.3.6.1.4.1.9.9.276.1.1.2.1.10";
        }

        leaf cieIfSpeedReceive {
          type yang:gauge32;
          description
           "An estimate of the interface's current receive bandwidth in
            bits per second.  This object is provided for interface with
            asymmetric interface speeds like ADSL and should be used in
            conjunction with ifSpeed object.  For interfaces which do not
            vary in bandwidth or for those where no accurate estimation can
            be made, this object should contain the nominal bandwidth. If
            the bandwidth of the interface is greater than the maximum value
            reportable by this object then this object should report its
            maximum value (4,294,967,295) and ifHighSpeed must be used to
            report the interace's speed.  For a sub-layer which has no
            concept of bandwidth, this object should be zero.";
          smiv2:max-access "read-only";
          smiv2:oid "1.3.6.1.4.1.9.9.276.1.1.2.1.11";
        }

        leaf cieIfHighSpeedReceive {
          type yang:gauge32;
          description
           "An estimate of the interface's current receive bandwidth in
            units of 1,000,000 bits per second.  If this object reports a
            value of `n' then the speed of the interface is somewhere in the
            range of `n-500,000' to `n+499,999'.  For interfaces which do
            not vary in bandwidth or for those where no accurate estimation
            can be made, this object should contain the nominal bandwidth. 
            For a sub-layer which has no concept of bandwidth, this object
            should be zero.";
          smiv2:max-access "read-only";
          smiv2:oid "1.3.6.1.4.1.9.9.276.1.1.2.1.12";
        }

        leaf cieIfOwner {
          type snmpv2-tc:DisplayString {
            length "0..80";
          }
          description
           "This data type is used to model an administratively assigned
            name of the current owner of the interface resource. This 
            information is taken from the NVT ASCII character set.  It is 
            suggested that this name contain one or more of the following: 
            SnmpEngineID, IP address, management station name, network 
            manager's name, location, or phone number.
            SNMP access control is articulated entirely in terms of the 
            contents of MIB views; access to a particular SNMP object 
            instance depends only upon its presence or absence in a 
            particular MIB view and never upon its value or the value of 
            related object instances.
            Thus, this object affords resolution of resource contention 
            only among cooperating managers; this object realizes no access
            control function with respect to uncooperative parties.";
          smiv2:max-access "read-write";
          smiv2:oid "1.3.6.1.4.1.9.9.276.1.1.2.1.13";
        }

        leaf cieIfSharedConfig {
          type enumeration {
            enum "notApplicable" {
              value "1";
            }
            enum "ownerDedicated" {
              value "2";
            }
            enum "ownerShared" {
              value "3";
            }
            enum "sharedOnly" {
              value "4";
            }
          }
          description
           "This object indicates the current configuration of
            interface sharing on the given interface.
            
            'notApplicable' - the interface sharing configuration on 
                        this interface is not applicable. 
            'ownerDedicated' - the interface is in the dedicated mode
                        to the binding physical interface.
            'ownerShared' - the interface is shared amongst virtual switches
                     and this interface physically belongs to a its 
                     virtual switch.  
            'sharedOnly' - the interface is in purely shared mode.";
          smiv2:max-access "read-only";
          smiv2:oid "1.3.6.1.4.1.9.9.276.1.1.2.1.14";
        }

        leaf cieIfSpeedGroupConfig {
          type enumeration {
            enum "notApplicable" {
              value "1";
            }
            enum "tenG" {
              value "2";
            }
            enum "oneTwoFourEightG" {
              value "3";
            }
            enum "twoFourEightSixteenG" {
              value "4";
            }
          }
          description
           "This object specifies the current speed group
            configuration on the given interface.
            
            'notApplicable' - the interface speed group configuration on
                        this interface is not applicable. It is a 
                        read-only value.
            '10G' - the interface speed group configuration on
                        this interface as 10G.
            '1G-2G-4G-8G' - the interface speed group configuration 
                        on this interface as 1G-2G-4G-8G.
            '2G-4G-8G-16G' - the interface speed group configuration 
                        on this interface as 2G-4G-8G-16G.";
          smiv2:max-access "read-write";
          smiv2:oid "1.3.6.1.4.1.9.9.276.1.1.2.1.15";
        }

        leaf cieIfTransceiverFrequencyConfig {
          type enumeration {
            enum "notApplicable" {
              value "1";
            }
            enum "fibreChannel" {
              value "2";
            }
            enum "ethernet" {
              value "3";
            }
          }
          description
           "This object specifies the current transceiver frequency
            configuration on the given interface.
            
            'notApplicable' - the interface transceiver frequency 
            				  configuration on this interface 
            				  is not applicable. It is a read-only value.
            'FibreChannel' - the interface transceiver frequency
            				 configuration on this interface as 
                             Fibre Channel.
            'Ethernet'	  -  the interface transceiver frequency on
            				 this interface as Ethernet.";
          smiv2:defval "fibreChannel";
          smiv2:max-access "read-write";
          smiv2:oid "1.3.6.1.4.1.9.9.276.1.1.2.1.16";
        }

        leaf cieIfFillPatternConfig {
          type enumeration {
            enum "arbff8G" {
              value "1";
            }
            enum "idle8G" {
              value "2";
            }
          }
          description
           "This object specifies the current switchport fill pattern
            configuration on the given interface.
            
            'arbff8G' - the inter frame gap fill pattern is
            			ARBFF for 8G speed.
            'idle8G' - the inter frame gap fill pattern is
            		   IDLE for 8G speed.";
          smiv2:defval "arbff8G";
          smiv2:max-access "read-write";
          smiv2:oid "1.3.6.1.4.1.9.9.276.1.1.2.1.17";
        }

        leaf cieIfIgnoreBitErrorsConfig {
          type boolean;
          description
           "This object specifies the current switchport biterrors
            configuration on the given interface.
            
            If 'true(1)' the ignore bit errors is enabled.In which case
            the interface ignores bit errors.
            If 'false(2)' the ignore bit errors is disabled. In which 
            case the interface acts on the bit errors. 
            For interfaces, for which bit errors 
            is not supported, then this object has the
            value 'true(1)'.";
          smiv2:defval "true";
          smiv2:max-access "read-write";
          smiv2:oid "1.3.6.1.4.1.9.9.276.1.1.2.1.18";
        }

        leaf cieIfIgnoreInterruptThresholdConfig {
          type boolean;
          description
           "This object specifies the current interrupt threshold
            configuration on the given interface.
            
            'If 'true(1)' the ignore interrupt thresholds is enabled.
            In which case the interface ignores interrupt thresholds.
            If 'false(2)' the ignore interrupt thresholds is disabled.
            In which case the interface acts on the interrupt 
            thresholds. 
            For interfaces, for which interrupt thresholds 
            is not supported, then this object has the 
            value 'true(1)'.";
          smiv2:defval "true";
          smiv2:max-access "read-write";
          smiv2:oid "1.3.6.1.4.1.9.9.276.1.1.2.1.19";
        }
      }
    }

    container cieIfStatusListTable {
      description
       "This table contains objects for providing
        the 'ifIndex', interface operational mode and 
        interface operational cause for all the 
        interfaces in the modules.
        
        This table contains one entry for each 
        64 interfaces in an module.
        
        This table provides efficient way of encoding 
        'ifIndex', interface operational mode and
        interface operational cause, from the point 
        of retrieval, by combining the values a set 
        of 64 interfaces in a single MIB object.";
      smiv2:oid "1.3.6.1.4.1.9.9.276.1.1.3";

      list cieIfStatusListEntry {
        key "entPhysicalIndex cieIfStatusListIndex";
        description
         "Each entry represents the 'ifIndex',
          interface operational mode and interface 
          operational cause for a set of 64 interfaces 
          in a module.";
        smiv2:oid "1.3.6.1.4.1.9.9.276.1.1.3.1";

        leaf entPhysicalIndex {
          type leafref {
            path "/entity-mib:ENTITY-MIB/entity-mib:entPhysicalTable/entity-mib:entPhysicalEntry/entity-mib:entPhysicalIndex";
          }
        }

        leaf cieIfStatusListIndex {
          type uint32 {
            range "1..33554432";
          }
          description
           "An arbitrary integer value, greater than
            zero, which identifies a list of 64 interfaces
            within a module.";
          smiv2:max-access "not-accessible";
          smiv2:oid "1.3.6.1.4.1.9.9.276.1.1.3.1.1";
        }

        leaf cieInterfacesIndex {
          type CISCO-IF-EXTENSION-MIB:InterfaceIndexList;
          description
           "This object represents the 'ifIndex' for a
            set of 64 interfaces in the module.";
          smiv2:max-access "read-only";
          smiv2:oid "1.3.6.1.4.1.9.9.276.1.1.3.1.2";
        }

        leaf cieInterfacesOperMode {
          type CISCO-IF-EXTENSION-MIB:InterfaceOperModeList;
          description
           "This object represents the operational mode
            for a set of 64 interfaces in the module.";
          smiv2:max-access "read-only";
          smiv2:oid "1.3.6.1.4.1.9.9.276.1.1.3.1.3";
        }

        leaf cieInterfacesOperCause {
          type CISCO-IF-EXTENSION-MIB:InterfaceOperCauseList;
          description
           "This object represents the operational status
            cause for a set of 64 interfaces in the 
            module.";
          smiv2:max-access "read-only";
          smiv2:oid "1.3.6.1.4.1.9.9.276.1.1.3.1.4";
        }

        leaf cieInterfaceOwnershipBitmap {
          type CISCO-IF-EXTENSION-MIB:InterfaceOwnershipList;
          description
           "This object indicates the status for a set of 64 interfaces
            in a module regarding whether or not each interface is 
            administratively assigned a name of the current owner of the 
            interface resource as per cieIfOwner.";
          smiv2:max-access "read-only";
          smiv2:oid "1.3.6.1.4.1.9.9.276.1.1.3.1.5";
        }
      }
    }

    container cieIfVlStatsTable {
      description
       "This table contains VL (Virtual Link) statistics
        for a capable interface.
        
        Objects defined in this table may be 
        applicable to physical interfaces only.";
      smiv2:oid "1.3.6.1.4.1.9.9.276.1.1.4";

      list cieIfVlStatsEntry {
        key "ifIndex";
        description
         "Each row contains managed objects for
          Virtual Link statistics on interface capable of 
          providing this information.";
        smiv2:oid "1.3.6.1.4.1.9.9.276.1.1.4.1";

        leaf ifIndex {
          type leafref {
            path "/if-mib:IF-MIB/if-mib:ifTable/if-mib:ifEntry/if-mib:ifIndex";
          }
        }

        leaf cieIfNoDropVlInPkts {
          type yang:counter64;
          description
           "This object indicates the number of input
            packets on all No-Drop Virtual Links belonged 
            to this interface.";
          smiv2:max-access "read-only";
          smiv2:oid "1.3.6.1.4.1.9.9.276.1.1.4.1.1";
        }

        leaf cieIfNoDropVlInOctets {
          type yang:counter64;
          description
           "This object indicates the number of input
            octets on all No-Drop Virtual Links belonged 
            to this interface.";
          smiv2:max-access "read-only";
          smiv2:oid "1.3.6.1.4.1.9.9.276.1.1.4.1.2";
        }

        leaf cieIfNoDropVlOutPkts {
          type yang:counter64;
          description
           "This object indicates the number of output
            packets on all No-Drop Virtual Links belonged 
            to this interface.";
          smiv2:max-access "read-only";
          smiv2:oid "1.3.6.1.4.1.9.9.276.1.1.4.1.3";
        }

        leaf cieIfNoDropVlOutOctets {
          type yang:counter64;
          description
           "This object indicates the number of output
            octets on all No-Drop Virtual Links belonged 
            to this interface.";
          smiv2:max-access "read-only";
          smiv2:oid "1.3.6.1.4.1.9.9.276.1.1.4.1.4";
        }

        leaf cieIfDropVlInPkts {
          type yang:counter64;
          description
           "This object indicates the number of input
            packets on all Drop Virtual Links belonged 
            to this interface.";
          smiv2:max-access "read-only";
          smiv2:oid "1.3.6.1.4.1.9.9.276.1.1.4.1.5";
        }

        leaf cieIfDropVlInOctets {
          type yang:counter64;
          description
           "This object indicates the number of input
            octets on all Drop Virtual Links belonged 
            to this interface.";
          smiv2:max-access "read-only";
          smiv2:oid "1.3.6.1.4.1.9.9.276.1.1.4.1.6";
        }

        leaf cieIfDropVlOutPkts {
          type yang:counter64;
          description
           "This object indicates the number of output
            packets on all Drop Virtual Links belonged 
            to this interface.";
          smiv2:max-access "read-only";
          smiv2:oid "1.3.6.1.4.1.9.9.276.1.1.4.1.7";
        }

        leaf cieIfDropVlOutOctets {
          type yang:counter64;
          description
           "This object indicates the number of output
            octets on all Drop Virtual Links belonged 
            to this interface.";
          smiv2:max-access "read-only";
          smiv2:oid "1.3.6.1.4.1.9.9.276.1.1.4.1.8";
        }
      }
    }

    container cieIfIndexPersistenceTable {
      description
       "This table lists configuration data relating to ifIndex
        persistence.
        
        This table has a sparse dependent relationship on the ifTable,
        containing a row for each ifEntry corresponding to an interface
        for which ifIndex persistence is supported.";
      smiv2:oid "1.3.6.1.4.1.9.9.276.1.2.5";

      list cieIfIndexPersistenceEntry {
        key "ifIndex";
        description
         "Each entry represents ifindex persistence configuration for an
          interface specified by ifIndex. Whenever an interface which
          supports ifindex persistence is created/destroyed in the
          ifTable, the corresponding ifindex persistence entry is
          created/destroyed respectively. Some of the interfaces may not
          support ifindex persistence, for example, a dynamic interface,
          such as a PPP connection or a IP subscriber interface.";
        smiv2:oid "1.3.6.1.4.1.9.9.276.1.2.5.1";

        leaf ifIndex {
          type leafref {
            path "/if-mib:IF-MIB/if-mib:ifTable/if-mib:ifEntry/if-mib:ifIndex";
          }
        }

        leaf cieIfIndexPersistenceEnabled {
          type boolean;
          status deprecated;
          description
           "This object specifies whether the interface's ifIndex value
            persist across reinitialization.
            
            Due to change in syntax, this object is deprecated by
            cieIfIndexPersistenceControl.";
          smiv2:defval "true";
          smiv2:max-access "read-write";
          smiv2:oid "1.3.6.1.4.1.9.9.276.1.2.5.1.1";
        }

        leaf cieIfIndexPersistenceControl {
          type CISCO-IF-EXTENSION-MIB:IfIndexPersistenceState;
          description
           "This object specifies whether the interface's ifIndex value
            persist across reinitialization. In global state, the interface
            uses the global setting data for persistence i.e.
            cieIfIndexGlobalPersistence.";
          smiv2:defval "global";
          smiv2:max-access "read-write";
          smiv2:oid "1.3.6.1.4.1.9.9.276.1.2.5.1.2";
        }
      }
    }

    container cieIfDot1qCustomEtherTypeTable {
      description
       "A list of the interfaces that support
        the 802.1q custom Ethertype feature.";
      smiv2:oid "1.3.6.1.4.1.9.9.276.1.3.1";

      list cieIfDot1qCustomEtherTypeEntry {
        key "ifIndex";
        description
         "An entry containing the custom EtherType
          information for the interface.
          
          Only interfaces with custom 802.1q
          ethertype control are listed in the 
          table.";
        smiv2:oid "1.3.6.1.4.1.9.9.276.1.3.1.1";

        leaf ifIndex {
          type leafref {
            path "/if-mib:IF-MIB/if-mib:ifTable/if-mib:ifEntry/if-mib:ifIndex";
          }
        }

        leaf cieIfDot1qCustomAdminEtherType {
          type int32 {
            range "0..65535";
          }
          description
           "The Dot1qEtherType allow administrator
            to select a non-standard (other than 0x8100)
            2-byte ethertype for the interface to 
            interoperate with third party vendor's system
            that do not use the standard 0x8100 ethertype
            to identify 802.1q-tagged frames.
            
            The current administrative value of the 
            802.1q ethertype for the interface.  The
            administrative 802.1q ethertype value may 
            differ from the operational 802.1q ethertype
            value.  On some platforms, 802.1q ethertype
            may be assigned per group rather than per port.
            If multiple ports belong to a port group,
            the 802.1q ethertype assigned to any of
            the ports in such group will apply to all
            ports in the same group.
            
            To configure non-standard dot1q ethertype
            is only recommended when the Cisco device
            is connected to any third party vendor device.
            Also be advised that the custom ethertype value
            needs to be changed in the whole cloud of 
            Cisco device with the same custom ethertype 
            value if the third party device are separated 
            by number of Cisco device in the middle.";
          smiv2:max-access "read-write";
          smiv2:oid "1.3.6.1.4.1.9.9.276.1.3.1.1.1";
        }

        leaf cieIfDot1qCustomOperEtherType {
          type int32 {
            range "0..65535";
          }
          description
           "The current operational value of the
            802.1q ethertype for the interface.";
          smiv2:max-access "read-only";
          smiv2:oid "1.3.6.1.4.1.9.9.276.1.3.1.1.2";
        }
      }
    }

    container cieIfUtilTable {
      description
       "This table contains the interface utilization
        rates for inbound and outbound traffic on an
        interface.";
      smiv2:oid "1.3.6.1.4.1.9.9.276.1.4.1";

      list cieIfUtilEntry {
        key "ifIndex";
        description
         "An entry containing utilization rates for the
          interface.
          
          Every interface for which the  inbound and 
          outbound traffic information is available
          has a corresponding entry in this table.";
        smiv2:oid "1.3.6.1.4.1.9.9.276.1.4.1.1";

        leaf ifIndex {
          type leafref {
            path "/if-mib:IF-MIB/if-mib:ifTable/if-mib:ifEntry/if-mib:ifIndex";
          }
        }

        leaf cieIfInPktRate {
          type yang:counter64;
          units "packets per second";
          description
           "By default, this is the five minute
            exponentially-decayed moving average of the
            inbound packet rate for this interface.
            However, if the corresponding instance of
            cieIfInterval is instantiated with a value
            which specifies an interval different from
            5-minutes, then cieIfInPktRate is the
            exponentially-decayed moving average of inbound
            packet rate over this different time interval.";
          smiv2:max-access "read-only";
          smiv2:oid "1.3.6.1.4.1.9.9.276.1.4.1.1.1";
        }

        leaf cieIfInOctetRate {
          type yang:counter64;
          units "octets per second";
          description
           "By default, this is the five minute
            exponentially-decayed moving average of the
            inbound octet rate for this interface.
            However, if the corresponding instance of
            cieIfInterval is instantiated with a value
            which specifies an interval different from
            5-minutes, then cieIfInOctetRate is the
            exponentially-decayed moving average of inbound
            octet rate over this different time interval.";
          smiv2:max-access "read-only";
          smiv2:oid "1.3.6.1.4.1.9.9.276.1.4.1.1.2";
        }

        leaf cieIfOutPktRate {
          type yang:counter64;
          units "packets per second";
          description
           "By default, this is the five minute
            exponentially-decayed moving average of the
            outbound packet rate for this interface.
            However, if the corresponding instance of
            cieIfInterval is instantiated with a value
            which specifies an interval different from
            5-minutes, then cieIfOutPktRate is the
            exponentially-decayed moving average of outbound
            packet rate over this different time interval.";
          smiv2:max-access "read-only";
          smiv2:oid "1.3.6.1.4.1.9.9.276.1.4.1.1.3";
        }

        leaf cieIfOutOctetRate {
          type yang:counter64;
          units "octets per second";
          description
           "By default, this is the five minute
            exponentially-decayed moving average of the
            outbound octet rate for this interface.
            However, if the corresponding instance of
            cieIfInterval is instantiated with a value
            which specifies an interval different from
            5-minutes, then cieIfOutOctetRate is the
            exponentially-decayed moving average of outbound
            octet rate over this different time interval.";
          smiv2:max-access "read-only";
          smiv2:oid "1.3.6.1.4.1.9.9.276.1.4.1.1.4";
        }

        leaf cieIfInterval {
          type uint32 {
            range "1..4294967295";
          }
          units "seconds";
          description
           "This object specifies the time interval over which
            the inbound and outbound traffic rates are
            calculated for this interface.";
          smiv2:max-access "read-write";
          smiv2:oid "1.3.6.1.4.1.9.9.276.1.4.1.1.5";
        }
      }
    }

    container cieIfDot1dBaseMappingTable {
      description
       "This table contains the mappings of the
        ifIndex of an interface to its
        corresponding dot1dBasePort value.";
      reference
       "dot1dBasePort is defined in BRIDGE-MIB.";
      smiv2:oid "1.3.6.1.4.1.9.9.276.1.5.1";

      list cieIfDot1dBaseMappingEntry {
        key "ifIndex";
        description
         "An entry containing the mapping between
          the ifIndex value of an interface and its
          corresponding dot1dBasePort value.
          
          Every interface which has been assigned
          a dot1dBasePort value by the system
          has a corresponding entry in this table.";
        reference
         "dot1dBasePort is defined in BRIDGE-MIB.";
        smiv2:oid "1.3.6.1.4.1.9.9.276.1.5.1.1";

        leaf ifIndex {
          type leafref {
            path "/if-mib:IF-MIB/if-mib:ifTable/if-mib:ifEntry/if-mib:ifIndex";
          }
        }

        leaf cieIfDot1dBaseMappingPort {
          type int32 {
            range "1..65535";
          }
          description
           "The dot1dBasePort value for this interface.";
          reference
           "dot1dBasePort is defined in BRIDGE-MIB.";
          smiv2:max-access "read-only";
          smiv2:oid "1.3.6.1.4.1.9.9.276.1.5.1.1.1";
        }
      }
    }

    container cieIfNameMappingTable {
      description
       "This table contains objects for providing
        the 'ifName' to 'ifIndex' mapping.
        This table contains one entry for each
        valid 'ifName' available in the system.
        Upon the first request, the implementation
        of this table will get all the available
        ifNames, and it will populate the entries
        in this table, it maintains this ifNames
        in a cache for ~30 seconds.";
      smiv2:oid "1.3.6.1.4.1.9.9.276.1.6.1";

      list cieIfNameMappingEntry {
        key "cieIfName";
        description
         "An entry into the cieIfNameMappingTable.";
        smiv2:oid "1.3.6.1.4.1.9.9.276.1.6.1.1";

        leaf cieIfName {
          type snmpv2-tc:DisplayString {
            length "1..112";
          }
          description
           "Represents an interface name mentioned
            in the 'ifName' object of this system.";
          smiv2:max-access "not-accessible";
          smiv2:oid "1.3.6.1.4.1.9.9.276.1.6.1.1.1";
        }

        leaf cieIfIndex {
          type if-mib:InterfaceIndexOrZero;
          description
           "This object represents the 'ifIndex'
            corresponding to the interface name mentioned
            in the 'cieIfName' object of this instance.
            If the 'ifName' mentioned in the 'cieIfName' 
            object of this instance corresponds to multiple
            'ifIndex' values, then the value of this object
            is the numerically smallest of those multiple 
            'ifIndex' values.";
          smiv2:max-access "read-only";
          smiv2:oid "1.3.6.1.4.1.9.9.276.1.6.1.1.2";
        }
      }
    }
  }

  notification cieLinkDown {
    description
     "A cisco specific linkDown notification
      signifies that the SNMP entity, acting in an
      agent role, has detected that the ifOperStatus
      object for one of its communication links is
      about to enter the down state from some other
      state (but not from the notPresent state).
      The varbinds for this notification indicate the
      interface information of the communication
      link.";
    smiv2:oid "1.3.6.1.4.1.9.9.276.0.1";

    container object-1 {

      leaf ifIndex {
        type leafref {
          path "/if-mib:IF-MIB/if-mib:ifTable/if-mib:ifEntry/if-mib:ifIndex";
        }
      }
    }

    container object-2 {

      leaf ifIndex {
        type leafref {
          path "/if-mib:IF-MIB/if-mib:ifTable/if-mib:ifEntry/if-mib:ifIndex";
        }
      }

      leaf ifAdminStatus {
        type leafref {
          path "/if-mib:IF-MIB/if-mib:ifTable/if-mib:ifEntry/if-mib:ifAdminStatus";
        }
      }
    }

    container object-3 {

      leaf ifIndex {
        type leafref {
          path "/if-mib:IF-MIB/if-mib:ifTable/if-mib:ifEntry/if-mib:ifIndex";
        }
      }

      leaf ifOperStatus {
        type leafref {
          path "/if-mib:IF-MIB/if-mib:ifTable/if-mib:ifEntry/if-mib:ifOperStatus";
        }
      }
    }

    container object-4 {

      leaf ifIndex {
        type leafref {
          path "/if-mib:IF-MIB/if-mib:ifTable/if-mib:ifEntry/if-mib:ifIndex";
        }
      }

      leaf ifName {
        type leafref {
          path "/if-mib:IF-MIB/if-mib:ifTable/if-mib:ifEntry/if-mib:ifName";
        }
      }
    }

    container object-5 {

      leaf ifIndex {
        type leafref {
          path "/if-mib:IF-MIB/if-mib:ifTable/if-mib:ifEntry/if-mib:ifIndex";
        }
      }

      leaf ifType {
        type leafref {
          path "/if-mib:IF-MIB/if-mib:ifTable/if-mib:ifEntry/if-mib:ifType";
        }
      }
    }
  }

  notification cieLinkUp {
    description
     "A cisco specific linkUp trap signifies that
      the SNMP entity, acting in an agent role, has
      detected that the ifOperStatus object for one
      of its communication links left the down state
      and transitioned into some other state (but not
      into the notPresent state). The varbinds for
      this notification indicate the interface
      information of the communication link.";
    smiv2:oid "1.3.6.1.4.1.9.9.276.0.2";

    container object-1 {

      leaf ifIndex {
        type leafref {
          path "/if-mib:IF-MIB/if-mib:ifTable/if-mib:ifEntry/if-mib:ifIndex";
        }
      }
    }

    container object-2 {

      leaf ifIndex {
        type leafref {
          path "/if-mib:IF-MIB/if-mib:ifTable/if-mib:ifEntry/if-mib:ifIndex";
        }
      }

      leaf ifAdminStatus {
        type leafref {
          path "/if-mib:IF-MIB/if-mib:ifTable/if-mib:ifEntry/if-mib:ifAdminStatus";
        }
      }
    }

    container object-3 {

      leaf ifIndex {
        type leafref {
          path "/if-mib:IF-MIB/if-mib:ifTable/if-mib:ifEntry/if-mib:ifIndex";
        }
      }

      leaf ifOperStatus {
        type leafref {
          path "/if-mib:IF-MIB/if-mib:ifTable/if-mib:ifEntry/if-mib:ifOperStatus";
        }
      }
    }

    container object-4 {

      leaf ifIndex {
        type leafref {
          path "/if-mib:IF-MIB/if-mib:ifTable/if-mib:ifEntry/if-mib:ifIndex";
        }
      }

      leaf ifName {
        type leafref {
          path "/if-mib:IF-MIB/if-mib:ifTable/if-mib:ifEntry/if-mib:ifName";
        }
      }
    }

    container object-5 {

      leaf ifIndex {
        type leafref {
          path "/if-mib:IF-MIB/if-mib:ifTable/if-mib:ifEntry/if-mib:ifIndex";
        }
      }

      leaf ifType {
        type leafref {
          path "/if-mib:IF-MIB/if-mib:ifTable/if-mib:ifEntry/if-mib:ifType";
        }
      }
    }
  }

  notification cieDelayedLinkUpDownNotif {
    description
     "This notification indicates when an interface's operational
      status has transitioned and remained in that state for a time
      specified by cieDelayedLinkUpDownDelay.";
    smiv2:oid "1.3.6.1.4.1.9.9.276.0.3";

    container object-1 {

      leaf ifIndex {
        type leafref {
          path "/if-mib:IF-MIB/if-mib:ifTable/if-mib:ifEntry/if-mib:ifIndex";
        }
      }

      leaf ifAdminStatus {
        type leafref {
          path "/if-mib:IF-MIB/if-mib:ifTable/if-mib:ifEntry/if-mib:ifAdminStatus";
        }
      }
    }

    container object-2 {

      leaf ifIndex {
        type leafref {
          path "/if-mib:IF-MIB/if-mib:ifTable/if-mib:ifEntry/if-mib:ifIndex";
        }
      }

      leaf ifOperStatus {
        type leafref {
          path "/if-mib:IF-MIB/if-mib:ifTable/if-mib:ifEntry/if-mib:ifOperStatus";
        }
      }
    }

    container object-3 {

      leaf ifIndex {
        type leafref {
          path "/if-mib:IF-MIB/if-mib:ifTable/if-mib:ifEntry/if-mib:ifIndex";
        }
      }

      leaf ifName {
        type leafref {
          path "/if-mib:IF-MIB/if-mib:ifTable/if-mib:ifEntry/if-mib:ifName";
        }
      }
    }

    container object-4 {

      leaf ifIndex {
        type leafref {
          path "/if-mib:IF-MIB/if-mib:ifTable/if-mib:ifEntry/if-mib:ifIndex";
        }
      }

      leaf ifType {
        type leafref {
          path "/if-mib:IF-MIB/if-mib:ifTable/if-mib:ifEntry/if-mib:ifType";
        }
      }
    }

    container object-5 {

      leaf ifIndex {
        type leafref {
          path "/if-mib:IF-MIB/if-mib:ifTable/if-mib:ifEntry/if-mib:ifIndex";
        }
      }

      leaf cieIfOperStatusCause {
        type leafref {
          path "/CISCO-IF-EXTENSION-MIB:CISCO-IF-EXTENSION-MIB/CISCO-IF-EXTENSION-MIB:cieIfInterfaceTable/CISCO-IF-EXTENSION-MIB:cieIfInterfaceEntry/CISCO-IF-EXTENSION-MIB:cieIfOperStatusCause";
        }
      }
    }
  }

  smiv2:alias "ciscoIfExtensionMIB" {
    smiv2:oid "1.3.6.1.4.1.9.9.276";
  }

  smiv2:alias "ciscoIfExtensionMIBNotifications" {
    smiv2:oid "1.3.6.1.4.1.9.9.276.0";
  }

  smiv2:alias "ciscoIfExtensionMIBObjects" {
    smiv2:oid "1.3.6.1.4.1.9.9.276.1";
  }

  smiv2:alias "ciscoIfExtensionStats" {
    smiv2:oid "1.3.6.1.4.1.9.9.276.1.1";
  }

  smiv2:alias "ciscoIfExtSystemConfig" {
    smiv2:oid "1.3.6.1.4.1.9.9.276.1.2";
  }

  smiv2:alias "ciscoIfExtDot1qCustomEtherType" {
    smiv2:oid "1.3.6.1.4.1.9.9.276.1.3";
  }

  smiv2:alias "ciscoIfExtUtilization" {
    smiv2:oid "1.3.6.1.4.1.9.9.276.1.4";
  }

  smiv2:alias "ciscoIfExtDot1dBaseMapping" {
    smiv2:oid "1.3.6.1.4.1.9.9.276.1.5";
  }

  smiv2:alias "ciscoIfExtIfNameMapping" {
    smiv2:oid "1.3.6.1.4.1.9.9.276.1.6";
  }

  smiv2:alias "ciscoIfExtensionMIBConformance" {
    smiv2:oid "1.3.6.1.4.1.9.9.276.2";
  }

  smiv2:alias "ciscoIfExtensionMIBCompliances" {
    smiv2:oid "1.3.6.1.4.1.9.9.276.2.1";
  }

  smiv2:alias "ciscoIfExtensionMIBGroups" {
    smiv2:oid "1.3.6.1.4.1.9.9.276.2.2";
  }

}
