/*
 * Generated by confdc --mib2yang-std
 * Source: mgmt/dmi/model/common/mib-source/CISCO-CONFIG-MAN-MIB.mib
 */
/*
 * This YANG module has been generated by smidump 0.5.0:
 *
 *      smidump -f yang CISCO-CONFIG-MAN-MIB
 *
 * Do not edit. Edit the source file instead!
 */

module CISCO-CONFIG-MAN-MIB {

  namespace "urn:ietf:params:xml:ns:yang:smiv2:CISCO-CONFIG-MAN-MIB";
  prefix CISCO-CONFIG-MAN-MIB;

  import CISCO-TC {
    prefix "cisco-tc";
  }

  import INET-ADDRESS-MIB {
    prefix "inet-address";
  }

  import SNMP-FRAMEWORK-MIB {
    prefix "snmp-framework";
  }

  import SNMPv2-TC {
    prefix "snmpv2-tc";
  }

  import ietf-inet-types {
    prefix "inet";
  }

  import ietf-yang-smiv2 {
    prefix "smiv2";
  }

  import ietf-yang-types {
    prefix "yang";
  }

  organization
   "Cisco Systems, Inc.";

  contact
   "Cisco Systems
    Customer Service
    
    
    Postal: 170 W Tasman Drive
    San Jose, CA  95134
    USA
    
    Tel: +1 800 553-NETS
    
    E-mail: cs-snmp@cisco.com";

  description
   "Configuration management MIB.
    
    The MIB represents a model of configuration data that
    exists in various locations:
    
    running       in use by the running system
    terminal      saved to whatever is attached as the terminal        
    local         saved locally in NVRAM or flash
    remote        saved to some server on the network
    
    Although some of the system functions that relate here
    can be used for general file storage and transfer, this
    MIB intends to include only such operations as clearly
    relate to configuration.  Its primary emphasis is to
    track changes and saves of the running configuration.
    
    As saved data moves further from startup use, such as
    into different local flash files or onto the network,
    tracking becomes difficult to impossible, so the MIB's
    interest and functions are confined in that area.
    
    Information from ccmCLIHistoryCommandTable can be used
    to track the exact configuration changes that took
    place within a particular Configuration History
    event. NMS' can use this information to update 
    the related components. 
    For example:
        If commands related only to MPLS are entered
        then the NMS need to update only the MPLS related
        management information rather than updating
        all of its management information.
        Acronyms and terms:
    
        CLI   Command Line Interface.";

  revision 2007-04-27 {
    description
     "Changes to definition of terminal as an output
      location.";
  }

  revision 2006-08-17 {
    description
     "Added a new group of objects to store the information
      related to the Config Change Tracking ID (CTID) feature. 
      
      CTID will provide a version number that is unique for 
      version-incrementing changes to the IOS
      running-configuration. It will also provide information
      about when CTID last changed.
      
      Added scalars: 
      * ccmCTID
      * ccmCTIDLastChangeTime
      * ccmCTIDWhoChanged
      * ccmCTIDRolledOverNotifEnable
      
      Added Notification:
      * ccmCTIDRolledOver
      
      Added Object Group:
      * ciscoConfigManCTIDObjectGroup
      
      Added Notification Group:
      * ciscoConfigManCTIDNotifyGroup
      
      Added Compliance:
      ciscoConfigManMIBComplianceRev4";
  }

  revision 2004-06-18 {
    description
     "The Objects ccmHistoryEventCommandSourceAddress and
      ccmHistoryEventServerAddress are deprecated since
      they support only IPv4 address. These objects have
      been replaced by two new objects 
      ccmHistoryEventCommandSourceAddrRev1 and 
      ccmHistoryEventServerAddrRev1. In addition to these
      objects two more new objects are defined
      ccmHistoryEventCommandSourceAddrType and
      ccmHistoryEventServerAddrType";
  }

  revision 2002-06-07 {
    description
     "Added new enumerations networkFtp(8) and
      networkScp(9) to HistoryEventMedium.";
  }

  revision 2002-03-12 {
    description
     "Added ccmCLIHistoryCommandTable for
      storing the CLI commands that took effect during
      a configuration event.
      
      Added scalars ccmCLIHistoryMaxCmdEntries
      ccmCLIHistoryCmdEntries and 
      ccmCLIHistoryCmdEntriesAllowed.
      
      Added ccmHistoryCLICmdEntriesBumped to 
      ccmHistoryEventTable to store the number of
      corresponding bumped entries in the 
      ccmCLIHistoryCommandTable.
      
      Added the ccmCLIRunningConfigChanged notification.
      Added ccmCLICfgRunConfNotifEnable to control the
      ccmCLIRunningConfigChanged notification.
      
      Added notification group 
      ciscoConfigManHistNotifyGroup.
      
      Updated the MIB description to indicate the use of
      the above additions.";
  }

  revision 1995-11-28 {
    description
     "Initial version of this MIB module.";
  }

  typedef HistoryEventMedium {
    type enumeration {
      enum "erase" {
        value "1";
      }
      enum "commandSource" {
        value "2";
      }
      enum "running" {
        value "3";
      }
      enum "startup" {
        value "4";
      }
      enum "local" {
        value "5";
      }
      enum "networkTftp" {
        value "6";
      }
      enum "networkRcp" {
        value "7";
      }
      enum "networkFtp" {
        value "8";
      }
      enum "networkScp" {
        value "9";
      }
    }
    description
     "The source or destination of a configuration change,
      save, or copy.
      
      erase        erasing destination (source only)
      running        live operational data
      commandSource    the command source itself
      startup        what the system will use next reboot
      local        local NVRAM or flash
      networkTftp    network host via Trivial File Transfer
      networkRcp    network host via Remote Copy
      networkFtp       network host via File transfer
      networkScp       network host via Secure Copy";
  }


  container CISCO-CONFIG-MAN-MIB {
    config false;

    container ccmHistory {
      smiv2:oid "1.3.6.1.4.1.9.9.43.1.1";

      leaf ccmHistoryRunningLastChanged {
        type yang:timeticks;
        description
         "The value of sysUpTime when the running configuration
          was last changed.
          
                  If the value of ccmHistoryRunningLastChanged is
                  greater than ccmHistoryRunningLastSaved, the 
                  configuration has been changed but not saved.";
        smiv2:max-access "read-only";
        smiv2:oid "1.3.6.1.4.1.9.9.43.1.1.1";
      }

      leaf ccmHistoryRunningLastSaved {
        type yang:timeticks;
        description
         "The value of sysUpTime when the running configuration
          was last saved (written).
          
          If the value of ccmHistoryRunningLastChanged is 
          greater than ccmHistoryRunningLastSaved, the 
          configuration has been changed but not saved.
          
          What constitutes a safe saving of the running
          configuration is a management policy issue beyond the
          scope of this MIB.  For some installations, writing the
          running configuration to a terminal may be a way of
          capturing and saving it.  Others may use local or
          remote storage.  Thus ANY write is considered saving
          for the purposes of the MIB.";
        smiv2:max-access "read-only";
        smiv2:oid "1.3.6.1.4.1.9.9.43.1.1.2";
      }

      leaf ccmHistoryStartupLastChanged {
        type yang:timeticks;
        description
         "The value of sysUpTime when the startup configuration
          was last written to.  In general this is the
          default configuration used when cold starting the
          system.  It may have been changed by a save of the
          running configuration or by a copy from elsewhere.";
        smiv2:max-access "read-only";
        smiv2:oid "1.3.6.1.4.1.9.9.43.1.1.3";
      }

      leaf ccmHistoryMaxEventEntries {
        type int32 {
          range "0..2147483647";
        }
        description
         "The maximum number of entries that can be held in
          ccmHistoryEventTable.
          
          The recommended value for implementations is 10.";
        smiv2:max-access "read-only";
        smiv2:oid "1.3.6.1.4.1.9.9.43.1.1.4";
      }

      leaf ccmHistoryEventEntriesBumped {
        type yang:counter32;
        description
         "The number of times the oldest entry in
          ccmHistoryEventTable was deleted to make room 
          for a new entry.";
        smiv2:max-access "read-only";
        smiv2:oid "1.3.6.1.4.1.9.9.43.1.1.5";
      }
    }

    container ccmCLIHistory {
      smiv2:oid "1.3.6.1.4.1.9.9.43.1.2";

      leaf ccmCLIHistoryMaxCmdEntries {
        type uint32 {
          range "0..4294967295";
        }
        description
         "The maximum number of entries that can be held in
          ccmCLIHistoryCommandTable.
          
          The recommended value for implementations is 100.
          
          If the number of entries in ccmCLIHistoryCommandTable 
          exceeds the value of this object, old entries will be 
          bumped to make room for new entries.
          
          The ccmCLIHistoryCommandTable will not be populated
          if the value of this object is 0.";
        smiv2:max-access "read-write";
        smiv2:oid "1.3.6.1.4.1.9.9.43.1.2.1";
      }

      leaf ccmCLIHistoryCmdEntries {
        type yang:gauge32;
        description
         "The current number of entries in
          ccmCLIHistoryCommandTable.";
        smiv2:max-access "read-only";
        smiv2:oid "1.3.6.1.4.1.9.9.43.1.2.2";
      }

      leaf ccmCLIHistoryCmdEntriesAllowed {
        type uint32;
        description
         "This object indicates the upper limit on the
          number of entries allowed in 
          ccmCLIHistoryCommandTable by the managed system.";
        smiv2:max-access "read-only";
        smiv2:oid "1.3.6.1.4.1.9.9.43.1.2.3";
      }
    }

    container ccmCLICfg {
      smiv2:oid "1.3.6.1.4.1.9.9.43.1.3";

      leaf ccmCLICfgRunConfNotifEnable {
        type boolean;
        description
         "This variable indicates whether the system produces
          the ccmCLIRunningConfigChanged notification. A false 
          value will prevent notifications from being generated 
          by this system.";
        smiv2:defval "false";
        smiv2:max-access "read-write";
        smiv2:oid "1.3.6.1.4.1.9.9.43.1.3.1";
      }
    }

    container ccmCTIDObjects {
      smiv2:oid "1.3.6.1.4.1.9.9.43.1.4";

      leaf ccmCTID {
        type cisco-tc:Unsigned64;
        description
         "This object indicates the Config Change Tracking ID which
          uniquely represents version-incrementing changes to the IOS 
          running configuration.";
        smiv2:max-access "read-only";
        smiv2:oid "1.3.6.1.4.1.9.9.43.1.4.1";
      }

      leaf ccmCTIDLastChangeTime {
        type snmpv2-tc:DateAndTime;
        description
         "This object indicates the time when the Config Change Tracking
          ID last changed.";
        smiv2:max-access "read-only";
        smiv2:oid "1.3.6.1.4.1.9.9.43.1.4.2";
      }

      leaf ccmCTIDWhoChanged {
        type snmp-framework:SnmpAdminString;
        description
         "This object indicates the user who last reset the Config Change
          Tracking ID.";
        smiv2:max-access "read-only";
        smiv2:oid "1.3.6.1.4.1.9.9.43.1.4.3";
      }

      leaf ccmCTIDRolledOverNotifEnable {
        type boolean;
        description
         "This variable indicates whether the system produces the
          ccmCTIDRolledOver notification. A false value will prevent
          notifications from being generated by this system.";
        smiv2:defval "false";
        smiv2:max-access "read-write";
        smiv2:oid "1.3.6.1.4.1.9.9.43.1.4.4";
      }
    }

    container ccmHistoryEventTable {
      description
       "A table of configuration events on this router.";
      smiv2:oid "1.3.6.1.4.1.9.9.43.1.1.6";

      list ccmHistoryEventEntry {
        key "ccmHistoryEventIndex";
        description
         "Information about a configuration event on this
          router.";
        smiv2:oid "1.3.6.1.4.1.9.9.43.1.1.6.1";

        leaf ccmHistoryEventIndex {
          type int32 {
            range "1..2147483647";
          }
          description
           "A monotonically increasing integer for the sole
            purpose of indexing events.  When it reaches the 
            maximum value, an extremely unlikely event, the agent 
            wraps the value back to 1 and may flush existing 
            entries.";
          smiv2:max-access "not-accessible";
          smiv2:oid "1.3.6.1.4.1.9.9.43.1.1.6.1.1";
        }

        leaf ccmHistoryEventTime {
          type yang:timeticks;
          description
           "The value of sysUpTime when the event occurred.";
          smiv2:max-access "read-only";
          smiv2:oid "1.3.6.1.4.1.9.9.43.1.1.6.1.2";
        }

        leaf ccmHistoryEventCommandSource {
          type enumeration {
            enum "commandLine" {
              value "1";
            }
            enum "snmp" {
              value "2";
            }
          }
          description
           "The source of the command that instigated the event.";
          smiv2:max-access "read-only";
          smiv2:oid "1.3.6.1.4.1.9.9.43.1.1.6.1.3";
        }

        leaf ccmHistoryEventConfigSource {
          type CISCO-CONFIG-MAN-MIB:HistoryEventMedium;
          description
           "The configuration data source for the event.";
          smiv2:max-access "read-only";
          smiv2:oid "1.3.6.1.4.1.9.9.43.1.1.6.1.4";
        }

        leaf ccmHistoryEventConfigDestination {
          type CISCO-CONFIG-MAN-MIB:HistoryEventMedium;
          description
           "The configuration data destination for the event.";
          smiv2:max-access "read-only";
          smiv2:oid "1.3.6.1.4.1.9.9.43.1.1.6.1.5";
        }

        leaf ccmHistoryEventTerminalType {
          type enumeration {
            enum "notApplicable" {
              value "1";
            }
            enum "unknown" {
              value "2";
            }
            enum "console" {
              value "3";
            }
            enum "terminal" {
              value "4";
            }
            enum "virtual" {
              value "5";
            }
            enum "auxiliary" {
              value "6";
            }
          }
          description
           "If ccmHistoryEventCommandSource is 'commandLine',
            the terminal type, otherwise 'notApplicable'.";
          smiv2:max-access "read-only";
          smiv2:oid "1.3.6.1.4.1.9.9.43.1.1.6.1.6";
        }

        leaf ccmHistoryEventTerminalNumber {
          type int32 {
            range "-2147483648..2147483647";
          }
          description
           "If ccmHistoryEventCommandSource is 'commandLine',
            the terminal number.  The value is -1 if not available
            or not applicable.";
          smiv2:max-access "read-only";
          smiv2:oid "1.3.6.1.4.1.9.9.43.1.1.6.1.7";
        }

        leaf ccmHistoryEventTerminalUser {
          type snmpv2-tc:DisplayString {
            length "0..64";
          }
          description
           "If ccmHistoryEventCommandSource is 'commandLine',
            the name of the logged in user.  The length is zero if
            not available or not applicable.";
          smiv2:max-access "read-only";
          smiv2:oid "1.3.6.1.4.1.9.9.43.1.1.6.1.8";
        }

        leaf ccmHistoryEventTerminalLocation {
          type snmpv2-tc:DisplayString {
            length "0..64";
          }
          description
           "If ccmHistoryEventCommandSource is 'commandLine',
            the hard-wired location of the terminal or the remote 
            host for an incoming connection.  The length is zero 
            if not available or not applicable.";
          smiv2:max-access "read-only";
          smiv2:oid "1.3.6.1.4.1.9.9.43.1.1.6.1.9";
        }

        leaf ccmHistoryEventCommandSourceAddress {
          type inet:ipv4-address;
          status deprecated;
          description
           "If ccmHistoryEventTerminalType is 'virtual', the
            internet address of the connected system.
            
            If ccmHistoryEventCommandSource is 'snmp', the internet
            address of the requester.
            
            The value is 0.0.0.0 if not available or not 
            applicable.
            
            This object is deprecated by
            ccmHistoryEventCommandSourceAddrRev1";
          smiv2:max-access "read-only";
          smiv2:oid "1.3.6.1.4.1.9.9.43.1.1.6.1.10";
        }

        leaf ccmHistoryEventVirtualHostName {
          type snmpv2-tc:DisplayString {
            length "0..64";
          }
          description
           "If ccmHistoryEventTerminalType is 'virtual', the host
            name of the connected system.  The length is zero if
            not available or not applicable.";
          smiv2:max-access "read-only";
          smiv2:oid "1.3.6.1.4.1.9.9.43.1.1.6.1.11";
        }

        leaf ccmHistoryEventServerAddress {
          type inet:ipv4-address;
          status deprecated;
          description
           "If ccmHistoryEventConfigSource or
            ccmHistoryEventConfigDestination is 'networkTftp' or
            'networkRcp', the internet address of the storage file
            server.  The value is 0.0.0.0 if not applicable or not
                    available.
                    This object is deprecated by
                    ccmHistoryEventServerAddrRev1";
          smiv2:max-access "read-only";
          smiv2:oid "1.3.6.1.4.1.9.9.43.1.1.6.1.12";
        }

        leaf ccmHistoryEventFile {
          type snmpv2-tc:DisplayString {
            length "0..64";
          }
          description
           "If ccmHistoryEventConfigSource or
            ccmHistoryEventConfigDestination is 'networkTftp' or
            'networkRcp', the configuration file name at the
            storage file server.  The length is zero if not
            available or not applicable.";
          smiv2:max-access "read-only";
          smiv2:oid "1.3.6.1.4.1.9.9.43.1.1.6.1.13";
        }

        leaf ccmHistoryEventRcpUser {
          type snmpv2-tc:DisplayString {
            length "0..64";
          }
          description
           "If ccmHistoryEventConfigSource or
            ccmHistoryEventConfigDestination is 'networkRcp', the
            remote user name.  The length is zero if not applicable
            or not available.";
          smiv2:max-access "read-only";
          smiv2:oid "1.3.6.1.4.1.9.9.43.1.1.6.1.14";
        }

        leaf ccmHistoryCLICmdEntriesBumped {
          type yang:counter32;
          description
           "The number of times the oldest entry in
            ccmCLIHistoryCommandTable with first index as 
            ccmHistoryEventIndex was deleted to make 
            room for a new entry.
            
            This object is applicable only if 
            ccmHistoryEventCommandSource has a value 
            of 'commandLine'.";
          smiv2:max-access "read-only";
          smiv2:oid "1.3.6.1.4.1.9.9.43.1.1.6.1.15";
        }

        leaf ccmHistoryEventCommandSourceAddrType {
          type inet-address:InetAddressType;
          description
           "This object indicates the transport type of the
            address contained in
            ccmHistoryEventCommandSourceAddrRev1.
            
            The value will be zero if not available or not
            applicable.";
          smiv2:max-access "read-only";
          smiv2:oid "1.3.6.1.4.1.9.9.43.1.1.6.1.16";
        }

        leaf ccmHistoryEventCommandSourceAddrRev1 {
          type inet-address:InetAddress;
          description
           "If ccmHistoryEventTerminalType is 'virtual', the
            internet address of the connected system.
            
            If ccmHistoryEventCommandSource is 'snmp', the
            internet address of the requester.
            
            The value of all bit's is zero  if not available or
            not applicable.
            
            The Format of this address depends on the value of the
            ccmHistoryEventCommandSourceAddrType object.
            
            This object deprecates
            ccmHistoryEventCommandSourceAddress";
          smiv2:max-access "read-only";
          smiv2:oid "1.3.6.1.4.1.9.9.43.1.1.6.1.17";
        }

        leaf ccmHistoryEventServerAddrType {
          type inet-address:InetAddressType;
          description
           "This object indicates the transport type of the
            address contained in ccmHistoryEventServerAddrRev1.
            
            The value will be zero if not available or not
            aplicable.";
          smiv2:max-access "read-only";
          smiv2:oid "1.3.6.1.4.1.9.9.43.1.1.6.1.18";
        }

        leaf ccmHistoryEventServerAddrRev1 {
          type inet-address:InetAddress;
          description
           "If ccmHistoryEventConfigSource or
            ccmHistoryEventConfigDestination is 'networkTftp' or
            'networkRcp', the internet address of the storage file
            server. 
            
            The value of all bits is 0s if not applicable or not
            available.
            
            The Format of this address depends on the value of the
            ccmHistoryEventServerAddrType object.
            
            This object deprecates ccmHistoryEventServerAddress.";
          smiv2:max-access "read-only";
          smiv2:oid "1.3.6.1.4.1.9.9.43.1.1.6.1.19";
        }
      }
    }

    container ccmCLIHistoryCommandTable {
      description
       "A table of CLI commands that took effect during
        configuration events.";
      smiv2:oid "1.3.6.1.4.1.9.9.43.1.2.4";

      list ccmCLIHistoryCommandEntry {
        key "ccmHistoryEventIndex ccmCLIHistoryCommandIndex";
        description
         "Information about the CLI commands that took effect
          during the configuration event pointed by 
          ccmCLIHistoryEventIndex.
          
          A set of rows in this table having the first
          index as ccmHistoryEventIndex will store the
          CLI commands entered during the corresponding 
          configuration event in ccmHistoryEventTable.
          
          An entry will be created in this table only if 
          the corresponding entry in ccmHistoryEventTable has 
          a value of 'commandLine' for 
          ccmHistoryEventCommandSource.";
        smiv2:oid "1.3.6.1.4.1.9.9.43.1.2.4.1";

        leaf ccmHistoryEventIndex {
          type leafref {
            path "/CISCO-CONFIG-MAN-MIB:CISCO-CONFIG-MAN-MIB/CISCO-CONFIG-MAN-MIB:ccmHistoryEventTable/CISCO-CONFIG-MAN-MIB:ccmHistoryEventEntry/CISCO-CONFIG-MAN-MIB:ccmHistoryEventIndex";
          }
        }

        leaf ccmCLIHistoryCommandIndex {
          type uint32 {
            range "1..4294967295";
          }
          description
           "A monotonically increasing integer for the
            purpose of indexing CLI commands which took effect
            during a configuration event.";
          smiv2:max-access "not-accessible";
          smiv2:oid "1.3.6.1.4.1.9.9.43.1.2.4.1.1";
        }

        leaf ccmCLIHistoryCommand {
          type snmpv2-tc:DisplayString;
          description
           "The CLI command entered which took effect
            during the configuration event pointed by 
            ccmHistoryEventIndex.";
          smiv2:max-access "read-only";
          smiv2:oid "1.3.6.1.4.1.9.9.43.1.2.4.1.2";
        }
      }
    }
  }

  notification ciscoConfigManEvent {
    description
     "Notification of a configuration management event as
      recorded in ccmHistoryEventTable.";
    smiv2:oid "1.3.6.1.4.1.9.9.43.2.0.1";

    container object-1 {

      leaf ccmHistoryEventIndex {
        type leafref {
          path "/CISCO-CONFIG-MAN-MIB:CISCO-CONFIG-MAN-MIB/CISCO-CONFIG-MAN-MIB:ccmHistoryEventTable/CISCO-CONFIG-MAN-MIB:ccmHistoryEventEntry/CISCO-CONFIG-MAN-MIB:ccmHistoryEventIndex";
        }
      }

      leaf ccmHistoryEventCommandSource {
        type leafref {
          path "/CISCO-CONFIG-MAN-MIB:CISCO-CONFIG-MAN-MIB/CISCO-CONFIG-MAN-MIB:ccmHistoryEventTable/CISCO-CONFIG-MAN-MIB:ccmHistoryEventEntry/CISCO-CONFIG-MAN-MIB:ccmHistoryEventCommandSource";
        }
      }
    }

    container object-2 {

      leaf ccmHistoryEventIndex {
        type leafref {
          path "/CISCO-CONFIG-MAN-MIB:CISCO-CONFIG-MAN-MIB/CISCO-CONFIG-MAN-MIB:ccmHistoryEventTable/CISCO-CONFIG-MAN-MIB:ccmHistoryEventEntry/CISCO-CONFIG-MAN-MIB:ccmHistoryEventIndex";
        }
      }

      leaf ccmHistoryEventConfigSource {
        type leafref {
          path "/CISCO-CONFIG-MAN-MIB:CISCO-CONFIG-MAN-MIB/CISCO-CONFIG-MAN-MIB:ccmHistoryEventTable/CISCO-CONFIG-MAN-MIB:ccmHistoryEventEntry/CISCO-CONFIG-MAN-MIB:ccmHistoryEventConfigSource";
        }
      }
    }

    container object-3 {

      leaf ccmHistoryEventIndex {
        type leafref {
          path "/CISCO-CONFIG-MAN-MIB:CISCO-CONFIG-MAN-MIB/CISCO-CONFIG-MAN-MIB:ccmHistoryEventTable/CISCO-CONFIG-MAN-MIB:ccmHistoryEventEntry/CISCO-CONFIG-MAN-MIB:ccmHistoryEventIndex";
        }
      }

      leaf ccmHistoryEventConfigDestination {
        type leafref {
          path "/CISCO-CONFIG-MAN-MIB:CISCO-CONFIG-MAN-MIB/CISCO-CONFIG-MAN-MIB:ccmHistoryEventTable/CISCO-CONFIG-MAN-MIB:ccmHistoryEventEntry/CISCO-CONFIG-MAN-MIB:ccmHistoryEventConfigDestination";
        }
      }
    }
  }

  notification ccmCLIRunningConfigChanged {
    description
     "This notification indicates that the running
      configuration of the managed system has changed
      from the CLI.
      
      If the managed system supports a separate 
      configuration mode(where the configuration commands 
      are entered under a  configuration session which 
      affects the running configuration of the system), 
      then this notification is sent when the configuration 
      mode is exited.
      During this configuration session there can be 
      one or more running configuration changes.";
    smiv2:oid "1.3.6.1.4.1.9.9.43.2.0.2";

    container object-1 {

      leaf ccmHistoryRunningLastChanged {
        type leafref {
          path "/CISCO-CONFIG-MAN-MIB:CISCO-CONFIG-MAN-MIB/CISCO-CONFIG-MAN-MIB:ccmHistory/CISCO-CONFIG-MAN-MIB:ccmHistoryRunningLastChanged";
        }
      }
    }

    container object-2 {

      leaf ccmHistoryEventIndex {
        type leafref {
          path "/CISCO-CONFIG-MAN-MIB:CISCO-CONFIG-MAN-MIB/CISCO-CONFIG-MAN-MIB:ccmHistoryEventTable/CISCO-CONFIG-MAN-MIB:ccmHistoryEventEntry/CISCO-CONFIG-MAN-MIB:ccmHistoryEventIndex";
        }
      }

      leaf ccmHistoryEventTerminalType {
        type leafref {
          path "/CISCO-CONFIG-MAN-MIB:CISCO-CONFIG-MAN-MIB/CISCO-CONFIG-MAN-MIB:ccmHistoryEventTable/CISCO-CONFIG-MAN-MIB:ccmHistoryEventEntry/CISCO-CONFIG-MAN-MIB:ccmHistoryEventTerminalType";
        }
      }
    }
  }

  notification ccmCTIDRolledOver {
    description
     "This notification indicates that the Config Change Tracking
      ID has rolled over and will be reset.";
    smiv2:oid "1.3.6.1.4.1.9.9.43.2.0.3";
  }

  smiv2:alias "ciscoConfigManMIB" {
    smiv2:oid "1.3.6.1.4.1.9.9.43";
  }

  smiv2:alias "ciscoConfigManMIBObjects" {
    smiv2:oid "1.3.6.1.4.1.9.9.43.1";
  }

  smiv2:alias "ccmHistory" {
    smiv2:oid "1.3.6.1.4.1.9.9.43.1.1";
  }

  smiv2:alias "ccmCLIHistory" {
    smiv2:oid "1.3.6.1.4.1.9.9.43.1.2";
  }

  smiv2:alias "ccmCLICfg" {
    smiv2:oid "1.3.6.1.4.1.9.9.43.1.3";
  }

  smiv2:alias "ccmCTIDObjects" {
    smiv2:oid "1.3.6.1.4.1.9.9.43.1.4";
  }

  smiv2:alias "ciscoConfigManMIBNotificationPrefix" {
    smiv2:oid "1.3.6.1.4.1.9.9.43.2";
  }

  smiv2:alias "ciscoConfigManMIBNotifications" {
    smiv2:oid "1.3.6.1.4.1.9.9.43.2.0";
  }

  smiv2:alias "ciscoConfigManMIBConformance" {
    smiv2:oid "1.3.6.1.4.1.9.9.43.3";
  }

  smiv2:alias "ciscoConfigManMIBCompliances" {
    smiv2:oid "1.3.6.1.4.1.9.9.43.3.1";
  }

  smiv2:alias "ciscoConfigManMIBGroups" {
    smiv2:oid "1.3.6.1.4.1.9.9.43.3.2";
  }

}
