/*
 * Generated by confdc --mib2yang-std
 * Source: mgmt/dmi/model/common/mib-source/RSVP-MIB.mib
 */
/*
 * This YANG module has been generated by smidump 0.5.0:
 *
 *      smidump -f yang RSVP-MIB
 *
 * Do not edit. Edit the source file instead!
 */

module RSVP-MIB {

  namespace "urn:ietf:params:xml:ns:yang:smiv2:RSVP-MIB";
  prefix RSVP-MIB;

  import IF-MIB {
    prefix "if-mib";
  }

  import INTEGRATED-SERVICES-MIB {
    prefix "integrated-services";
  }

  import SNMPv2-TC {
    prefix "snmpv2-tc";
  }

  import ietf-yang-smiv2 {
    prefix "smiv2";
  }

  import ietf-yang-types {
    prefix "yang";
  }

  organization
   "IETF RSVP Working Group";

  contact
   "	   Fred	Baker
    Postal: Cisco Systems
    	   519 Lado Drive
    	   Santa Barbara, California 93111
    Tel:	   +1 805 681 0115
    E-Mail: fred@cisco.com
    
    	   John	Krawczyk
    Postal: ArrowPoint Communications
    	   235 Littleton Road
    	   Westford, Massachusetts 01886
    Tel:	   +1 508 692 5875
    E-Mail: jjk@tiac.net
    
    	   Arun	Sastry
    Postal: Cisco Systems
    	   3 The Square
    	   Stockley Park, Uxbridge
    	   Middlesex, UB11 1BN
    	   UK
    Tel:	   +44 181 756 8693
    E-Mail: arun@cisco.com";

  description
   "The MIB module to describe the RSVP Protocol";

  revision 1998-08-25 {
    description
     "[Revision added by libsmi due to a LAST-UPDATED clause.]";
  }

  typedef RsvpEncapsulation {
    type enumeration {
      enum "ip" {
        value "1";
      }
      enum "udp" {
        value "2";
      }
      enum "both" {
        value "3";
      }
    }
    description
     "This indicates the encapsulation that an  RSVP
      Neighbor is perceived to be using.";
  }

  typedef RefreshInterval {
    type int32 {
      range "0..2147483647";
    }
    description
     "The	number of milliseconds that  are  expected
      to	elapse	 between   refreshes  of  path	or
      reservation	 state.	   Unrefreshed	 Path	or
      reservation	state  is  removed  after  a small
      multiple of this period.";
    smiv2:display-hint "d";
  }


  container RSVP-MIB {
    config false;

    container rsvpGenObjects {
      smiv2:oid "1.3.6.1.2.1.51.2";

      leaf rsvpBadPackets {
        type yang:gauge32;
        description
         "This object	keeps a	count of the number of bad
          RSVP	packets	received.";
        smiv2:max-access "read-only";
        smiv2:oid "1.3.6.1.2.1.51.2.1";
      }

      leaf rsvpSenderNewIndex {
        type snmpv2-tc:TestAndIncr;
        description
         "This  object  is  used  to	assign	values	to
          rsvpSenderNumber   as   described  in  'Textual
          Conventions for SNMPv2'.  The  network  manager
          reads  the  object,	and  then writes the value
          back	in the SET that	creates	a new instance	of
          rsvpSenderEntry.   If  the  SET  fails with the
          code	'inconsistentValue', then the process must
          be  repeated;  If  the  SET	succeeds, then the
          object is incremented, and the new instance	is
          created according to	the manager's directions.";
        smiv2:max-access "read-write";
        smiv2:oid "1.3.6.1.2.1.51.2.2";
      }

      leaf rsvpResvNewIndex {
        type snmpv2-tc:TestAndIncr;
        description
         "This  object  is  used  to	assign	values	to
          rsvpResvNumber   as	 described   in	  'Textual
          Conventions for SNMPv2'.  The  network  manager
          reads  the  object,	and  then writes the value
          back	in the SET that	creates	a new instance	of
          rsvpResvEntry.   If the SET fails with the code
          'inconsistentValue',	then the process  must	be
          repeated;  If the SET succeeds, then	the object
          is incremented, and the new instance	is created
          according to	the manager's directions.";
        smiv2:max-access "read-write";
        smiv2:oid "1.3.6.1.2.1.51.2.3";
      }

      leaf rsvpResvFwdNewIndex {
        type snmpv2-tc:TestAndIncr;
        description
         "This  object  is  used  to	assign	values	to
          rsvpResvFwdNumber   as  described  in  'Textual
          Conventions for SNMPv2'.  The  network  manager
          reads  the  object,	and  then writes the value
          back	in the SET that	creates	a new instance	of
          rsvpResvFwdEntry.   If  the	SET fails with the
          code	'inconsistentValue', then the process must
          be  repeated;  If  the  SET	succeeds, then the
          object is incremented, and the new instance	is
          created according to	the manager's directions.";
        smiv2:max-access "read-write";
        smiv2:oid "1.3.6.1.2.1.51.2.4";
      }

      leaf rsvpSessionNewIndex {
        type snmpv2-tc:TestAndIncr;
        description
         "This  object  is  used  to	assign	values	to
          rsvpSessionNumber   as  described  in  'Textual
          Conventions for SNMPv2'.  The  network  manager
          reads  the  object,	and  then writes the value
          back	in the SET that	creates	a new instance	of
          rsvpSessionEntry.   If  the	SET fails with the
          code	'inconsistentValue', then the process must
          be  repeated;  If  the  SET	succeeds, then the
          object is incremented, and the new instance	is
          created according to	the manager's directions.";
        smiv2:max-access "read-write";
        smiv2:oid "1.3.6.1.2.1.51.2.5";
      }
    }

    container rsvpSessionTable {
      description
       "A table  of	 all  sessions	seen  by  a  given
        system.";
      smiv2:oid "1.3.6.1.2.1.51.1.1";

      list rsvpSessionEntry {
        key "rsvpSessionNumber";
        description
         "A single session seen by a given system.";
        smiv2:oid "1.3.6.1.2.1.51.1.1.1";

        leaf rsvpSessionNumber {
          type integrated-services:SessionNumber;
          description
           "The	number of this session.	 This is for  SNMP
            Indexing  purposes  only and	has no relation	to
            any protocol	value.";
          smiv2:max-access "not-accessible";
          smiv2:oid "1.3.6.1.2.1.51.1.1.1.1";
        }

        leaf rsvpSessionType {
          type integrated-services:SessionType;
          description
           "The	type of	session	(IP4, IP6, IP6	with  flow
            information,	etc).";
          smiv2:max-access "read-only";
          smiv2:oid "1.3.6.1.2.1.51.1.1.1.2";
        }

        leaf rsvpSessionDestAddr {
          type binary {
            length "4..16";
          }
          description
           "The	destination address used by all	senders	in
            this	 session.   This object	may not	be changed
            when	the  value  of	the  RowStatus	object	is
            'active'.";
          smiv2:max-access "read-only";
          smiv2:oid "1.3.6.1.2.1.51.1.1.1.3";
        }

        leaf rsvpSessionDestAddrLength {
          type int32 {
            range "0..128";
          }
          description
           "The	CIDR prefix length of the session address,
            which   is	32  for	 IP4  host  and	 multicast
            addresses, and 128  for  IP6	 addresses.   This
            object may not be changed when the value of the
            RowStatus object is 'active'.";
          smiv2:max-access "read-only";
          smiv2:oid "1.3.6.1.2.1.51.1.1.1.4";
        }

        leaf rsvpSessionProtocol {
          type integrated-services:Protocol;
          description
           "The	IP Protocol used by  this  session.   This
            object may not be changed when the value of the
            RowStatus object is 'active'.";
          smiv2:max-access "read-only";
          smiv2:oid "1.3.6.1.2.1.51.1.1.1.5";
        }

        leaf rsvpSessionPort {
          type integrated-services:Port;
          description
           "The	 UDP  or  TCP  port  number  used   as	 a
            destination	 port  for  all	 senders  in  this
            session.  If	the IP protocol	in use,	 specified
            by  rsvpSenderProtocol, is 50 (ESP) or 51 (AH),
            this	 represents  a	virtual	 destination  port
            number.   A value of	zero indicates that the	IP
            protocol in use  does  not  have  ports.   This
            object may not be changed when the value of the
            RowStatus object is 'active'.";
          smiv2:max-access "read-only";
          smiv2:oid "1.3.6.1.2.1.51.1.1.1.6";
        }

        leaf rsvpSessionSenders {
          type yang:gauge32;
          description
           "The	number of distinct senders currently known
            to be part of this session.";
          smiv2:max-access "read-only";
          smiv2:oid "1.3.6.1.2.1.51.1.1.1.7";
        }

        leaf rsvpSessionReceivers {
          type yang:gauge32;
          description
           "The	number of reservations being requested	of
            this	system for this	session.";
          smiv2:max-access "read-only";
          smiv2:oid "1.3.6.1.2.1.51.1.1.1.8";
        }

        leaf rsvpSessionRequests {
          type yang:gauge32;
          description
           "The	number of reservation requests this system
            is sending upstream for this	session.";
          smiv2:max-access "read-only";
          smiv2:oid "1.3.6.1.2.1.51.1.1.1.9";
        }
      }
    }

    container rsvpSenderTable {
      description
       "Information	describing the	state  information
        displayed by	senders	in PATH	messages.";
      smiv2:oid "1.3.6.1.2.1.51.1.2";

      list rsvpSenderEntry {
        key "rsvpSessionNumber rsvpSenderNumber";
        description
         "Information	describing the	state  information
          displayed by	a single sender's PATH message.";
        smiv2:oid "1.3.6.1.2.1.51.1.2.1";

        leaf rsvpSessionNumber {
          type leafref {
            path "/RSVP-MIB:RSVP-MIB/RSVP-MIB:rsvpSessionTable/RSVP-MIB:rsvpSessionEntry/RSVP-MIB:rsvpSessionNumber";
          }
        }

        leaf rsvpSenderNumber {
          type integrated-services:SessionNumber;
          description
           "The	number of this sender.	This is	 for  SNMP
            Indexing  purposes  only and	has no relation	to
            any protocol	value.";
          smiv2:max-access "not-accessible";
          smiv2:oid "1.3.6.1.2.1.51.1.2.1.1";
        }

        leaf rsvpSenderType {
          type integrated-services:SessionType;
          description
           "The	type of	session	(IP4, IP6, IP6	with  flow
            information,	etc).";
          smiv2:max-access "read-write";
          smiv2:oid "1.3.6.1.2.1.51.1.2.1.2";
        }

        leaf rsvpSenderDestAddr {
          type binary {
            length "4..16";
          }
          description
           "The	destination address used by all	senders	in
            this	 session.   This object	may not	be changed
            when	the  value  of	the  RowStatus	object	is
            'active'.";
          smiv2:max-access "read-write";
          smiv2:oid "1.3.6.1.2.1.51.1.2.1.3";
        }

        leaf rsvpSenderAddr {
          type binary {
            length "4..16";
          }
          description
           "The	source address used by this sender in this
            session.   This  object may not be changed when
            the value of	the RowStatus object is	'active'.";
          smiv2:max-access "read-write";
          smiv2:oid "1.3.6.1.2.1.51.1.2.1.4";
        }

        leaf rsvpSenderDestAddrLength {
          type int32 {
            range "0..128";
          }
          description
           "The	length of the destination address in bits.
            This	 is  the CIDR Prefix Length, which for IP4
            hosts and multicast addresses is 32 bits.  This
            object may not be changed when the value of the
            RowStatus object is 'active'.";
          smiv2:max-access "read-write";
          smiv2:oid "1.3.6.1.2.1.51.1.2.1.5";
        }

        leaf rsvpSenderAddrLength {
          type int32 {
            range "0..128";
          }
          description
           "The	length of the sender's	address	 in  bits.
            This	 is  the CIDR Prefix Length, which for IP4
            hosts and multicast addresses is 32 bits.  This
            object may not be changed when the value of the
            RowStatus object is 'active'.";
          smiv2:max-access "read-write";
          smiv2:oid "1.3.6.1.2.1.51.1.2.1.6";
        }

        leaf rsvpSenderProtocol {
          type integrated-services:Protocol;
          description
           "The	IP Protocol used by  this  session.   This
            object may not be changed when the value of the
            RowStatus object is 'active'.";
          smiv2:max-access "read-write";
          smiv2:oid "1.3.6.1.2.1.51.1.2.1.7";
        }

        leaf rsvpSenderDestPort {
          type integrated-services:Port;
          description
           "The	 UDP  or  TCP  port  number  used   as	 a
            destination	 port  for  all	 senders  in  this
            session.  If	the IP protocol	in use,	 specified
            by  rsvpSenderProtocol, is 50 (ESP) or 51 (AH),
            this	 represents  a	virtual	 destination  port
            number.   A value of	zero indicates that the	IP
            protocol in use  does  not  have  ports.   This
            object may not be changed when the value of the
            RowStatus object is 'active'.";
          smiv2:max-access "read-write";
          smiv2:oid "1.3.6.1.2.1.51.1.2.1.8";
        }

        leaf rsvpSenderPort {
          type integrated-services:Port;
          description
           "The	UDP or TCP port	number used  as	 a  source
            port	 for  this sender in this session.  If the
            IP	 protocol    in	   use,	   specified	by
            rsvpSenderProtocol is 50 (ESP) or 51	(AH), this
            represents a	generalized port identifier (GPI).
            A  value of zero indicates that the IP protocol
            in use does not have	ports.	 This  object  may
            not	be changed when	the value of the RowStatus
            object is 'active'.";
          smiv2:max-access "read-write";
          smiv2:oid "1.3.6.1.2.1.51.1.2.1.9";
        }

        leaf rsvpSenderFlowId {
          type int32 {
            range "0..16777215";
          }
          description
           "The	flow ID	that  this  sender  is	using,	if
            this	 is  an	IPv6 session.";
          smiv2:max-access "read-only";
          smiv2:oid "1.3.6.1.2.1.51.1.2.1.10";
        }

        leaf rsvpSenderHopAddr {
          type binary {
            length "4..16";
          }
          description
           "The	address	used  by  the  previous	 RSVP  hop
            (which may be the original sender).";
          smiv2:max-access "read-write";
          smiv2:oid "1.3.6.1.2.1.51.1.2.1.11";
        }

        leaf rsvpSenderHopLih {
          type int32;
          description
           "The	 Logical  Interface  Handle  used  by  the
            previous  RSVP  hop	(which may be the original
            sender).";
          smiv2:max-access "read-write";
          smiv2:oid "1.3.6.1.2.1.51.1.2.1.12";
        }

        leaf rsvpSenderInterface {
          type if-mib:InterfaceIndex;
          description
           "The	ifIndex	value of the  interface	 on  which
            this	PATH message was most recently received.";
          smiv2:max-access "read-write";
          smiv2:oid "1.3.6.1.2.1.51.1.2.1.13";
        }

        leaf rsvpSenderTSpecRate {
          type integrated-services:BitRate;
          units "bits per second";
          description
           "The	Average	Bit  Rate  of  the  sender's  data
            stream.    Within  a	 transmission  burst,  the
            arrival   rate    may    be	  as	fast	as
            rsvpSenderTSpecPeakRate  (if	 supported  by the
            service model); however, averaged across two	or
            more	 burst	intervals,  the	 rate  should  not
            exceed rsvpSenderTSpecRate.
            
            Note	that this is a prediction, often based	on
            the	general	 capability  of	a type of codec	or
            particular encoding;	the measured average  rate
            may be significantly	lower.";
          smiv2:max-access "read-write";
          smiv2:oid "1.3.6.1.2.1.51.1.2.1.14";
        }

        leaf rsvpSenderTSpecPeakRate {
          type integrated-services:BitRate;
          units "bits per second";
          description
           "The	Peak Bit Rate of the sender's data stream.
            Traffic  arrival is not expected to exceed this
            rate	at any time, apart  from  the  effects	of
            jitter in the network.  If not specified in the
            TSpec, this returns zero or noSuchValue.";
          smiv2:max-access "read-write";
          smiv2:oid "1.3.6.1.2.1.51.1.2.1.15";
        }

        leaf rsvpSenderTSpecBurst {
          type integrated-services:BurstSize;
          units "bytes";
          description
           "The	size of	the largest  burst  expected  from
            the sender at a time.";
          smiv2:max-access "read-write";
          smiv2:oid "1.3.6.1.2.1.51.1.2.1.16";
        }

        leaf rsvpSenderTSpecMinTU {
          type integrated-services:MessageSize;
          description
           "The	minimum	message	size for  this	flow.  The
            policing  algorithm will treat smaller messages
            as though they are this size.";
          smiv2:max-access "read-write";
          smiv2:oid "1.3.6.1.2.1.51.1.2.1.17";
        }

        leaf rsvpSenderTSpecMaxTU {
          type integrated-services:MessageSize;
          description
           "The	maximum	message	size for  this	flow.  The
            admission  algorithm	 will  reject TSpecs whose
            Maximum Transmission	Unit, plus  the	 interface
            headers, exceed the interface MTU.";
          smiv2:max-access "read-write";
          smiv2:oid "1.3.6.1.2.1.51.1.2.1.18";
        }

        leaf rsvpSenderInterval {
          type RSVP-MIB:RefreshInterval;
          description
           "The	 interval  between  refresh  messages	as
            advertised by the Previous Hop.";
          smiv2:max-access "read-write";
          smiv2:oid "1.3.6.1.2.1.51.1.2.1.19";
        }

        leaf rsvpSenderRSVPHop {
          type boolean;
          description
           "If TRUE, the node believes that  the  previous
            IP  hop  is	an  RSVP  hop.	If FALSE, the node
            believes that the previous IP hop may not be	an
            RSVP	hop.";
          smiv2:max-access "read-write";
          smiv2:oid "1.3.6.1.2.1.51.1.2.1.20";
        }

        leaf rsvpSenderLastChange {
          type yang:timestamp;
          description
           "The	time of	 the  last  change  in	this  PATH
            message;  This  is either the first time it was
            received or the time	of the most recent  change
            in parameters.";
          smiv2:max-access "read-only";
          smiv2:oid "1.3.6.1.2.1.51.1.2.1.21";
        }

        leaf rsvpSenderPolicy {
          type binary {
            length "4..65536";
          }
          description
           "The	contents of the	policy	object,	 displayed
            as an uninterpreted string of octets, including
            the object header.  In the absence of  such	an
            object, this	should be of zero length.";
          smiv2:max-access "read-write";
          smiv2:oid "1.3.6.1.2.1.51.1.2.1.22";
        }

        leaf rsvpSenderAdspecBreak {
          type boolean;
          description
           "The	global break bit general  characterization
            parameter  from  the	ADSPEC.	 If TRUE, at least
            one non-IS hop was detected in  the	path.	If
            FALSE, no non-IS hops were detected.";
          smiv2:max-access "read-write";
          smiv2:oid "1.3.6.1.2.1.51.1.2.1.23";
        }

        leaf rsvpSenderAdspecHopCount {
          type int32 {
            range "0..65535";
          }
          description
           "The	  hop	count	general	  characterization
            parameter from the ADSPEC.  A return	of zero	or
            noSuchValue	indicates  one	of  the	 following
            conditions:
            
               the invalid bit was set
               the parameter was	not present";
          smiv2:max-access "read-write";
          smiv2:oid "1.3.6.1.2.1.51.1.2.1.24";
        }

        leaf rsvpSenderAdspecPathBw {
          type integrated-services:BitRate;
          units "bits per second";
          description
           "The	  path	  bandwidth    estimate	   general
            characterization  parameter from the	ADSPEC.	 A
            return of zero or noSuchValue indicates one	of
            the following conditions:
            
               the invalid bit was set
               the parameter was	not present";
          smiv2:max-access "read-write";
          smiv2:oid "1.3.6.1.2.1.51.1.2.1.25";
        }

        leaf rsvpSenderAdspecMinLatency {
          type int32;
          units "microseconds";
          description
           "The	   minimum    path     latency	   general
            characterization  parameter from the	ADSPEC.	 A
            return of zero or noSuchValue indicates one	of
            the following conditions:
            
               the invalid bit was set
               the parameter was	not present";
          smiv2:max-access "read-write";
          smiv2:oid "1.3.6.1.2.1.51.1.2.1.26";
        }

        leaf rsvpSenderAdspecMtu {
          type int32 {
            range "0..65535";
          }
          units "bytes";
          description
           "The	composed Maximum Transmission Unit general
            characterization  parameter from the	ADSPEC.	 A
            return of zero or noSuchValue indicates one	of
            the following conditions:
            
               the invalid bit was set
               the parameter was	not present";
          smiv2:max-access "read-write";
          smiv2:oid "1.3.6.1.2.1.51.1.2.1.27";
        }

        leaf rsvpSenderAdspecGuaranteedSvc {
          type boolean;
          description
           "If TRUE,  the  ADSPEC  contains  a	Guaranteed
            Service  fragment.	If  FALSE, the ADSPEC does
            not contain a Guaranteed Service fragment.";
          smiv2:max-access "read-write";
          smiv2:oid "1.3.6.1.2.1.51.1.2.1.28";
        }

        leaf rsvpSenderAdspecGuaranteedBreak {
          type boolean;
          description
           "If TRUE, the Guaranteed Service  fragment  has
            its	'break'	 bit  set,  indicating that one	or
            more	nodes along the	path do	 not  support  the
            guaranteed	  service.     If    FALSE,    and
            rsvpSenderAdspecGuaranteedSvc  is   TRUE,   the
            'break' bit is not set.
            
            If rsvpSenderAdspecGuaranteedSvc is FALSE, this
            returns FALSE or noSuchValue.";
          smiv2:max-access "read-write";
          smiv2:oid "1.3.6.1.2.1.51.1.2.1.29";
        }

        leaf rsvpSenderAdspecGuaranteedCtot {
          type int32;
          units "bytes";
          description
           "If rsvpSenderAdspecGuaranteedSvc is	TRUE, this
            is	the  end-to-end	 composed  value  for  the
            guaranteed service 'C' parameter.  A	return	of
            zero	  or  noSuchValue  indicates  one  of  the
            following conditions:
            
               the invalid bit was set
               the parameter was	not present
            
            If rsvpSenderAdspecGuaranteedSvc is FALSE, this
            returns zero	or noSuchValue.";
          smiv2:max-access "read-write";
          smiv2:oid "1.3.6.1.2.1.51.1.2.1.30";
        }

        leaf rsvpSenderAdspecGuaranteedDtot {
          type int32;
          units "microseconds";
          description
           "If rsvpSenderAdspecGuaranteedSvc is	TRUE, this
            is	the  end-to-end	 composed  value  for  the
            guaranteed service 'D' parameter.  A	return	of
            zero	  or  noSuchValue  indicates  one  of  the
            following conditions:
            
               the invalid bit was set
               the parameter was	not present
            
            If rsvpSenderAdspecGuaranteedSvc is FALSE, this
            returns zero	or noSuchValue.";
          smiv2:max-access "read-write";
          smiv2:oid "1.3.6.1.2.1.51.1.2.1.31";
        }

        leaf rsvpSenderAdspecGuaranteedCsum {
          type int32;
          units "bytes";
          description
           "If rsvpSenderAdspecGuaranteedSvc is	TRUE, this
            is	the  composed  value  for  the	guaranteed
            service 'C' parameter since the last	 reshaping
            point.    A	 return	 of  zero  or  noSuchValue
            indicates one of the	following conditions:
            
               the invalid bit was set
               the parameter was	not present
            
            If rsvpSenderAdspecGuaranteedSvc is FALSE, this
            returns zero	or noSuchValue.";
          smiv2:max-access "read-write";
          smiv2:oid "1.3.6.1.2.1.51.1.2.1.32";
        }

        leaf rsvpSenderAdspecGuaranteedDsum {
          type int32;
          units "microseconds";
          description
           "If rsvpSenderAdspecGuaranteedSvc is	TRUE, this
            is	the  composed  value  for  the	guaranteed
            service 'D' parameter since the last	 reshaping
            point.    A	 return	 of  zero  or  noSuchValue
            indicates one of the	following conditions:
            
               the invalid bit was set
               the parameter was	not present
            
            If rsvpSenderAdspecGuaranteedSvc is FALSE, this
            returns zero	or noSuchValue.";
          smiv2:max-access "read-write";
          smiv2:oid "1.3.6.1.2.1.51.1.2.1.33";
        }

        leaf rsvpSenderAdspecGuaranteedHopCount {
          type int32 {
            range "0..65535";
          }
          description
           "If rsvpSenderAdspecGuaranteedSvc is	TRUE, this
            is  the  service-specific  override	of the hop
            count general characterization  parameter  from
            the	ADSPEC.	  A  return of zero or noSuchValue
            indicates one of the	following conditions:
            
               the invalid bit was set
               the parameter was	not present
            
            If rsvpSenderAdspecGuaranteedSvc is FALSE, this
            returns zero	or noSuchValue.";
          smiv2:max-access "read-write";
          smiv2:oid "1.3.6.1.2.1.51.1.2.1.34";
        }

        leaf rsvpSenderAdspecGuaranteedPathBw {
          type integrated-services:BitRate;
          units "bits per second";
          description
           "If rsvpSenderAdspecGuaranteedSvc is	TRUE, this
            is  the  service-specific  override of the path
            bandwidth  estimate	general	  characterization
            parameter from the ADSPEC.  A return	of zero	or
            noSuchValue	indicates  one	of  the	 following
            conditions:
            
               the invalid bit was set
               the parameter was	not present
            
            If rsvpSenderAdspecGuaranteedSvc is FALSE, this
            returns zero	or noSuchValue.";
          smiv2:max-access "read-write";
          smiv2:oid "1.3.6.1.2.1.51.1.2.1.35";
        }

        leaf rsvpSenderAdspecGuaranteedMinLatency {
          type int32;
          units "microseconds";
          description
           "If rsvpSenderAdspecGuaranteedSvc is	TRUE, this
            is the service-specific override of the minimum
            path	latency	general	characterization parameter
            from	  the	ADSPEC.	   A  return  of  zero	or
            noSuchValue	indicates  one	of  the	 following
            conditions:
            
               the invalid bit was set
               the parameter was	not present
            
            If rsvpSenderAdspecGuaranteedSvc is FALSE, this
            returns zero	or noSuchValue.";
          smiv2:max-access "read-write";
          smiv2:oid "1.3.6.1.2.1.51.1.2.1.36";
        }

        leaf rsvpSenderAdspecGuaranteedMtu {
          type int32 {
            range "0..65535";
          }
          units "bytes";
          description
           "If rsvpSenderAdspecGuaranteedSvc is	TRUE, this
            is	the   service-specific	 override  of  the
            composed  Maximum  Transmission  Unit   general
            characterization  parameter from the	ADSPEC.	 A
            return of zero or noSuchValue indicates one	of
            the following conditions:
            
               the invalid bit was set
               the parameter was	not present
            
            If rsvpSenderAdspecGuaranteedSvc is FALSE, this
            returns zero	or noSuchValue.";
          smiv2:max-access "read-write";
          smiv2:oid "1.3.6.1.2.1.51.1.2.1.37";
        }

        leaf rsvpSenderAdspecCtrlLoadSvc {
          type boolean;
          description
           "If TRUE, the ADSPEC	contains a Controlled Load
            Service  fragment.	If  FALSE, the ADSPEC does
            not	 contain   a   Controlled   Load   Service
            fragment.";
          smiv2:max-access "read-write";
          smiv2:oid "1.3.6.1.2.1.51.1.2.1.38";
        }

        leaf rsvpSenderAdspecCtrlLoadBreak {
          type boolean;
          description
           "If TRUE, the Controlled Load Service  fragment
            has its 'break' bit set, indicating that one	or
            more	nodes along the	path do	 not  support  the
            controlled	load   service.	   If  FALSE,  and
            rsvpSenderAdspecCtrlLoadSvc	 is   TRUE,    the
            'break' bit is not set.
            
            If rsvpSenderAdspecCtrlLoadSvc is  FALSE,  this
            returns FALSE or noSuchValue.";
          smiv2:max-access "read-write";
          smiv2:oid "1.3.6.1.2.1.51.1.2.1.39";
        }

        leaf rsvpSenderAdspecCtrlLoadHopCount {
          type int32 {
            range "0..65535";
          }
          description
           "If rsvpSenderAdspecCtrlLoadSvc is  TRUE,  this
            is  the  service-specific  override	of the hop
            count general characterization  parameter  from
            the	ADSPEC.	  A  return of zero or noSuchValue
            indicates one of the	following conditions:
            
               the invalid bit was set
               the parameter was	not present
            
            If rsvpSenderAdspecCtrlLoadSvc is  FALSE,  this
            returns zero	or noSuchValue.";
          smiv2:max-access "read-write";
          smiv2:oid "1.3.6.1.2.1.51.1.2.1.40";
        }

        leaf rsvpSenderAdspecCtrlLoadPathBw {
          type integrated-services:BitRate;
          units "bits per second";
          description
           "If rsvpSenderAdspecCtrlLoadSvc is  TRUE,  this
            is  the  service-specific  override of the path
            bandwidth  estimate	general	  characterization
            parameter from the ADSPEC.  A return	of zero	or
            noSuchValue	indicates  one	of  the	 following
            conditions:
            
               the invalid bit was set
               the parameter was	not present
            
            If rsvpSenderAdspecCtrlLoadSvc is  FALSE,  this
            returns zero	or noSuchValue.";
          smiv2:max-access "read-write";
          smiv2:oid "1.3.6.1.2.1.51.1.2.1.41";
        }

        leaf rsvpSenderAdspecCtrlLoadMinLatency {
          type int32;
          units "microseconds";
          description
           "If rsvpSenderAdspecCtrlLoadSvc is  TRUE,  this
            is the service-specific override of the minimum
            path	latency	general	characterization parameter
            from	  the	ADSPEC.	   A  return  of  zero	or
            noSuchValue	indicates  one	of  the	 following
            conditions:
            
               the invalid bit was set
               the parameter was	not present
            
            If rsvpSenderAdspecCtrlLoadSvc is  FALSE,  this
            returns zero	or noSuchValue.";
          smiv2:max-access "read-write";
          smiv2:oid "1.3.6.1.2.1.51.1.2.1.42";
        }

        leaf rsvpSenderAdspecCtrlLoadMtu {
          type int32 {
            range "0..65535";
          }
          units "bytes";
          description
           "If rsvpSenderAdspecCtrlLoadSvc is  TRUE,  this
            is	the   service-specific	 override  of  the
            composed  Maximum  Transmission  Unit   general
            characterization  parameter from the	ADSPEC.	 A
            return of zero or noSuchValue indicates one	of
            the following conditions:
            
               the invalid bit was set
               the parameter was	not present
            
            If rsvpSenderAdspecCtrlLoadSvc is  FALSE,  this
            returns zero	or noSuchValue.";
          smiv2:max-access "read-write";
          smiv2:oid "1.3.6.1.2.1.51.1.2.1.43";
        }

        leaf rsvpSenderStatus {
          type snmpv2-tc:RowStatus;
          description
           "'active' for all active PATH  messages.   This
            object  may	be  used  to  install  static PATH
            information or delete PATH information.";
          smiv2:max-access "read-write";
          smiv2:oid "1.3.6.1.2.1.51.1.2.1.44";
        }

        leaf rsvpSenderTTL {
          type int32 {
            range "0..255";
          }
          description
           "The	TTL value in the RSVP header that was last
            received.";
          smiv2:max-access "read-only";
          smiv2:oid "1.3.6.1.2.1.51.1.2.1.45";
        }
      }
    }

    container rsvpSenderOutInterfaceTable {
      description
       "List of outgoing interfaces	that PATH messages
        use.	 The  ifIndex  is the ifIndex value of the
        egress interface.";
      smiv2:oid "1.3.6.1.2.1.51.1.3";

      list rsvpSenderOutInterfaceEntry {
        key "rsvpSessionNumber rsvpSenderNumber ifIndex";
        description
         "List of outgoing interfaces	that a	particular
          PATH	message	has.";
        smiv2:oid "1.3.6.1.2.1.51.1.3.1";

        leaf rsvpSessionNumber {
          type leafref {
            path "/RSVP-MIB:RSVP-MIB/RSVP-MIB:rsvpSessionTable/RSVP-MIB:rsvpSessionEntry/RSVP-MIB:rsvpSessionNumber";
          }
        }

        leaf rsvpSenderNumber {
          type leafref {
            path "/RSVP-MIB:RSVP-MIB/RSVP-MIB:rsvpSenderTable/RSVP-MIB:rsvpSenderEntry/RSVP-MIB:rsvpSenderNumber";
          }
        }

        leaf ifIndex {
          type leafref {
            path "/if-mib:IF-MIB/if-mib:ifTable/if-mib:ifEntry/if-mib:ifIndex";
          }
        }

        leaf rsvpSenderOutInterfaceStatus {
          type snmpv2-tc:RowStatus;
          description
           "'active' for all active PATH messages.";
          smiv2:max-access "read-only";
          smiv2:oid "1.3.6.1.2.1.51.1.3.1.1";
        }
      }
    }

    container rsvpResvTable {
      description
       "Information	describing the	state  information
        displayed by	receivers in RESV messages.";
      smiv2:oid "1.3.6.1.2.1.51.1.4";

      list rsvpResvEntry {
        key "rsvpSessionNumber rsvpResvNumber";
        description
         "Information	describing the	state  information
          displayed  by  a single receiver's RESV message
          concerning a	single sender.";
        smiv2:oid "1.3.6.1.2.1.51.1.4.1";

        leaf rsvpSessionNumber {
          type leafref {
            path "/RSVP-MIB:RSVP-MIB/RSVP-MIB:rsvpSessionTable/RSVP-MIB:rsvpSessionEntry/RSVP-MIB:rsvpSessionNumber";
          }
        }

        leaf rsvpResvNumber {
          type integrated-services:SessionNumber;
          description
           "The	number of this reservation request.   This
            is  for  SNMP Indexing purposes only	and has	no
            relation to any protocol value.";
          smiv2:max-access "not-accessible";
          smiv2:oid "1.3.6.1.2.1.51.1.4.1.1";
        }

        leaf rsvpResvType {
          type integrated-services:SessionType;
          description
           "The	type of	session	(IP4, IP6, IP6	with  flow
            information,	etc).";
          smiv2:max-access "read-write";
          smiv2:oid "1.3.6.1.2.1.51.1.4.1.2";
        }

        leaf rsvpResvDestAddr {
          type binary {
            length "4..16";
          }
          description
           "The	destination address used by all	senders	in
            this	 session.   This object	may not	be changed
            when	the  value  of	the  RowStatus	object	is
            'active'.";
          smiv2:max-access "read-write";
          smiv2:oid "1.3.6.1.2.1.51.1.4.1.3";
        }

        leaf rsvpResvSenderAddr {
          type binary {
            length "4..16";
          }
          description
           "The	source address of the sender  selected	by
            this	 reservation.	The  value  of	all zeroes
            indicates 'all senders'.  This object  may  not
            be  changed	when  the  value  of the RowStatus
            object is 'active'.";
          smiv2:max-access "read-write";
          smiv2:oid "1.3.6.1.2.1.51.1.4.1.4";
        }

        leaf rsvpResvDestAddrLength {
          type int32 {
            range "0..128";
          }
          description
           "The	length of the destination address in bits.
            This	 is  the CIDR Prefix Length, which for IP4
            hosts and multicast addresses is 32 bits.  This
            object may not be changed when the value of the
            RowStatus object is 'active'.";
          smiv2:max-access "read-write";
          smiv2:oid "1.3.6.1.2.1.51.1.4.1.5";
        }

        leaf rsvpResvSenderAddrLength {
          type int32 {
            range "0..128";
          }
          description
           "The	length of the sender's	address	 in  bits.
            This	 is  the CIDR Prefix Length, which for IP4
            hosts and multicast addresses is 32 bits.  This
            object may not be changed when the value of the
            RowStatus object is 'active'.";
          smiv2:max-access "read-write";
          smiv2:oid "1.3.6.1.2.1.51.1.4.1.6";
        }

        leaf rsvpResvProtocol {
          type integrated-services:Protocol;
          description
           "The	IP Protocol used by  this  session.   This
            object may not be changed when the value of the
            RowStatus object is 'active'.";
          smiv2:max-access "read-write";
          smiv2:oid "1.3.6.1.2.1.51.1.4.1.7";
        }

        leaf rsvpResvDestPort {
          type integrated-services:Port;
          description
           "The	 UDP  or  TCP  port  number  used   as	 a
            destination	 port  for  all	 senders  in  this
            session.  If	the IP protocol	in use,	 specified
            by  rsvpResvProtocol,  is  50 (ESP) or 51 (AH),
            this	 represents  a	virtual	 destination  port
            number.   A value of	zero indicates that the	IP
            protocol in use  does  not  have  ports.   This
            object may not be changed when the value of the
            RowStatus object is 'active'.";
          smiv2:max-access "read-write";
          smiv2:oid "1.3.6.1.2.1.51.1.4.1.8";
        }

        leaf rsvpResvPort {
          type integrated-services:Port;
          description
           "The	UDP or TCP port	number used  as	 a  source
            port	 for  this sender in this session.  If the
            IP	 protocol    in	   use,	   specified	by
            rsvpResvProtocol  is	 50 (ESP) or 51	(AH), this
            represents a	generalized port identifier (GPI).
            A  value of zero indicates that the IP protocol
            in use does not have	ports.	 This  object  may
            not	be changed when	the value of the RowStatus
            object is 'active'.";
          smiv2:max-access "read-write";
          smiv2:oid "1.3.6.1.2.1.51.1.4.1.9";
        }

        leaf rsvpResvHopAddr {
          type binary {
            length "4..16";
          }
          description
           "The	address	used by	the next RSVP  hop  (which
            may be the ultimate receiver).";
          smiv2:max-access "read-write";
          smiv2:oid "1.3.6.1.2.1.51.1.4.1.10";
        }

        leaf rsvpResvHopLih {
          type int32;
          description
           "The	Logical	Interface Handle received from the
            previous  RSVP  hop	(which may be the ultimate
            receiver).";
          smiv2:max-access "read-write";
          smiv2:oid "1.3.6.1.2.1.51.1.4.1.11";
        }

        leaf rsvpResvInterface {
          type if-mib:InterfaceIndex;
          description
           "The	ifIndex	value of the  interface	 on  which
            this	RESV message was most recently received.";
          smiv2:max-access "read-write";
          smiv2:oid "1.3.6.1.2.1.51.1.4.1.12";
        }

        leaf rsvpResvService {
          type integrated-services:QosService;
          description
           "The	QoS Service  classification  requested	by
            the receiver.";
          smiv2:max-access "read-write";
          smiv2:oid "1.3.6.1.2.1.51.1.4.1.13";
        }

        leaf rsvpResvTSpecRate {
          type integrated-services:BitRate;
          units "bits per second";
          description
           "The	Average	Bit  Rate  of  the  sender's  data
            stream.    Within  a	 transmission  burst,  the
            arrival   rate    may    be	  as	fast	as
            rsvpResvTSpecPeakRate   (if	supported  by  the
            service model); however, averaged across two	or
            more	 burst	intervals,  the	 rate  should  not
            exceed rsvpResvTSpecRate.
            
            Note	that this is a prediction, often based	on
            the	general	 capability  of	a type of codec	or
            particular encoding;	the measured average  rate
            may be significantly	lower.";
          smiv2:max-access "read-write";
          smiv2:oid "1.3.6.1.2.1.51.1.4.1.14";
        }

        leaf rsvpResvTSpecPeakRate {
          type integrated-services:BitRate;
          units "bits per second";
          description
           "The	Peak Bit Rate of the sender's data stream.
            Traffic  arrival is not expected to exceed this
            rate	at any time, apart  from  the  effects	of
            jitter in the network.  If not specified in the
            TSpec, this returns zero or noSuchValue.";
          smiv2:max-access "read-write";
          smiv2:oid "1.3.6.1.2.1.51.1.4.1.15";
        }

        leaf rsvpResvTSpecBurst {
          type integrated-services:BurstSize;
          units "bytes";
          description
           "The	size of	the largest  burst  expected  from
            the sender at a time.
            
            If this is less than	 the  sender's	advertised
            burst  size,	the receiver is	asking the network
            to provide flow pacing  beyond  what	 would	be
            provided   under   normal  circumstances.  Such
            pacing is at	the network's option.";
          smiv2:max-access "read-write";
          smiv2:oid "1.3.6.1.2.1.51.1.4.1.16";
        }

        leaf rsvpResvTSpecMinTU {
          type integrated-services:MessageSize;
          description
           "The	minimum	message	size for  this	flow.  The
            policing  algorithm will treat smaller messages
            as though they are this size.";
          smiv2:max-access "read-write";
          smiv2:oid "1.3.6.1.2.1.51.1.4.1.17";
        }

        leaf rsvpResvTSpecMaxTU {
          type integrated-services:MessageSize;
          description
           "The	maximum	message	size for  this	flow.  The
            admission  algorithm	 will  reject TSpecs whose
            Maximum Transmission	Unit, plus  the	 interface
            headers, exceed the interface MTU.";
          smiv2:max-access "read-write";
          smiv2:oid "1.3.6.1.2.1.51.1.4.1.18";
        }

        leaf rsvpResvRSpecRate {
          type integrated-services:BitRate;
          units "bits per second";
          description
           "If the requested  service  is  Guaranteed,	as
            specified   by  rsvpResvService,  this  is  the
            clearing  rate   that   is	being	requested.
            Otherwise,  it is zero, or the agent	may return
            noSuchValue.";
          smiv2:max-access "read-write";
          smiv2:oid "1.3.6.1.2.1.51.1.4.1.19";
        }

        leaf rsvpResvRSpecSlack {
          type int32;
          units "microseconds";
          description
           "If the requested  service  is  Guaranteed,	as
            specified by	rsvpResvService, this is the delay
            slack.  Otherwise, it is zero, or the agent may
            return noSuchValue.";
          smiv2:max-access "read-write";
          smiv2:oid "1.3.6.1.2.1.51.1.4.1.20";
        }

        leaf rsvpResvInterval {
          type RSVP-MIB:RefreshInterval;
          description
           "The	 interval  between  refresh  messages	as
            advertised by the Next Hop.";
          smiv2:max-access "read-write";
          smiv2:oid "1.3.6.1.2.1.51.1.4.1.21";
        }

        leaf rsvpResvScope {
          type binary {
            length "0..65536";
          }
          description
           "The	contents of the	scope object, displayed	as
            an  uninterpreted  string  of octets, including
            the object header.  In the absence of  such	an
            object, this	should be of zero length.
            
            If the length  is  non-zero,	 this  contains	 a
            series of IP4 or IP6	addresses.";
          smiv2:max-access "read-write";
          smiv2:oid "1.3.6.1.2.1.51.1.4.1.22";
        }

        leaf rsvpResvShared {
          type boolean;
          description
           "If TRUE, a reservation shared among	senders	is
            requested.  If FALSE, a reservation specific	to
            this	sender is requested.";
          smiv2:max-access "read-write";
          smiv2:oid "1.3.6.1.2.1.51.1.4.1.23";
        }

        leaf rsvpResvExplicit {
          type boolean;
          description
           "If TRUE, individual	senders	are  listed  using
            Filter  Specifications.   If	FALSE, all senders
            are implicitly selected.  The Scope Object will
            contain  a list of senders that need	to receive
            this	reservation request  for  the  purpose	of
            routing the RESV message.";
          smiv2:max-access "read-write";
          smiv2:oid "1.3.6.1.2.1.51.1.4.1.24";
        }

        leaf rsvpResvRSVPHop {
          type boolean;
          description
           "If TRUE, the node believes that  the  previous
            IP  hop  is	an  RSVP  hop.	If FALSE, the node
            believes that the previous IP hop may not be	an
            RSVP	hop.";
          smiv2:max-access "read-write";
          smiv2:oid "1.3.6.1.2.1.51.1.4.1.25";
        }

        leaf rsvpResvLastChange {
          type yang:timestamp;
          description
           "The	 time  of  the	 last	change	 in   this
            reservation	request;  This is either the first
            time	it was received	or the time  of	 the  most
            recent change in parameters.";
          smiv2:max-access "read-only";
          smiv2:oid "1.3.6.1.2.1.51.1.4.1.26";
        }

        leaf rsvpResvPolicy {
          type binary {
            length "0..65536";
          }
          description
           "The	contents of the	policy	object,	 displayed
            as an uninterpreted string of octets, including
            the object header.  In the absence of  such	an
            object, this	should be of zero length.";
          smiv2:max-access "read-write";
          smiv2:oid "1.3.6.1.2.1.51.1.4.1.27";
        }

        leaf rsvpResvStatus {
          type snmpv2-tc:RowStatus;
          description
           "'active' for all active RESV  messages.   This
            object  may	be  used  to  install  static RESV
            information or delete RESV information.";
          smiv2:max-access "read-write";
          smiv2:oid "1.3.6.1.2.1.51.1.4.1.28";
        }

        leaf rsvpResvTTL {
          type int32 {
            range "0..255";
          }
          description
           "The	TTL value in the RSVP header that was last
            received.";
          smiv2:max-access "read-only";
          smiv2:oid "1.3.6.1.2.1.51.1.4.1.29";
        }

        leaf rsvpResvFlowId {
          type int32 {
            range "0..16777215";
          }
          description
           "The	flow ID	that this receiver  is	using,	if
            this	 is  an	IPv6 session.";
          smiv2:max-access "read-only";
          smiv2:oid "1.3.6.1.2.1.51.1.4.1.30";
        }
      }
    }

    container rsvpResvFwdTable {
      description
       "Information	describing the	state  information
        displayed upstream in RESV messages.";
      smiv2:oid "1.3.6.1.2.1.51.1.5";

      list rsvpResvFwdEntry {
        key "rsvpSessionNumber rsvpResvFwdNumber";
        description
         "Information	describing the	state  information
          displayed   upstream	  in   an   RESV   message
          concerning a	single sender.";
        smiv2:oid "1.3.6.1.2.1.51.1.5.1";

        leaf rsvpSessionNumber {
          type leafref {
            path "/RSVP-MIB:RSVP-MIB/RSVP-MIB:rsvpSessionTable/RSVP-MIB:rsvpSessionEntry/RSVP-MIB:rsvpSessionNumber";
          }
        }

        leaf rsvpResvFwdNumber {
          type integrated-services:SessionNumber;
          description
           "The	number of this reservation request.   This
            is  for  SNMP Indexing purposes only	and has	no
            relation to any protocol value.";
          smiv2:max-access "not-accessible";
          smiv2:oid "1.3.6.1.2.1.51.1.5.1.1";
        }

        leaf rsvpResvFwdType {
          type integrated-services:SessionType;
          description
           "The	type of	session	(IP4, IP6, IP6	with  flow
            information,	etc).";
          smiv2:max-access "read-only";
          smiv2:oid "1.3.6.1.2.1.51.1.5.1.2";
        }

        leaf rsvpResvFwdDestAddr {
          type binary {
            length "4..16";
          }
          description
           "The	destination address used by all	senders	in
            this	 session.   This object	may not	be changed
            when	the  value  of	the  RowStatus	object	is
            'active'.";
          smiv2:max-access "read-only";
          smiv2:oid "1.3.6.1.2.1.51.1.5.1.3";
        }

        leaf rsvpResvFwdSenderAddr {
          type binary {
            length "4..16";
          }
          description
           "The	source address of the sender  selected	by
            this	 reservation.	The  value  of	all zeroes
            indicates 'all senders'.  This object  may  not
            be  changed	when  the  value  of the RowStatus
            object is 'active'.";
          smiv2:max-access "read-only";
          smiv2:oid "1.3.6.1.2.1.51.1.5.1.4";
        }

        leaf rsvpResvFwdDestAddrLength {
          type int32 {
            range "0..128";
          }
          description
           "The	length of the destination address in bits.
            This	 is  the CIDR Prefix Length, which for IP4
            hosts and multicast addresses is 32 bits.  This
            object may not be changed when the value of the
            RowStatus object is 'active'.";
          smiv2:max-access "read-only";
          smiv2:oid "1.3.6.1.2.1.51.1.5.1.5";
        }

        leaf rsvpResvFwdSenderAddrLength {
          type int32 {
            range "0..128";
          }
          description
           "The	length of the sender's	address	 in  bits.
            This	 is  the CIDR Prefix Length, which for IP4
            hosts and multicast addresses is 32 bits.  This
            object may not be changed when the value of the
            RowStatus object is 'active'.";
          smiv2:max-access "read-only";
          smiv2:oid "1.3.6.1.2.1.51.1.5.1.6";
        }

        leaf rsvpResvFwdProtocol {
          type integrated-services:Protocol;
          description
           "The	IP Protocol used by a session. for  secure
            sessions,  this  indicates  IP  Security.  This
            object may not be changed when the value of the
            RowStatus object is 'active'.";
          smiv2:max-access "read-only";
          smiv2:oid "1.3.6.1.2.1.51.1.5.1.7";
        }

        leaf rsvpResvFwdDestPort {
          type integrated-services:Port;
          description
           "The	 UDP  or  TCP  port  number  used   as	 a
            destination	 port  for  all	 senders  in  this
            session.  If	the IP protocol	in use,	 specified
            by rsvpResvFwdProtocol, is 50 (ESP) or 51 (AH),
            this	 represents  a	virtual	 destination  port
            number.   A value of	zero indicates that the	IP
            protocol in use  does  not  have  ports.   This
            object may not be changed when the value of the
            RowStatus object is 'active'.";
          smiv2:max-access "read-only";
          smiv2:oid "1.3.6.1.2.1.51.1.5.1.8";
        }

        leaf rsvpResvFwdPort {
          type integrated-services:Port;
          description
           "The	UDP or TCP port	number used  as	 a  source
            port	 for  this sender in this session.  If the
            IP	 protocol    in	   use,	   specified	by
            rsvpResvFwdProtocol	is  50	(ESP)  or 51 (AH),
            this	represents a generalized  port	identifier
            (GPI).   A  value of	zero indicates that the	IP
            protocol in use  does  not  have  ports.   This
            object may not be changed when the value of the
            RowStatus object is 'active'.";
          smiv2:max-access "read-only";
          smiv2:oid "1.3.6.1.2.1.51.1.5.1.9";
        }

        leaf rsvpResvFwdHopAddr {
          type binary {
            length "4..16";
          }
          description
           "The	address	of the (previous) RSVP	that  will
            receive this	message.";
          smiv2:max-access "read-only";
          smiv2:oid "1.3.6.1.2.1.51.1.5.1.10";
        }

        leaf rsvpResvFwdHopLih {
          type int32;
          description
           "The	 Logical  Interface  Handle  sent  to  the
            (previous)	RSVP   that   will   receive  this
            message.";
          smiv2:max-access "read-only";
          smiv2:oid "1.3.6.1.2.1.51.1.5.1.11";
        }

        leaf rsvpResvFwdInterface {
          type if-mib:InterfaceIndex;
          description
           "The	ifIndex	value of the  interface	 on  which
            this	RESV message was most recently sent.";
          smiv2:max-access "read-only";
          smiv2:oid "1.3.6.1.2.1.51.1.5.1.12";
        }

        leaf rsvpResvFwdService {
          type integrated-services:QosService;
          description
           "The	QoS Service classification requested.";
          smiv2:max-access "read-only";
          smiv2:oid "1.3.6.1.2.1.51.1.5.1.13";
        }

        leaf rsvpResvFwdTSpecRate {
          type integrated-services:BitRate;
          units "bits per second";
          description
           "The	Average	Bit  Rate  of  the  sender's  data
            stream.    Within  a	 transmission  burst,  the
            arrival   rate    may    be	  as	fast	as
            rsvpResvFwdTSpecPeakRate  (if  supported by the
            service model); however, averaged across two	or
            more	 burst	intervals,  the	 rate  should  not
            exceed rsvpResvFwdTSpecRate.
            
            Note	that this is a prediction, often based	on
            the	general	 capability  of	a type of codec	or
            particular encoding;	the measured average  rate
            may be significantly	lower.";
          smiv2:max-access "read-only";
          smiv2:oid "1.3.6.1.2.1.51.1.5.1.14";
        }

        leaf rsvpResvFwdTSpecPeakRate {
          type integrated-services:BitRate;
          units "bits per second";
          description
           "The	Peak Bit Rate of the sender's data  stream
            Traffic  arrival is not expected to exceed this
            rate	at any time, apart  from  the  effects	of
            jitter in the network.  If not specified in the
            TSpec, this returns zero or noSuchValue.";
          smiv2:max-access "read-only";
          smiv2:oid "1.3.6.1.2.1.51.1.5.1.15";
        }

        leaf rsvpResvFwdTSpecBurst {
          type integrated-services:BurstSize;
          units "bytes";
          description
           "The	size of	the largest  burst  expected  from
            the sender at a time.
            
            If this is less than	 the  sender's	advertised
            burst  size,	the receiver is	asking the network
            to provide flow pacing  beyond  what	 would	be
            provided   under   normal  circumstances.  Such
            pacing is at	the network's option.";
          smiv2:max-access "read-only";
          smiv2:oid "1.3.6.1.2.1.51.1.5.1.16";
        }

        leaf rsvpResvFwdTSpecMinTU {
          type integrated-services:MessageSize;
          description
           "The	minimum	message	size for  this	flow.  The
            policing  algorithm will treat smaller messages
            as though they are this size.";
          smiv2:max-access "read-only";
          smiv2:oid "1.3.6.1.2.1.51.1.5.1.17";
        }

        leaf rsvpResvFwdTSpecMaxTU {
          type integrated-services:MessageSize;
          description
           "The	maximum	message	size for  this	flow.  The
            admission  algorithm	 will  reject TSpecs whose
            Maximum Transmission	Unit, plus  the	 interface
            headers, exceed the interface MTU.";
          smiv2:max-access "read-only";
          smiv2:oid "1.3.6.1.2.1.51.1.5.1.18";
        }

        leaf rsvpResvFwdRSpecRate {
          type integrated-services:BitRate;
          units "bytes per second";
          description
           "If the requested  service  is  Guaranteed,	as
            specified   by  rsvpResvService,  this  is  the
            clearing  rate   that   is	being	requested.
            Otherwise,  it is zero, or the agent	may return
            noSuchValue.";
          smiv2:max-access "read-only";
          smiv2:oid "1.3.6.1.2.1.51.1.5.1.19";
        }

        leaf rsvpResvFwdRSpecSlack {
          type int32;
          units "microseconds";
          description
           "If the requested  service  is  Guaranteed,	as
            specified by	rsvpResvService, this is the delay
            slack.  Otherwise, it is zero, or the agent may
            return noSuchValue.";
          smiv2:max-access "read-only";
          smiv2:oid "1.3.6.1.2.1.51.1.5.1.20";
        }

        leaf rsvpResvFwdInterval {
          type RSVP-MIB:RefreshInterval;
          description
           "The	  interval   between   refresh	  messages
            advertised to the Previous Hop.";
          smiv2:max-access "read-only";
          smiv2:oid "1.3.6.1.2.1.51.1.5.1.21";
        }

        leaf rsvpResvFwdScope {
          type binary {
            length "0..65536";
          }
          description
           "The	contents of the	scope object, displayed	as
            an  uninterpreted  string  of octets, including
            the object header.  In the absence of  such	an
            object, this	should be of zero length.";
          smiv2:max-access "read-only";
          smiv2:oid "1.3.6.1.2.1.51.1.5.1.22";
        }

        leaf rsvpResvFwdShared {
          type boolean;
          description
           "If TRUE, a reservation shared among	senders	is
            requested.  If FALSE, a reservation specific	to
            this	sender is requested.";
          smiv2:max-access "read-only";
          smiv2:oid "1.3.6.1.2.1.51.1.5.1.23";
        }

        leaf rsvpResvFwdExplicit {
          type boolean;
          description
           "If TRUE, individual	senders	are  listed  using
            Filter  Specifications.   If	FALSE, all senders
            are implicitly selected.  The Scope Object will
            contain  a list of senders that need	to receive
            this	reservation request  for  the  purpose	of
            routing the RESV message.";
          smiv2:max-access "read-only";
          smiv2:oid "1.3.6.1.2.1.51.1.5.1.24";
        }

        leaf rsvpResvFwdRSVPHop {
          type boolean;
          description
           "If TRUE, the node believes that  the  next	IP
            hop	is  an	RSVP  hop.   If	 FALSE,	 the  node
            believes that the next IP hop  may  not  be	an
            RSVP	hop.";
          smiv2:max-access "read-only";
          smiv2:oid "1.3.6.1.2.1.51.1.5.1.25";
        }

        leaf rsvpResvFwdLastChange {
          type yang:timestamp;
          description
           "The	time of	the last change	in  this  request;
            This	 is  either  the first time it was sent	or
            the	time  of  the  most   recent   change	in
            parameters.";
          smiv2:max-access "read-only";
          smiv2:oid "1.3.6.1.2.1.51.1.5.1.26";
        }

        leaf rsvpResvFwdPolicy {
          type binary {
            length "0..65536";
          }
          description
           "The	contents of the	policy	object,	 displayed
            as an uninterpreted string of octets, including
            the object header.  In the absence of  such	an
            object, this	should be of zero length.";
          smiv2:max-access "read-only";
          smiv2:oid "1.3.6.1.2.1.51.1.5.1.27";
        }

        leaf rsvpResvFwdStatus {
          type snmpv2-tc:RowStatus;
          description
           "'active' for all active RESV  messages.   This
            object may be used to delete	RESV information.";
          smiv2:max-access "read-write";
          smiv2:oid "1.3.6.1.2.1.51.1.5.1.28";
        }

        leaf rsvpResvFwdTTL {
          type int32 {
            range "0..255";
          }
          description
           "The	TTL value in the RSVP header that was last
            received.";
          smiv2:max-access "read-only";
          smiv2:oid "1.3.6.1.2.1.51.1.5.1.29";
        }

        leaf rsvpResvFwdFlowId {
          type int32 {
            range "0..16777215";
          }
          description
           "The	flow ID	that this receiver  is	using,	if
            this	 is  an	IPv6 session.";
          smiv2:max-access "read-only";
          smiv2:oid "1.3.6.1.2.1.51.1.5.1.30";
        }
      }
    }

    container rsvpIfTable {
      description
       "The	RSVP-specific attributes of  the  system's
        interfaces.";
      smiv2:oid "1.3.6.1.2.1.51.1.6";

      list rsvpIfEntry {
        key "ifIndex";
        description
         "The	RSVP-specific attributes of  the  a  given
          interface.";
        smiv2:oid "1.3.6.1.2.1.51.1.6.1";

        leaf ifIndex {
          type leafref {
            path "/if-mib:IF-MIB/if-mib:ifTable/if-mib:ifEntry/if-mib:ifIndex";
          }
        }

        leaf rsvpIfUdpNbrs {
          type yang:gauge32;
          description
           "The	number of neighbors perceived to be  using
            only	the RSVP UDP Encapsulation.";
          smiv2:max-access "read-only";
          smiv2:oid "1.3.6.1.2.1.51.1.6.1.1";
        }

        leaf rsvpIfIpNbrs {
          type yang:gauge32;
          description
           "The	number of neighbors perceived to be  using
            only	the RSVP IP Encapsulation.";
          smiv2:max-access "read-only";
          smiv2:oid "1.3.6.1.2.1.51.1.6.1.2";
        }

        leaf rsvpIfNbrs {
          type yang:gauge32;
          description
           "The	number of neighbors  currently	perceived;
            this	 will  exceed rsvpIfIpNbrs + rsvpIfUdpNbrs
            by  the  number   of	  neighbors   using   both
            encapsulations.";
          smiv2:max-access "read-only";
          smiv2:oid "1.3.6.1.2.1.51.1.6.1.3";
        }

        leaf rsvpIfRefreshBlockadeMultiple {
          type int32 {
            range "1..65536";
          }
          description
           "The	value of the RSVP value	'Kb', Which is the
            minimum   number   of  refresh  intervals  that
            blockade state will last once entered.";
          smiv2:defval "4";
          smiv2:max-access "read-write";
          smiv2:oid "1.3.6.1.2.1.51.1.6.1.4";
        }

        leaf rsvpIfRefreshMultiple {
          type int32 {
            range "1..65536";
          }
          description
           "The	value of the RSVP value	'K', which is  the
            number  of  refresh intervals which must elapse
            (minimum) before a PATH or RESV  message  which
            is not being	refreshed will be aged out.";
          smiv2:defval "3";
          smiv2:max-access "read-write";
          smiv2:oid "1.3.6.1.2.1.51.1.6.1.5";
        }

        leaf rsvpIfTTL {
          type int32 {
            range "0..255";
          }
          description
           "The	value of SEND_TTL used on  this	 interface
            for	messages  this node originates.	 If set	to
            zero, the node determines  the  TTL	via  other
            means.";
          smiv2:defval "0";
          smiv2:max-access "read-write";
          smiv2:oid "1.3.6.1.2.1.51.1.6.1.6";
        }

        leaf rsvpIfRefreshInterval {
          type snmpv2-tc:TimeInterval;
          units "milliseconds";
          description
           "The	value of the RSVP value	'R', which is  the
            minimum period between refresh transmissions	of
            a given PATH	or RESV	message	on an interface.";
          smiv2:defval "3000";
          smiv2:max-access "read-write";
          smiv2:oid "1.3.6.1.2.1.51.1.6.1.7";
        }

        leaf rsvpIfRouteDelay {
          type snmpv2-tc:TimeInterval;
          units "hundredths	of a second";
          description
           "The	approximate period from	the time  a  route
            is  changed	to  the	 time  a resulting message
            appears on the interface.";
          smiv2:defval "200";
          smiv2:max-access "read-write";
          smiv2:oid "1.3.6.1.2.1.51.1.6.1.8";
        }

        leaf rsvpIfEnabled {
          type boolean;
          description
           "If TRUE, RSVP is enabled  on  this	Interface.
            If	FALSE,	 RSVP	is  not	 enabled  on  this
            interface.";
          smiv2:max-access "read-write";
          smiv2:oid "1.3.6.1.2.1.51.1.6.1.9";
        }

        leaf rsvpIfUdpRequired {
          type boolean;
          description
           "If TRUE, manual configuration forces  the  use
            of  UDP  encapsulation  on  the  interface.	If
            FALSE,  UDP	encapsulation  is  only	 used	if
            rsvpIfUdpNbrs is not	zero.";
          smiv2:max-access "read-write";
          smiv2:oid "1.3.6.1.2.1.51.1.6.1.10";
        }

        leaf rsvpIfStatus {
          type snmpv2-tc:RowStatus;
          description
           "'active' on	interfaces that	are configured for
            RSVP.";
          smiv2:max-access "read-write";
          smiv2:oid "1.3.6.1.2.1.51.1.6.1.11";
        }
      }
    }

    container rsvpNbrTable {
      description
       "Information	describing  the	 Neighbors  of	an
        RSVP	system.";
      smiv2:oid "1.3.6.1.2.1.51.1.7";

      list rsvpNbrEntry {
        key "ifIndex rsvpNbrAddress";
        description
         "Information	  describing   a    single    RSVP
          Neighbor.";
        smiv2:oid "1.3.6.1.2.1.51.1.7.1";

        leaf ifIndex {
          type leafref {
            path "/if-mib:IF-MIB/if-mib:ifTable/if-mib:ifEntry/if-mib:ifIndex";
          }
        }

        leaf rsvpNbrAddress {
          type binary {
            length "4..16";
          }
          description
           "The	IP4 or IP6 Address used	by this	 neighbor.
            This	 object	 may not be changed when the value
            of the RowStatus object is 'active'.";
          smiv2:max-access "not-accessible";
          smiv2:oid "1.3.6.1.2.1.51.1.7.1.1";
        }

        leaf rsvpNbrProtocol {
          type RSVP-MIB:RsvpEncapsulation;
          description
           "The	  encapsulation	  being	  used	 by   this
            neighbor.";
          smiv2:max-access "read-write";
          smiv2:oid "1.3.6.1.2.1.51.1.7.1.2";
        }

        leaf rsvpNbrStatus {
          type snmpv2-tc:RowStatus;
          description
           "'active' for all neighbors.	 This  object  may
            be	used   to  configure  neighbors.   In  the
            presence   of   configured	 neighbors,    the
            implementation  may	(but  is  not required to)
            limit the  set  of  valid  neighbors	 to  those
            configured.";
          smiv2:max-access "read-write";
          smiv2:oid "1.3.6.1.2.1.51.1.7.1.3";
        }
      }
    }
  }

  notification newFlow {
    description
     "The	  newFlow   trap   indicates   that    the
      originating	system has installed a new flow	in
      its	 classifier,	or    (when    reservation
      authorization   is  in  view)  is  prepared	to
      install such	a flow in the  classifier  and	is
      requesting authorization.  The objects included
      with	the  Notification  may	be  used  to  read
      further   information   using   the	Integrated
      Services and	RSVP MIBs.  Authorization or  non-
      authorization  may be enacted by a write to the
      variable intSrvFlowStatus.";
    smiv2:oid "1.3.6.1.2.1.51.3.0.1";

    container object-1 {

      leaf intSrvFlowNumber {
        type leafref {
          path "/integrated-services:INTEGRATED-SERVICES-MIB/integrated-services:intSrvFlowTable/integrated-services:intSrvFlowEntry/integrated-services:intSrvFlowNumber";
        }
      }

      leaf intSrvFlowStatus {
        type leafref {
          path "/integrated-services:INTEGRATED-SERVICES-MIB/integrated-services:intSrvFlowTable/integrated-services:intSrvFlowEntry/integrated-services:intSrvFlowStatus";
        }
      }
    }

    container object-2 {

      leaf rsvpSessionNumber {
        type leafref {
          path "/RSVP-MIB:RSVP-MIB/RSVP-MIB:rsvpSessionTable/RSVP-MIB:rsvpSessionEntry/RSVP-MIB:rsvpSessionNumber";
        }
      }

      leaf rsvpSessionDestAddr {
        type leafref {
          path "/RSVP-MIB:RSVP-MIB/RSVP-MIB:rsvpSessionTable/RSVP-MIB:rsvpSessionEntry/RSVP-MIB:rsvpSessionDestAddr";
        }
      }
    }

    container object-3 {

      leaf rsvpSessionNumber {
        type leafref {
          path "/RSVP-MIB:RSVP-MIB/RSVP-MIB:rsvpSessionTable/RSVP-MIB:rsvpSessionEntry/RSVP-MIB:rsvpSessionNumber";
        }
      }

      leaf rsvpResvFwdNumber {
        type leafref {
          path "/RSVP-MIB:RSVP-MIB/RSVP-MIB:rsvpResvFwdTable/RSVP-MIB:rsvpResvFwdEntry/RSVP-MIB:rsvpResvFwdNumber";
        }
      }

      leaf rsvpResvFwdStatus {
        type leafref {
          path "/RSVP-MIB:RSVP-MIB/RSVP-MIB:rsvpResvFwdTable/RSVP-MIB:rsvpResvFwdEntry/RSVP-MIB:rsvpResvFwdStatus";
        }
      }
    }

    container object-4 {

      leaf rsvpSessionNumber {
        type leafref {
          path "/RSVP-MIB:RSVP-MIB/RSVP-MIB:rsvpSessionTable/RSVP-MIB:rsvpSessionEntry/RSVP-MIB:rsvpSessionNumber";
        }
      }

      leaf rsvpResvNumber {
        type leafref {
          path "/RSVP-MIB:RSVP-MIB/RSVP-MIB:rsvpResvTable/RSVP-MIB:rsvpResvEntry/RSVP-MIB:rsvpResvNumber";
        }
      }

      leaf rsvpResvStatus {
        type leafref {
          path "/RSVP-MIB:RSVP-MIB/RSVP-MIB:rsvpResvTable/RSVP-MIB:rsvpResvEntry/RSVP-MIB:rsvpResvStatus";
        }
      }
    }

    container object-5 {

      leaf rsvpSessionNumber {
        type leafref {
          path "/RSVP-MIB:RSVP-MIB/RSVP-MIB:rsvpSessionTable/RSVP-MIB:rsvpSessionEntry/RSVP-MIB:rsvpSessionNumber";
        }
      }

      leaf rsvpSenderNumber {
        type leafref {
          path "/RSVP-MIB:RSVP-MIB/RSVP-MIB:rsvpSenderTable/RSVP-MIB:rsvpSenderEntry/RSVP-MIB:rsvpSenderNumber";
        }
      }

      leaf rsvpSenderStatus {
        type leafref {
          path "/RSVP-MIB:RSVP-MIB/RSVP-MIB:rsvpSenderTable/RSVP-MIB:rsvpSenderEntry/RSVP-MIB:rsvpSenderStatus";
        }
      }
    }
  }

  notification lostFlow {
    description
     "The	  lostFlow   trap   indicates	that   the
      originating	system has removed a flow from its
      classifier.";
    smiv2:oid "1.3.6.1.2.1.51.3.0.2";

    container object-1 {

      leaf intSrvFlowNumber {
        type leafref {
          path "/integrated-services:INTEGRATED-SERVICES-MIB/integrated-services:intSrvFlowTable/integrated-services:intSrvFlowEntry/integrated-services:intSrvFlowNumber";
        }
      }

      leaf intSrvFlowStatus {
        type leafref {
          path "/integrated-services:INTEGRATED-SERVICES-MIB/integrated-services:intSrvFlowTable/integrated-services:intSrvFlowEntry/integrated-services:intSrvFlowStatus";
        }
      }
    }

    container object-2 {

      leaf rsvpSessionNumber {
        type leafref {
          path "/RSVP-MIB:RSVP-MIB/RSVP-MIB:rsvpSessionTable/RSVP-MIB:rsvpSessionEntry/RSVP-MIB:rsvpSessionNumber";
        }
      }

      leaf rsvpSessionDestAddr {
        type leafref {
          path "/RSVP-MIB:RSVP-MIB/RSVP-MIB:rsvpSessionTable/RSVP-MIB:rsvpSessionEntry/RSVP-MIB:rsvpSessionDestAddr";
        }
      }
    }

    container object-3 {

      leaf rsvpSessionNumber {
        type leafref {
          path "/RSVP-MIB:RSVP-MIB/RSVP-MIB:rsvpSessionTable/RSVP-MIB:rsvpSessionEntry/RSVP-MIB:rsvpSessionNumber";
        }
      }

      leaf rsvpResvFwdNumber {
        type leafref {
          path "/RSVP-MIB:RSVP-MIB/RSVP-MIB:rsvpResvFwdTable/RSVP-MIB:rsvpResvFwdEntry/RSVP-MIB:rsvpResvFwdNumber";
        }
      }

      leaf rsvpResvFwdStatus {
        type leafref {
          path "/RSVP-MIB:RSVP-MIB/RSVP-MIB:rsvpResvFwdTable/RSVP-MIB:rsvpResvFwdEntry/RSVP-MIB:rsvpResvFwdStatus";
        }
      }
    }

    container object-4 {

      leaf rsvpSessionNumber {
        type leafref {
          path "/RSVP-MIB:RSVP-MIB/RSVP-MIB:rsvpSessionTable/RSVP-MIB:rsvpSessionEntry/RSVP-MIB:rsvpSessionNumber";
        }
      }

      leaf rsvpResvNumber {
        type leafref {
          path "/RSVP-MIB:RSVP-MIB/RSVP-MIB:rsvpResvTable/RSVP-MIB:rsvpResvEntry/RSVP-MIB:rsvpResvNumber";
        }
      }

      leaf rsvpResvStatus {
        type leafref {
          path "/RSVP-MIB:RSVP-MIB/RSVP-MIB:rsvpResvTable/RSVP-MIB:rsvpResvEntry/RSVP-MIB:rsvpResvStatus";
        }
      }
    }

    container object-5 {

      leaf rsvpSessionNumber {
        type leafref {
          path "/RSVP-MIB:RSVP-MIB/RSVP-MIB:rsvpSessionTable/RSVP-MIB:rsvpSessionEntry/RSVP-MIB:rsvpSessionNumber";
        }
      }

      leaf rsvpSenderNumber {
        type leafref {
          path "/RSVP-MIB:RSVP-MIB/RSVP-MIB:rsvpSenderTable/RSVP-MIB:rsvpSenderEntry/RSVP-MIB:rsvpSenderNumber";
        }
      }

      leaf rsvpSenderStatus {
        type leafref {
          path "/RSVP-MIB:RSVP-MIB/RSVP-MIB:rsvpSenderTable/RSVP-MIB:rsvpSenderEntry/RSVP-MIB:rsvpSenderStatus";
        }
      }
    }
  }

  smiv2:alias "rsvp" {
    smiv2:oid "1.3.6.1.2.1.51";
  }

  smiv2:alias "rsvpObjects" {
    smiv2:oid "1.3.6.1.2.1.51.1";
  }

  smiv2:alias "rsvpGenObjects" {
    smiv2:oid "1.3.6.1.2.1.51.2";
  }

  smiv2:alias "rsvpNotificationsPrefix" {
    smiv2:oid "1.3.6.1.2.1.51.3";
  }

  smiv2:alias "rsvpNotifications" {
    smiv2:oid "1.3.6.1.2.1.51.3.0";
  }

  smiv2:alias "rsvpConformance" {
    smiv2:oid "1.3.6.1.2.1.51.4";
  }

  smiv2:alias "rsvpGroups" {
    smiv2:oid "1.3.6.1.2.1.51.4.1";
  }

  smiv2:alias "rsvpCompliances" {
    smiv2:oid "1.3.6.1.2.1.51.4.2";
  }

}
