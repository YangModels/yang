/*
 * Generated by confdc --mib2yang-std
 * Source: mgmt/dmi/model/common/mib-source/IEEE8021-TC-MIB.mib
 */
/*
 * This YANG module has been generated by smidump 0.5.0:
 *
 *      smidump -f yang IEEE8021-TC-MIB
 *
 * Do not edit. Edit the source file instead!
 */

module IEEE8021-TC-MIB {

  namespace "urn:ietf:params:xml:ns:yang:smiv2:IEEE8021-TC-MIB";
  prefix IEEE8021-TC-MIB;

  import ietf-yang-smiv2 {
    prefix "smiv2";
  }

  organization
   "IEEE 802.1 Working Group";

  contact
   "  WG-URL: http://grouper.ieee.org/groups/802/1/index.html
    WG-EMail: stds-802-1@ieee.org
    
     Contact: David Levi
      Postal: 4655 GREAT AMERICA PARKWAY
              SANTA CLARA, CALIFORNIA
              95054
              USA
         Tel: +1-408-495-5138
      E-mail: dlevi@nortel.com";

  description
   "Textual conventions used throughout the various IEEE 802.1 MIB
    modules.
    
    Unless otherwise indicated, the references in this MIB
    module are to IEEE 802.1Q-2005 as amended by IEEE 802.1ad,
    IEEE 802.1ak, IEEE 802.1ag and IEEE 802.1ah.
    
    Copyright (C) IEEE.
    This version of this MIB module is part of IEEE802.1Q;
    see the draft itself for full legal notices.";

  revision 2008-10-15 {
    description
     "Initial version.";
  }

  typedef IEEE8021PbbComponentIdentifier {
    type uint32 {
      range "1..4294967295";
    }
    description
     "The component identifier is used to distinguish between the
      multiple virtual bridge instances within a PB or PBB.  Each
      virtual bridge instance is called a component.  In simple
      situations where there is only a single component the default
      value is 1.  The component is identified by a component
      identifier unique within the BEB and by a MAC address unique
      within the PBBN.  Each component is associated with a Backbone
      Edge Bridge (BEB) Configuration managed object.";
    reference
     "12.3 l)";
    smiv2:display-hint "d";
  }

  typedef IEEE8021PbbComponentIdentifierOrZero {
    type uint32 {
      range "0..4294967295";
    }
    description
     "The component identifier is used to distinguish between the
      multiple virtual bridge instances within a PB or PBB.  In simple
      situations where there is only a single component the default
      value is 1.  The component is identified by a component
      identifier unique within the BEB and by a MAC address unique
      within the PBBN.  Each component is associated with a Backbone
      Edge Bridge (BEB) Configuration managed object.
      
      The special value '0' means 'no component identifier'.  When
      this TC is used as the SYNTAX of an object, that object must
      specify the its exact meaning for this value.";
    reference
     "12.3 l)";
    smiv2:display-hint "d";
  }

  typedef IEEE8021PbbServiceIdentifier {
    type uint32 {
      range "256..16777214";
    }
    description
     "The service instance identifier is used at the Customer
      Backbone Port of a PBB to distinguish a service instance
      (Local-SID). If the Local-SID field is supported, it is
      used to perform a bidirectional 1:1 mapping between the
      Backbone I-SID and the Local-SID. If the Local-SID field
      is not supported, the Local-SID value is the same as the
      Backbone I-SID value.";
    reference
     "12.16.3, 12.16.5";
    smiv2:display-hint "d";
  }

  typedef IEEE8021PbbServiceIdentifierOrUnassigned {
    type uint32 {
      range "1|256..16777214";
    }
    description
     "The service instance identifier is used at the Customer
      Backbone Port of a PBB to distinguish a service instance
      (Local-SID). If the Local-SID field is supported, it is
      used to perform a bidirectional 1:1 mapping between the
      Backbone I-SID and the Local-SID. If the Local-SID field
      is not supported, the Local-SID value is the same as the
      Backbone I-SID value.
      
      The special value of 1 indicates an unassigned I-SID.";
    reference
     "12.16.3, 12.16.5";
    smiv2:display-hint "d";
  }

  typedef IEEE8021PbbIngressEgress {
    type bits {
      bit ingress {
        position "0";
      }
      bit egress {
        position "1";
      }
    }
    description
     "A 2 bit selector which determines if frames on this VIP may
      ingress to the PBBN but not egress the PBBN, egress to the
      PBBN but not ingress the PBBN, or both ingress and egress
      the PBBN.";
    reference
     "12.16.3, 12.16.5, 12.16.6";
  }

  typedef IEEE8021PriorityCodePoint {
    type enumeration {
      enum "codePoint8p0d" {
        value "1";
      }
      enum "codePoint7p1d" {
        value "2";
      }
      enum "codePoint6p2d" {
        value "3";
      }
      enum "codePoint5p3d" {
        value "4";
      }
    }
    description
     "Bridge ports may encode or decode the PCP value of the 
      frames that traverse the port. This textual convention 
      names the possible encoding and decoding schemes that
      the port may use.  The priority and drop_eligible
      parameters are encoded in the Priority Code Point (PCP)
      field of the VLAN tag using the Priority Code Point
      Encoding Table for the Port, and they are decoded from
      the PCP using the Priority Code Point Decoding Table.";
    reference
     "12.6.2.6";
  }

  typedef IEEE8021BridgePortNumber {
    type uint32 {
      range "1..65535";
    }
    description
     "An integer that uniquely identifies a bridge port, as
      specified in 17.3.2.2 of IEEE 802.1ap.
      This value is used within the spanning tree
      protocol to identify this port to neighbor bridges.";
    reference
     "17.3.2.2";
    smiv2:display-hint "d";
  }

  typedef IEEE8021BridgePortNumberOrZero {
    type uint32 {
      range "0..65535";
    }
    description
     "An integer that uniquely identifies a bridge port, as
      specified in 17.3.2.2 of IEEE 802.1ap.  The value 0
      means no port number, and this must be clarified in the
      DESCRIPTION clause of any object defined using this
      TEXTUAL-CONVENTION.";
    reference
     "17.3.2.2";
    smiv2:display-hint "d";
  }

  typedef IEEE8021BridgePortType {
    type enumeration {
      enum "none" {
        value "1";
      }
      enum "customerVlanPort" {
        value "2";
      }
      enum "providerNetworkPort" {
        value "3";
      }
      enum "customerNetworkPort" {
        value "4";
      }
      enum "customerEdgePort" {
        value "5";
      }
      enum "customerBackbonePort" {
        value "6";
      }
      enum "virtualInstancePort" {
        value "7";
      }
      enum "dBridgePort" {
        value "8";
      }
    }
    description
     "A port type.  The possible port types are:
      
      customerVlanPort(2) - Indicates a port is a C-tag
          aware port of an enterprise VLAN aware bridge.
      
      providerNetworkPort(3) - Indicates a port is an S-tag
          aware port of a Provider Bridge or Backbone Edge
          Bridge used for connections within a PBN or PBBN.
      
      customerNetworkPort(4) - Indicates a port is an S-tag
          aware port of a Provider Bridge or Backbone Edge
          Bridge used for connections to the exterior of a
          PBN or PBBN.
      
      customerEdgePort(5) - Indicates a port is a C-tag
          aware port of a Provider Bridge used for connections
          to the exterior of a PBN or PBBN.
      
      customerBackbonePort(6) - Indicates a port is a I-tag
          aware port of a Backbone Edge Bridge's B-component.
      
      virtualInstancePort(7) - Indicates a port is a virtual
          S-tag aware port within a Backbone Edge Bridge's
          I-component which is responsible for handling
          S-tagged traffic for a specific backbone service
          instance.
      
      dBridgePort(8) - Indicates a port is a VLAN-unaware
          member of an 802.1D bridge.";
    reference
     "12.16.1.1.3 h4), 12.16.2.1/2,
      12.13.1.1, 12.13.1.2, 12.15.2.1, 12.15.2.2";
  }

  typedef IEEE8021VlanIndex {
    type uint32 {
      range "1..4094|4096..4294967295";
    }
    description
     "A value used to index per-VLAN tables: values of 0 and
      4095 are not permitted.  If the value is between 1 and
      4094 inclusive, it represents an IEEE 802.1Q VLAN-ID with
      global scope within a given bridged domain (see VlanId
      textual convention).  If the value is greater than 4095,
      then it represents a VLAN with scope local to the
      particular agent, i.e., one without a global VLAN-ID
      assigned to it.  Such VLANs are outside the scope of
      IEEE 802.1Q, but it is convenient to be able to manage them
      in the same way using this MIB.";
    reference
     "9.6";
    smiv2:display-hint "d";
  }

  typedef IEEE8021VlanIndexOrWildcard {
    type uint32 {
      range "1..4294967295";
    }
    description
     "A value used to index per-VLAN tables.  The value 0 is not
      permitted, while the value 4095 represents a 'wildcard'
      value.  An object whose SYNTAX is IEEE8021VlanIndexOrWildcard
      must specify in its DESCRIPTION the specific meaning of the
      wildcard value.  If the value is between 1 and
      4094 inclusive, it represents an IEEE 802.1Q VLAN-ID with
      global scope within a given bridged domain (see VlanId
      textual convention).  If the value is greater than 4095,
      then it represents a VLAN with scope local to the
      particular agent, i.e., one without a global VLAN-ID
      assigned to it.  Such VLANs are outside the scope of
      IEEE 802.1Q, but it is convenient to be able to manage them
      in the same way using this MIB.";
    reference
     "9.6";
    smiv2:display-hint "d";
  }

  typedef IEEE8021MstIdentifier {
    type uint32 {
      range "1..4094";
    }
    description
     "In an MSTP Bridge, an MSTID, i.e., a value used to identify
      a spanning tree (or MST) instance.";
    smiv2:display-hint "d";
  }

  typedef IEEE8021ServiceSelectorType {
    type enumeration {
      enum "vlanId" {
        value "1";
      }
      enum "isid" {
        value "2";
      }
    }
    description
     "A value that represents a type (and thereby the format)
      of a IEEE8021ServiceSelectorValue.  The value can be one of
      the following:
      
      ieeeReserved(0)   Reserved for definition by IEEE 802.1
                        recommend to not use zero unless
                        absolutely needed.
      vlanId(1)         12-Bit identifier as described in IEEE802.1Q.
      isid(2)           20-Bit identifier as described in IEEE802.1ah.
      ieeeReserved(xx)  Reserved for definition by IEEE 802.1
                        xx values can be [3..7].
      
      To support future extensions, the IEEE8021ServiceSelectorType
      textual convention SHOULD NOT be sub-typed in object type
      definitions.  It MAY be sub-typed in compliance statements in
      order to require only a subset of these address types for a
      compliant implementation.
      
      Implementations MUST ensure that IEEE8021ServiceSelectorType
      objects and any dependent objects (e.g.,
      IEEE8021ServiceSelectorValue objects) are consistent.  An
      inconsistentValue error MUST be generated if an attempt to
      change an IEEE8021ServiceSelectorType object would, for
      example, lead to an undefined IEEE8021ServiceSelectorValue value.";
  }

  typedef IEEE8021ServiceSelectorValueOrNone {
    type uint32 {
      range "0..4294967295";
    }
    description
     "An integer that uniquely identifies a generic MAC service,
      or none.  Examples of service selectors are a VLAN-ID
      (IEEE 802.1Q) and an I-SID (IEEE 802.1ah).
      
      An IEEE8021ServiceSelectorValueOrNone value is always
      interpreted within the context of an
      IEEE8021ServiceSelectorType value.  Every usage of the
      IEEE8021ServiceSelectorValueOrNone textual convention is
      required to specify the IEEE8021ServiceSelectorType object
      that provides the context.  It is suggested that the
      IEEE8021ServiceSelectorType object be logically registered
      before the object(s) that use the
      IEEE8021ServiceSelectorValueOrNone textual convention, if
      they appear in the same logical row.
      
      The value of an IEEE8021ServiceSelectorValueOrNone object
      must always be consistent with the value of the associated
      IEEE8021ServiceSelectorType object.  Attempts to set an
      IEEE8021ServiceSelectorValueOrNone object to a value
      inconsistent with the associated
      IEEE8021ServiceSelectorType must fail with an
      inconsistentValue error.
      
      The special value of zero is used to indicate that no
      service selector is present or used.  This can be used in
      any situation where an object or a table entry MUST either
      refer to a specific service, or not make a selection.
      
      Note that a MIB object that is defined using this
      TEXTUAL-CONVENTION SHOULD clarify the meaning of
      'no service' (i.e., the special value 0), as well as the
      maximum value (i.e., 4094, for a VLAN ID).";
    smiv2:display-hint "d";
  }

  typedef IEEE8021ServiceSelectorValue {
    type uint32 {
      range "1..4294967295";
    }
    description
     "An integer that uniquely identifies a generic MAC service.
      Examples of service selectors are a VLAN-ID (IEEE 802.1Q)
      and an I-SID (IEEE 802.1ah).
      
      An IEEE8021ServiceSelectorValue value is always interpreted
      within the context of an IEEE8021ServiceSelectorType value.
      Every usage of the IEEE8021ServiceSelectorValue textual
      convention is required to specify the
      IEEE8021ServiceSelectorType object that provides the context.
      It is suggested that the IEEE8021ServiceSelectorType object
      be logically registered before the object(s) that use the
      IEEE8021ServiceSelectorValue textual convention, if they
      appear in the same logical row.
      
      The value of an IEEE8021ServiceSelectorValue object must
      always be consistent with the value of the associated
      IEEE8021ServiceSelectorType object.  Attempts to set an
      IEEE8021ServiceSelectorValue object to a value inconsistent
      with the associated IEEE8021ServiceSelectorType must fail
      with an inconsistentValue error.
      
      Note that a MIB object that is defined using this
      TEXTUAL-CONVENTION SHOULD clarify the
      maximum value (i.e., 4094, for a VLAN ID).";
    smiv2:display-hint "d";
  }

  typedef IEEE8021PortAcceptableFrameTypes {
    type enumeration {
      enum "admitAll" {
        value "1";
      }
      enum "admitUntaggedAndPriority" {
        value "2";
      }
      enum "admitTagged" {
        value "3";
      }
    }
    description
     "Acceptable frame types on a port.";
    reference
     "12.10.1.3, 12.13.3.3, 12.13.3.4";
  }

  typedef IEEE8021PriorityValue {
    type uint32 {
      range "0..7";
    }
    description
     "An 802.1Q user priority value.";
    reference
     "12.13.3.3";
    smiv2:display-hint "d";
  }

  smiv2:alias "ieee802dot1mibs" {
    smiv2:oid "1.3.111.2.802.1.1";
  }

  smiv2:alias "ieee8021TcMib" {
    smiv2:oid "1.3.111.2.802.1.1.1";
  }

}
