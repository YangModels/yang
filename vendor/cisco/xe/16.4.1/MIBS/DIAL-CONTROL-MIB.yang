/*
 * Generated by confdc --mib2yang-std
 * Source: mgmt/dmi/model/common/mib-source/DIAL-CONTROL-MIB.mib
 */
/*
 * This YANG module has been generated by smidump 0.5.0:
 *
 *      smidump -f yang DIAL-CONTROL-MIB
 *
 * Do not edit. Edit the source file instead!
 */

module DIAL-CONTROL-MIB {

  namespace "urn:ietf:params:xml:ns:yang:smiv2:DIAL-CONTROL-MIB";
  prefix DIAL-CONTROL-MIB;

  import IANAifType-MIB {
    prefix "ianaiftype-mib";
  }

  import IF-MIB {
    prefix "if-mib";
  }

  import SNMPv2-TC {
    prefix "snmpv2-tc";
  }

  import ietf-yang-smiv2 {
    prefix "smiv2";
  }

  import ietf-yang-types {
    prefix "yang";
  }

  organization
   "IETF ISDN Working Group";

  contact
   "        Guenter Roeck
    Postal: cisco Systems
            170 West Tasman Drive
            San Jose, CA 95134
            U.S.A.
    Phone:  +1 408 527 3143
    E-mail: groeck@cisco.com";

  description
   "The MIB module to describe peer information for
    demand access and possibly other kinds of interfaces.";

  revision 1996-09-23 {
    description
     "[Revision added by libsmi due to a LAST-UPDATED clause.]";
  }

  typedef AbsoluteCounter32 {
    type yang:gauge32;
    description
     "Represents a Counter32-like value that starts at zero,
      does not decrease, and does not wrap. This may be used
      only in situations where wrapping is not possible or
      extremely unlikely. Should such a counter overflow,
      it locks at the maxium value of 4,294,967,295.
      
      The primary use of this type of counter is situations
      where a counter value is to be recorded as history
      and is thus no longer subject to reading for changing
      values.";
  }


  container DIAL-CONTROL-MIB {
    config false;

    container dialCtlConfiguration {
      smiv2:oid "1.3.6.1.2.1.10.21.1.1";

      leaf dialCtlAcceptMode {
        type enumeration {
          enum "acceptNone" {
            value "1";
          }
          enum "acceptAll" {
            value "2";
          }
          enum "acceptKnown" {
            value "3";
          }
        }
        description
         "The security level for acceptance of incoming calls.
          acceptNone(1)  - incoming calls will not be accepted
          acceptAll(2)   - incoming calls will be accepted,
                           even if there is no matching entry
                           in the dialCtlPeerCfgTable
          acceptKnown(3) - incoming calls will be accepted only
                           if there is a matching entry in the
                           dialCtlPeerCfgTable";
        smiv2:max-access "read-write";
        smiv2:oid "1.3.6.1.2.1.10.21.1.1.1";
      }

      leaf dialCtlTrapEnable {
        type enumeration {
          enum "enabled" {
            value "1";
          }
          enum "disabled" {
            value "2";
          }
        }
        description
         "This object indicates whether dialCtlPeerCallInformation
          and dialCtlPeerCallSetup traps should be generated for
          all peers. If the value of this object is enabled(1),
          traps will be generated for all peers. If the value
          of this object is disabled(2), traps will be generated
          only for peers having dialCtlPeerCfgTrapEnable set
          to enabled(1).";
        smiv2:defval "disabled";
        smiv2:max-access "read-write";
        smiv2:oid "1.3.6.1.2.1.10.21.1.1.2";
      }
    }

    container callHistory {
      smiv2:oid "1.3.6.1.2.1.10.21.1.4";

      leaf callHistoryTableMaxLength {
        type int32 {
          range "0..2147483647";
        }
        description
         "The upper limit on the number of entries that the
          callHistoryTable may contain.  A value of 0
          will prevent any history from being retained. When
          this table is full, the oldest entry will be deleted
          and the new one will be created.";
        smiv2:max-access "read-write";
        smiv2:oid "1.3.6.1.2.1.10.21.1.4.1";
      }

      leaf callHistoryRetainTimer {
        type int32 {
          range "0..2147483647";
        }
        units "minutes";
        description
         "The minimum amount of time that an callHistoryEntry
          will be maintained before being deleted. A value of
          0 will prevent any history from being retained in the
          callHistoryTable, but will neither prevent callCompletion
          traps being generated nor affect other tables.";
        smiv2:max-access "read-write";
        smiv2:oid "1.3.6.1.2.1.10.21.1.4.2";
      }
    }

    container dialCtlPeerCfgTable {
      description
       "The list of peers from which the managed device
        will accept calls or to which it will place them.";
      smiv2:oid "1.3.6.1.2.1.10.21.1.2.1";

      list dialCtlPeerCfgEntry {
        key "dialCtlPeerCfgId ifIndex";
        description
         "Configuration data for a single Peer. This entry is
          effectively permanent, and contains information
          to identify the peer, how to connect to the peer,
          how to identify the peer and its permissions.
          The value of dialCtlPeerCfgOriginateAddress must be
          specified before a new row in this table can become
          active(1). Any writeable parameters in an existing entry
          can be modified while the entry is active. The modification
          will take effect when the peer in question will be
          called the next time.
          An entry in this table can only be created if the
          associated ifEntry already exists.";
        smiv2:oid "1.3.6.1.2.1.10.21.1.2.1.1";

        leaf ifIndex {
          type leafref {
            path "/if-mib:IF-MIB/if-mib:ifTable/if-mib:ifEntry/if-mib:ifIndex";
          }
        }

        leaf dialCtlPeerCfgId {
          type int32 {
            range "1..2147483647";
          }
          description
           "This object identifies a single peer. There may
            be several entries in this table for one peer,
            defining different ways of reaching this peer.
            Thus, there may be several entries in this table
            with the same value of dialCtlPeerCfgId.
            Multiple entries for one peer may be used to support
            multilink as well as backup lines.
            A single peer will be identified by a unique value
            of this object. Several entries for one peer MUST
            have the same value of dialCtlPeerCfgId, but different
            ifEntries and thus different values of ifIndex.";
          smiv2:max-access "not-accessible";
          smiv2:oid "1.3.6.1.2.1.10.21.1.2.1.1.1";
        }

        leaf dialCtlPeerCfgIfType {
          type ianaiftype-mib:IANAifType;
          description
           "The interface type to be used for calling this peer.
            In case of ISDN, the value of isdn(63) is to be used.";
          smiv2:defval "other";
          smiv2:max-access "read-write";
          smiv2:oid "1.3.6.1.2.1.10.21.1.2.1.1.2";
        }

        leaf dialCtlPeerCfgLowerIf {
          type if-mib:InterfaceIndexOrZero;
          description
           "ifIndex value of an interface the peer will have to be
            called on. For example, on an ISDN interface, this can be
            the ifIndex value of a D channel or the ifIndex value of a
            B channel, whatever is appropriate for a given peer.
            As an example, for Basic Rate leased lines it will be
            necessary to specify a B channel ifIndex, while for
            
            
            
            
            semi-permanent connections the D channel ifIndex has
            to be specified.
            If the interface can be dynamically assigned, this object
            has a value of zero.";
          smiv2:defval "0";
          smiv2:max-access "read-write";
          smiv2:oid "1.3.6.1.2.1.10.21.1.2.1.1.3";
        }

        leaf dialCtlPeerCfgOriginateAddress {
          type snmpv2-tc:DisplayString;
          description
           "Call Address at which the peer will be called.
            Think of this as the set of characters following 'ATDT '
            or the 'phone number' included in a D channel call request.
            
            The structure of this information will be switch type
            specific. If there is no address information required
            for reaching the peer, i.e., for leased lines,
            this object will be a zero length string.";
          smiv2:max-access "read-write";
          smiv2:oid "1.3.6.1.2.1.10.21.1.2.1.1.4";
        }

        leaf dialCtlPeerCfgAnswerAddress {
          type snmpv2-tc:DisplayString;
          description
           "Calling Party Number information element, as for example
            passed in an ISDN SETUP message by a PBX or switch,
            for incoming calls.
            This address can be used to identify the peer.
            If this address is either unknown or identical
            to dialCtlPeerCfgOriginateAddress, this object will be
            a zero length string.";
          smiv2:defval "";
          smiv2:max-access "read-write";
          smiv2:oid "1.3.6.1.2.1.10.21.1.2.1.1.5";
        }

        leaf dialCtlPeerCfgSubAddress {
          type snmpv2-tc:DisplayString;
          description
           "Subaddress at which the peer will be called.
            If the subaddress is undefined for the given media or
            unused, this is a zero length string.";
          smiv2:defval "";
          smiv2:max-access "read-write";
          smiv2:oid "1.3.6.1.2.1.10.21.1.2.1.1.6";
        }

        leaf dialCtlPeerCfgClosedUserGroup {
          type snmpv2-tc:DisplayString;
          description
           "Closed User Group at which the peer will be called.
            If the Closed User Group is undefined for the given media
            or unused, this is a zero length string.";
          reference
           "Q.931, chapter 4.6.1.";
          smiv2:defval "";
          smiv2:max-access "read-write";
          smiv2:oid "1.3.6.1.2.1.10.21.1.2.1.1.7";
        }

        leaf dialCtlPeerCfgSpeed {
          type int32 {
            range "0..2147483647";
          }
          description
           "The desired information transfer speed in bits/second
            when calling this peer.
            The detailed media specific information, e.g. information
            type and information transfer rate for ISDN circuits,
            has to be extracted from this object.
            If the transfer speed to be used is unknown or the default
            speed for this type of interfaces, the value of this object
            may be zero.";
          smiv2:defval "0";
          smiv2:max-access "read-write";
          smiv2:oid "1.3.6.1.2.1.10.21.1.2.1.1.8";
        }

        leaf dialCtlPeerCfgInfoType {
          type enumeration {
            enum "other" {
              value "1";
            }
            enum "speech" {
              value "2";
            }
            enum "unrestrictedDigital" {
              value "3";
            }
            enum "unrestrictedDigital56" {
              value "4";
            }
            enum "restrictedDigital" {
              value "5";
            }
            enum "audio31" {
              value "6";
            }
            enum "audio7" {
              value "7";
            }
            enum "video" {
              value "8";
            }
            enum "packetSwitched" {
              value "9";
            }
            enum "fax" {
              value "10";
            }
          }
          description
           "The Information Transfer Capability to be used when
            calling this peer.
            
            speech(2) refers to a non-data connection, whereas
            audio31(6) and audio7(7) refer to data mode
            connections.";
          smiv2:defval "other";
          smiv2:max-access "read-write";
          smiv2:oid "1.3.6.1.2.1.10.21.1.2.1.1.9";
        }

        leaf dialCtlPeerCfgPermission {
          type enumeration {
            enum "originate" {
              value "1";
            }
            enum "answer" {
              value "2";
            }
            enum "both" {
              value "3";
            }
            enum "callback" {
              value "4";
            }
            enum "none" {
              value "5";
            }
          }
          description
           "Applicable permissions. callback(4) either rejects the
            call and then calls back, or uses the 'Reverse charging'
            information element if it is available.
            Note that callback(4) is supposed to control charging, not
            security, and applies to callback prior to accepting a
            call. Callback for security reasons can be handled using
            PPP callback.";
          smiv2:defval "both";
          smiv2:max-access "read-write";
          smiv2:oid "1.3.6.1.2.1.10.21.1.2.1.1.10";
        }

        leaf dialCtlPeerCfgInactivityTimer {
          type int32 {
            range "0..2147483647";
          }
          units "seconds";
          description
           "The connection will be automatically disconnected
            if no longer carrying useful data for a time
            period, in seconds, specified in this object.
            Useful data in this context refers to forwarding
            packets, including routing information; it
            excludes the encapsulator maintenance frames.
            A value of zero means the connection will not be
            automatically taken down due to inactivity,
            which implies that it is a dedicated circuit.";
          smiv2:defval "0";
          smiv2:max-access "read-write";
          smiv2:oid "1.3.6.1.2.1.10.21.1.2.1.1.11";
        }

        leaf dialCtlPeerCfgMinDuration {
          type int32 {
            range "0..2147483647";
          }
          description
           "Minimum duration of a call in seconds, starting from the
            time the call is connected until the call is disconnected.
            This is to accomplish the fact that in most countries
            charging applies to units of time, which should be matched
            as closely as possible.";
          smiv2:defval "0";
          smiv2:max-access "read-write";
          smiv2:oid "1.3.6.1.2.1.10.21.1.2.1.1.12";
        }

        leaf dialCtlPeerCfgMaxDuration {
          type int32 {
            range "0..2147483647";
          }
          description
           "Maximum call duration in seconds. Zero means 'unlimited'.";
          smiv2:defval "0";
          smiv2:max-access "read-write";
          smiv2:oid "1.3.6.1.2.1.10.21.1.2.1.1.13";
        }

        leaf dialCtlPeerCfgCarrierDelay {
          type int32 {
            range "0..2147483647";
          }
          units "seconds";
          description
           "The call timeout time in seconds. The default value
            of zero means that the call timeout as specified for
            the media in question will apply.";
          smiv2:defval "0";
          smiv2:max-access "read-write";
          smiv2:oid "1.3.6.1.2.1.10.21.1.2.1.1.14";
        }

        leaf dialCtlPeerCfgCallRetries {
          type int32 {
            range "0..2147483647";
          }
          description
           "The number of calls to a non-responding address
            that may be made. A retry count of zero means
            there is no bound. The intent is to bound
            the number of successive calls to an address
            which is inaccessible, or which refuses those calls.
            
            Some countries regulate the number of call retries
            to a given peer that can be made.";
          smiv2:defval "0";
          smiv2:max-access "read-write";
          smiv2:oid "1.3.6.1.2.1.10.21.1.2.1.1.15";
        }

        leaf dialCtlPeerCfgRetryDelay {
          type int32 {
            range "0..2147483647";
          }
          units "seconds";
          description
           "The time in seconds between call retries if a peer
            cannot be reached.
            A value of zero means that call retries may be done
            without any delay.";
          smiv2:defval "0";
          smiv2:max-access "read-write";
          smiv2:oid "1.3.6.1.2.1.10.21.1.2.1.1.16";
        }

        leaf dialCtlPeerCfgFailureDelay {
          type int32 {
            range "0..2147483647";
          }
          units "seconds";
          description
           "The time in seconds after which call attempts are
            to be placed again after a peer has been noticed
            to be unreachable, i.e. after dialCtlPeerCfgCallRetries
            unsuccessful call attempts.
            A value of zero means that a peer will not be called
            again after dialCtlPeerCfgCallRetries unsuccessful call
            attempts.";
          smiv2:defval "0";
          smiv2:max-access "read-write";
          smiv2:oid "1.3.6.1.2.1.10.21.1.2.1.1.17";
        }

        leaf dialCtlPeerCfgTrapEnable {
          type enumeration {
            enum "enabled" {
              value "1";
            }
            enum "disabled" {
              value "2";
            }
          }
          description
           "This object indicates whether dialCtlPeerCallInformation
            and dialCtlPeerCallSetup traps should be generated for
            this peer.";
          smiv2:defval "disabled";
          smiv2:max-access "read-write";
          smiv2:oid "1.3.6.1.2.1.10.21.1.2.1.1.18";
        }

        leaf dialCtlPeerCfgStatus {
          type snmpv2-tc:RowStatus;
          description
           "Status of one row in this table.";
          smiv2:max-access "read-write";
          smiv2:oid "1.3.6.1.2.1.10.21.1.2.1.1.19";
        }
      }
    }

    container callActiveTable {
      description
       "A table containing information about active
        calls to a specific destination.";
      smiv2:oid "1.3.6.1.2.1.10.21.1.3.1";

      list callActiveEntry {
        key "callActiveSetupTime callActiveIndex";
        description
         "The information regarding a single active Connection.
          An entry in this table will be created when a call is
          started. An entry in this table will be deleted when
          an active call clears.";
        smiv2:oid "1.3.6.1.2.1.10.21.1.3.1.1";

        leaf callActiveSetupTime {
          type yang:timestamp;
          description
           "The value of sysUpTime when the call associated to this
            entry was started. This will be useful for an NMS to
            retrieve all calls after a specific time. Also, this object
            can be useful in finding large delays between the time the
            call was started and the time the call was connected.
            For ISDN media, this will be the time when the setup
            message was received from or sent to the network.";
          smiv2:max-access "not-accessible";
          smiv2:oid "1.3.6.1.2.1.10.21.1.3.1.1.1";
        }

        leaf callActiveIndex {
          type int32 {
            range "1..2147483647";
          }
          description
           "Small index variable to distinguish calls that start in
            the same hundredth of a second.";
          smiv2:max-access "not-accessible";
          smiv2:oid "1.3.6.1.2.1.10.21.1.3.1.1.2";
        }

        leaf callActivePeerAddress {
          type snmpv2-tc:DisplayString;
          description
           "The number this call is connected to. If the number is
            not available, then it will have a length of zero.";
          smiv2:max-access "read-only";
          smiv2:oid "1.3.6.1.2.1.10.21.1.3.1.1.3";
        }

        leaf callActivePeerSubAddress {
          type snmpv2-tc:DisplayString;
          description
           "The subaddress this call is connected to. If the subaddress
            is undefined or not available, this will be a zero length
            string.";
          smiv2:max-access "read-only";
          smiv2:oid "1.3.6.1.2.1.10.21.1.3.1.1.4";
        }

        leaf callActivePeerId {
          type int32 {
            range "0..2147483647";
          }
          description
           "This is the Id value of the peer table entry
            to which this call was made. If a peer table entry
            for this call does not exist or is unknown, the value
            of this object will be zero.";
          smiv2:max-access "read-only";
          smiv2:oid "1.3.6.1.2.1.10.21.1.3.1.1.5";
        }

        leaf callActivePeerIfIndex {
          type int32 {
            range "0..2147483647";
          }
          description
           "This is the ifIndex value of the peer table entry
            to which this call was made. If a peer table entry
            for this call does not exist or is unknown, the value
            of this object will be zero.";
          smiv2:max-access "read-only";
          smiv2:oid "1.3.6.1.2.1.10.21.1.3.1.1.6";
        }

        leaf callActiveLogicalIfIndex {
          type if-mib:InterfaceIndexOrZero;
          description
           "This is the ifIndex value of the logical interface through
            which this call was made. For ISDN media, this would be
            the ifIndex of the B channel which was used for this call.
            If the ifIndex value is unknown, the value of this object
            will be zero.";
          smiv2:max-access "read-only";
          smiv2:oid "1.3.6.1.2.1.10.21.1.3.1.1.7";
        }

        leaf callActiveConnectTime {
          type yang:timestamp;
          description
           "The value of sysUpTime when the call was connected.
            If the call is not connected, this object will have a
            value of zero.";
          smiv2:max-access "read-only";
          smiv2:oid "1.3.6.1.2.1.10.21.1.3.1.1.8";
        }

        leaf callActiveCallState {
          type enumeration {
            enum "unknown" {
              value "1";
            }
            enum "connecting" {
              value "2";
            }
            enum "connected" {
              value "3";
            }
            enum "active" {
              value "4";
            }
          }
          description
           "The current call state.
            unknown(1)     - The call state is unknown.
            connecting(2)  - A connection attempt (outgoing call)
                             is being made.
            connected(3)   - An incoming call is in the process
                             of validation.
            active(4)      - The call is active.";
          smiv2:max-access "read-only";
          smiv2:oid "1.3.6.1.2.1.10.21.1.3.1.1.9";
        }

        leaf callActiveCallOrigin {
          type enumeration {
            enum "originate" {
              value "1";
            }
            enum "answer" {
              value "2";
            }
            enum "callback" {
              value "3";
            }
          }
          description
           "The call origin.";
          smiv2:max-access "read-only";
          smiv2:oid "1.3.6.1.2.1.10.21.1.3.1.1.10";
        }

        leaf callActiveChargedUnits {
          type DIAL-CONTROL-MIB:AbsoluteCounter32;
          description
           "The number of charged units for this connection.
            For incoming calls or if charging information is
            not supplied by the switch, the value of this object
            will be zero.";
          smiv2:max-access "read-only";
          smiv2:oid "1.3.6.1.2.1.10.21.1.3.1.1.11";
        }

        leaf callActiveInfoType {
          type enumeration {
            enum "other" {
              value "1";
            }
            enum "speech" {
              value "2";
            }
            enum "unrestrictedDigital" {
              value "3";
            }
            enum "unrestrictedDigital56" {
              value "4";
            }
            enum "restrictedDigital" {
              value "5";
            }
            enum "audio31" {
              value "6";
            }
            enum "audio7" {
              value "7";
            }
            enum "video" {
              value "8";
            }
            enum "packetSwitched" {
              value "9";
            }
            enum "fax" {
              value "10";
            }
          }
          description
           "The information type for this call.";
          smiv2:max-access "read-only";
          smiv2:oid "1.3.6.1.2.1.10.21.1.3.1.1.12";
        }

        leaf callActiveTransmitPackets {
          type DIAL-CONTROL-MIB:AbsoluteCounter32;
          description
           "The number of packets which were transmitted for this
            call.";
          smiv2:max-access "read-only";
          smiv2:oid "1.3.6.1.2.1.10.21.1.3.1.1.13";
        }

        leaf callActiveTransmitBytes {
          type DIAL-CONTROL-MIB:AbsoluteCounter32;
          description
           "The number of bytes which were transmitted for this
            call.";
          smiv2:max-access "read-only";
          smiv2:oid "1.3.6.1.2.1.10.21.1.3.1.1.14";
        }

        leaf callActiveReceivePackets {
          type DIAL-CONTROL-MIB:AbsoluteCounter32;
          description
           "The number of packets which were received for this
            call.";
          smiv2:max-access "read-only";
          smiv2:oid "1.3.6.1.2.1.10.21.1.3.1.1.15";
        }

        leaf callActiveReceiveBytes {
          type DIAL-CONTROL-MIB:AbsoluteCounter32;
          description
           "The number of bytes which were received for this call.";
          smiv2:max-access "read-only";
          smiv2:oid "1.3.6.1.2.1.10.21.1.3.1.1.16";
        }
      }
    }

    container callHistoryTable {
      description
       "A table containing information about specific
        calls to a specific destination.";
      smiv2:oid "1.3.6.1.2.1.10.21.1.4.3";

      list callHistoryEntry {
        key "callActiveSetupTime callActiveIndex";
        description
         "The information regarding a single Connection.";
        smiv2:oid "1.3.6.1.2.1.10.21.1.4.3.1";

        leaf callActiveSetupTime {
          type leafref {
            path "/DIAL-CONTROL-MIB:DIAL-CONTROL-MIB/DIAL-CONTROL-MIB:callActiveTable/DIAL-CONTROL-MIB:callActiveEntry/DIAL-CONTROL-MIB:callActiveSetupTime";
          }
        }

        leaf callActiveIndex {
          type leafref {
            path "/DIAL-CONTROL-MIB:DIAL-CONTROL-MIB/DIAL-CONTROL-MIB:callActiveTable/DIAL-CONTROL-MIB:callActiveEntry/DIAL-CONTROL-MIB:callActiveIndex";
          }
        }

        leaf callHistoryPeerAddress {
          type snmpv2-tc:DisplayString;
          description
           "The number this call was connected to. If the number is
            not available, then it will have a length of zero.";
          smiv2:max-access "read-only";
          smiv2:oid "1.3.6.1.2.1.10.21.1.4.3.1.1";
        }

        leaf callHistoryPeerSubAddress {
          type snmpv2-tc:DisplayString;
          description
           "The subaddress this call was connected to. If the subaddress
            is undefined or not available, this will be a zero length
            string.";
          smiv2:max-access "read-only";
          smiv2:oid "1.3.6.1.2.1.10.21.1.4.3.1.2";
        }

        leaf callHistoryPeerId {
          type int32 {
            range "0..2147483647";
          }
          description
           "This is the Id value of the peer table entry
            to which this call was made. If a peer table entry
            for this call does not exist, the value of this object
            will be zero.";
          smiv2:max-access "read-only";
          smiv2:oid "1.3.6.1.2.1.10.21.1.4.3.1.3";
        }

        leaf callHistoryPeerIfIndex {
          type int32 {
            range "0..2147483647";
          }
          description
           "This is the ifIndex value of the peer table entry
            to which this call was made. If a peer table entry
            for this call does not exist, the value of this object
            will be zero.";
          smiv2:max-access "read-only";
          smiv2:oid "1.3.6.1.2.1.10.21.1.4.3.1.4";
        }

        leaf callHistoryLogicalIfIndex {
          type if-mib:InterfaceIndex;
          description
           "This is the ifIndex value of the logical interface through
            which this call was made. For ISDN media, this would be
            the ifIndex of the B channel which was used for this call.";
          smiv2:max-access "read-only";
          smiv2:oid "1.3.6.1.2.1.10.21.1.4.3.1.5";
        }

        leaf callHistoryDisconnectCause {
          type binary {
            length "0..4";
          }
          description
           "The encoded network cause value associated with this call.
            
            The value of this object will depend on the interface type
            as well as on the protocol and protocol version being
            used on this interface. Some references for possible cause
            values are given below.";
          reference
           "- Bellcore SR-NWT-001953, Generic Guidelines for
            ISDN Terminal Equipment On Basic Access Interfaces,
            chapter 5.2.5.8.
            - Bellcore SR-NWT-002343, ISDN Primary Rate Interface
            Generic Guidelines for Customer Premises Equipment,
            chapter 8.2.5.8.
            - ITU-T Q.931, Appendix I.
            - ITU-T X.25, CAUSE and DIAGNOSTIC field values.
            - German Telekom FTZ 1TR6, chapter 3.2.3.4.4.4.";
          smiv2:max-access "read-only";
          smiv2:oid "1.3.6.1.2.1.10.21.1.4.3.1.6";
        }

        leaf callHistoryDisconnectText {
          type snmpv2-tc:DisplayString;
          description
           "ASCII text describing the reason for call termination.
            
            This object exists because it would be impossible for
            a management station to store all possible cause values
            for all types of interfaces. It should be used only if
            a management station is unable to decode the value of
            dialCtlPeerStatsLastDisconnectCause.";
          smiv2:max-access "read-only";
          smiv2:oid "1.3.6.1.2.1.10.21.1.4.3.1.7";
        }

        leaf callHistoryConnectTime {
          type yang:timestamp;
          description
           "The value of sysUpTime when the call was connected.";
          smiv2:max-access "read-only";
          smiv2:oid "1.3.6.1.2.1.10.21.1.4.3.1.8";
        }

        leaf callHistoryDisconnectTime {
          type yang:timestamp;
          description
           "The value of sysUpTime when the call was disconnected.";
          smiv2:max-access "read-only";
          smiv2:oid "1.3.6.1.2.1.10.21.1.4.3.1.9";
        }

        leaf callHistoryCallOrigin {
          type enumeration {
            enum "originate" {
              value "1";
            }
            enum "answer" {
              value "2";
            }
            enum "callback" {
              value "3";
            }
          }
          description
           "The call origin.";
          smiv2:max-access "read-only";
          smiv2:oid "1.3.6.1.2.1.10.21.1.4.3.1.10";
        }

        leaf callHistoryChargedUnits {
          type DIAL-CONTROL-MIB:AbsoluteCounter32;
          description
           "The number of charged units for this connection.
            For incoming calls or if charging information is
            not supplied by the switch, the value of this object
            will be zero.";
          smiv2:max-access "read-only";
          smiv2:oid "1.3.6.1.2.1.10.21.1.4.3.1.11";
        }

        leaf callHistoryInfoType {
          type enumeration {
            enum "other" {
              value "1";
            }
            enum "speech" {
              value "2";
            }
            enum "unrestrictedDigital" {
              value "3";
            }
            enum "unrestrictedDigital56" {
              value "4";
            }
            enum "restrictedDigital" {
              value "5";
            }
            enum "audio31" {
              value "6";
            }
            enum "audio7" {
              value "7";
            }
            enum "video" {
              value "8";
            }
            enum "packetSwitched" {
              value "9";
            }
            enum "fax" {
              value "10";
            }
          }
          description
           "The information type for this call.";
          smiv2:max-access "read-only";
          smiv2:oid "1.3.6.1.2.1.10.21.1.4.3.1.12";
        }

        leaf callHistoryTransmitPackets {
          type DIAL-CONTROL-MIB:AbsoluteCounter32;
          description
           "The number of packets which were transmitted while this
            call was active.";
          smiv2:max-access "read-only";
          smiv2:oid "1.3.6.1.2.1.10.21.1.4.3.1.13";
        }

        leaf callHistoryTransmitBytes {
          type DIAL-CONTROL-MIB:AbsoluteCounter32;
          description
           "The number of bytes which were transmitted while this
            call was active.";
          smiv2:max-access "read-only";
          smiv2:oid "1.3.6.1.2.1.10.21.1.4.3.1.14";
        }

        leaf callHistoryReceivePackets {
          type DIAL-CONTROL-MIB:AbsoluteCounter32;
          description
           "The number of packets which were received while this
            call was active.";
          smiv2:max-access "read-only";
          smiv2:oid "1.3.6.1.2.1.10.21.1.4.3.1.15";
        }

        leaf callHistoryReceiveBytes {
          type DIAL-CONTROL-MIB:AbsoluteCounter32;
          description
           "The number of bytes which were received while this
            call was active.";
          smiv2:max-access "read-only";
          smiv2:oid "1.3.6.1.2.1.10.21.1.4.3.1.16";
        }
      }
    }
  }

  smiv2:alias "dialCtlPeerStatsTable" {
    description
     "Statistics information for each peer entry.
      There will be one entry in this table for each entry
      in the dialCtlPeerCfgTable.";
    smiv2:oid "1.3.6.1.2.1.10.21.1.2.2";
  }

  smiv2:alias "dialCtlPeerStatsEntry" {
    description
     "Statistics information for a single Peer. This entry
      is effectively permanent, and contains information
      describing the last call attempt as well as supplying
      statistical information.";
    smiv2:oid "1.3.6.1.2.1.10.21.1.2.2.1";
  }

  augment "/DIAL-CONTROL-MIB:DIAL-CONTROL-MIB/DIAL-CONTROL-MIB:dialCtlPeerCfgTable/DIAL-CONTROL-MIB:dialCtlPeerCfgEntry" {
    description
     "Statistics information for a single Peer. This entry
      is effectively permanent, and contains information
      describing the last call attempt as well as supplying
      statistical information.";
    smiv2:oid "1.3.6.1.2.1.10.21.1.2.2.1";

    leaf dialCtlPeerStatsConnectTime {
      type DIAL-CONTROL-MIB:AbsoluteCounter32;
      units "seconds";
      description
       "Accumulated connect time to the peer since system startup.
        This is the total connect time, i.e. the connect time
        for outgoing calls plus the time for incoming calls.";
      smiv2:max-access "read-only";
      smiv2:oid "1.3.6.1.2.1.10.21.1.2.2.1.1";
    }

    leaf dialCtlPeerStatsChargedUnits {
      type DIAL-CONTROL-MIB:AbsoluteCounter32;
      description
       "The total number of charging units applying to this
        peer since system startup.
        Only the charging units applying to the local interface,
        i.e. for originated calls or for calls with 'Reverse
        charging' being active, will be counted here.";
      smiv2:max-access "read-only";
      smiv2:oid "1.3.6.1.2.1.10.21.1.2.2.1.2";
    }

    leaf dialCtlPeerStatsSuccessCalls {
      type DIAL-CONTROL-MIB:AbsoluteCounter32;
      description
       "Number of completed calls to this peer.";
      smiv2:max-access "read-only";
      smiv2:oid "1.3.6.1.2.1.10.21.1.2.2.1.3";
    }

    leaf dialCtlPeerStatsFailCalls {
      type DIAL-CONTROL-MIB:AbsoluteCounter32;
      description
       "Number of failed call attempts to this peer since system
        startup.";
      smiv2:max-access "read-only";
      smiv2:oid "1.3.6.1.2.1.10.21.1.2.2.1.4";
    }

    leaf dialCtlPeerStatsAcceptCalls {
      type DIAL-CONTROL-MIB:AbsoluteCounter32;
      description
       "Number of calls from this peer accepted since system
        startup.";
      smiv2:max-access "read-only";
      smiv2:oid "1.3.6.1.2.1.10.21.1.2.2.1.5";
    }

    leaf dialCtlPeerStatsRefuseCalls {
      type DIAL-CONTROL-MIB:AbsoluteCounter32;
      description
       "Number of calls from this peer refused since system
        startup.";
      smiv2:max-access "read-only";
      smiv2:oid "1.3.6.1.2.1.10.21.1.2.2.1.6";
    }

    leaf dialCtlPeerStatsLastDisconnectCause {
      type binary {
        length "0..4";
      }
      description
       "The encoded network cause value associated with the last
        call.
        This object will be updated whenever a call is started
        or cleared.
        The value of this object will depend on the interface type
        as well as on the protocol and protocol version being
        used on this interface. Some references for possible cause
        values are given below.";
      reference
       "- Bellcore SR-NWT-001953, Generic Guidelines for
        ISDN Terminal Equipment On Basic Access Interfaces,
        chapter 5.2.5.8.
        - Bellcore SR-NWT-002343, ISDN Primary Rate Interface
        Generic Guidelines for Customer Premises Equipment,
        chapter 8.2.5.8.
        - ITU-T Q.931, Appendix I.
        - ITU-T X.25, CAUSE and DIAGNOSTIC field values.
        - German Telekom FTZ 1TR6, chapter 3.2.3.4.4.4.";
      smiv2:max-access "read-only";
      smiv2:oid "1.3.6.1.2.1.10.21.1.2.2.1.7";
    }

    leaf dialCtlPeerStatsLastDisconnectText {
      type snmpv2-tc:DisplayString;
      description
       "ASCII text describing the reason for the last call
        termination.
        
        This object exists because it would be impossible for
        a management station to store all possible cause values
        for all types of interfaces. It should be used only if
        a management station is unable to decode the value of
        dialCtlPeerStatsLastDisconnectCause.
        
        This object will be updated whenever a call is started
        or cleared.";
      smiv2:max-access "read-only";
      smiv2:oid "1.3.6.1.2.1.10.21.1.2.2.1.8";
    }

    leaf dialCtlPeerStatsLastSetupTime {
      type yang:timestamp;
      description
       "The value of sysUpTime when the last call to this peer
        was started.
        For ISDN media, this will be the time when the setup
        message was received from or sent to the network.
        This object will be updated whenever a call is started
        or cleared.";
      smiv2:max-access "read-only";
      smiv2:oid "1.3.6.1.2.1.10.21.1.2.2.1.9";
    }
  }

  notification dialCtlPeerCallInformation {
    description
     "This trap/inform is sent to the manager whenever
      a successful call clears, or a failed call attempt
      is determined to have ultimately failed. In the
      event that call retry is active, then this is after
      all retry attempts have failed. However, only one such
      trap is sent in between successful call attempts;
      subsequent call attempts result in no trap.
      ifOperStatus will return the operational status of the
      virtual interface associated with the peer to whom
      this call was made to.";
    smiv2:oid "1.3.6.1.2.1.10.21.2.0.1";

    container object-1 {

      leaf callActiveSetupTime {
        type leafref {
          path "/DIAL-CONTROL-MIB:DIAL-CONTROL-MIB/DIAL-CONTROL-MIB:callActiveTable/DIAL-CONTROL-MIB:callActiveEntry/DIAL-CONTROL-MIB:callActiveSetupTime";
        }
      }

      leaf callActiveIndex {
        type leafref {
          path "/DIAL-CONTROL-MIB:DIAL-CONTROL-MIB/DIAL-CONTROL-MIB:callActiveTable/DIAL-CONTROL-MIB:callActiveEntry/DIAL-CONTROL-MIB:callActiveIndex";
        }
      }

      leaf callHistoryPeerId {
        type leafref {
          path "/DIAL-CONTROL-MIB:DIAL-CONTROL-MIB/DIAL-CONTROL-MIB:callHistoryTable/DIAL-CONTROL-MIB:callHistoryEntry/DIAL-CONTROL-MIB:callHistoryPeerId";
        }
      }
    }

    container object-2 {

      leaf callActiveSetupTime {
        type leafref {
          path "/DIAL-CONTROL-MIB:DIAL-CONTROL-MIB/DIAL-CONTROL-MIB:callActiveTable/DIAL-CONTROL-MIB:callActiveEntry/DIAL-CONTROL-MIB:callActiveSetupTime";
        }
      }

      leaf callActiveIndex {
        type leafref {
          path "/DIAL-CONTROL-MIB:DIAL-CONTROL-MIB/DIAL-CONTROL-MIB:callActiveTable/DIAL-CONTROL-MIB:callActiveEntry/DIAL-CONTROL-MIB:callActiveIndex";
        }
      }

      leaf callHistoryPeerIfIndex {
        type leafref {
          path "/DIAL-CONTROL-MIB:DIAL-CONTROL-MIB/DIAL-CONTROL-MIB:callHistoryTable/DIAL-CONTROL-MIB:callHistoryEntry/DIAL-CONTROL-MIB:callHistoryPeerIfIndex";
        }
      }
    }

    container object-3 {

      leaf callActiveSetupTime {
        type leafref {
          path "/DIAL-CONTROL-MIB:DIAL-CONTROL-MIB/DIAL-CONTROL-MIB:callActiveTable/DIAL-CONTROL-MIB:callActiveEntry/DIAL-CONTROL-MIB:callActiveSetupTime";
        }
      }

      leaf callActiveIndex {
        type leafref {
          path "/DIAL-CONTROL-MIB:DIAL-CONTROL-MIB/DIAL-CONTROL-MIB:callActiveTable/DIAL-CONTROL-MIB:callActiveEntry/DIAL-CONTROL-MIB:callActiveIndex";
        }
      }

      leaf callHistoryLogicalIfIndex {
        type leafref {
          path "/DIAL-CONTROL-MIB:DIAL-CONTROL-MIB/DIAL-CONTROL-MIB:callHistoryTable/DIAL-CONTROL-MIB:callHistoryEntry/DIAL-CONTROL-MIB:callHistoryLogicalIfIndex";
        }
      }
    }

    container object-4 {

      leaf ifIndex {
        type leafref {
          path "/if-mib:IF-MIB/if-mib:ifTable/if-mib:ifEntry/if-mib:ifIndex";
        }
      }

      leaf ifOperStatus {
        type leafref {
          path "/if-mib:IF-MIB/if-mib:ifTable/if-mib:ifEntry/if-mib:ifOperStatus";
        }
      }
    }

    container object-5 {

      leaf callActiveSetupTime {
        type leafref {
          path "/DIAL-CONTROL-MIB:DIAL-CONTROL-MIB/DIAL-CONTROL-MIB:callActiveTable/DIAL-CONTROL-MIB:callActiveEntry/DIAL-CONTROL-MIB:callActiveSetupTime";
        }
      }

      leaf callActiveIndex {
        type leafref {
          path "/DIAL-CONTROL-MIB:DIAL-CONTROL-MIB/DIAL-CONTROL-MIB:callActiveTable/DIAL-CONTROL-MIB:callActiveEntry/DIAL-CONTROL-MIB:callActiveIndex";
        }
      }

      leaf callHistoryPeerAddress {
        type leafref {
          path "/DIAL-CONTROL-MIB:DIAL-CONTROL-MIB/DIAL-CONTROL-MIB:callHistoryTable/DIAL-CONTROL-MIB:callHistoryEntry/DIAL-CONTROL-MIB:callHistoryPeerAddress";
        }
      }
    }

    container object-6 {

      leaf callActiveSetupTime {
        type leafref {
          path "/DIAL-CONTROL-MIB:DIAL-CONTROL-MIB/DIAL-CONTROL-MIB:callActiveTable/DIAL-CONTROL-MIB:callActiveEntry/DIAL-CONTROL-MIB:callActiveSetupTime";
        }
      }

      leaf callActiveIndex {
        type leafref {
          path "/DIAL-CONTROL-MIB:DIAL-CONTROL-MIB/DIAL-CONTROL-MIB:callActiveTable/DIAL-CONTROL-MIB:callActiveEntry/DIAL-CONTROL-MIB:callActiveIndex";
        }
      }

      leaf callHistoryPeerSubAddress {
        type leafref {
          path "/DIAL-CONTROL-MIB:DIAL-CONTROL-MIB/DIAL-CONTROL-MIB:callHistoryTable/DIAL-CONTROL-MIB:callHistoryEntry/DIAL-CONTROL-MIB:callHistoryPeerSubAddress";
        }
      }
    }

    container object-7 {

      leaf callActiveSetupTime {
        type leafref {
          path "/DIAL-CONTROL-MIB:DIAL-CONTROL-MIB/DIAL-CONTROL-MIB:callActiveTable/DIAL-CONTROL-MIB:callActiveEntry/DIAL-CONTROL-MIB:callActiveSetupTime";
        }
      }

      leaf callActiveIndex {
        type leafref {
          path "/DIAL-CONTROL-MIB:DIAL-CONTROL-MIB/DIAL-CONTROL-MIB:callActiveTable/DIAL-CONTROL-MIB:callActiveEntry/DIAL-CONTROL-MIB:callActiveIndex";
        }
      }

      leaf callHistoryDisconnectCause {
        type leafref {
          path "/DIAL-CONTROL-MIB:DIAL-CONTROL-MIB/DIAL-CONTROL-MIB:callHistoryTable/DIAL-CONTROL-MIB:callHistoryEntry/DIAL-CONTROL-MIB:callHistoryDisconnectCause";
        }
      }
    }

    container object-8 {

      leaf callActiveSetupTime {
        type leafref {
          path "/DIAL-CONTROL-MIB:DIAL-CONTROL-MIB/DIAL-CONTROL-MIB:callActiveTable/DIAL-CONTROL-MIB:callActiveEntry/DIAL-CONTROL-MIB:callActiveSetupTime";
        }
      }

      leaf callActiveIndex {
        type leafref {
          path "/DIAL-CONTROL-MIB:DIAL-CONTROL-MIB/DIAL-CONTROL-MIB:callActiveTable/DIAL-CONTROL-MIB:callActiveEntry/DIAL-CONTROL-MIB:callActiveIndex";
        }
      }

      leaf callHistoryConnectTime {
        type leafref {
          path "/DIAL-CONTROL-MIB:DIAL-CONTROL-MIB/DIAL-CONTROL-MIB:callHistoryTable/DIAL-CONTROL-MIB:callHistoryEntry/DIAL-CONTROL-MIB:callHistoryConnectTime";
        }
      }
    }

    container object-9 {

      leaf callActiveSetupTime {
        type leafref {
          path "/DIAL-CONTROL-MIB:DIAL-CONTROL-MIB/DIAL-CONTROL-MIB:callActiveTable/DIAL-CONTROL-MIB:callActiveEntry/DIAL-CONTROL-MIB:callActiveSetupTime";
        }
      }

      leaf callActiveIndex {
        type leafref {
          path "/DIAL-CONTROL-MIB:DIAL-CONTROL-MIB/DIAL-CONTROL-MIB:callActiveTable/DIAL-CONTROL-MIB:callActiveEntry/DIAL-CONTROL-MIB:callActiveIndex";
        }
      }

      leaf callHistoryDisconnectTime {
        type leafref {
          path "/DIAL-CONTROL-MIB:DIAL-CONTROL-MIB/DIAL-CONTROL-MIB:callHistoryTable/DIAL-CONTROL-MIB:callHistoryEntry/DIAL-CONTROL-MIB:callHistoryDisconnectTime";
        }
      }
    }

    container object-10 {

      leaf callActiveSetupTime {
        type leafref {
          path "/DIAL-CONTROL-MIB:DIAL-CONTROL-MIB/DIAL-CONTROL-MIB:callActiveTable/DIAL-CONTROL-MIB:callActiveEntry/DIAL-CONTROL-MIB:callActiveSetupTime";
        }
      }

      leaf callActiveIndex {
        type leafref {
          path "/DIAL-CONTROL-MIB:DIAL-CONTROL-MIB/DIAL-CONTROL-MIB:callActiveTable/DIAL-CONTROL-MIB:callActiveEntry/DIAL-CONTROL-MIB:callActiveIndex";
        }
      }

      leaf callHistoryInfoType {
        type leafref {
          path "/DIAL-CONTROL-MIB:DIAL-CONTROL-MIB/DIAL-CONTROL-MIB:callHistoryTable/DIAL-CONTROL-MIB:callHistoryEntry/DIAL-CONTROL-MIB:callHistoryInfoType";
        }
      }
    }

    container object-11 {

      leaf callActiveSetupTime {
        type leafref {
          path "/DIAL-CONTROL-MIB:DIAL-CONTROL-MIB/DIAL-CONTROL-MIB:callActiveTable/DIAL-CONTROL-MIB:callActiveEntry/DIAL-CONTROL-MIB:callActiveSetupTime";
        }
      }

      leaf callActiveIndex {
        type leafref {
          path "/DIAL-CONTROL-MIB:DIAL-CONTROL-MIB/DIAL-CONTROL-MIB:callActiveTable/DIAL-CONTROL-MIB:callActiveEntry/DIAL-CONTROL-MIB:callActiveIndex";
        }
      }

      leaf callHistoryCallOrigin {
        type leafref {
          path "/DIAL-CONTROL-MIB:DIAL-CONTROL-MIB/DIAL-CONTROL-MIB:callHistoryTable/DIAL-CONTROL-MIB:callHistoryEntry/DIAL-CONTROL-MIB:callHistoryCallOrigin";
        }
      }
    }
  }

  notification dialCtlPeerCallSetup {
    description
     "This trap/inform is sent to the manager whenever
      a call setup message is received or sent.
      ifOperStatus will return the operational status of the
      virtual interface associated with the peer to whom
      this call was made to.";
    smiv2:oid "1.3.6.1.2.1.10.21.2.0.2";

    container object-1 {

      leaf callActiveSetupTime {
        type leafref {
          path "/DIAL-CONTROL-MIB:DIAL-CONTROL-MIB/DIAL-CONTROL-MIB:callActiveTable/DIAL-CONTROL-MIB:callActiveEntry/DIAL-CONTROL-MIB:callActiveSetupTime";
        }
      }

      leaf callActiveIndex {
        type leafref {
          path "/DIAL-CONTROL-MIB:DIAL-CONTROL-MIB/DIAL-CONTROL-MIB:callActiveTable/DIAL-CONTROL-MIB:callActiveEntry/DIAL-CONTROL-MIB:callActiveIndex";
        }
      }

      leaf callActivePeerId {
        type leafref {
          path "/DIAL-CONTROL-MIB:DIAL-CONTROL-MIB/DIAL-CONTROL-MIB:callActiveTable/DIAL-CONTROL-MIB:callActiveEntry/DIAL-CONTROL-MIB:callActivePeerId";
        }
      }
    }

    container object-2 {

      leaf callActiveSetupTime {
        type leafref {
          path "/DIAL-CONTROL-MIB:DIAL-CONTROL-MIB/DIAL-CONTROL-MIB:callActiveTable/DIAL-CONTROL-MIB:callActiveEntry/DIAL-CONTROL-MIB:callActiveSetupTime";
        }
      }

      leaf callActiveIndex {
        type leafref {
          path "/DIAL-CONTROL-MIB:DIAL-CONTROL-MIB/DIAL-CONTROL-MIB:callActiveTable/DIAL-CONTROL-MIB:callActiveEntry/DIAL-CONTROL-MIB:callActiveIndex";
        }
      }

      leaf callActivePeerIfIndex {
        type leafref {
          path "/DIAL-CONTROL-MIB:DIAL-CONTROL-MIB/DIAL-CONTROL-MIB:callActiveTable/DIAL-CONTROL-MIB:callActiveEntry/DIAL-CONTROL-MIB:callActivePeerIfIndex";
        }
      }
    }

    container object-3 {

      leaf callActiveSetupTime {
        type leafref {
          path "/DIAL-CONTROL-MIB:DIAL-CONTROL-MIB/DIAL-CONTROL-MIB:callActiveTable/DIAL-CONTROL-MIB:callActiveEntry/DIAL-CONTROL-MIB:callActiveSetupTime";
        }
      }

      leaf callActiveIndex {
        type leafref {
          path "/DIAL-CONTROL-MIB:DIAL-CONTROL-MIB/DIAL-CONTROL-MIB:callActiveTable/DIAL-CONTROL-MIB:callActiveEntry/DIAL-CONTROL-MIB:callActiveIndex";
        }
      }

      leaf callActiveLogicalIfIndex {
        type leafref {
          path "/DIAL-CONTROL-MIB:DIAL-CONTROL-MIB/DIAL-CONTROL-MIB:callActiveTable/DIAL-CONTROL-MIB:callActiveEntry/DIAL-CONTROL-MIB:callActiveLogicalIfIndex";
        }
      }
    }

    container object-4 {

      leaf ifIndex {
        type leafref {
          path "/if-mib:IF-MIB/if-mib:ifTable/if-mib:ifEntry/if-mib:ifIndex";
        }
      }

      leaf ifOperStatus {
        type leafref {
          path "/if-mib:IF-MIB/if-mib:ifTable/if-mib:ifEntry/if-mib:ifOperStatus";
        }
      }
    }

    container object-5 {

      leaf callActiveSetupTime {
        type leafref {
          path "/DIAL-CONTROL-MIB:DIAL-CONTROL-MIB/DIAL-CONTROL-MIB:callActiveTable/DIAL-CONTROL-MIB:callActiveEntry/DIAL-CONTROL-MIB:callActiveSetupTime";
        }
      }

      leaf callActiveIndex {
        type leafref {
          path "/DIAL-CONTROL-MIB:DIAL-CONTROL-MIB/DIAL-CONTROL-MIB:callActiveTable/DIAL-CONTROL-MIB:callActiveEntry/DIAL-CONTROL-MIB:callActiveIndex";
        }
      }

      leaf callActivePeerAddress {
        type leafref {
          path "/DIAL-CONTROL-MIB:DIAL-CONTROL-MIB/DIAL-CONTROL-MIB:callActiveTable/DIAL-CONTROL-MIB:callActiveEntry/DIAL-CONTROL-MIB:callActivePeerAddress";
        }
      }
    }

    container object-6 {

      leaf callActiveSetupTime {
        type leafref {
          path "/DIAL-CONTROL-MIB:DIAL-CONTROL-MIB/DIAL-CONTROL-MIB:callActiveTable/DIAL-CONTROL-MIB:callActiveEntry/DIAL-CONTROL-MIB:callActiveSetupTime";
        }
      }

      leaf callActiveIndex {
        type leafref {
          path "/DIAL-CONTROL-MIB:DIAL-CONTROL-MIB/DIAL-CONTROL-MIB:callActiveTable/DIAL-CONTROL-MIB:callActiveEntry/DIAL-CONTROL-MIB:callActiveIndex";
        }
      }

      leaf callActivePeerSubAddress {
        type leafref {
          path "/DIAL-CONTROL-MIB:DIAL-CONTROL-MIB/DIAL-CONTROL-MIB:callActiveTable/DIAL-CONTROL-MIB:callActiveEntry/DIAL-CONTROL-MIB:callActivePeerSubAddress";
        }
      }
    }

    container object-7 {

      leaf callActiveSetupTime {
        type leafref {
          path "/DIAL-CONTROL-MIB:DIAL-CONTROL-MIB/DIAL-CONTROL-MIB:callActiveTable/DIAL-CONTROL-MIB:callActiveEntry/DIAL-CONTROL-MIB:callActiveSetupTime";
        }
      }

      leaf callActiveIndex {
        type leafref {
          path "/DIAL-CONTROL-MIB:DIAL-CONTROL-MIB/DIAL-CONTROL-MIB:callActiveTable/DIAL-CONTROL-MIB:callActiveEntry/DIAL-CONTROL-MIB:callActiveIndex";
        }
      }

      leaf callActiveInfoType {
        type leafref {
          path "/DIAL-CONTROL-MIB:DIAL-CONTROL-MIB/DIAL-CONTROL-MIB:callActiveTable/DIAL-CONTROL-MIB:callActiveEntry/DIAL-CONTROL-MIB:callActiveInfoType";
        }
      }
    }

    container object-8 {

      leaf callActiveSetupTime {
        type leafref {
          path "/DIAL-CONTROL-MIB:DIAL-CONTROL-MIB/DIAL-CONTROL-MIB:callActiveTable/DIAL-CONTROL-MIB:callActiveEntry/DIAL-CONTROL-MIB:callActiveSetupTime";
        }
      }

      leaf callActiveIndex {
        type leafref {
          path "/DIAL-CONTROL-MIB:DIAL-CONTROL-MIB/DIAL-CONTROL-MIB:callActiveTable/DIAL-CONTROL-MIB:callActiveEntry/DIAL-CONTROL-MIB:callActiveIndex";
        }
      }

      leaf callActiveCallOrigin {
        type leafref {
          path "/DIAL-CONTROL-MIB:DIAL-CONTROL-MIB/DIAL-CONTROL-MIB:callActiveTable/DIAL-CONTROL-MIB:callActiveEntry/DIAL-CONTROL-MIB:callActiveCallOrigin";
        }
      }
    }
  }

  smiv2:alias "dialControlMib" {
    smiv2:oid "1.3.6.1.2.1.10.21";
  }

  smiv2:alias "dialControlMibObjects" {
    smiv2:oid "1.3.6.1.2.1.10.21.1";
  }

  smiv2:alias "dialCtlConfiguration" {
    smiv2:oid "1.3.6.1.2.1.10.21.1.1";
  }

  smiv2:alias "dialCtlPeer" {
    smiv2:oid "1.3.6.1.2.1.10.21.1.2";
  }

  smiv2:alias "callActive" {
    smiv2:oid "1.3.6.1.2.1.10.21.1.3";
  }

  smiv2:alias "callHistory" {
    smiv2:oid "1.3.6.1.2.1.10.21.1.4";
  }

  smiv2:alias "dialControlMibTrapPrefix" {
    smiv2:oid "1.3.6.1.2.1.10.21.2";
  }

  smiv2:alias "dialControlMibTraps" {
    smiv2:oid "1.3.6.1.2.1.10.21.2.0";
  }

  smiv2:alias "dialControlMibConformance" {
    smiv2:oid "1.3.6.1.2.1.10.21.3";
  }

  smiv2:alias "dialControlMibCompliances" {
    smiv2:oid "1.3.6.1.2.1.10.21.3.1";
  }

  smiv2:alias "dialControlMibGroups" {
    smiv2:oid "1.3.6.1.2.1.10.21.3.2";
  }

}
