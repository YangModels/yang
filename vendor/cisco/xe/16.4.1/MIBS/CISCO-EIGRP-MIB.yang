/*
 * Generated by confdc --mib2yang-std
 * Source: mgmt/dmi/model/common/mib-source/CISCO-EIGRP-MIB.mib
 */
/*
 * This YANG module has been generated by smidump 0.5.0:
 *
 *      smidump -f yang CISCO-EIGRP-MIB
 *
 * Do not edit. Edit the source file instead!
 */

module CISCO-EIGRP-MIB {

  namespace "urn:ietf:params:xml:ns:yang:smiv2:CISCO-EIGRP-MIB";
  prefix CISCO-EIGRP-MIB;

  import IF-MIB {
    prefix "if-mib";
  }

  import INET-ADDRESS-MIB {
    prefix "inet-address";
  }

  import SNMP-FRAMEWORK-MIB {
    prefix "snmp-framework";
  }

  import ietf-yang-smiv2 {
    prefix "smiv2";
  }

  import ietf-yang-types {
    prefix "yang";
  }

  organization
   "Cisco Systems, Inc.";

  contact
   "Cisco Systems
    Customer Service
    
    Postal: 170 W Tasman Drive
            San Jose, CA  95134
            USA
    
    Tel: +1 800 553-NETS
    
    E-mail: cs-eigrp@cisco.com";

  description
   "Enhanced Interior Gateway Protocol (EIGRP) is a Cisco
    proprietary distance vector routing protocol.   It is based on
    the Diffusing Update Algorithm (DUAL), which is a method of
    finding loop-free paths through a network.   Directly
    connected routers running EIGRP form neighbor adjacencies in
    order to propagate best-path and alternate-path routing
    information for configured and learned routes.
    
    The tables defined within the MIB are closely aligned with how
    the router command-line interface for EIGRP displays
    information on EIGRP configurations, i.e., the topology table
    contains objects associated with the EIGRP topology commands,
    and the peer table contains objects associated withe EIGRP
    neighbor commands, etc.
    
    There are five main tables within this mib:
    
       EIGRP VPN table
          Contains information regarding which virtual private
          networks (VPN) are configured with EIGRP.
    
       EIGRP traffic statistics table
          Contains counter & statistcs regarding specific types of
          EIGRP packets sent and related collective information
          per VPN and per autonomous system (AS).
    
       EIGRP topology table
          Contains information regarding EIGRP routes received in
          updates and originated locally.   EIGRP sends and
          receives routing updates from adjacent routers running
          EIGRP with which it formed a peer relationship.
    
       EIGRP peer (neighbor) table
          Contains information about neighbor EIGRP routers with
          which peer adjacencies have been established.   EIGRP
          uses a Hello protocol to form neighbor relationships
          with directly connected routers also running EIGRP.
    
       EIGRP interfaces table
          Contains information and statistics on each of the
          interfaces on the router over which EIGRP has been
          configured to run.";

  revision 2004-11-16 {
    description
     "Initial version of the MIB module.";
  }

  typedef EigrpUpTimeString {
    type string;
    description
     "Specifies a timer value in days, hours, minutes,
      and seconds in ASCII format.
      
      If the up time is less than 24 hours, the number
      of days will not be reflected and the string will
      be formatted like this: 'hh:mm:ss', reflecting
      hours, minutes, and seconds.
      
      If the up time is greater than 24 hours, EIGRP is
      less precise and the minutes and seconds are not
      reflected.  Instead only the days and hours are shown
      and the string will be formatted like this: 'xxxdxxh'.";
    smiv2:display-hint "8a";
  }

  typedef EigrpVersionString {
    type string;
    description
     "Specifies an ASCII string representing the IOS major
      and minor version followed by the EIGRP major and minor
      version.";
    smiv2:display-hint "1d.1d/1d.1d";
  }


  container CISCO-EIGRP-MIB {
    config false;

    container cEigrpVpnTable {
      description
       "This table contains information on those VPN's configured
        to run EIGRP.  The VPN creation on a router is independent
        of the routing protocol to be used over it.   A VPN is
        given a name and has a dedicated routing table associated
        with it.  This routing table is identified internally
        by a unique integer value.";
      smiv2:oid "1.3.6.1.4.1.9.9.449.1.1.1";

      list cEigrpVpnEntry {
        key "cEigrpVpnId";
        description
         "Information relating to a single VPN which is configured
          to run EIGRP.";
        smiv2:oid "1.3.6.1.4.1.9.9.449.1.1.1.1";

        leaf cEigrpVpnId {
          type uint32;
          description
           "The unique VPN identifier.  This is a unique integer
            relative to all other VPN's defined on the router.  It
            also identifies internally the routing table instance.";
          smiv2:max-access "not-accessible";
          smiv2:oid "1.3.6.1.4.1.9.9.449.1.1.1.1.1";
        }

        leaf cEigrpVpnName {
          type snmp-framework:SnmpAdminString;
          description
           "The name given to the VPN.";
          smiv2:max-access "read-only";
          smiv2:oid "1.3.6.1.4.1.9.9.449.1.1.1.1.2";
        }
      }
    }

    container cEigrpTraffStatsTable {
      description
       "Table of EIGRP traffic statistics and information
        associated with all EIGRP autonomous systems.";
      smiv2:oid "1.3.6.1.4.1.9.9.449.1.2.1";

      list cEigrpTraffStatsEntry {
        key "cEigrpVpnId cEigrpAsNumber";
        description
         "The set of statistics and information for a single EIGRP
          Autonomous System.";
        smiv2:oid "1.3.6.1.4.1.9.9.449.1.2.1.1";

        leaf cEigrpVpnId {
          type leafref {
            path "/CISCO-EIGRP-MIB:CISCO-EIGRP-MIB/CISCO-EIGRP-MIB:cEigrpVpnTable/CISCO-EIGRP-MIB:cEigrpVpnEntry/CISCO-EIGRP-MIB:cEigrpVpnId";
          }
        }

        leaf cEigrpAsNumber {
          type uint32;
          description
           "The Autonomous System number which is unique integer
            per VPN.";
          smiv2:max-access "not-accessible";
          smiv2:oid "1.3.6.1.4.1.9.9.449.1.2.1.1.1";
        }

        leaf cEigrpNbrCount {
          type uint32;
          description
           "The total number of live EIGRP neighbors formed on all
            interfaces whose IP addresses fall under networks configured
            in the EIGRP AS.";
          smiv2:max-access "read-only";
          smiv2:oid "1.3.6.1.4.1.9.9.449.1.2.1.1.2";
        }

        leaf cEigrpHellosSent {
          type yang:counter32;
          description
           "The total number Hello packets that have been sent to all
            EIGRP neighbors formed on all interfaces whose IP addresses
            fall under networks configured for the EIGRP AS.";
          smiv2:max-access "read-only";
          smiv2:oid "1.3.6.1.4.1.9.9.449.1.2.1.1.3";
        }

        leaf cEigrpHellosRcvd {
          type yang:counter32;
          description
           "The total number Hello packets that have been received
            from all EIGRP neighbors formed on all interfaces whose IP
            addresses fall under networks configured for the
            EIGRP AS.";
          smiv2:max-access "read-only";
          smiv2:oid "1.3.6.1.4.1.9.9.449.1.2.1.1.4";
        }

        leaf cEigrpUpdatesSent {
          type yang:counter32;
          description
           "The total number routing update packets that have been
            sent to all EIGRP neighbors formed on all interfaces whose
            IP addresses fall under networks configured for the
            EIGRP AS.";
          smiv2:max-access "read-only";
          smiv2:oid "1.3.6.1.4.1.9.9.449.1.2.1.1.5";
        }

        leaf cEigrpUpdatesRcvd {
          type yang:counter32;
          description
           "The total number routing update packets that have been
            received from all EIGRP neighbors formed on all interfaces
            whose IP addresses fall under networks configured for the
            EIGRP AS.";
          smiv2:max-access "read-only";
          smiv2:oid "1.3.6.1.4.1.9.9.449.1.2.1.1.6";
        }

        leaf cEigrpQueriesSent {
          type yang:counter32;
          description
           "The total number alternate route query packets that have
            been sent to all EIGRP neighbors formed on all interfaces
            whose IP addresses fall under networks configured for the
            EIGRP AS.";
          smiv2:max-access "read-only";
          smiv2:oid "1.3.6.1.4.1.9.9.449.1.2.1.1.7";
        }

        leaf cEigrpQueriesRcvd {
          type yang:counter32;
          description
           "The total number alternate route query packets that
            have been received from all EIGRP neighbors formed on
            all interfaces whose IP addresses fall under networks
            configured for the EIGRP AS.";
          smiv2:max-access "read-only";
          smiv2:oid "1.3.6.1.4.1.9.9.449.1.2.1.1.8";
        }

        leaf cEigrpRepliesSent {
          type yang:counter32;
          description
           "The total number query reply packets that have been sent
            to all EIGRP neighbors formed on all interfaces whose IP
            addresses fall under networks configured for the
            EIGRP AS.";
          smiv2:max-access "read-only";
          smiv2:oid "1.3.6.1.4.1.9.9.449.1.2.1.1.9";
        }

        leaf cEigrpRepliesRcvd {
          type yang:counter32;
          description
           "The total number query reply packets that have been
            received from all EIGRP neighbors formed on all interfaces
            whose IP addresses fall under networks configured for the
            EIGRP AS.";
          smiv2:max-access "read-only";
          smiv2:oid "1.3.6.1.4.1.9.9.449.1.2.1.1.10";
        }

        leaf cEigrpAcksSent {
          type yang:counter32;
          description
           "The total number packet acknowledgements that have been
            sent to all EIGRP neighbors formed on all interfaces whose
            IP addresses fall under networks configured for the
            EIGRP AS.";
          smiv2:max-access "read-only";
          smiv2:oid "1.3.6.1.4.1.9.9.449.1.2.1.1.11";
        }

        leaf cEigrpAcksRcvd {
          type yang:counter32;
          description
           "The total number packet acknowledgements that have been
            received from all EIGRP neighbors formed on all interfaces
            whose IP addresses fall under networks configured for the
            EIGRP AS.";
          smiv2:max-access "read-only";
          smiv2:oid "1.3.6.1.4.1.9.9.449.1.2.1.1.12";
        }

        leaf cEigrpInputQHighMark {
          type uint32;
          description
           "The highest number of EIGRP packets in the input queue
            waiting to be processed internally addressed to this
            AS.";
          smiv2:max-access "read-only";
          smiv2:oid "1.3.6.1.4.1.9.9.449.1.2.1.1.13";
        }

        leaf cEigrpInputQDrops {
          type yang:counter32;
          description
           "The number of EIGRP packets dropped from the input
            queue due to it being full within the AS.";
          smiv2:max-access "read-only";
          smiv2:oid "1.3.6.1.4.1.9.9.449.1.2.1.1.14";
        }

        leaf cEigrpSiaQueriesSent {
          type yang:counter32;
          description
           "The total number of Stuck-In-Active (SIA) query packets
            sent to all EIGRP neighbors formed on all interfaces whose
            IP addresses fall under networks configured for the
            EIGRP AS.";
          smiv2:max-access "read-only";
          smiv2:oid "1.3.6.1.4.1.9.9.449.1.2.1.1.15";
        }

        leaf cEigrpSiaQueriesRcvd {
          type yang:counter32;
          description
           "The total number of Stuck-In-Active (SIA) query packets
            received from all EIGRP neighbors formed on all interfaces
            whose IP addresses fall under networks configured for the
            EIGRP AS.";
          smiv2:max-access "read-only";
          smiv2:oid "1.3.6.1.4.1.9.9.449.1.2.1.1.16";
        }

        leaf cEigrpAsRouterIdType {
          type inet-address:InetAddressType;
          description
           "The format of the router-id configured or automatically
            selected for the EIGRP AS.";
          smiv2:max-access "read-only";
          smiv2:oid "1.3.6.1.4.1.9.9.449.1.2.1.1.17";
        }

        leaf cEigrpAsRouterId {
          type inet-address:InetAddress;
          description
           "The router-id configured or automatically selected for the
            EIGRP AS.   Each EIGRP routing process has a unique
            router-id selected from each autonomous system configured.
            The format is governed by object cEigrpAsRouterIdType.";
          smiv2:max-access "read-only";
          smiv2:oid "1.3.6.1.4.1.9.9.449.1.2.1.1.18";
        }

        leaf cEigrpTopoRoutes {
          type yang:counter32;
          description
           "The total number of EIGRP derived routes currently existing
            in the topology table for the AS.";
          smiv2:max-access "read-only";
          smiv2:oid "1.3.6.1.4.1.9.9.449.1.2.1.1.19";
        }

        leaf cEigrpHeadSerial {
          type yang:counter64;
          description
           "Routes in a topology table for an AS are assigned serial
            numbers and are sequenced internally as they are inserted
            and deleted.   The serial number of the first route in
            that internal sequence is called the head serial number.
            Each AS has its own topology table, and its own serial
            number space, each of which begins with the value 1.
            A serial number of zero implies that there are no routes
            in the topology.";
          smiv2:max-access "read-only";
          smiv2:oid "1.3.6.1.4.1.9.9.449.1.2.1.1.20";
        }

        leaf cEigrpNextSerial {
          type yang:counter64;
          description
           "The serial number that would be assigned to the next new
            or changed route in the topology table for the AS.";
          smiv2:max-access "read-only";
          smiv2:oid "1.3.6.1.4.1.9.9.449.1.2.1.1.21";
        }

        leaf cEigrpXmitPendReplies {
          type uint32;
          description
           "When alternate route query packets are sent to adjacent
            EIGRP peers in an AS, replies are expected.   This object
            is the total number of outstanding replies expected to
            queries that have been sent to peers in the current AS.
            It remains at zero most of the time until an EIGRP route
            becomes active.";
          smiv2:max-access "read-only";
          smiv2:oid "1.3.6.1.4.1.9.9.449.1.2.1.1.22";
        }

        leaf cEigrpXmitDummies {
          type uint32;
          description
           "A dummy is a temporary internal entity used as a place
            holder in the topology table for an AS. They are not
            transmitted in routing updates.  This is the total
            number currently in existence associated with the AS.";
          smiv2:max-access "read-only";
          smiv2:oid "1.3.6.1.4.1.9.9.449.1.2.1.1.23";
        }
      }
    }

    container cEigrpTopoTable {
      description
       "The table of EIGRP routes and their associated
        attributes for an Autonomous System (AS) configured
        in a VPN is called a topology table.  All route entries in
        the topology table will be indexed by IP network type,
        IP network number and network mask (prefix) size.";
      smiv2:oid "1.3.6.1.4.1.9.9.449.1.3.1";

      list cEigrpTopoEntry {
        key "cEigrpVpnId cEigrpAsNumber cEigrpDestNetType cEigrpDestNet cEigrpDestNetPrefixLen";
        description
         "The entry for a single EIGRP topology table in the given
          AS.";
        smiv2:oid "1.3.6.1.4.1.9.9.449.1.3.1.1";

        leaf cEigrpVpnId {
          type leafref {
            path "/CISCO-EIGRP-MIB:CISCO-EIGRP-MIB/CISCO-EIGRP-MIB:cEigrpVpnTable/CISCO-EIGRP-MIB:cEigrpVpnEntry/CISCO-EIGRP-MIB:cEigrpVpnId";
          }
        }

        leaf cEigrpAsNumber {
          type leafref {
            path "/CISCO-EIGRP-MIB:CISCO-EIGRP-MIB/CISCO-EIGRP-MIB:cEigrpTraffStatsTable/CISCO-EIGRP-MIB:cEigrpTraffStatsEntry/CISCO-EIGRP-MIB:cEigrpAsNumber";
          }
        }

        leaf cEigrpDestNetType {
          type inet-address:InetAddressType;
          description
           "The format of the destination IP network number for
            a single route in the topology table in the AS specified
            in cEigrpDestNet.";
          smiv2:max-access "not-accessible";
          smiv2:oid "1.3.6.1.4.1.9.9.449.1.3.1.1.1";
        }

        leaf cEigrpDestNet {
          type inet-address:InetAddress;
          description
           "The destination IP network number for a single route in
            the topology table in the AS.  The format is governed
            by object cEigrpDestNetType.";
          smiv2:max-access "not-accessible";
          smiv2:oid "1.3.6.1.4.1.9.9.449.1.3.1.1.2";
        }

        leaf cEigrpDestNetPrefixLen {
          type inet-address:InetAddressPrefixLength;
          description
           "The prefix length associated with the destination IP
            network address for a single route in the topology
            table in the AS.  The format is governed by the object
            cEigrpDestNetType.";
          smiv2:max-access "not-accessible";
          smiv2:oid "1.3.6.1.4.1.9.9.449.1.3.1.1.4";
        }

        leaf cEigrpActive {
          type boolean;
          description
           "A value of true(1) indicates the route to the
            destination network has failed and an active (query)
            search for an alternative path is in progress.  A value
            of false(2) indicates the route is stable (passive).";
          smiv2:max-access "read-only";
          smiv2:oid "1.3.6.1.4.1.9.9.449.1.3.1.1.5";
        }

        leaf cEigrpStuckInActive {
          type boolean;
          description
           "A value of true(1) indicates that that this route which is
            in active state (cEigrpActive = true(1)) has not received
            any replies to queries for alternate paths, and a second
            EIGRP route query, called a stuck-in-active query, has
            now been sent.";
          smiv2:max-access "read-only";
          smiv2:oid "1.3.6.1.4.1.9.9.449.1.3.1.1.6";
        }

        leaf cEigrpDestSuccessors {
          type uint32;
          description
           "A successor is the next routing hop for a path to the
            destination IP network number for a single route in the
            topology table in the AS.  There can be several
            potential successors if there are multiple paths to the
            destination.   This is the total number of successors for
            a topology entry.";
          smiv2:max-access "read-only";
          smiv2:oid "1.3.6.1.4.1.9.9.449.1.3.1.1.7";
        }

        leaf cEigrpFdistance {
          type uint32;
          description
           "The feasibility (best) distance is the minimum distance
            from this router to the destination IP network in
            this topology entry.  The feasibility distance is
            used in determining the best successor for a path to the
            destination network.";
          smiv2:max-access "read-only";
          smiv2:oid "1.3.6.1.4.1.9.9.449.1.3.1.1.8";
        }

        leaf cEigrpRouteOriginType {
          type snmp-framework:SnmpAdminString;
          description
           "This is a text string describing the internal origin
            of the EIGRP route represented by the topology entry.";
          smiv2:max-access "read-only";
          smiv2:oid "1.3.6.1.4.1.9.9.449.1.3.1.1.9";
        }

        leaf cEigrpRouteOriginAddrType {
          type inet-address:InetAddressType;
          description
           "The format of the IP address defined as the origin of
            this topology route entry.";
          smiv2:max-access "read-only";
          smiv2:oid "1.3.6.1.4.1.9.9.449.1.3.1.1.10";
        }

        leaf cEigrpRouteOriginAddr {
          type inet-address:InetAddress;
          description
           "If the origin of the topology route entry is external
            to this router, then this object is the IP address
            of the router from which it originated.  The format 
            is governed by object cEigrpRouteOriginAddrType.";
          smiv2:max-access "read-only";
          smiv2:oid "1.3.6.1.4.1.9.9.449.1.3.1.1.11";
        }

        leaf cEigrpNextHopAddressType {
          type inet-address:InetAddressType;
          description
           "The format of the next hop IP address for the route
            represented by the topology entry.";
          smiv2:max-access "read-only";
          smiv2:oid "1.3.6.1.4.1.9.9.449.1.3.1.1.12";
        }

        leaf cEigrpNextHopAddress {
          type inet-address:InetAddress;
          description
           "This is the next hop IP address for the route represented
            by the topology entry.   The next hop is where
            network traffic will be routed to in order to reach
            the destination network for this topology entry.  The
            format is governed by cEigrpNextHopAddressType.";
          smiv2:max-access "read-only";
          smiv2:oid "1.3.6.1.4.1.9.9.449.1.3.1.1.13";
        }

        leaf cEigrpNextHopInterface {
          type snmp-framework:SnmpAdminString;
          description
           "The interface through which the next hop IP address
            is reached to send network traffic to the destination
            network represented by the topology entry.";
          smiv2:max-access "read-only";
          smiv2:oid "1.3.6.1.4.1.9.9.449.1.3.1.1.14";
        }

        leaf cEigrpDistance {
          type uint32;
          description
           "The computed distance to the destination network entry
            from this router.";
          smiv2:max-access "read-only";
          smiv2:oid "1.3.6.1.4.1.9.9.449.1.3.1.1.15";
        }

        leaf cEigrpReportDistance {
          type uint32;
          description
           "The computed distance to the destination network in the
            topology entry reported to this router by the originator
            of this route.";
          smiv2:max-access "read-only";
          smiv2:oid "1.3.6.1.4.1.9.9.449.1.3.1.1.16";
        }
      }
    }

    container cEigrpPeerTable {
      description
       "The table of established EIGRP peers (neighbors) in the
        selected autonomous system.   Peers are indexed by their
        unique internal handle id, as well as the AS number and
        VPN id.   The peer entry is removed from the table if
        the peer is declared down.";
      smiv2:oid "1.3.6.1.4.1.9.9.449.1.4.1";

      list cEigrpPeerEntry {
        key "cEigrpVpnId cEigrpAsNumber cEigrpHandle";
        description
         "Statistics and operational parameters for a single peer
          in the AS.";
        smiv2:oid "1.3.6.1.4.1.9.9.449.1.4.1.1";

        leaf cEigrpVpnId {
          type leafref {
            path "/CISCO-EIGRP-MIB:CISCO-EIGRP-MIB/CISCO-EIGRP-MIB:cEigrpVpnTable/CISCO-EIGRP-MIB:cEigrpVpnEntry/CISCO-EIGRP-MIB:cEigrpVpnId";
          }
        }

        leaf cEigrpAsNumber {
          type leafref {
            path "/CISCO-EIGRP-MIB:CISCO-EIGRP-MIB/CISCO-EIGRP-MIB:cEigrpTraffStatsTable/CISCO-EIGRP-MIB:cEigrpTraffStatsEntry/CISCO-EIGRP-MIB:cEigrpAsNumber";
          }
        }

        leaf cEigrpHandle {
          type uint32;
          description
           "The unique internal identifier for the peer in the AS.
            This is a unique value among peer entries in a selected
            table.";
          smiv2:max-access "not-accessible";
          smiv2:oid "1.3.6.1.4.1.9.9.449.1.4.1.1.1";
        }

        leaf cEigrpPeerAddrType {
          type inet-address:InetAddressType;
          description
           "The format of the remote source IP address used by the
            peer to establish the EIGRP adjacency with this router.";
          smiv2:max-access "read-only";
          smiv2:oid "1.3.6.1.4.1.9.9.449.1.4.1.1.2";
        }

        leaf cEigrpPeerAddr {
          type inet-address:InetAddress;
          description
           "The source IP address used by the peer to establish the
            EIGRP adjacency with this router.  The format is
            governed by object cEigrpPeerAddrType.";
          smiv2:max-access "read-only";
          smiv2:oid "1.3.6.1.4.1.9.9.449.1.4.1.1.3";
        }

        leaf cEigrpPeerIfIndex {
          type if-mib:InterfaceIndexOrZero;
          description
           "The ifIndex of the interface on this router through
            which this peer can be reached.";
          smiv2:max-access "read-only";
          smiv2:oid "1.3.6.1.4.1.9.9.449.1.4.1.1.4";
        }

        leaf cEigrpHoldTime {
          type uint32;
          units "seconds";
          description
           "The count-down timer indicating how much time must
            pass without receiving a hello packet from this
            EIGRP peer before this router declares the peer down.
            A peer declared as down is removed from the table and
            is no longer visible.";
          smiv2:max-access "read-only";
          smiv2:oid "1.3.6.1.4.1.9.9.449.1.4.1.1.5";
        }

        leaf cEigrpUpTime {
          type CISCO-EIGRP-MIB:EigrpUpTimeString;
          description
           "The elapsed time since the EIGRP adjacency was first
            established with the peer.";
          smiv2:max-access "read-only";
          smiv2:oid "1.3.6.1.4.1.9.9.449.1.4.1.1.6";
        }

        leaf cEigrpSrtt {
          type uint32;
          units "milliseconds";
          description
           "The computed smooth round trip time for packets to and
            from the peer.";
          smiv2:max-access "read-only";
          smiv2:oid "1.3.6.1.4.1.9.9.449.1.4.1.1.7";
        }

        leaf cEigrpRto {
          type uint32;
          units "milliseconds";
          description
           "The computed retransmission timeout for the peer.
            This value is computed over time as packets are sent to
            the peer and acknowledgements are received from it,
            and is the amount of time to wait before resending
            a packet from the retransmission queue to the peer
            when an expected acknowledgement has not been received.";
          smiv2:max-access "read-only";
          smiv2:oid "1.3.6.1.4.1.9.9.449.1.4.1.1.8";
        }

        leaf cEigrpPktsEnqueued {
          type uint32;
          description
           "The number of any EIGRP packets currently enqueued
            waiting to be sent to this peer.";
          smiv2:max-access "read-only";
          smiv2:oid "1.3.6.1.4.1.9.9.449.1.4.1.1.9";
        }

        leaf cEigrpLastSeq {
          type uint32;
          description
           "All transmitted EIGRP packets have a sequence number
            assigned. This is the sequence number of the last EIGRP
            packet sent to this peer.";
          smiv2:max-access "read-only";
          smiv2:oid "1.3.6.1.4.1.9.9.449.1.4.1.1.10";
        }

        leaf cEigrpVersion {
          type CISCO-EIGRP-MIB:EigrpVersionString;
          description
           "The EIGRP version information reported by the remote
            peer.";
          smiv2:max-access "read-only";
          smiv2:oid "1.3.6.1.4.1.9.9.449.1.4.1.1.11";
        }

        leaf cEigrpRetrans {
          type yang:counter32;
          description
           "The cumulative number of retransmissions to this peer
            during the period that the peer adjacency has remained
            up.";
          smiv2:max-access "read-only";
          smiv2:oid "1.3.6.1.4.1.9.9.449.1.4.1.1.12";
        }

        leaf cEigrpRetries {
          type uint32;
          description
           "The number of times the current unacknowledged packet
            has been retried, i.e. resent to this peer to be
            acknowledged.";
          smiv2:max-access "read-only";
          smiv2:oid "1.3.6.1.4.1.9.9.449.1.4.1.1.13";
        }
      }
    }

    container cEigrpInterfaceTable {
      description
       "The table of interfaces over which EIGRP is running, and
        their associated statistics.   This table is independent
        of whether any peer adjacencies have been formed over
        the interfaces or not.   Interfaces running EIGRP are
        determined by whether their assigned IP addresses fall
        within configured EIGRP network statements.";
      smiv2:oid "1.3.6.1.4.1.9.9.449.1.5.1";

      list cEigrpInterfaceEntry {
        key "cEigrpVpnId cEigrpAsNumber ifIndex";
        description
         "Information for a single interface running EIGRP in the
          AS and VPN.";
        smiv2:oid "1.3.6.1.4.1.9.9.449.1.5.1.1";

        leaf cEigrpVpnId {
          type leafref {
            path "/CISCO-EIGRP-MIB:CISCO-EIGRP-MIB/CISCO-EIGRP-MIB:cEigrpVpnTable/CISCO-EIGRP-MIB:cEigrpVpnEntry/CISCO-EIGRP-MIB:cEigrpVpnId";
          }
        }

        leaf cEigrpAsNumber {
          type leafref {
            path "/CISCO-EIGRP-MIB:CISCO-EIGRP-MIB/CISCO-EIGRP-MIB:cEigrpTraffStatsTable/CISCO-EIGRP-MIB:cEigrpTraffStatsEntry/CISCO-EIGRP-MIB:cEigrpAsNumber";
          }
        }

        leaf ifIndex {
          type leafref {
            path "/if-mib:IF-MIB/if-mib:ifTable/if-mib:ifEntry/if-mib:ifIndex";
          }
        }

        leaf cEigrpPeerCount {
          type yang:gauge32;
          description
           "The number of EIGRP adjacencies currently formed with
            peers reached through this interface.";
          smiv2:max-access "read-only";
          smiv2:oid "1.3.6.1.4.1.9.9.449.1.5.1.1.3";
        }

        leaf cEigrpXmitReliableQ {
          type yang:gauge32;
          description
           "The number of EIGRP packets currently waiting in the
            reliable transport (acknowledgement-required) 
            transmission queue to be sent to a peer.";
          smiv2:max-access "read-only";
          smiv2:oid "1.3.6.1.4.1.9.9.449.1.5.1.1.4";
        }

        leaf cEigrpXmitUnreliableQ {
          type yang:gauge32;
          description
           "The number EIGRP of packets currently waiting in
            the unreliable transport (no acknowledgement required)
            transmission queue.";
          smiv2:max-access "read-only";
          smiv2:oid "1.3.6.1.4.1.9.9.449.1.5.1.1.5";
        }

        leaf cEigrpMeanSrtt {
          type uint32;
          units "milliseconds";
          description
           "The average of all the computed smooth round trip time
            values for a packet to and from all peers established on
            this interface.";
          smiv2:max-access "read-only";
          smiv2:oid "1.3.6.1.4.1.9.9.449.1.5.1.1.6";
        }

        leaf cEigrpPacingReliable {
          type uint32;
          units "milliseconds";
          description
           "The configured time interval between EIGRP packet
            transmissions on the interface when the reliable transport
            method is used.";
          smiv2:max-access "read-only";
          smiv2:oid "1.3.6.1.4.1.9.9.449.1.5.1.1.7";
        }

        leaf cEigrpPacingUnreliable {
          type uint32;
          units "milliseconds";
          description
           "The configured time interval between EIGRP packet
            transmissions on the interface when the unreliable
            transport method is used.";
          smiv2:max-access "read-only";
          smiv2:oid "1.3.6.1.4.1.9.9.449.1.5.1.1.8";
        }

        leaf cEigrpMFlowTimer {
          type uint32;
          units "milliseconds";
          description
           "The configured multicast flow control timer value for
            this interface.";
          smiv2:max-access "read-only";
          smiv2:oid "1.3.6.1.4.1.9.9.449.1.5.1.1.9";
        }

        leaf cEigrpPendingRoutes {
          type yang:gauge32;
          description
           "The number of queued EIGRP routing updates awaiting
            transmission on this interface.";
          smiv2:max-access "read-only";
          smiv2:oid "1.3.6.1.4.1.9.9.449.1.5.1.1.10";
        }

        leaf cEigrpHelloInterval {
          type uint32;
          units "seconds";
          description
           "The configured time interval between Hello packet
            transmissions for this interface.";
          smiv2:max-access "read-only";
          smiv2:oid "1.3.6.1.4.1.9.9.449.1.5.1.1.11";
        }

        leaf cEigrpXmitNextSerial {
          type yang:counter64;
          description
           "The serial number of the next EIGRP packet that is to
            be queued for transmission on this interface.";
          smiv2:max-access "read-only";
          smiv2:oid "1.3.6.1.4.1.9.9.449.1.5.1.1.12";
        }

        leaf cEigrpUMcasts {
          type yang:counter32;
          description
           "The total number of unreliable (no acknowledgement
            required) EIGRP multicast packets sent on this
            interface.";
          smiv2:max-access "read-only";
          smiv2:oid "1.3.6.1.4.1.9.9.449.1.5.1.1.13";
        }

        leaf cEigrpRMcasts {
          type yang:counter32;
          description
           "The total number of reliable (acknowledgement required)
            EIGRP multicast packets sent on this interface.";
          smiv2:max-access "read-only";
          smiv2:oid "1.3.6.1.4.1.9.9.449.1.5.1.1.14";
        }

        leaf cEigrpUUcasts {
          type yang:counter32;
          description
           "The total number of unreliable (no acknowledgement
            required) EIGRP unicast packets sent on this
            interface.";
          smiv2:max-access "read-only";
          smiv2:oid "1.3.6.1.4.1.9.9.449.1.5.1.1.15";
        }

        leaf cEigrpRUcasts {
          type yang:counter32;
          description
           "The total number of reliable (acknowledgement required)
            unicast packets sent on this interface.";
          smiv2:max-access "read-only";
          smiv2:oid "1.3.6.1.4.1.9.9.449.1.5.1.1.16";
        }

        leaf cEigrpMcastExcepts {
          type yang:counter32;
          description
           "The total number of EIGRP multicast exception
            transmissions that have occurred on this interface.";
          smiv2:max-access "read-only";
          smiv2:oid "1.3.6.1.4.1.9.9.449.1.5.1.1.17";
        }

        leaf cEigrpCRpkts {
          type yang:counter32;
          description
           "The total number EIGRP Conditional-Receive packets sent on
            this interface.";
          smiv2:max-access "read-only";
          smiv2:oid "1.3.6.1.4.1.9.9.449.1.5.1.1.18";
        }

        leaf cEigrpAcksSuppressed {
          type yang:counter32;
          description
           "The total number of individual EIGRP acknowledgement
            packets that have been suppressed and combined in
            an already enqueued outbound reliable packet on this
            interface.";
          smiv2:max-access "read-only";
          smiv2:oid "1.3.6.1.4.1.9.9.449.1.5.1.1.19";
        }

        leaf cEigrpRetransSent {
          type yang:counter32;
          description
           "The total number EIGRP packet retransmissions sent on
            the interface.";
          smiv2:max-access "read-only";
          smiv2:oid "1.3.6.1.4.1.9.9.449.1.5.1.1.20";
        }

        leaf cEigrpOOSrvcd {
          type yang:counter32;
          description
           "The total number of out-of-sequence EIGRP packets
            received.";
          smiv2:max-access "read-only";
          smiv2:oid "1.3.6.1.4.1.9.9.449.1.5.1.1.21";
        }

        leaf cEigrpAuthMode {
          type enumeration {
            enum "none" {
              value "1";
            }
            enum "md5" {
              value "2";
            }
          }
          description
           "The EIGRP authentication mode of the interface.
            none  :  no authentication enabled on the interface
            md5   :  MD5 authentication enabled on the interface";
          smiv2:max-access "read-only";
          smiv2:oid "1.3.6.1.4.1.9.9.449.1.5.1.1.22";
        }

        leaf cEigrpAuthKeyChain {
          type snmp-framework:SnmpAdminString;
          description
           "The name of the authentication key-chain configured
            on this interface.   The key-chain is a reference to
            which set of secret keys are to be accessed in order
            to determine which secret key string to use.  The key
            chain name is not the secret key string password and
            can also be used in other routing protocols, such
            as RIP and ISIS.";
          smiv2:max-access "read-only";
          smiv2:oid "1.3.6.1.4.1.9.9.449.1.5.1.1.23";
        }
      }
    }
  }

  notification cEigrpAuthFailureEvent {
    description
     "This notification is sent when EIGRP MD5 authentication
      is enabled on any interface and peer adjacencies are
      formed, and any adjacencies go down as a result of an
      authentication failure.";
    smiv2:oid "1.3.6.1.4.1.9.9.449.0.1";

    container object-1 {

      leaf cEigrpVpnId {
        type leafref {
          path "/CISCO-EIGRP-MIB:CISCO-EIGRP-MIB/CISCO-EIGRP-MIB:cEigrpVpnTable/CISCO-EIGRP-MIB:cEigrpVpnEntry/CISCO-EIGRP-MIB:cEigrpVpnId";
        }
      }

      leaf cEigrpAsNumber {
        type leafref {
          path "/CISCO-EIGRP-MIB:CISCO-EIGRP-MIB/CISCO-EIGRP-MIB:cEigrpTraffStatsTable/CISCO-EIGRP-MIB:cEigrpTraffStatsEntry/CISCO-EIGRP-MIB:cEigrpAsNumber";
        }
      }

      leaf cEigrpHandle {
        type leafref {
          path "/CISCO-EIGRP-MIB:CISCO-EIGRP-MIB/CISCO-EIGRP-MIB:cEigrpPeerTable/CISCO-EIGRP-MIB:cEigrpPeerEntry/CISCO-EIGRP-MIB:cEigrpHandle";
        }
      }

      leaf cEigrpPeerAddrType {
        type leafref {
          path "/CISCO-EIGRP-MIB:CISCO-EIGRP-MIB/CISCO-EIGRP-MIB:cEigrpPeerTable/CISCO-EIGRP-MIB:cEigrpPeerEntry/CISCO-EIGRP-MIB:cEigrpPeerAddrType";
        }
      }
    }

    container object-2 {

      leaf cEigrpVpnId {
        type leafref {
          path "/CISCO-EIGRP-MIB:CISCO-EIGRP-MIB/CISCO-EIGRP-MIB:cEigrpVpnTable/CISCO-EIGRP-MIB:cEigrpVpnEntry/CISCO-EIGRP-MIB:cEigrpVpnId";
        }
      }

      leaf cEigrpAsNumber {
        type leafref {
          path "/CISCO-EIGRP-MIB:CISCO-EIGRP-MIB/CISCO-EIGRP-MIB:cEigrpTraffStatsTable/CISCO-EIGRP-MIB:cEigrpTraffStatsEntry/CISCO-EIGRP-MIB:cEigrpAsNumber";
        }
      }

      leaf cEigrpHandle {
        type leafref {
          path "/CISCO-EIGRP-MIB:CISCO-EIGRP-MIB/CISCO-EIGRP-MIB:cEigrpPeerTable/CISCO-EIGRP-MIB:cEigrpPeerEntry/CISCO-EIGRP-MIB:cEigrpHandle";
        }
      }

      leaf cEigrpPeerAddr {
        type leafref {
          path "/CISCO-EIGRP-MIB:CISCO-EIGRP-MIB/CISCO-EIGRP-MIB:cEigrpPeerTable/CISCO-EIGRP-MIB:cEigrpPeerEntry/CISCO-EIGRP-MIB:cEigrpPeerAddr";
        }
      }
    }
  }

  notification cEigrpRouteStuckInActive {
    description
     "This notification is sent when a route in the topology
      table is stuck in an active state.  During the query
      phase for a new route to a destination network, a route
      is described as being in the active state if when an
      alternate path is actively being sought, no replies are
      received to normal queries or stuck-in-active queries.";
    smiv2:oid "1.3.6.1.4.1.9.9.449.0.2";

    container object-1 {

      leaf cEigrpVpnId {
        type leafref {
          path "/CISCO-EIGRP-MIB:CISCO-EIGRP-MIB/CISCO-EIGRP-MIB:cEigrpVpnTable/CISCO-EIGRP-MIB:cEigrpVpnEntry/CISCO-EIGRP-MIB:cEigrpVpnId";
        }
      }

      leaf cEigrpAsNumber {
        type leafref {
          path "/CISCO-EIGRP-MIB:CISCO-EIGRP-MIB/CISCO-EIGRP-MIB:cEigrpTraffStatsTable/CISCO-EIGRP-MIB:cEigrpTraffStatsEntry/CISCO-EIGRP-MIB:cEigrpAsNumber";
        }
      }

      leaf cEigrpHandle {
        type leafref {
          path "/CISCO-EIGRP-MIB:CISCO-EIGRP-MIB/CISCO-EIGRP-MIB:cEigrpPeerTable/CISCO-EIGRP-MIB:cEigrpPeerEntry/CISCO-EIGRP-MIB:cEigrpHandle";
        }
      }

      leaf cEigrpPeerAddrType {
        type leafref {
          path "/CISCO-EIGRP-MIB:CISCO-EIGRP-MIB/CISCO-EIGRP-MIB:cEigrpPeerTable/CISCO-EIGRP-MIB:cEigrpPeerEntry/CISCO-EIGRP-MIB:cEigrpPeerAddrType";
        }
      }
    }

    container object-2 {

      leaf cEigrpVpnId {
        type leafref {
          path "/CISCO-EIGRP-MIB:CISCO-EIGRP-MIB/CISCO-EIGRP-MIB:cEigrpVpnTable/CISCO-EIGRP-MIB:cEigrpVpnEntry/CISCO-EIGRP-MIB:cEigrpVpnId";
        }
      }

      leaf cEigrpAsNumber {
        type leafref {
          path "/CISCO-EIGRP-MIB:CISCO-EIGRP-MIB/CISCO-EIGRP-MIB:cEigrpTraffStatsTable/CISCO-EIGRP-MIB:cEigrpTraffStatsEntry/CISCO-EIGRP-MIB:cEigrpAsNumber";
        }
      }

      leaf cEigrpHandle {
        type leafref {
          path "/CISCO-EIGRP-MIB:CISCO-EIGRP-MIB/CISCO-EIGRP-MIB:cEigrpPeerTable/CISCO-EIGRP-MIB:cEigrpPeerEntry/CISCO-EIGRP-MIB:cEigrpHandle";
        }
      }

      leaf cEigrpPeerAddr {
        type leafref {
          path "/CISCO-EIGRP-MIB:CISCO-EIGRP-MIB/CISCO-EIGRP-MIB:cEigrpPeerTable/CISCO-EIGRP-MIB:cEigrpPeerEntry/CISCO-EIGRP-MIB:cEigrpPeerAddr";
        }
      }
    }

    container object-3 {

      leaf cEigrpVpnId {
        type leafref {
          path "/CISCO-EIGRP-MIB:CISCO-EIGRP-MIB/CISCO-EIGRP-MIB:cEigrpVpnTable/CISCO-EIGRP-MIB:cEigrpVpnEntry/CISCO-EIGRP-MIB:cEigrpVpnId";
        }
      }

      leaf cEigrpAsNumber {
        type leafref {
          path "/CISCO-EIGRP-MIB:CISCO-EIGRP-MIB/CISCO-EIGRP-MIB:cEigrpTraffStatsTable/CISCO-EIGRP-MIB:cEigrpTraffStatsEntry/CISCO-EIGRP-MIB:cEigrpAsNumber";
        }
      }

      leaf cEigrpDestNetType {
        type leafref {
          path "/CISCO-EIGRP-MIB:CISCO-EIGRP-MIB/CISCO-EIGRP-MIB:cEigrpTopoTable/CISCO-EIGRP-MIB:cEigrpTopoEntry/CISCO-EIGRP-MIB:cEigrpDestNetType";
        }
      }

      leaf cEigrpDestNet {
        type leafref {
          path "/CISCO-EIGRP-MIB:CISCO-EIGRP-MIB/CISCO-EIGRP-MIB:cEigrpTopoTable/CISCO-EIGRP-MIB:cEigrpTopoEntry/CISCO-EIGRP-MIB:cEigrpDestNet";
        }
      }

      leaf cEigrpDestNetPrefixLen {
        type leafref {
          path "/CISCO-EIGRP-MIB:CISCO-EIGRP-MIB/CISCO-EIGRP-MIB:cEigrpTopoTable/CISCO-EIGRP-MIB:cEigrpTopoEntry/CISCO-EIGRP-MIB:cEigrpDestNetPrefixLen";
        }
      }

      leaf cEigrpStuckInActive {
        type leafref {
          path "/CISCO-EIGRP-MIB:CISCO-EIGRP-MIB/CISCO-EIGRP-MIB:cEigrpTopoTable/CISCO-EIGRP-MIB:cEigrpTopoEntry/CISCO-EIGRP-MIB:cEigrpStuckInActive";
        }
      }
    }
  }

  smiv2:alias "ciscoEigrpMIB" {
    smiv2:oid "1.3.6.1.4.1.9.9.449";
  }

  smiv2:alias "cEigrpMIBNotifications" {
    smiv2:oid "1.3.6.1.4.1.9.9.449.0";
  }

  smiv2:alias "cEigrpMIBObjects" {
    smiv2:oid "1.3.6.1.4.1.9.9.449.1";
  }

  smiv2:alias "cEigrpVpnInfo" {
    smiv2:oid "1.3.6.1.4.1.9.9.449.1.1";
  }

  smiv2:alias "cEigrpAsInfo" {
    smiv2:oid "1.3.6.1.4.1.9.9.449.1.2";
  }

  smiv2:alias "cEigrpTopologyInfo" {
    smiv2:oid "1.3.6.1.4.1.9.9.449.1.3";
  }

  smiv2:alias "cEigrpPeerInfo" {
    smiv2:oid "1.3.6.1.4.1.9.9.449.1.4";
  }

  smiv2:alias "cEigrpInterfaceInfo" {
    smiv2:oid "1.3.6.1.4.1.9.9.449.1.5";
  }

  smiv2:alias "cEigrpMIBConformance" {
    smiv2:oid "1.3.6.1.4.1.9.9.449.2";
  }

  smiv2:alias "cEigrpMIBCompliances" {
    smiv2:oid "1.3.6.1.4.1.9.9.449.2.1";
  }

  smiv2:alias "cEigrpMIBGroups" {
    smiv2:oid "1.3.6.1.4.1.9.9.449.2.2";
  }

}
