/*
 * Generated by confdc --mib2yang-std
 * Source: mgmt/dmi/model/common/mib-source/CISCO-IETF-FRR-MIB.mib
 */
/*
 * This YANG module has been generated by smidump 0.5.0:
 *
 *      smidump -f yang CISCO-IETF-FRR-MIB
 *
 * Do not edit. Edit the source file instead!
 */

module CISCO-IETF-FRR-MIB {

  namespace "urn:ietf:params:xml:ns:yang:smiv2:CISCO-IETF-FRR-MIB";
  prefix CISCO-IETF-FRR-MIB;

  import IF-MIB {
    prefix "if-mib";
  }

  import MPLS-TC-STD-MIB {
    prefix "mpls-tc";
  }

  import SNMPv2-TC {
    prefix "snmpv2-tc";
  }

  import ietf-yang-smiv2 {
    prefix "smiv2";
  }

  import ietf-yang-types {
    prefix "yang";
  }

  organization
   "Cisco Systems, Inc.";

  contact
   "
    Adrien Grise
    Postal: 300 Apollo Drive
    Cisco Systems, Inc.
    Chelmsford, MA 01824
    Tel:    +1-978-497-3989
    Email:  agrise@cisco.com
    
    Thomas D. Nadeau
    Postal: Cisco Systems, Inc.
    250 Apollo Drive
    Chelmsford, MA 01924
    Tel:    +1-978-244-3051
    Email:  tnadeau@cisco.com
    
    MPLS MIB Development Team
    Postal: Cisco Systems, Inc.
    250 Apollo Drive
    Chelmsford, MA 01924
    Tel:    +1-978-497-3989
    Email:  ch-mpls-mib-dev@cisco.com";

  description
   "This MIB module contains managed object definitions for MPLS
    Fast Reroute (FRR) as defined in:Pan, P., Gan, D., Swallow, G.,
    Vasseur, J.Ph., Cooper, D., Atlas, A., Jork, M., Fast Reroute
    Techniques in RSVP-TE, draft-ietf-mpls-rsvp-lsp-fastreroute-
    00.txt, January 2002.";

  revision 2008-04-29 {
    description
     "Added support for cmplsFrrUnProtected notification.  It is
      defined in version 2 of the ietf draft.  The notification's
      variable bindings have been modified from the draft form to
      match the previous approved Cisco-ized draft form as defined
      for the cmplsFrrProtected notification.";
  }

  revision 2002-11-05 {
    description
     "Cisco'ized the MPLS-FRR-MIB.my file";
  }

  revision 2002-11-01 {
    description
     "Added support for Facility-based FRR.
      
      Removed tables that were redundant with
        other MPLS MIBs.
      
      Assigned experimental.120.";
  }

  revision 2002-03-22 {
    description
     "Initial draft version.";
  }

  typedef MplsFrrDetourIndex {
    type int32 {
      range "1..65535";
    }
    description
     "Index into mplsFrrDetourTable.";
  }


  container CISCO-IETF-FRR-MIB {
    config false;

    container cmplsFrrScalars {
      smiv2:oid "1.3.6.1.4.1.9.10.98.1";

      leaf cmplsFrrDetourIncoming {
        type uint32;
        description
         "The number of detour LSPs entering the device if
          mplsFrrConstProtectionMethod is set to oneToOneBackup(0), or
          or 0 if mplsFrrConstProtectionMethod is set to
          facilityBackup(1).";
        smiv2:defval "0";
        smiv2:max-access "read-only";
        smiv2:oid "1.3.6.1.4.1.9.10.98.1.1";
      }

      leaf cmplsFrrDetourOutgoing {
        type uint32;
        description
         "The number of detour LSPs leaving the device if
          mplsFrrConstProtectionMethod is set to oneToOneBackup(0),
          or 0 if mplsFrrConstProtectionMethod is set to 
          to facilityBackup(1).";
        smiv2:defval "0";
        smiv2:max-access "read-only";
        smiv2:oid "1.3.6.1.4.1.9.10.98.1.2";
      }

      leaf cmplsFrrDetourOriginating {
        type uint32;
        description
         "The number of detour LSPs originating at this PLR if
          mplsFrrConstProtectionMethod is set to oneToOneBackup(0).
          This object MUST return 0 if the mplsFrrConstProtectionMethod 
          is set to facilityBackup(1).";
        smiv2:defval "0";
        smiv2:max-access "read-only";
        smiv2:oid "1.3.6.1.4.1.9.10.98.1.3";
      }

      leaf cmplsFrrSwitchover {
        type uint32;
        description
         "The number of tunnel instances that are switched over to their
          corresponding detour LSP if mplsFrrConstProtectionMethod is set
          to oneToOneBackup(0), or tunnels being switched over if
          mplsFrrConstProtectionMethod is set to facilityBackup(1).";
        smiv2:defval "0";
        smiv2:max-access "read-only";
        smiv2:oid "1.3.6.1.4.1.9.10.98.1.4";
      }

      leaf cmplsFrrNumOfConfIfs {
        type uint32;
        description
         "Indicates the number of MPLS interfaces configured for 
          protection by the FRR feature, otherwise this value
          MUST return 0 to indicate that LSPs traversing any 
          interface may be protected.";
        smiv2:defval "0";
        smiv2:max-access "read-only";
        smiv2:oid "1.3.6.1.4.1.9.10.98.1.5";
      }

      leaf cmplsFrrActProtectedIfs {
        type uint32;
        description
         "Indicates the number of interfaces currently being protected 
          by the FRR feature if mplsFrrConstProtectionMethod is set to
          facilityBackup(1), otherwise this value should return 0 to
          indicate that LSPs traversing any interface may be protected.
          This value MUST be less than or equal to mplsFrrConfIfs.";
        smiv2:defval "0";
        smiv2:max-access "read-only";
        smiv2:oid "1.3.6.1.4.1.9.10.98.1.6";
      }

      leaf cmplsFrrConfProtectingTuns {
        type uint32;
        description
         "Indicates the number of bypass tunnels configured to 
          protect facilities on this LSR using the FRR feature 
          if mplsFrrConstProtectionMethod is set to 
          facilityBackup(1), otherwise this value MUST return 
          0.";
        smiv2:defval "0";
        smiv2:max-access "read-only";
        smiv2:oid "1.3.6.1.4.1.9.10.98.1.7";
      }

      leaf cmplsFrrActProtectedTuns {
        type uint32;
        description
         "Indicates the number of bypass tunnels indicated in
          mplsFrrConfProtectingTuns whose operStatus
          is up(1) indicating that they are currently protecting
          facilities on this LSR using the FRR feature. This
          object MUST return 0 if mplsFrrConstProtectionMethod 
          is set to facilityBackup(1).";
        smiv2:defval "0";
        smiv2:max-access "read-only";
        smiv2:oid "1.3.6.1.4.1.9.10.98.1.8";
      }

      leaf cmplsFrrActProtectedLSPs {
        type uint32;
        description
         "Indicates the number of LSPs currently protected by 
          the FRR feature. If mplsFrrConstProtectionMethod is set 
          to facilityBackup(1)this object MUST return 0.";
        smiv2:defval "0";
        smiv2:max-access "read-only";
        smiv2:oid "1.3.6.1.4.1.9.10.98.1.9";
      }

      leaf cmplsFrrConstProtectionMethod {
        type enumeration {
          enum "oneToOneBackup" {
            value "0";
          }
          enum "facilityBackup" {
            value "1";
          }
        }
        description
         "Indicates which protection method is to be used for fast
          reroute. Some devices may require a reboot of their routing
          processors if this variable is changed. An agent which
          does not wish to reboot or modify its FRR mode 
          MUST return an inconsistentValue error. Please 
          consult the device's agent capability statement 
          for more details.";
        smiv2:max-access "read-write";
        smiv2:oid "1.3.6.1.4.1.9.10.98.1.10";
      }

      leaf cmplsFrrNotifsEnabled {
        type boolean;
        description
         "Enables or disables FRR notifications defined in this MIB
          module. Notifications are disabled by default.";
        smiv2:defval "false";
        smiv2:max-access "read-write";
        smiv2:oid "1.3.6.1.4.1.9.10.98.1.11";
      }

      leaf cmplsFrrLogTableMaxEntries {
        type uint32;
        description
         "Indicates the maximum number of entries allowed in the FRR
          Log table. Agents receiving SETs for values that cannot be
          used must return an inconsistent value error. If a manager
          sets this value to 0, this indicates that no logging should
          take place by the agent.  
          
          If this value is returned as 0, this indicates
          that no additional log entries will be added to the current
          table either because the table has been completely
          filled or logging has been disabled. However, agents
          may wish to not delete existing entries in the log table
          so that managers may review them in the future. 
          
          It is implied that when mplsFrrLogTableCurrEntries 
          has reached the value of this variable, that logging 
          entries may not continue to be added to the table, 
          although existing ones may remain.  Furthermore, an
          agent may begin to delete existing (perhaps the
          oldest entries) entries to make room for new ones.";
        smiv2:defval "0";
        smiv2:max-access "read-write";
        smiv2:oid "1.3.6.1.4.1.9.10.98.1.12";
      }

      leaf cmplsFrrLogTableCurrEntries {
        type yang:counter32;
        description
         "Indicates the current number of entries in the FRR log
          table.";
        smiv2:max-access "read-only";
        smiv2:oid "1.3.6.1.4.1.9.10.98.1.13";
      }

      leaf cmplsFrrNotifMaxRate {
        type uint32;
        description
         "This variable indicates the number of milliseconds
          that must elapse between notification emissions. If
          events occur more rapidly, the implementation may
          simply fail to emit these notifications during that
          period, or may queue them until an appropriate
          time in the future. A value of 0 means no minimum 
          elapsed period is specified.";
        smiv2:defval "0";
        smiv2:max-access "read-write";
        smiv2:oid "1.3.6.1.4.1.9.10.98.1.14";
      }
    }

    container cmplsFrrConstTable {
      description
       "This table shows detour setup constraints.";
      smiv2:oid "1.3.6.1.4.1.9.10.98.2.1.1";

      list cmplsFrrConstEntry {
        key "cmplsFrrConstIfIndex cmplsFrrConstTunnelIndex cmplsFrrConstTunnelInstance";
        description
         "An entry in this table represents detour LSP or bypass tunnel 
          setup constraints for a tunnel instance to be protected by 
          detour LSPs or a tunnel. Agents must allow entries in this table 
          to be created only for tunnel instances that require fast-reroute.
          Entries indexed with mplsFrrConstIfIndex set to 0 apply to all
          interfaces on this device for which the FRR feature can operate
          on.";
        smiv2:oid "1.3.6.1.4.1.9.10.98.2.1.1.1";

        leaf cmplsFrrConstIfIndex {
          type if-mib:InterfaceIndexOrZero;
          description
           "Uniquely identifies an interface for which fast reroute is
            configured. Tabular entries indexed with a 0 value apply to all
            interfaces on this device for which the FRR feature can operate
            on.";
          smiv2:max-access "not-accessible";
          smiv2:oid "1.3.6.1.4.1.9.10.98.2.1.1.1.1";
        }

        leaf cmplsFrrConstTunnelIndex {
          type mpls-tc:MplsTunnelIndex;
          description
           "Uniquely identifies a tunnel for which fast reroute is
            requested.";
          smiv2:max-access "not-accessible";
          smiv2:oid "1.3.6.1.4.1.9.10.98.2.1.1.1.2";
        }

        leaf cmplsFrrConstTunnelInstance {
          type mpls-tc:MplsTunnelInstanceIndex;
          description
           "Uniquely identifies an instance of this tunnel for which fast
            reroute is requested.";
          smiv2:max-access "not-accessible";
          smiv2:oid "1.3.6.1.4.1.9.10.98.2.1.1.1.3";
        }

        leaf cmplsFrrConstSetupPrio {
          type uint32 {
            range "0..7";
          }
          description
           "Indicates the setup priority of detour LSP.";
          reference
           "1. RSVP-TE: Extensions to RSVP for LSP Tunnels, Awduche et al,
            RFC 3209, December 2001";
          smiv2:defval "7";
          smiv2:max-access "read-write";
          smiv2:oid "1.3.6.1.4.1.9.10.98.2.1.1.1.4";
        }

        leaf cmplsFrrConstHoldingPrio {
          type uint32 {
            range "0..7";
          }
          description
           "Indicates the holding priority for detour LSP.";
          reference
           "1. RSVP-TE: Extensions to RSVP for LSP Tunnels, Awduche et al,
            RFC 3209, December 2001";
          smiv2:defval "0";
          smiv2:max-access "read-write";
          smiv2:oid "1.3.6.1.4.1.9.10.98.2.1.1.1.5";
        }

        leaf cmplsFrrConstInclAnyAffinity {
          type mpls-tc:MplsTunnelAffinity;
          description
           "A link satisfies the include-any constraint if and only if the
            constraint is zero, or the link and the constraint have a
            resource class in common.";
          reference
           "1. RSVP-TE: Extensions to RSVP for LSP Tunnels, Awduche et al,
            RFC 3209, December 2001.";
          smiv2:defval "0";
          smiv2:max-access "read-write";
          smiv2:oid "1.3.6.1.4.1.9.10.98.2.1.1.1.6";
        }

        leaf cmplsFrrConstInclAllAffinity {
          type mpls-tc:MplsTunnelAffinity;
          description
           "A link satisfies the include-all constraint if and only if the
            link contains all of the administrative groups specified in the
            constraint.";
          reference
           "1. RSVP-TE: Extensions to RSVP for LSP Tunnels, Awduche et al,
            RFC 3209, December 2001.";
          smiv2:defval "0";
          smiv2:max-access "read-write";
          smiv2:oid "1.3.6.1.4.1.9.10.98.2.1.1.1.7";
        }

        leaf cmplsFrrConstExclAllAffinity {
          type mpls-tc:MplsTunnelAffinity;
          description
           "A link satisfies the exclude-all constraint if and only if the
            link contains none of the administrative groups specified in the
            constraint.";
          reference
           "1. RSVP-TE: Extensions to RSVP for LSP Tunnels, Awduche et al,
            RFC 3209, December 2001.";
          smiv2:defval "0";
          smiv2:max-access "read-write";
          smiv2:oid "1.3.6.1.4.1.9.10.98.2.1.1.1.8";
        }

        leaf cmplsFrrConstHopLimit {
          type uint32 {
            range "1..65535";
          }
          description
           "The maximum number of hops that the detour LSP may traverse.";
          reference
           "Pan, P., Gan, D., Swallow, G., Vasseur, J.Ph., Cooper, D.,
            Atlas, A., Jork, M., Fast Reroute Techniques in RSVP-TE, draft-
            ietf-mpls-rsvp-lsp-fastreroute-00.txt, January 2002. Work in
            progress.";
          smiv2:defval "32";
          smiv2:max-access "read-write";
          smiv2:oid "1.3.6.1.4.1.9.10.98.2.1.1.1.9";
        }

        leaf cmplsFrrConstBandwidth {
          type mpls-tc:MplsBitRate;
          description
           "This variable represents the bandwidth for detour LSPs of this
            tunnel, in units of thousands of bits per second (Kbps).";
          smiv2:defval "1";
          smiv2:max-access "read-write";
          smiv2:oid "1.3.6.1.4.1.9.10.98.2.1.1.1.10";
        }

        leaf cmplsFrrConstRowStatus {
          type snmpv2-tc:RowStatus;
          description
           "This object is used to create, modify, and/or delete a row in
            this table.";
          smiv2:max-access "read-write";
          smiv2:oid "1.3.6.1.4.1.9.10.98.2.1.1.1.11";
        }

        leaf cmplsFrrConstNumProtectingTunOnIf {
          type yang:gauge32;
          description
           "The number of backup tunnels protecting the specified
            interface.";
          smiv2:max-access "read-only";
          smiv2:oid "1.3.6.1.4.1.9.10.98.2.1.1.1.12";
        }

        leaf cmplsFrrConstNumProtectedTunOnIf {
          type yang:gauge32;
          description
           "The number of tunnels protected on this interface.";
          smiv2:max-access "read-only";
          smiv2:oid "1.3.6.1.4.1.9.10.98.2.1.1.1.13";
        }
      }
    }

    container cmplsFrrLogTable {
      description
       "The fast reroute log table records fast reroute events such
        as protected links going up or down or the FRR feature
        kicking in.";
      smiv2:oid "1.3.6.1.4.1.9.10.98.2.1.2";

      list cmplsFrrLogEntry {
        key "cmplsFrrLogIndex";
        description
         "An entry in this table is created to describe one fast
          reroute event.  Entries in this table are only created and
          destroyed by the agent implementation. The maximum number 
          of entries in this log is governed by the scalar.";
        smiv2:oid "1.3.6.1.4.1.9.10.98.2.1.2.1";

        leaf cmplsFrrLogIndex {
          type uint32;
          description
           "Uniquely identifies a fast reroute event entry.";
          smiv2:max-access "not-accessible";
          smiv2:oid "1.3.6.1.4.1.9.10.98.2.1.2.1.1";
        }

        leaf cmplsFrrLogEventTime {
          type yang:timestamp;
          description
           "This object provides the amount of time ticks since this
            event occured.";
          smiv2:max-access "read-only";
          smiv2:oid "1.3.6.1.4.1.9.10.98.2.1.2.1.2";
        }

        leaf cmplsFrrLogInterface {
          type if-mib:InterfaceIndexOrZero;
          description
           "This object indicates which interface was affected by this
            FRR event. This value may be set to 0 if
            mplsFrrConstProtectionMethod is set to oneToOneBackup(0).";
          smiv2:max-access "read-only";
          smiv2:oid "1.3.6.1.4.1.9.10.98.2.1.2.1.3";
        }

        leaf cmplsFrrLogEventType {
          type enumeration {
            enum "other" {
              value "1";
            }
            enum "protected" {
              value "2";
            }
          }
          description
           "This object describes what type of fast reroute event
            occured.";
          smiv2:max-access "read-only";
          smiv2:oid "1.3.6.1.4.1.9.10.98.2.1.2.1.4";
        }

        leaf cmplsFrrLogEventDuration {
          type yang:timeticks;
          description
           "This object describes the duration of this event.";
          smiv2:max-access "read-only";
          smiv2:oid "1.3.6.1.4.1.9.10.98.2.1.2.1.5";
        }

        leaf cmplsFrrLogEventReasonString {
          type binary {
            length "128";
          }
          description
           "This object contains an implementation-specific explanation
            of the event.";
          smiv2:max-access "read-only";
          smiv2:oid "1.3.6.1.4.1.9.10.98.2.1.2.1.6";
        }
      }
    }

    container cmplsFrrFacRouteDBTable {
      description
       "The mplsFrrFacRouteDBTable provides information about the 
        fast reroute database.  Each entry belongs to an interface,
        protecting backup tunnel and protected tunnel. MPLS 
        interfaces defined on this node are protected by backup
        tunnels and are indexed by mplsFrrFacRouteProtectedIndex.
        Backup tunnels defined to protect the tunnels traversing an
        interface, and are indexed by 
        mplsFrrFacRouteProtectingTunIndex.  Note that the tunnel 
        instance index is not required, since it is implied to be 0, 
        which indicates the tunnel head interface for the protecting 
        tunnel. The protecting tunnel is defined to exist on the PLR 
        in the FRR specification.  Protected tunnels are the LSPs that 
        traverse the protected link.  These LSPs are uniquely 
        identified by mplsFrrFacRouteProtectedTunIndex,
        mplsFrrFacRouteProtectedTunInstance, 
        mplsFrrFacRouteProtectedTunIngressLSRId, and 
        mplsFrrFacRouteProtectedTunEgressLSRId.";
      reference
       "Srinivansan, C., and A. Viswanathan, T. Nadeau, MPLS Traffic
        Engineering Management Information Base Using SMIv2,
         draft-ietf-mpls-te-mib-06.txt ";
      smiv2:oid "1.3.6.1.4.1.9.10.98.2.3.1";

      list cmplsFrrFacRouteDBEntry {
        key "cmplsFrrFacRouteProtectedIfIndex cmplsFrrFacRouteProtectingTunIndex cmplsFrrFacRouteProtectedTunIndex cmplsFrrFacRouteProtectedTunInstance cmplsFrrFacRouteProtectedTunIngressLSRId cmplsFrrFacRouteProtectedTunEgressLSRId";
        description
         "An entry in the mplsFrrDBTable represents a single protected
          LSP, protected by a backup tunnel and defined for a specific
          protected interface. Note that for brevity, managers should
          consult the mplsTunnelTable present in the MPLS-TE MIB for
          additional information about the protecting and protected
          tunnels, and the ifEntry in the IF-MIB for the protected
          interface.";
        reference
         "Srinivansan, C., and A. Viswanathan, T. Nadeau, MPLS Label
          Switch Router Management Information Base Using SMIv2,
          draft-ietf-mpls-lsr-mib-07.txt Srinivansan, C., and A.
          Viswanathan, T. Nadeau, MPLS Traffic Engineering Management
          Information Base Using SMIv2, draft-ietf-mpls-te-mib-
          06.txt.";
        smiv2:oid "1.3.6.1.4.1.9.10.98.2.3.1.1";

        leaf cmplsFrrFacRouteProtectedIfIndex {
          type if-mib:InterfaceIndex;
          description
           "Uniquely identifies the interface configured for FRR protection.";
          smiv2:max-access "not-accessible";
          smiv2:oid "1.3.6.1.4.1.9.10.98.2.3.1.1.1";
        }

        leaf cmplsFrrFacRouteProtectingTunIndex {
          type mpls-tc:MplsTunnelIndex;
          description
           "Uniquely identifies the mplsTunnelEntry primary index for
            the tunnel head interface designated to protect the 
            interface as specified in the mplsFrrFacRouteIfProtectedIndex
            (and all of the tunnels using this interface).";
          smiv2:max-access "not-accessible";
          smiv2:oid "1.3.6.1.4.1.9.10.98.2.3.1.1.2";
        }

        leaf cmplsFrrFacRouteProtectedTunIndex {
          type mpls-tc:MplsTunnelIndex;
          description
           "Uniquely identifies an mplsTunnelEntry that is
            being protected by FRR.";
          smiv2:max-access "not-accessible";
          smiv2:oid "1.3.6.1.4.1.9.10.98.2.3.1.1.3";
        }

        leaf cmplsFrrFacRouteProtectedTunInstance {
          type mpls-tc:MplsTunnelInstanceIndex;
          description
           "Uniquely identifies an mplsTunnelEntry that is
            being protected by FRR.";
          smiv2:max-access "not-accessible";
          smiv2:oid "1.3.6.1.4.1.9.10.98.2.3.1.1.4";
        }

        leaf cmplsFrrFacRouteProtectedTunIngressLSRId {
          type mpls-tc:MplsLsrIdentifier;
          description
           "Uniquely identifies an mplsTunnelEntry that is
            being protected by FRR.";
          reference
           "1. RSVP-TE: Extensions to RSVP for LSP Tunnels,
            Awduche et al, RFC 3209, December 2001
            2. Constraint-Based LSP Setup using LDP, Jamoussi
            (Editor), RFC 3212, January 2002";
          smiv2:max-access "not-accessible";
          smiv2:oid "1.3.6.1.4.1.9.10.98.2.3.1.1.5";
        }

        leaf cmplsFrrFacRouteProtectedTunEgressLSRId {
          type mpls-tc:MplsLsrIdentifier;
          description
           "Uniquely identifies an mplsTunnelEntry that is
            being protected by FRR.";
          smiv2:max-access "not-accessible";
          smiv2:oid "1.3.6.1.4.1.9.10.98.2.3.1.1.6";
        }

        leaf cmplsFrrFacRouteProtectedTunStatus {
          type enumeration {
            enum "active" {
              value "1";
            }
            enum "ready" {
              value "2";
            }
            enum "partial" {
              value "3";
            }
          }
          description
           "Specifies the state of the protected tunnel.
            
            active  This tunnel's label has been placed in the
                     LFIB and is ready to be applied to incoming
                     packets.
                     
            ready -  This tunnel's label entry has been created but is
                     not yet in the LFIB.
                     
            partial - This tunnel's label entry as not been fully
                      created.";
          smiv2:max-access "read-only";
          smiv2:oid "1.3.6.1.4.1.9.10.98.2.3.1.1.7";
        }

        leaf cmplsFrrFacRouteProtectingTunResvBw {
          type mpls-tc:MplsBitRate;
          description
           "Specifies the amount of bandwidth in megabytes per second
            that is actually reserved by the backup tunnel for
            facility backup. This value is repeated here from the MPLS-
            TE MIB because the tunnel entry will reveal the bandwidth
            reserved by the signaling protocol, which is typically 0
            for backup tunnels so as to not over-book bandwidth.
            However, internal reservations are typically made on the
            PLR, thus this value should be revealed here.";
          smiv2:max-access "read-only";
          smiv2:oid "1.3.6.1.4.1.9.10.98.2.3.1.1.8";
        }

        leaf cmplsFrrFacRouteProtectingTunProtectionType {
          type enumeration {
            enum "linkProtection" {
              value "0";
            }
            enum "nodeProtection" {
              value "1";
            }
          }
          description
           "Indicates type of the resource protection.";
          smiv2:defval "nodeProtection";
          smiv2:max-access "read-write";
          smiv2:oid "1.3.6.1.4.1.9.10.98.2.3.1.1.9";
        }
      }
    }
  }

  notification cmplsFrrProtected {
    description
     "This notification is generated when a tunnel running over an
      interface as specified in the mplsFrrConstTable is initially
      protected by the backup tunnel also specified in the
      cmplsFrrConstTable. This notification should not be generated
      for each subsequent tunnel that is backed up by the FRR feature
      on this LSR, as this may result in potential scaling issues
      with regard to LSR performance and network loading. Note also
      that notifications MUST be generated in accordance with the
      cmplsFrrNotifMaxRate.";
    smiv2:oid "1.3.6.1.4.1.9.10.98.0.1";

    container object-1 {

      leaf cmplsFrrConstIfIndex {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstIfIndex";
        }
      }

      leaf cmplsFrrConstTunnelIndex {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstTunnelIndex";
        }
      }

      leaf cmplsFrrConstTunnelInstance {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstTunnelInstance";
        }
      }

      leaf cmplsFrrConstNumProtectingTunOnIf {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstNumProtectingTunOnIf";
        }
      }
    }

    container object-2 {

      leaf cmplsFrrConstIfIndex {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstIfIndex";
        }
      }

      leaf cmplsFrrConstTunnelIndex {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstTunnelIndex";
        }
      }

      leaf cmplsFrrConstTunnelInstance {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstTunnelInstance";
        }
      }

      leaf cmplsFrrConstNumProtectedTunOnIf {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstNumProtectedTunOnIf";
        }
      }
    }

    container object-3 {

      leaf cmplsFrrConstIfIndex {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstIfIndex";
        }
      }

      leaf cmplsFrrConstTunnelIndex {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstTunnelIndex";
        }
      }

      leaf cmplsFrrConstTunnelInstance {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstTunnelInstance";
        }
      }

      leaf cmplsFrrConstBandwidth {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstBandwidth";
        }
      }
    }
  }

  notification cmplsFrrUnProtected {
    description
     "This notification is generated when the final tunnel that is
      being protected by a backup tunnel as specified in the
      cmplsFrrConstTable is restored to normal operation. This
      notification should not be generated for each restored tunnel,
      as this may result in potential scaling issues with regard to
      LSR performance and network loading. Note also that
      notifications MUST be generated in accordance with the
      cmplsFrrNotifMaxRate.";
    smiv2:oid "1.3.6.1.4.1.9.10.98.0.2";

    container object-1 {

      leaf cmplsFrrConstIfIndex {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstIfIndex";
        }
      }

      leaf cmplsFrrConstTunnelIndex {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstTunnelIndex";
        }
      }

      leaf cmplsFrrConstTunnelInstance {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstTunnelInstance";
        }
      }

      leaf cmplsFrrConstNumProtectingTunOnIf {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstNumProtectingTunOnIf";
        }
      }
    }

    container object-2 {

      leaf cmplsFrrConstIfIndex {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstIfIndex";
        }
      }

      leaf cmplsFrrConstTunnelIndex {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstTunnelIndex";
        }
      }

      leaf cmplsFrrConstTunnelInstance {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstTunnelInstance";
        }
      }

      leaf cmplsFrrConstNumProtectedTunOnIf {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstNumProtectedTunOnIf";
        }
      }
    }

    container object-3 {

      leaf cmplsFrrConstIfIndex {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstIfIndex";
        }
      }

      leaf cmplsFrrConstTunnelIndex {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstTunnelIndex";
        }
      }

      leaf cmplsFrrConstTunnelInstance {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstTunnelInstance";
        }
      }

      leaf cmplsFrrConstBandwidth {
        type leafref {
          path "/CISCO-IETF-FRR-MIB:CISCO-IETF-FRR-MIB/CISCO-IETF-FRR-MIB:cmplsFrrConstTable/CISCO-IETF-FRR-MIB:cmplsFrrConstEntry/CISCO-IETF-FRR-MIB:cmplsFrrConstBandwidth";
        }
      }
    }
  }

  smiv2:alias "cmplsFrrMIB" {
    smiv2:oid "1.3.6.1.4.1.9.10.98";
  }

  smiv2:alias "cmplsFrrNotif" {
    smiv2:oid "1.3.6.1.4.1.9.10.98.0";
  }

  smiv2:alias "cmplsFrrScalars" {
    smiv2:oid "1.3.6.1.4.1.9.10.98.1";
  }

  smiv2:alias "cmplsFrrObjects" {
    smiv2:oid "1.3.6.1.4.1.9.10.98.2";
  }

  smiv2:alias "cmplsFrrGeneralObjects" {
    smiv2:oid "1.3.6.1.4.1.9.10.98.2.1";
  }

  smiv2:alias "cmplsFrr1to1Objects" {
    smiv2:oid "1.3.6.1.4.1.9.10.98.2.2";
  }

  smiv2:alias "cmplsFrrFacObjects" {
    smiv2:oid "1.3.6.1.4.1.9.10.98.2.3";
  }

  smiv2:alias "cmplsFrrConformance" {
    smiv2:oid "1.3.6.1.4.1.9.10.98.3";
  }

  smiv2:alias "cmplsFrrGroups" {
    smiv2:oid "1.3.6.1.4.1.9.10.98.3.1";
  }

  smiv2:alias "cmplsFrrCompliances" {
    smiv2:oid "1.3.6.1.4.1.9.10.98.3.2";
  }

}
