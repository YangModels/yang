module cisco-odm {
  namespace "http://cisco.com/yang/cisco-odm";
  prefix codm;

  import cisco-self-mgmt {
    prefix cisco-sfm;
  }
 
  import tailf-common {
    prefix tailf;
  }

  description
    "Copyright (c) 2016 by Cisco Systems, Inc."+
    "All rights reserved.";

  revision "2016-08-05" {
    description "Changed action names to be type identity. Obsoleted on-demand features.";
  }

  revision "2016-05-16" {
    description "Add augment statement";
  }

  revision "2016-05-04" {
    description "Add tail-f annotation to boolean leaves";
  }

  revision 2016-03-30 {
    description
      "Update description with copyright notice.";
  }

  revision "2015-06-19" {
    description "initial commit";
  }
  identity parsername {
	description " ODM parser names";
  }
  identity ACL {
	description "show ip access-lists";
	base parsername;
  }
  identity BGP {
        description "show bgp";
        base parsername;
  }
  identity Archive {
        description "show ip route";
        base parsername;
  }
  identity IPRoute {
        description "show ip route";
        base parsername;
  }
  identity Interfaces {
        description "show interfaces";
        base parsername;
  }
  identity Environment {
        description "show environment";
        base parsername;
  }
  identity FlowMonitor {
        description "show flow monitor";
        base parsername;
  }
  identity BFDNeighbors {
        description "show bfd neighbors";
        base parsername;
  }
  identity BridgeDomain {
        description "show bridge domain";
        base parsername;
  }
  identity CPUProcesses {
        description "show processes cpu";
        base parsername;
  }
  identity EFPStats {
        description "show ethernet service instance stats";
        base parsername;
  }
  identity LLDPNeighbors {
        description "show ldp neighbors";
        base parsername;
  }
  identity VirtualService {
        description "show vritual-service";
        base parsername;
  }
  identity IPSLAStats {
        description "show ip sla statistics";
        base parsername;
  }
  identity MPLSLDPNeighbors {
        description "show mpls ldp neighbor detail";
        base parsername;
  }
  identity MemoryProcesses {
        description "show processes memory";
        base parsername;
  }
  identity MemoryStats {
        description "show memory statistics";
        base parsername;
  }
  identity PlatformSoftware {
        description "show platform software";
        base parsername;
  }
  identity MPLSStaticBinding {
        description "show mpls static binding";
        base parsername;
  }
  identity MPLSForwardingTable {
        description "show mpls forwarding-table";
        base parsername;
  }
  identity OSPF {
        description "show ospf";
        base parsername;
  }
  identity EthernetCFMStats {
        description "show ethernet cfm statistics";
        base parsername;
  }

  augment "/cisco-sfm:netconf-yang" {     
  container cisco-odm {
    leaf polling-enable {
      tailf:cli-boolean-no;
      type boolean;
    }
    leaf on-demand-default-time {
      status obsolete;
      type uint32 {
        range "500..max";
      }
      default 30000;
    }
    leaf on-demand-enable {
	status obsolete;
      tailf:cli-boolean-no;
      type boolean;
      default false;
    }
    list actions {
      key action-name;
      leaf action-name {
        type identityref {
		base parsername;
	}
      }
      leaf polling-interval {
        type uint32 {
          range "1..max";
	       } 
        default 120000;
      }
      leaf mode {
        type enumeration {
          enum poll;
          enum on-demand;
          enum none;
        }
        default poll;
      }
      leaf cdb-xpath {
         type string;
      }
    }
  }
  }
}
