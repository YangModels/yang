/*-------------------------------------------------------------------
 *  cisco-qos-action-marking-cfg.yang - Action marking 
 * 
 *  April 2015, Xia Wu   
 *                                           
 *  Copyright (c) 2015 by Cisco Systems, Inc.
 *  All rights reserved.                     
 *-------------------------------------------------------------------
 */

module cisco-qos-action-marking-cfg {
    namespace "urn:cisco:params:xml:ns:yang:cisco-qos-action-marking-cfg";
    prefix set;

    import cisco-qos-common {
        prefix qos;
    }

    import ietf-diffserv-policy {
        prefix policy;
    }

    import ietf-diffserv-action {
        prefix action;
    }

    import policy-types {
        prefix c3pl;
    }

    import cisco-table-map {
        prefix table-map;
    }

    organization "Cisco Systems";
    contact
        "Editor:   Xia Wu
        <mailto:xiaw2@cisco.com>";
    description
        "This module contains YANG definitions for
        configuring marking

        Copyright (c) 2015 by Cisco Systems, Inc.
        All rights reserved.";

    revision 2015-05-09 {
        description "first revision";
        reference "ietf-diffserv-action.yang";
    }

    identity marking-dscp-tunnel {
        base policy:action-type;
        description "set dscp tunnel action type";
    }

    identity marking-cos {
        base policy:action-type;
        description "set cos action type";
    }

    identity marking-cos-inner {
        base policy:action-type;
        description "set cos inner action type";
    }

    identity marking-discard-class {
        base policy:action-type;
        description "set discard class action type";
    }

    identity marking-qos-grp {
        base policy:action-type;
        description "set qos group action type";
    }

    identity marking-prec {
        base policy:action-type;
        description "set precendence action type";
    }   

    identity marking-prec-tunnel {
        base policy:action-type;
        description "set precendence tunnel action type";
    }

    identity marking-mpls-exp-imp {
        base policy:action-type;
        description "set mpls exp imposition action type";
    }

    identity marking-mpls-exp-top {
        base policy:action-type;
        description "set mpls exp topmost action type";
    }

    identity marking-atm-clp {
        base policy:action-type;
        description "set atm clp action type";
    }

    identity marking-dei {
        base policy:action-type;
        description "set dei action type";
    }

    identity marking-dei-imp {
        base policy:action-type;
        description "set dei imposition action type";
    }

    identity marking-frde {
        base policy:action-type;
        description "set frde action type";
    }

    identity marking-fr-fecn-becn {
        base policy:action-type;
        description "set fr fecn becn action type";
    }

    identity marking-srp-priority {
        base policy:action-type;
        description "set srp priority action type";
    }

    identity marking-vlan-inner {
        base policy:action-type;
        description "set vlan inner action type";
    }

    identity marking-wlan-user-priority {
        base policy:action-type;
        description "set wlan user priority action type";
    }

    feature set-dscp-tunnel-support{
        description "The feture allows set dscp tunnel to be configured";
    }
    feature set-cos-support {
        description "The feture allows set cos to be configured";    
    }
    feature set-cos-inner-suppport {
        description "The feture allows set cos inner to be configured";
    }
    feature set-discard-class-support {
        description "The feture allows set discard class to be configured";
    }
    feature set-qos-grp-support {
        description "The feture allows set qos group to be configured";
    }
    feature set-prec-support {
        description "The feture allows set precedence to be configured";
    }
    feature set-prec-tunnel-support {
        description "The feture allows set precedence tunnel to be configured";
    }
    feature set-mpls-exp-imp-support {
        description "The feture allows set mpls exp imposition to be configured";
    }
    feature set-mpls-exp-top-support {
        description "The feture allows set mpls exp topmost to be configured";
    }
    feature set-fr-de-support {
        description "The feture allows set fr de to be configured";
    }
    feature set-fr-fecn-becn-support {
        description "The feture allows set fr fecn becn to be configured";
    }
    feature set-atm-clp-support {
        description "The feture allows set atm clp to be configured";
    }
    feature set-vlan-inner-support {
        description "The feture allows set vlan inner to be configured";
    }
    feature set-dei-support {
        description "The feture allows set dei to be configured";
    }
    feature set-dei-imp-support {
        description "The feture allows set dei imposition to be configured";
    }
    feature set-srp-priority-support {
        description "The feture allows set srp priority to be configured";
    }
    feature set-wlan-user-priority-support {
        description "The feture allows set wlan user priority to be configured";
    }  

    grouping SET-VAL-TABLEMAP {      
        container set-val-tablemap {
            leaf to-type {
                if-feature table-map:table-map-template-support;
                type qos:match-type;
                description "The type to map to";
            }

            leaf tablemap-name {
                if-feature table-map:table-map-template-support;
                type leafref {
                    path "/table-map:table-maps/table-map:table-entry/" 
                        + "table-map:table-name";
                }
                description "Table-map name, which refer \
                    to the table-map configured";
            }   
            description "set <from-type> <to-type> tablemap";
        }
        description "set <from-type> <to-type> tablemap";
    }

    grouping MARKING{
        container marking {
            uses MARKING-DSCP-TUNNEL;
            uses MARKING-COS;
            uses MARKING-COS-INNER;
            uses MARKING-DISCARD-CLASS;
            uses MARKING-QOS-GRP;
            uses MARKING-PREC;
            uses MARKING-PREC-TUNNEL;
            uses MARKING-MPLS-EXP-IMP;
            uses MARKING-MPLS-EXP-TOP;
            uses MARKING-FR-DE;
            uses MARKING-FR-FECN-BECN;
            uses MARKING-ATM-CLP;
            uses MARKING-VLAN-INNER;
            uses MARKING-DEI;
            uses MARKING-DEI-IMP;
            uses MARKING-SRP-PRIORITY;
            uses MARKING-WLAN-USER-PRIORITY;
            description "The container for all marking type";
        }
        description "The grouping for all marking type";
    }

    grouping MARKING-DSCP-TUNNEL {
        container marking-dscp-tunnel-cfg {
            if-feature set-dscp-tunnel-support;
            leaf dscp-val { 
                type qos:dscp;
                description "dscp value";
            }
            uses SET-VAL-TABLEMAP;
            description "set dscp on tunnel pkts";
        }
        description "set dscp-tunnel";
    }
    grouping MARKING-COS {
        container marking-cos-cfg {
            if-feature set-cos-support;
            leaf cos-val { 
                type c3pl:cos-type;
                description "cos value";
            }  
            uses SET-VAL-TABLEMAP;
            description "set cos";
        }
        description "set cos";
    }

    grouping MARKING-COS-INNER {
        container marking-cos-inner-cfg {
            if-feature set-cos-inner-suppport;
            leaf cos-inner-val { 
                type c3pl:cos-type;
                description "cos inner value";
            } 
            uses SET-VAL-TABLEMAP;
            description "set Q-in-Q Cos";
        }
        description "set cos-inner";
    }

    grouping MARKING-DISCARD-CLASS {
        container marking-discard-class-cfg {
            if-feature set-discard-class-support;
            leaf disc-class-val { 
                type c3pl:discard-class-type;
                description "discard-class value";
            } 
            uses SET-VAL-TABLEMAP;
            description "set discard-class metadata";
        }
        description "set discard-class";
    }  

    grouping MARKING-QOS-GRP {
        container marking-qos-grp-cfg {
            if-feature set-qos-grp-support;
            leaf qos-grp-val { 
                type c3pl:qos-group-type;
                description "qos group value";
            } 
            uses SET-VAL-TABLEMAP;
            description "set qos-group metadata";
        }
        description "set qos-group";
    }

    grouping MARKING-PREC {
        container marking-prec-cfg {
            if-feature set-prec-support;
            leaf prec-val { 
                type c3pl:prec-val-type;
                description "precedence value";
            } 
            uses SET-VAL-TABLEMAP;
            description "set precendence";
        } 
        description "set precendence";
    }

    grouping MARKING-PREC-TUNNEL {
        container marking-prec-tunnel-cfg {
            if-feature set-prec-tunnel-support;
            leaf prec-val { 
                type c3pl:prec-val-type;
                description "precedence value";
            }
            uses SET-VAL-TABLEMAP;
            description "set precendence on tunnel pkts";
        }
        description "set precendence-tunnel";
    }

    grouping MARKING-MPLS-EXP-IMP {
        container marking-mpls-exp-imp-cfg {
            if-feature set-mpls-exp-imp-support;
            leaf mpls-exp-imp-val { 
                type c3pl:mpls-exp-type;
                description "mpls exp value";
            } 
            uses SET-VAL-TABLEMAP;
            description "set mpls-exp-imposition";
        }
        description "set mpls-exp-imposition";
    }

    grouping MARKING-MPLS-EXP-TOP {
        container marking-mpls-exp-top-cfg {
            if-feature set-mpls-exp-top-support;
            leaf mpls-exp-top-val { 
                type c3pl:mpls-exp-type;
                description "mpls exp value";
            } 
            uses SET-VAL-TABLEMAP;
            description "set mpls-exp-topmost";
        }
        description "set mpls-exp-topmost";
    }

    grouping MARKING-FR-DE {
        container marking-fr-de-cfg {
            if-feature set-fr-de-support;
            leaf fr-de { 
                type empty;
                description "fr de set or not";
            }
            uses SET-VAL-TABLEMAP;
            description "set FR DE Bit";
        }
        description "set fr-de";
    }

    grouping MARKING-FR-FECN-BECN {
        container marking-fr-fecn-becn-cfg {
            if-feature set-fr-fecn-becn-support;
            leaf fecn-becn-val {
                type qos:percent-value-1to100;
                description "fecn becn value";
            }
            uses SET-VAL-TABLEMAP;
            description "set FR FECN-BECN";
        }
        description "set fr-fecn-becn";
    }


    grouping MARKING-ATM-CLP {
        container marking-atm-clp-cfg {
            if-feature set-atm-clp-support;
            leaf atm-clp-val {
                type uint8 {
                    range "0..1";    
                }
                description "atm clp value";
            }
            uses SET-VAL-TABLEMAP;
            description "set ATM CLP bit";
        }
        description "set atm-clp";
    }

    grouping MARKING-VLAN-INNER {
        container marking-vlan-inner-cfg {
            if-feature set-vlan-inner-support;
            leaf vlan-inner-val {
                type c3pl:vlan-type;
                description "vlan value";
            }
            uses SET-VAL-TABLEMAP;
            description "set Q-in-Q vlan";
        }
        description "set vlan-inner";
    }

    grouping MARKING-DEI {
        container marking-dei-cfg {
            if-feature set-dei-support;
            leaf dei-value {
                type c3pl:dei-type;
                description "dei value";
            }
            uses SET-VAL-TABLEMAP;
            description "set dei value";
        }
        description "set dei";
    }

    grouping MARKING-DEI-IMP {
        container marking-dei-imp-cfg {
            if-feature set-dei-imp-support;
            leaf dei-imp-value {
                type c3pl:dei-type;
                description "dei value";
            }
            uses SET-VAL-TABLEMAP;
            description "set dei imposition";
        }
        description "set dei imposition";
    }

    grouping MARKING-SRP-PRIORITY {
        container marking-srp-priority {
            if-feature set-srp-priority-support;
            leaf srp-priority-value {
                type uint8 {
                    range "0..7";
                }
                description "srp priority value";
            }
            uses SET-VAL-TABLEMAP;
            description "set SRP priority";
        }
        description "set srp-priority";
    }

    grouping MARKING-WLAN-USER-PRIORITY {
        container marking-wlan-user-priority {
            if-feature set-wlan-user-priority-support;
            leaf wlan-user-priority-value {
                type uint8 {
                    range "0..7";
                }
                description "wlan user priority value";
            }
            uses SET-VAL-TABLEMAP;
            description "set wlan user priority";
        }
        description "set wlan-user-priority";
    }

    augment "/policy:policies/policy:policy-entry"
        + "/policy:classifier-entry"
        + "/policy:classifier-action-entry-cfg/"
        + "policy:action-cfg-params" {    
            description "extend action-cfg-params to add additional actions";
            case marking-dscp-tunnel {
                uses MARKING-DSCP-TUNNEL;
            }     

            case marking-cos {
                uses MARKING-COS;
            }

            case marking-cos-inner {
                uses MARKING-COS-INNER;
            }

            case marking-discard-class {
                uses MARKING-DISCARD-CLASS;
            }

            case marking-qos-grp {
                uses MARKING-QOS-GRP;
            }

            case marking-prec {
                uses MARKING-PREC;
            }

            case marking-prec-tunnel {
                uses MARKING-PREC-TUNNEL;
            }

            case marking-mpls-exp-imp {
                uses MARKING-MPLS-EXP-IMP;
            }

            case marking-mpls-exp-top {
                uses MARKING-MPLS-EXP-TOP;
            }

            case marking-fr-de {
                uses MARKING-FR-DE;
            }
            case marking-fr-fecn-becn {
                uses  MARKING-FR-FECN-BECN;
            }

            case marking-atm-clp {
                uses MARKING-ATM-CLP;
            }
            case marking-vlan-inner {
                uses MARKING-VLAN-INNER;
            }

            case marking-dei {
                uses MARKING-DEI;
            }

            case marking-dei-imp {
                uses MARKING-DEI-IMP;
            }

            case marking-srp-priority {
                uses MARKING-SRP-PRIORITY;
            }
        }

/*
    augment "/policy:policies/policy:policy-entry"
        + "/policy:classifier-entry"
        + "/policy:classifier-action-entry-cfg/"
        + "policy:action-cfg-params/action:marking/action:marking-cfg" {
            description "extend the marking dscp to add set from a tablemap";
            uses SET-VAL-TABLEMAP;
        }
*/

}
