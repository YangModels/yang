module cisco-environment {

    yang-version 1;

    namespace "urn:cisco:params:xml:ns:yang:cisco-environment";
    prefix envt;


    organization
        "Cisco Systems, Inc.";

    contact
        " Cisco Systems, Inc.
          Customer Service

          Postal: 170 W Tasman Drive
          San Jose, CA 95134

          Tel: +1 1800 553-NETS

          E-mail: cs-yang@cisco.com";
    
    description
        " This module contains a collection of YANG definitions for
          monitoring Environment of a Network Element.";
    
    reference "TODO";

    revision 2015-04-09 {
        description "Proposed";
    }

    container environment-state {
        config false;
        description
            "Data nodes for Environmental Monitoring.";

        list sensor {
            key "name location";

            description
                "The list of components on the device chasis.";

            leaf name {
                type string;
                description
                    "The name of the sensor component.

                     This includes all physical components of the chasis - 
                     both fixed and pluggable.";
            }

            leaf location {
                type string;
                description
                    "The name of the location where this slot is present.";
            }

            leaf state {
                type string;
                description
                    "A description of current state of the sensor.";
            }

            leaf current-reading {
                description
                    "Numerical value of current sensor reading in sensor-units.";
                type uint32;
            }

            leaf sensor-units {
                description
                    "Units corresponding to current-reading value.";
                type enumeration {
                    enum Watts;
			enum Celsius;
                    enum milliVolts;
                    enum Amperes;
					enum Volts-DC;
					enum Volts-AC;
					enum milliAmperes;
                }
            }   
        }
    }

}
