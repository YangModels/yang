module cisco-checkpoint-archive {

     yang-version 1;

     namespace "urn:cisco:params:xml:ns:yang:cisco-checkpoint-archive";
     prefix checkpoint-archive;


     organization
    "Cisco Systems, Inc.";

   contact
    " Cisco Systems, Inc.
    Customer Service

    Postal: 170 W Tasman Drive
    San Jose, CA 95134

    Tel: +1 1800 553-NETS

    E-mail: cs-yang@cisco.com";
    
    description
       "This module contains a collection of YANG definitions for
        monitoring the checkpoint archives in a Network Element.";
    
    reference "TODO";

    revision 2015-05-20 {
    description "Proposed";  
  }
  
	container checkpoint-archive {
		config false;
		description
			"Contents of the show archive cli";
			
		leaf max {
			type uint8;
			description
				"The maxium number of archives";
		}
		
		leaf current {
			type uint8;
			description
				"The current number of archives";
		}
		
		leaf recent {
			type string;
			description
			"The most recent archive";
		}
		
		list archive {
			key "number";
			description
				"Archive information";
				
			leaf number {
				type uint8;
				description
					"The archive number";
			}
			
			leaf name {
				type string;
				description
					"the name of the archive";
			}
			
		}
	
	}

}
