module Cisco-IOS-XE-controller {
  yang-version 1.1;
  namespace "http://cisco.com/ns/yang/Cisco-IOS-XE-controller";
  prefix ios-ctrl;

  import cisco-semver {
    prefix cisco-semver;
  }
  import ietf-inet-types {
    prefix inet;
  }
  import Cisco-IOS-XE-native {
    prefix ios;
  }
  import Cisco-IOS-XE-features {
    prefix ios-features;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Controller Yang Model.
     Copyright (c) 2016-2021 by Cisco Systems, Inc.
     All rights reserved.";

  revision 2022-03-01 {
    description
      "- Deprecate white-list and add allow-list under controller * lte mobile-app
       - Add controller Cellular Serviceability enhancement";
    cisco-semver:module-version "4.3.0";
  }
  revision 2021-07-01 {
    description
      "- Add controller * Gps-Dr NMEA UDP socket";
    cisco-semver:module-version "4.2.0";
  }
  revision 2021-03-01 {
    description
      "- Add controller * Gps-Dr
       - Added dependency for T1/E1 pri-group and serial interface";
    cisco-semver:module-version "4.1.0";
  }
  revision 2020-11-01 {
    description
      "- Added dependency for T1/E1 channel-group and serial interface";
    cisco-semver:module-version "4.0.0";
  }
  revision 2020-07-01 {
    description
      "- Added cli-recursive-delete to T1/E1 list
       - Removed trunk-group
       - Added default value to framing for T1/E1 controller
       - Changed default value from 75-ohm to 120-ohm for line-termination
       - Added src-ip-violation-action to Cellular list
       - Added range for timeslots in channel-group";
    cisco-semver:module-version "3.0.0";
  }
  revision 2020-03-01 {
    description
      "- Added pri-group and trunk-group
       - Added SHDSL controller configurations";
    cisco-semver:module-version "2.0.0";
  }
  revision 2019-11-01 {
    description
      "
       - Added new framing config";
    cisco-semver:module-version "1.1.0";
  }
  revision 2019-07-01 {
    description
      "Establish semantic version baseline";
    cisco-semver:module-version "1.0.0";
  }
  revision 2018-11-07 {
    description
      "Cleanup spelling errors in description statements";
  }
  revision 2018-07-24 {
    description
      "Add dependency to data-profile on profile id";
  }
  revision 2018-05-19 {
    description
      "Add options under vdsl operating mode auto";
  }
  revision 2018-05-02 {
    description
      "Remove cli-full-command for profile id authentication";
  }
  revision 2018-04-19 {
    description
      "Add firmware filename CLI to VDSL controller";
  }
  revision 2018-04-18 {
    description
      "Make linecode specific to controller type, and add profile for controller Cellular";
  }
  revision 2018-04-02 {
    description
      "Add tailf:cli-remove-before-change for channel group timeslots";
  }
  revision 2018-03-28 {
    description
      "Add configuration for VDSL controller";
  }
  revision 2018-03-06 {
    description
      "Add model for VDSL controller";
  }
  revision 2018-02-21 {
    description
      "Add options for lte modem and lte event";
  }
  revision 2018-02-14 {
    description
      "Add lte sms to controller Cellular";
  }
  revision 2018-02-10 {
    description
      "Add lte dying gasp";
  }
  revision 2018-02-03 {
    description
      "Remove lower case t1/e1/t3 controller name";
  }
  revision 2017-12-16 {
    description
      "Add data model for Controller Cellular lte options";
  }
  revision 2017-12-15 {
    description
      "Support lte failovertimer/firmware auto-sim/radio off";
  }
  revision 2017-11-28 {
    description
      "Add description node for tx-ex controllers";
  }
  revision 2017-02-07 {
    description
      "Initial revision";
  }

  grouping sonet-grouping {
    leaf framing {
      description
        "SONET framing";
      type enumeration {
        enum sonet;
        enum sdh;
      }
    }
    leaf shutdown {
      type empty;
    }
    container clock {
      description
        "SONET clock";
      leaf source {
        description
          "SONET clock source";
        type enumeration {
          enum internal;
          enum line;
        }
      }
    }
    container aug {
      description
        "AUG";
      leaf mapping {
        type enumeration {
          enum au-3;
          enum au-4;
        }
      }
    }
    list au-3 {
      description
        "AU-3";
      key "number";
      leaf number {
        description
          "AU-3 number";
        type int8 {
          range "1..3";
        }
      }
      container overhead {
        description
          "overhead";
        leaf byte {
          type enumeration {
            enum j1;
          }
        }
        leaf length {
          type uint8;
        }
      }
      container mode {
        description
          "mode";
        leaf mapping {
          type enumeration {
            enum c-11;
            enum c-12;
            enum c-2;
          }
        }
      }
    }
    container au-4-atm {
      container au-4 {
        description
          "AU-4";
        leaf number {
          description
            "AU-4 number";
          type int8 {
            range "1..3";
          }
        }
        leaf atm {
          type empty;
        }
      }
    }
    list au-4 {
      description
        "AU-4";
      key "number tug-3";
      leaf number {
        description
          "AU-4 number";
        type int8 {
          range "1..3";
        }
      }
      leaf tug-3 {
        description
          "TUG-3";
        type int8 {
          range "1..3";
        }
      }
      leaf mode {
        description
          "mode";
        type enumeration {
          enum c-11;
          enum c-12;
          enum c-2;
          enum c-3;
          enum c-4;
          enum e3;
        }
      }
      leaf cem-group {
        description
          "CEM group";
        type int32;
      }
      choice framing-choice {
        case unframed-case {
          leaf unframed {
            description
              "Unframed";
            type empty;
          }
        }
        case framing-case {
          leaf framing {
            type enumeration {
              enum unframed;
            }
          }
        }
      }
      container cem-group-timeslots {
        list tug-2 {
          description
            "TUG-2";
          key "number e1 cem-group";
          leaf number {
            description
              "TUG-2 number";
            type int8 {
              range "1..7";
            }
          }
          leaf e1 {
            description
              "E1";
            type int8 {
              range "1..3";
            }
          }
          leaf cem-group {
            description
              "CEM group";
            type int32;
          }
          leaf timeslots {
            description
              "Time slots";
            type string;
          }
        }
      }
      container channel-group-timeslots {
        list tug-2 {
          description
            "TUG-2";
          key "number e1 channel-group";
          leaf number {
            description
              "TUG-2 number";
            type int8 {
              range "1..7";
            }
          }
          leaf e1 {
            description
              "E1";
            type int8 {
              range "1..3";
            }
          }
          leaf channel-group {
            description
              "Channel group";
            type int32;
          }
          leaf timeslots {
            description
              "Time slots";
            type string;
          }
        }
      }
      container cem-group-unframed {
        list tug-2 {
          description
            "TUG-2";
          key "number e1 cem-group";
          leaf number {
            description
              "TUG-2 number";
            type int8 {
              range "1..7";
            }
          }
          leaf e1 {
            description
              "E1";
            type int8 {
              range "1..3";
            }
          }
          leaf cem-group {
            description
              "CEM group";
            type int32;
          }
          leaf unframed {
            description
              "Unframed";
            type empty;
          }
        }
      }
      container framing-unframed {
        list tug-2 {
          description
            "TUG-2";
          key "number e1";
          leaf number {
            description
              "TUG-2 number";
            type int8 {
              range "1..7";
            }
          }
          leaf e1 {
            description
              "E1";
            type int8 {
              range "1..3";
            }
          }
          leaf framing {
            type enumeration {
              enum unframed;
            }
          }
        }
      }
      container cem-group-atm {
        list tug-2 {
          description
            "TUG-2";
          key "number e1";
          leaf number {
            description
              "TUG-2 number";
            type int8 {
              range "1..7";
            }
          }
          leaf e1 {
            description
              "E1";
            type int8 {
              range "1..3";
            }
          }
          leaf atm {
            type empty;
          }
        }
      }
      container ima-group {
        list tug-2 {
          description
            "TUG-2";
          key "number e1 ima-group";
          leaf number {
            description
              "TUG-2 number";
            type int8 {
              range "1..7";
            }
          }
          leaf e1 {
            description
              "E1";
            type int8 {
              range "1..3";
            }
          }
          leaf ima-group {
            description
              "IMA group";
            type int32;
          }
        }
      }
    }
    container aps {
      description
        "SONET APS";
      container group {
        description
          "SONET APS group";
        leaf group-number {
          type uint8;
        }
        leaf acr {
          description
            "ACR";
          type int8;
        }
      }
      leaf working {
        description
          "Working line";
        type int8;
      }
      container protect {
        description
          "Protect line";
        leaf number {
          type int8;
        }
        leaf ip-addr {
          type inet:ipv4-address;
        }
      }
      leaf hspw-icrm-grp {
        type uint8;
      }
      container interchassis {
        leaf group {
          type uint8;
        }
      }
    }
  }

  grouping shdsl-coding-grouping {
    container coding {
      choice coding-choice {
        case sixteen-tcpam-case {
          leaf sixteen-tcpam {
            when "../../../../../../termination = 'co'";
            type empty;
          }
        }
        case thirty-two-tcpam-case {
          leaf thirtytwo-tcpam {
            when "../../../../../../termination = 'co'";
            type empty;
          }
        }
        case sixty-four-tcpam-case {
          leaf sixtyfour-tcpam {
            when "../../../../../../termination = 'co' and ../../../../../../mode = 'efm'";
            type empty;
          }
        }
        case one-twenty-eight-tcpam-case {
          leaf onetwentyeight-tcpam {
            when "../../../../../../termination = 'co' and ../../../../../../mode = 'efm'";
            type empty;
          }
        }
        case four-tcpam-case {
          leaf four-tcpam {
            when "../../../../../../termination = 'co' and ../../../../../../mode = 'efm'";
            type empty;
          }
        }
        case eight-tcpam-case {
          leaf eight-tcpam {
            when "../../../../../../termination = 'co' and ../../../../../../mode = 'efm'";
            type empty;
          }
        }
      }
    }
  }

  grouping threshold-grouping {
    leaf threshold {
      type int16 {
        range "-150..0";
      }
    }
  }

  grouping high-threshold-grouping {
    leaf threshold {
      type int8 {
        range "-20..0";
      }
    }
  }

  grouping mib-trap-grouping {
    leaf mib-trap {
      description
        "mibtrap";
      type empty;
    }
  }

  grouping ecio-option-grouping {
    leaf-list mib-trap {
      description
        "mibtrap";
      type enumeration {
        enum 1xrtt;
        enum All-lte;
        enum edge;
        enum evdoRel0;
        enum evdoRelA;
        enum evdoRelB;
        enum gprs;
        enum umts/wcdma;
        enum hsdpa;
        enum hsupa;
        enum hspa;
        enum hspa-plus;
        enum lte-tdd;
        enum lte-fdd;
      }
    }
    uses threshold-grouping;
  }

  grouping mib-trap-lte-grouping {
    leaf-list mib-trap {
      description
        "mibtrap";
      type enumeration {
        enum All-lte;
        enum lte-tdd;
        enum lte-fdd;
      }
    }
  }

  grouping threshold-mib-trap-lte-grouping {
    container abate {
      uses mib-trap-lte-grouping;
      uses threshold-grouping;
    }
    container onset {
      uses mib-trap-lte-grouping;
      uses threshold-grouping;
    }
  }

  grouping high-threshold-mib-trap-lte-grouping {
    container abate {
      uses mib-trap-lte-grouping;
      uses high-threshold-grouping;
    }
    container onset {
      uses mib-trap-lte-grouping;
      uses high-threshold-grouping;
    }
  }

  grouping config-controller-grouping {
    list controller-tx-ex-list {
      key "name number";
      leaf name {
        type enumeration {
          enum T1;
          enum E1;
          enum T3;
        }
      }
      leaf number {
        type string;
      }
      leaf atm {
        description
          "Specify atm";
        type empty;
      }
      container framing-config {
        description
          "Specify the type of Framing";
        leaf tx-framing {
          when "../../name = 'T1' or ../../name = 'T3'";
          type enumeration {
            enum esf;
            enum sf;
          }
          default "esf";
        }
        leaf e1-framing {
          when "../../name = 'E1'";
          type enumeration {
            enum crc4;
            enum no-crc4;
          }
          default "crc4";
        }
        leaf australia {
          when '../e1-framing';
          description
            "Australian Layer 1 homologation";
          type empty;
        }
      }
      leaf framing {
        status deprecated;
        type string;
      }
      container clock {
        container source {
          choice source-choice {
            container line {
              presence "true";
              leaf line-mode {
                type enumeration {
                  enum primary;
                  enum secondary;
                }
              }
            }
            leaf internal {
              type empty;
            }
            leaf loop-timed {
              type empty;
            }
            leaf network {
              description
                "Internal TDM Switch Source";
              type empty;
            }
          }
        }
      }
      leaf description {
        description
          "Controller specific description";
        type string {
          length "1..240";
        }
      }
      leaf linecode-t1 {
        when "../name = 'T1'";
        type enumeration {
          enum ami;
          enum b8zs;
        }
        default "b8zs";
      }
      leaf linecode-e1 {
        when "../name = 'E1'";
        type enumeration {
          enum ami;
          enum hdb3;
        }
        default "hdb3";
      }
      leaf linecode-t3 {
        when "../name = 'T3'";
        type enumeration {
          enum b3zs;
        }
      }
      container cablelength {
        choice cablelength-choice {
          leaf long {
            type string;
          }
          leaf short {
            type string;
          }
        }
      }
      leaf line-termination {
        when "../name = 'E1'";
        description
          "Specify the line termination for E1";
        type enumeration {
          enum 75-ohm;
          enum 120-ohm;
        }
        default "120-ohm";
      }
      list channel-group {
        key "number";
        leaf number {
          type uint8 {
            range "0..30";
          }
        }
        leaf-list timeslots {
          type union {
            type uint8 {
              range "1..31";
            }
            type string;
          }
        }
      }
      leaf fdl {
        when "../name = 'T1'";
        description
          "Specify the FDL standard for a T1 data link";
        type enumeration {
          enum ansi;
          enum att;
          enum both;
        }
      }
      leaf shutdown {
        description
          "Shut down this link (send Blue Alarm)";
        type boolean;
        default "false";
      }
      container pri-group {
        when "../name = 'T1' or ../name = 'E1'";
        description
          "Configure the specified timeslots for PRI";
        presence "true";
        leaf timeslots {
          description
            "List of timeslots in the pri-group";
          type string;
        }
        choice pri-group-choice {
          case voice-dsp-choice {
            leaf voice-dsp-ce1t1pri {
              description
                "Configure pri-group for voice applications";
              type empty;
            }
          }
          case service-choice {
            leaf service {
              description
                "Specify the service type";
              type enumeration {
                enum mgcp;
              }
            }
          }
          case nfas-choice {
            leaf nfas_d {
              description
                "Specify the operation of the D-channel time slot";
              type enumeration {
                enum backup;
                enum none;
                enum primary;
              }
            }
            leaf nfas_int {
              description
                "Specify the operation of the D-channel time slot";
              type uint8 {
                range "0..96";
              }
            }
            leaf nfas_group {
              description
                "Specify the NFAS group";
              type uint8 {
                range "0..31";
              }
            }
            leaf voice-dsp {
              description
                "Configure pri-group for voice applications";
              type empty;
            }
          }
        }
      }
    }
    container Gps-Dr {
      description
        "GPS/DR Module";
      container dead-reckoning {
        container nmea {
          container udp {
            description
              "UDP Transport";
            leaf source-address {
              description
                "Source address";
              type inet:ipv4-address;
            }
            leaf destination-address {
              description
                "Destination address";
              type inet:ipv4-address;
            }
            leaf destination-port {
              description
                "Destination port";
              type uint16;
            }
          }
        }
        leaf enable {
          description
            "enable GPS/DR feature";
          type empty;
        }
      }
    }
    list Cellular {
      key "id";
      leaf id {
        type string;
      }
      container lte {
        description
          "LTE type carrier";
        container sim {
          description
            "Subscriber Identity Module";
          container authenticate {
            description
              "CHV1 authentication";
            leaf pin-type {
              description
                "0 Specifies an UNENCRYPTED (cleartext) PIN will follow 7 Specifies a HIDDEN PIN will follow";
              type enumeration {
                enum 0;
                enum 7;
              }
            }
            leaf pin {
              description
                "Unecrypted PIN (Length 4 to 8 characters)Encrypted PIN";
              type string;
            }
            leaf slot {
              description
                "Slot number";
              type uint8;
            }
          }
          list data-profile-list {
            description
              "Data Profile number";
            key "slot";
            leaf slot {
              description
                "Slot number";
              type uint8;
            }
            leaf data-profile {
              description
                "Profile Number corresponding to the data bearer APN";
              type leafref {
                path "../../../../profile/id";
              }
            }
            leaf attach-profile {
              description
                "Profile Number corresponding to initial attach APN";
              type leafref {
                path "../../../../profile/id";
              }
            }
          }
          leaf max-retry {
            description
              "Maximum number of SIM switchover retries";
            type uint16;
          }
          container primary {
            description
              "Controller's primary SIM";
            leaf slot {
              description
                "Slot number";
              type uint8;
            }
          }
        }
        container sms {
          description
            "SMS configuration";
          container archive {
            description
              "SMS archive configuration";
            leaf path {
              description
                "path in URL to archive SMS";
              type enumeration {
                enum ftp:;
                enum http:;
                enum https:;
                enum pram:;
                enum rcp:;
                enum scp:;
                enum tftp:;
              }
            }
          }
        }
        container gps {
          description
            "GPS configuration";
          leaf enable {
            description
              "enable GPS feature";
            type empty;
          }
          leaf mode {
            description
              "select GPS mode";
            type enumeration {
              enum ms-based;
              enum standalone;
            }
          }
          container nmea-conf {
            leaf nmea {
              description
                "enable NMEA data";
              type empty;
            }
          }
          container nmea {
            container ip {
              description
                "enable NMEA stream over IP UDP interface";
              container udp {
                description
                  "UDP Transport";
                leaf source-address {
                  description
                    "Source address";
                  type inet:ipv4-address;
                }
                leaf destination-address {
                  description
                    "Destination address";
                  type inet:ipv4-address;
                }
                leaf destination-port {
                  description
                    "Destination port";
                  type uint16;
                }
              }
            }
          }
        }
        leaf failovertimer {
          description
            "Failover timeout value in mins";
          type uint8 {
            range "3..7";
          }
        }
        container firmware {
          description
            "Select firmware option";
          presence "true";
          leaf auto-sim {
            description
              "Select firmware auto-sim";
            type empty;
          }
        }
        container radio {
          description
            "Controller's radio";
          leaf off {
            description
              "Power down radio";
            type empty;
          }
        }
        container mobile-app {
          description
            "Mobile app configuration";
          container user-profile {
            description
              "Configure user profile with username, password, and privilege";
            leaf id {
              description
                "user profile ID number";
              type uint16 {
                range "1..15";
              }
            }
            leaf username {
              description
                "username";
              type string;
            }
            leaf password {
              description
                "password";
              type string;
            }
            leaf privilege {
              description
                "privilege";
              type string;
            }
          }
          container allow-list {
            description
              "List of allowed MSISDN's (phone numbers) to securely use the mobile app";
            leaf id {
              description
                "MSISDN ID number";
              type uint16 {
                range "1..15";
              }
            }
            leaf msisdn {
              description
                "MSISDN (phone number)";
              type string;
            }
          }
          container white-list {
            status deprecated;
            description
              "DEPRECATED: use 'allow-list' instead";
            leaf id {
              status deprecated;
              description
                "MSISDN ID number";
              type uint16 {
                range "1..15";
              }
            }
            leaf msisdn {
              status deprecated;
              description
                "MSISDN (phone number)";
              type string;
            }
          }
        }
        container modem {
          container dm-log {
            description
              "Modem DM logging configuration";
            container output {
              description
                "DM logging output files";
              choice output-choice {
                leaf local-uf {
                  description
                    "Use Module Utility flash to store DM logs";
                  type empty;
                }
                leaf path {
                  description
                    "URL to store DM log files";
                  type enumeration {
                    enum bootflash:;
                    enum flash:;
                    enum ftp:;
                    enum http:;
                    enum https:;
                    enum pram:;
                    enum rcp:;
                    enum scp:;
                    enum tftp:;
                  }
                }
              }
            }
            leaf filter {
              description
                "DM log filter file. Specify DM log filter location (in .sqf format)";
              type union {
                type enumeration {
                  enum bootflash:;
                  enum flash:;
                  enum webui:;
                }
                type string;
              }
            }
            leaf size {
              description
                "Specify maximum log size. Maximum log size in MB (default is 64MB, 0 means no upper limit)";
              type uint16 {
                range "0..1024";
              }
            }
            leaf filesize {
              description
                "Specify maximum log file size. Maximum file size in MB (default is 20MB)";
              type int8 {
                range "1..64";
              }
            }
            leaf rotation {
              description
                "DM log rotation (only supported on flash:)";
              type empty;
            }
            leaf enable {
              description
                "Enable DM logging";
              type empty;
            }
            container autostop {
              description
                "Auto stop trigger event";
              choice autostop-choice {
                leaf link-down {
                  description
                    "Cellular interface link down event";
                  type empty;
                }
                leaf timer {
                  description
                    "Timer interval in minutes";
                  type int8 {
                    range "12..120";
                  }
                }
              }
            }
          }
          container fota {
            description
              "Firmware upgrade over the air";
            leaf enable {
              description
                "Enable FOTA";
              type empty;
            }
            leaf poll-timer {
              description
                "Set poll timer for AVMS, Interval(in minutes) at which modem polls server for firmware.";
              type uint32 {
                range "15..525600";
              }
            }
          }
          container link-recovery {
            container rssi {
              leaf onset-threshold {
                type int32;
              }
            }
            leaf monitor-timer {
              type uint32;
            }
            leaf wait-timer {
              type uint32;
            }
            leaf debounce-count {
              type uint32;
            }
            leaf disable {
              type empty;
            }
          }
          container nas-log {
            description
              "Modem NAS logging configuration";
            container output {
              description
                "DM logging output files";
              leaf path {
                description
                  "URL to store DM log files";
                type enumeration {
                  enum bootflash:;
                  enum flash:;
                }
              }
            }
            leaf size {
              description
                "Specify maximum log size. Maximum log size in MB (default is 64MB, 0 means no upper limit)";
              type uint16 {
                range "0..1024";
              }
            }
            leaf filesize {
              description
                "Specify maximum log file size. Maximum file size in MB (default is 20MB)";
              type int8 {
                range "1..64";
              }
            }
            leaf enable {
              description
                "Enable NAS logging";
              type empty;
            }
          }
          container serviceability {
            if-feature "ios-features:cellular-serviceability-enhancement";
            description
              "Modem serviceability configuration";
            leaf modem-resets {
              description
                "Enable modem reset logging";
              type empty;
            }
            leaf interface-resets {
              description
                "Enable interface status logging";
              type empty;
            }
            leaf gps {
              description
                "Enable GPS logging";
              type empty;
            }
          }
        }
        container event {
          description
            "cellular snmp event persistence";
          container connection-status {
            description
              "connection status";
            leaf-list mib-trap {
              description
                "mibtrap";
              type enumeration {
                enum All-lte;
                enum active;
                enum inactive;
              }
            }
          }
          container ecio {
            description
              "ecio";
            container abate {
              uses ecio-option-grouping;
            }
            container onset {
              uses ecio-option-grouping;
            }
          }
          container modem-state {
            description
              "modem state";
            leaf-list mib-trap {
              description
                "mibtrap";
              type enumeration {
                enum all;
                enum down;
                enum up;
              }
            }
          }
          container network {
            description
              "enable trap for network";
            uses mib-trap-grouping;
          }
          container rsrp {
            description
              "Reference Signal Received Power";
            uses threshold-mib-trap-lte-grouping;
          }
          container rsrq {
            description
              "Reference Signal Received Quality";
            uses high-threshold-mib-trap-lte-grouping;
          }
          container rssi {
            description
              "rssi";
            uses threshold-mib-trap-lte-grouping;
          }
          container service {
            description
              "enable trap for service";
            uses mib-trap-grouping;
          }
          container temperature {
            description
              "modem temperature";
            container abate {
              uses mib-trap-grouping;
              uses threshold-grouping;
            }
            container onset {
              uses mib-trap-grouping;
              uses threshold-grouping;
            }
          }
        }
        container dyinggasp {
          description
            "Dying Gasp Configuration";
          container detach {
            description
              "Send Detach Request";
            leaf enable {
              description
                "Enable Dying Gasp Detach Request";
              type empty;
            }
          }
          container sms {
            description
              "SMS Commands";
            leaf send {
              description
                "Send SMS";
              type string;
            }
            leaf sms-text {
              description
                "SMS text until the end of line (EOL) up to 160 characters";
              type string {
                length "1..160";
              }
            }
          }
        }
      }
      list profile {
        description
          "LTE Profile management commands";
        key "id";
        leaf id {
          description
            "Profile identification number configuration";
          type int8 {
            range "1..16";
          }
        }
        leaf apn {
          description
            "Access point name configuration";
          type string;
        }
        leaf authentication {
          description
            "Select authentication type";
          type enumeration {
            enum chap;
            enum none;
            enum pap;
            enum pap_chap;
          }
        }
        leaf username {
          description
            "Username";
          when "../authentication and not(../authentication = 'none')";
          type string;
        }
        leaf password {
          description
            "Password";
          when "../authentication and not(../authentication = 'none')";
          type string;
        }
        leaf pdn-type {
          description
            "Select pdn type";
          type enumeration {
            enum ipv4;
            enum ipv4v6;
            enum ipv6;
          }
        }
        leaf slot {
          description
            "Associated sim slot";
          type uint8 {
            range "0..1";
          }
          default "0";
        }
        leaf no-overwrite {
          description
            "Don't replace, if profile exists";
          type empty;
        }
      }
      container src-ip-violation-action {
        description
          "Action to be performed on source ip violated pkts";
        leaf drop {
          description
            "Drop the packets if violation occurs";
          type enumeration {
            enum ipv4;
            enum ipv4v6;
            enum ipv6;
          }
        }
      }
    }
    list SONET {
      description
        "SONET";
      key "name";
      leaf name {
        type string;
      }
      uses sonet-grouping;
    }
    list SONET-ACR {
      description
        "SONET-ACR";
      key "name";
      leaf name {
        type string {
          pattern '([0-9\.])+';
        }
      }
      uses sonet-grouping;
    }
    list wanphy {
      description
        "wanphy";
      key "name";
      leaf name {
        type string;
      }
    }
    list VDSL {
      description
        "VDSL2 controller";
      key "name";
      leaf name {
        type string;
      }
      container operating {
        description
          "Configure auto or specific VDSL operating mode";
        container mode {
          choice operating-mode-choice-new {
            default "default-auto-config";
            leaf adsl1-new {
              type empty;
            }
            container adsl2-new {
              presence "true";
              leaf annex-new {
                type enumeration {
                  enum A;
                  enum M;
                  enum B;
                  enum J;
                }
              }
            }
            leaf default-auto-config {
              type enumeration {
                enum auto;
              }
              default "auto";
            }
            container auto-config {
              leaf adsl1-new {
                type empty;
              }
              leaf adsl2-new {
                type empty;
              }
              leaf adsl2plus-new {
                type empty;
              }
              leaf vdsl2-new {
                type empty;
              }
              leaf ansi-new {
                type empty;
              }
            }
            leaf vdsl2-new {
              type empty;
            }
            leaf ansi-new {
              type empty;
            }
            container adsl2plus-new {
              presence "true";
              leaf annex-new {
                type enumeration {
                  enum A;
                  enum M;
                  enum B;
                  enum J;
                }
              }
            }
          }
          choice operating-mode-choice {
            leaf adsl1 {
              status deprecated;
              type empty;
            }
            container adsl2 {
              status deprecated;
              presence "true";
              leaf annex {
                status deprecated;
                type enumeration {
                  enum A;
                  enum M;
                  enum B;
                  enum J;
                }
              }
            }
            container auto {
              status deprecated;
              presence "true";
              leaf adsl1 {
                status deprecated;
                type empty;
              }
              leaf adsl2 {
                status deprecated;
                type empty;
              }
              leaf adsl2plus {
                status deprecated;
                type empty;
              }
              leaf vdsl2 {
                status deprecated;
                type empty;
              }
              leaf ansi {
                status deprecated;
                type empty;
              }
            }
            leaf vdsl2 {
              status deprecated;
              type empty;
            }
            leaf ansi {
              status deprecated;
              type empty;
            }
            container adsl2plus {
              status deprecated;
              presence "true";
              leaf annex {
                status deprecated;
                type enumeration {
                  enum A;
                  enum M;
                  enum B;
                  enum J;
                }
              }
            }
          }
        }
      }
      container line-mode {
        description
          "Line Mode configuration to select Bonding/Single-wire";
        choice line-mode-choice {
          default "single-wire";
          leaf bonding {
            type empty;
          }
          container single-wire {
            leaf line-config {
              type enumeration {
                enum 0;
                enum 1;
              }
              default "0";
            }
            leaf profile {
              when "../line-config = '1'";
              type enumeration {
                enum 30a;
              }
            }
            container line {
              status deprecated;
              leaf zero {
                status deprecated;
                type empty;
              }
              container one {
                status deprecated;
                presence "true";
                leaf profile {
                  status deprecated;
                  type enumeration {
                    enum 30a;
                  }
                }
              }
            }
          }
        }
      }
      container training {
        description
          "Dsl firmware training log";
        container log {
          leaf filename {
            description
              "file name to store dsl training log";
            type string;
            default "flash:vdsllog.bin";
          }
        }
      }
      container firmware {
        description
          "xDSL PHY FW update";
        container phy {
          description
            "Component name";
          leaf filename {
            description
              "file name to read firmware";
            type string;
          }
        }
      }
      container sync {
        description
          "xDSL sync preferences";
        container interval {
          description
            "How many seconds between ITU and ANSI sync";
          leaf seconds {
            type uint32;
            default "0";
          }
        }
        container mode {
          description
            "Choose preferred sync mode";
          container itu {
            presence "true";
            leaf previous {
              type empty;
            }
          }
          leaf none {
            type empty;
          }
          container ansi {
            presence "true";
            leaf previous {
              type empty;
            }
          }
        }
      }
      container diagnostics-config {
        leaf DELT {
          type boolean;
          default "false";
        }
      }
      leaf diagnostics {
        status deprecated;
        type enumeration {
          enum DELT;
        }
      }
      leaf modem {
        description
          "vdsl modem configuration";
        type string {
          length "1..48";
        }
      }
      leaf shutdown-config {
        type boolean;
        default "false";
      }
      leaf shutdown {
        status deprecated;
        type empty;
      }
      leaf sra-config {
        description
          "Seamless rate adaptation";
        type boolean;
        default "true";
      }
      leaf sra {
        description
          "Seamless rate adaptation";
        status obsolete;
        type empty;
      }
      leaf bitswap-config {
        description
          "Bit swap";
        type boolean;
        default "true";
      }
      leaf bitswap {
        description
          "Bit swap";
        status obsolete;
        type empty;
      }
      leaf description {
        description
          "Controller specific description";
        type string {
          length "1..240";
        }
      }
    }
    list SHDSL {
      description
        "SHDSL controller";
      key "name";
      leaf name {
        type string;
      }
      leaf description {
        description
          "SHDSL controller description";
        type string {
          length "1..240";
        }
      }
      container firmware {
        description
          "Active firmware file name";
        container phy {
          description
            "Component name";
          leaf filename {
            description
              "File name to read firmware";
            type string;
          }
        }
      }
      leaf termination {
        description
          "Line termination for this interface";
        type enumeration {
          enum cpe;
          enum co;
        }
        default "cpe";
      }
      leaf mode {
        description
          "Operating mode";
        type enumeration {
          enum atm;
          enum efm;
        }
        default "atm";
      }
      list dsl-group {
        description
          "DSL group";
        key "group";
        leaf group {
          type enumeration {
            enum auto;
            enum 0;
            enum 1;
            enum 2;
            enum 3;
          }
        }
        leaf pairs {
          when "../group = '0' or ../group = '1' or ../group = '2' or ../group = '3'";
          type string {
            pattern '[0-3,-]*';
          }
        }
        leaf efm-bond {
          when "../../mode = 'efm' and not(../group = 'auto')";
          type empty;
        }
        leaf m-pair {
          when "not(../group = 'auto')";
          must "(../pairs = '0-1' or ../pairs = '0-2' or ../pairs = '0-3' or ../pairs = '2-3' or ../pairs = '0,1' or ../pairs = '0,1,2' or ../pairs = '0,1,2,3' or ../pairs = '2,3') and ../../mode = 'atm'" {
            error-message "M-pair mode requires pairs 0-1 or 0-2 or 0-3 or 2-3";
          }
          type empty;
        }
        container efm-grp {
          status obsolete;
          when '../efm-bond';
          container add {
            status obsolete;
            leaf link {
              status obsolete;
              type uint8 {
                range "0..3";
              }
            }
          }
          container delete {
            status obsolete;
            leaf link {
              status obsolete;
              type uint8 {
                range "0..3";
              }
            }
          }
        }
        container handshake {
          when "../../termination = 'cpe'";
          choice handshake-sample-choice {
            default "auto-case";
            case ieee-case {
              leaf ieee {
                when "../../../mode = 'efm'";
                type empty;
              }
            }
            case itut-case {
              leaf itut {
                when "../../../mode = 'efm'";
                type empty;
              }
            }
            case auto-case {
              leaf auto-config {
                when "../../../termination = 'cpe'";
                type enumeration {
                  enum auto;
                }
                default "auto";
              }
              leaf auto {
                status obsolete;
                when "../../../termination = 'cpe'";
                type empty;
              }
            }
            case g-shdsl-case {
              leaf g-shdsl {
                when "../../../termination = 'cpe' and ../../../mode = 'atm'";
                type empty;
              }
            }
            case g-shdsl-bis-case {
              leaf g-shdsl-bis {
                when "../../../termination = 'cpe' and ../../../mode = 'atm'";
                type empty;
              }
            }
          }
        }
        container handshake-config {
          when "../../termination = 'co' and ../../mode = 'efm'";
          choice handshake-sample-choice {
            default "itut-case";
            case ieee-case {
              leaf ieee {
                when "../../../mode = 'efm'";
                type empty;
              }
            }
            case itut-case {
              leaf itut {
                when "../../../mode = 'efm'";
                type enumeration {
                  enum itut;
                }
                default "itut";
              }
            }
            case auto-case {
              leaf auto {
                when "../../../termination = 'cpe'";
                type empty;
              }
            }
            case g-shdsl-case {
              leaf g-shdsl {
                when "../../../termination = 'cpe' and ../../../mode = 'atm'";
                type empty;
              }
            }
            case g-shdsl-bis-case {
              leaf g-shdsl-bis {
                when "../../../termination = 'cpe' and ../../../mode = 'atm'";
                type empty;
              }
            }
          }
        }
        container ignore {
          container crc {
            choice crc-choice {
              default "crc-value-choice";
              case crc-value-choice {
                leaf crc-value {
                  type uint16 {
                    range "0..60";
                  }
                  default "6";
                }
              }
              case always-choice {
                leaf always {
                  type empty;
                }
              }
            }
          }
        }
        leaf shutdown {
          type empty;
        }
        container shdsl {
          container four-wire {
            when "../../../mode = 'atm' and (../../group = 'auto' or ../../pairs = '0-1' or ../../pairs = '2-3' or ../../pairs = '0,1' or ../../pairs = '2,3')";
            container mode {
              container enhanced-config {
                presence "true";
                leaf vendor-id-npsg {
                  type empty;
                }
              }
              container enhanced {
                status deprecated;
                leaf vendor-id-npsg {
                  status deprecated;
                  type empty;
                }
              }
            }
          }
          container rate {
            when 'not(../rate-config)';
            choice rate-choice {
              case rate-value-case {
                leaf rate-value {
                  type uint16;
                }
              }
              case default-rate-auto-case {
                leaf default-auto-config {
                  type enumeration {
                    enum auto;
                  }
                  default "auto";
                }
              }
              case rate-auto-case {
                container auto-config {
                  leaf current-config {
                    type int8 {
                      range "-10..21";
                    }
                  }
                  leaf worst-config {
                    type int8 {
                      range "-10..21";
                    }
                  }
                }
                container auto {
                  status obsolete;
                  presence "true";
                  leaf current {
                    status obsolete;
                    type int8 {
                      range "-10..21";
                    }
                  }
                  leaf worst {
                    status obsolete;
                    type int8 {
                      range "-10..21";
                    }
                  }
                }
              }
              case rate-enhanced-case {
                container enhanced {
                  when "../../../../termination = 'co' and ../../../../mode = 'efm'";
                  choice enhanced-rate-choice {
                    case enhanced-rate-value-case {
                      leaf enhanced-rate-value {
                        type uint16;
                      }
                    }
                    case enhanced-rate-auto-case {
                      container auto {
                        presence "true";
                        leaf current {
                          type int8 {
                            range "-10..21";
                          }
                        }
                        leaf worst {
                          type int8 {
                            range "-10..21";
                          }
                        }
                      }
                    }
                  }
                }
              }
            }
          }
          container rate-config {
            when "((../../../termination = 'co') or (../../../mode = 'efm')) and ((((../annex/a-f/coding/four-tcpam or ../annex/a-f/coding/eight-tcpam) or (../annex/b-g/coding/four-tcpam or ../annex/b-g/coding/eight-tcpam)) or ((../annex/f/coding/four-tcpam or ../annex/f/coding/eight-tcpam) or (../annex/f/coding/four-tcpam or ../annex/f/coding/eight-tcpam))) or (((../annex/a-f/coding/sixtyfour-tcpam or ../annex/a-f/coding/onetwentyeight-tcpam) or (../annex/b-g/coding/sixtyfour-tcpam or ../annex/b-g/coding/onetwentyeight-tcpam)) or ((../annex/f/coding/sixtyfour-tcpam or ../annex/f/coding/onetwentyeight-tcpam) or (../annex/f/coding/sixtyfour-tcpam or ../annex/f/coding/onetwentyeight-tcpam))))";
            choice rate-choice {
              case rate-value-case {
                leaf rate-value {
                  type uint16;
                }
              }
              case rate-auto-case {
                container auto {
                  leaf current {
                    type int8 {
                      range "-10..21";
                    }
                  }
                  leaf worst {
                    type int8 {
                      range "-10..21";
                    }
                  }
                }
              }
              case rate-enhanced-case {
                container enhanced {
                  when "../../../../termination = 'co' and ../../../../mode = 'efm'";
                  choice enhanced-rate-choice {
                    default "default-enhanced-rate-auto-case";
                    case enhanced-rate-value-case {
                      leaf enhanced-rate-value {
                        type uint16;
                      }
                    }
                    case default-enhanced-rate-auto-case {
                      leaf default-enhanced-auto-config {
                        type enumeration {
                          enum auto;
                        }
                        default "auto";
                      }
                    }
                    case enhanced-rate-auto-case {
                      container auto {
                        leaf current {
                          type int8 {
                            range "-10..21";
                          }
                        }
                        leaf worst {
                          type int8 {
                            range "-10..21";
                          }
                        }
                      }
                    }
                  }
                }
              }
            }
          }
          container annex {
            when "../../../termination = 'co'";
            choice annex-choice {
              default "annex-b-case";
              case annex-a-case {
                leaf a {
                  type empty;
                }
              }
              case annex-a-f-case {
                container a-f {
                  uses shdsl-coding-grouping;
                }
              }
              case annex-b-case {
                leaf b-config {
                  type enumeration {
                    enum b;
                  }
                  default "b";
                }
                leaf b {
                  status obsolete;
                  type empty;
                }
              }
              case annex-b-g-case {
                container b-g {
                  uses shdsl-coding-grouping;
                }
              }
              case annex-f-case {
                container f {
                  uses shdsl-coding-grouping;
                }
              }
              case annex-g-case {
                container g {
                  uses shdsl-coding-grouping;
                }
              }
            }
          }
        }
      }
    }
  }

  augment "/ios:native/ios:controller" {
    uses config-controller-grouping;
  }
}
