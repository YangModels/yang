module Cisco-IOS-XE-nwpi-oper {
  yang-version 1.1;
  namespace "http://cisco.com/ns/yang/Cisco-IOS-XE-nwpi-oper";
  prefix Cisco-IOS-XE-nwpi-oper;

  import Cisco-IOS-XE-common-types {
    prefix common-types-ios-xe;
  }
  import Cisco-IOS-XE-nwpi-types {
    prefix Cisco-IOS-XE-nwpi-types;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Network Wide Path Insight operational data.
     Copyright (c) 2020-2021 by Cisco Systems, Inc.
     All rights reserved.";

  revision 2022-03-01 {
    description
      "- Added new enum for event type
       - Added new enum for nexthop type";
    reference
      "1.3.0";
    cisco-semver:module-version "1.3.0";
  }
  revision 2021-11-01 {
    description
      "1, Add new drop causes for 17.7.1 release.";
    reference
      "1.2.0";
    cisco-semver:module-version "1.2.0";
  }
  revision 2021-07-01 {
    description
      "1, packet: added event and parent packet support.
       2, flow: added ART metrics, qos statistics, per cause drop
          statistics, event, and flow insight support.
       3, domain: added domain monitor support.
       4, Change max vpn id from 65530 to 65531.";
    reference
      "1.1.0";
    cisco-semver:module-version "1.1.0";
  }
  revision 2020-11-01 {
    description
      "Initial revision";
    reference
      "1.0.0";
    cisco-semver:module-version "1.0.0";
  }

  typedef nwpi-feature-type {
    type enumeration {
      enum feature-without-policy {
        value 0;
        description
          "Feature without policy configured";
      }
      enum feature-with-policy {
        value 1;
        description
          "Feature with policy configured";
      }
    }
    description
      "Feature type";
  }

  typedef nwpi-flow-dir {
    type enumeration {
      enum flow-upstream {
        value 0;
        description
          "Flow forwarding from first hop to last hop";
      }
      enum flow-downstream {
        value 1;
        description
          "Flow forwarding from last hop to first hop";
      }
    }
    description
      "Flow direction";
  }

  typedef nwpi-feature-dir {
    type enumeration {
      enum feature-input {
        value 0;
        description
          "Feature running on input side";
      }
      enum feature-output {
        value 1;
        description
          "Feature running on output side";
      }
    }
    description
      "Feature direction";
  }

  typedef nwpi-event-type {
    type enumeration {
      enum event-none {
        value 0;
        description
          "Event no event";
      }
      enum event-first-packet {
        value 1;
        description
          "Event first packet of the flow";
      }
      enum event-dpi-ongoing {
        value 2;
        description
          "Event deep packet inspection ongoing";
      }
      enum event-dpi-done {
        value 3;
        description
          "Event deep packet inspection done";
      }
      enum event-path-change {
        value 4;
        description
          "Event flow network path changed";
      }
      enum event-sla-change {
        value 5;
        description
          "Event flow SLA level changed";
      }
      enum event-tcp-rst {
        value 6;
        description
          "Event TCP connection reset";
      }
      enum event-sn-packet {
        value 7;
        description
          "Event first packet of the flow from service node";
      }
      enum event-sn-resume {
        value 8;
        description
          "Event packet resumed from service node";
      }
    }
    description
      "Event type";
  }

  typedef nwpi-ms-category {
    type enumeration {
      enum endpoint-default {
        value 0;
        description
          "Default category";
      }
      enum endpoint-allow {
        value 1;
        description
          "Allow category";
      }
      enum endpoint-optimize {
        value 2;
        description
          "Optimize category";
      }
    }
    description
      "Microsoft Office 365 endpoint category";
  }

  typedef nwpi-flow-type {
    type enumeration {
      enum flow-unicast {
        value 0;
        description
          "Unicast flow";
      }
      enum flow-multicast {
        value 1;
        description
          "Multicast flow";
      }
    }
    description
      "Flow type";
  }

  typedef nwpi-nexthop-type {
    type enumeration {
      enum nexthop-invalid {
        value 0;
        description
          "Invalid nexthop";
      }
      enum nexthop-local-consumed {
        value 1;
        description
          "Local consumed";
      }
      enum nexthop-sdwan-session {
        value 2;
        description
          "SD-WAN session";
      }
      enum nexthop-sdwan-session-tloc-extension {
        value 3;
        description
          "SD-WAN session with TLOC extension";
      }
      enum nexthop-service-lan {
        value 4;
        description
          "Service LAN";
      }
      enum nexthop-nat-dia {
        value 5;
        description
          "NAT local breakout";
      }
      enum nexthop-cxp {
        value 6;
        description
          "SD-WAN cloud express";
      }
      enum nexthop-sig-tunnel {
        value 7;
        description
          "SD-WAN secure internet gateway";
      }
      enum nexthop-service-node {
        value 8;
        description
          "SD-WAN service node";
      }
    }
    description
      "Nexthop type";
  }

  typedef nwpi-color-type {
    type enumeration {
      enum color-invalid {
        value 0;
        description
          "Invalid color";
      }
      enum color-default {
        value 1;
        description
          "Default color";
      }
      enum color-mpls {
        value 2;
        description
          "MPLS color";
      }
      enum color-metro-ethernet {
        value 3;
        description
          "Metro ethernet color";
      }
      enum color-biz-internet {
        value 4;
        description
          "Business internet color";
      }
      enum color-public-internet {
        value 5;
        description
          "Public internet color";
      }
      enum color-lte {
        value 6;
        description
          "LTE color";
      }
      enum color-3g {
        value 7;
        description
          "Third generation color";
      }
      enum color-red {
        value 8;
        description
          "Red color";
      }
      enum color-green {
        value 9;
        description
          "Green color";
      }
      enum color-blue {
        value 10;
        description
          "Blue color";
      }
      enum color-gold {
        value 11;
        description
          "Gold color";
      }
      enum color-silver {
        value 12;
        description
          "Silver color";
      }
      enum color-bronze {
        value 13;
        description
          "Bronze color";
      }
      enum color-custom1 {
        value 14;
        description
          "Custom 1 color";
      }
      enum color-custom2 {
        value 15;
        description
          "Custom 2 color";
      }
      enum color-custom3 {
        value 16;
        description
          "Custom 3 color";
      }
      enum color-private1 {
        value 17;
        description
          "Private 1 color";
      }
      enum color-private2 {
        value 18;
        description
          "Private 2 color";
      }
      enum color-private3 {
        value 19;
        description
          "Private 3 color";
      }
      enum color-private4 {
        value 20;
        description
          "Private 4 color";
      }
      enum color-private5 {
        value 21;
        description
          "Private 5 color";
      }
      enum color-private6 {
        value 22;
        description
          "Private 6 color";
      }
    }
    description
      "SD-WAN color type";
  }

  typedef nwpi-encap-type {
    type enumeration {
      enum nwpi-encap-none {
        value 0;
        description
          "No encap";
      }
      enum nwpi-encap-gre {
        value 1;
        description
          "Generic routing encapsulation";
      }
      enum nwpi-encap-ipsec {
        value 2;
        description
          "IPSec";
      }
      enum nwpi-encap-control {
        value 3;
        description
          "Control";
      }
    }
    description
      "SD-WAN tunnel encap type";
  }

  typedef nwpi-stats-type {
    type enumeration {
      enum stats-base {
        value 0;
        description
          "Base statistics";
      }
      enum stats-advanced {
        value 1;
        description
          "Advanced statistics";
      }
    }
    description
      "Statistics type";
  }

  typedef nwpi-drop-cause {
    type enumeration {
      enum drop-reserved {
        value 0;
        description
          "Reserved";
      }
      enum drop-uidb-not-cfgd {
        value 1;
        description
          "Interface not configured";
      }
      enum drop-bad-uidb-idx {
        value 2;
        description
          "Bad interface index";
      }
      enum drop-bad-uidb-sub-idx {
        value 3;
        description
          "Bad interface sub index";
      }
      enum drop-unknown-encap {
        value 4;
        description
          "Unknown encapsulation";
      }
      enum drop-inv-l2-hdr {
        value 5;
        description
          "Invalid layer 2 header";
      }
      enum drop-bad-len {
        value 6;
        description
          "Bad length";
      }
      enum drop-tcp-badfrag {
        value 7;
        description
          "TCP bad fragment";
      }
      enum drop-ipv4-acl {
        value 8;
        description
          "IPv4 access control list (ACL)";
      }
      enum drop-ipv4-acl-lookup-miss {
        value 9;
        description
          "IPv4 access control list (ACL) lookup miss";
      }
      enum drop-bad-ip-checksum {
        value 10;
        description
          "Bad IP checksum";
      }
      enum drop-ip-format-err {
        value 11;
        description
          "IP format error";
      }
      enum drop-ip-bad-options {
        value 12;
        description
          "IP bad options";
      }
      enum drop-ipv4-martian {
        value 13;
        description
          "IPv4 martian";
      }
      enum drop-mpass-err {
        value 14;
        description
          "Multi pass error";
      }
      enum drop-ipv4-pbr {
        value 15;
        description
          "IPv4 policy based routing (PBR)";
      }
      enum drop-inv-hdr-err {
        value 16;
        description
          "Invalid header error";
      }
      enum drop-punt-err {
        value 17;
        description
          "Punt error";
      }
      enum drop-inject-err {
        value 18;
        description
          "Inject error";
      }
      enum drop-ipv4-no-route {
        value 19;
        description
          "IPv4 no route";
      }
      enum drop-qos-policing {
        value 20;
        description
          "Quality of service (QoS) policing";
      }
      enum drop-qos-actions {
        value 21;
        description
          "Quality of service (QoS) actions";
      }
      enum drop-null-jib-hdr-tbl {
        value 22;
        description
          "Null JIB header table";
      }
      enum drop-tail-drop {
        value 23;
        description
          "Tail drop";
      }
      enum drop-wred {
        value 24;
        description
          "Weighted random early detection (WRED)";
      }
      enum drop-invalid-queue {
        value 25;
        description
          "Invalid queue";
      }
      enum drop-invalid-wred {
        value 26;
        description
          "Invalid weighted random early detection (WRED)";
      }
      enum drop-mpls {
        value 27;
        description
          "Multiprotocol label switching (MPLS)";
      }
      enum drop-ipv6-truncatedpkts {
        value 28;
        description
          "IPv6 truncated packets";
      }
      enum drop-ipv6-formaterr {
        value 29;
        description
          "IPv6 format error";
      }
      enum drop-ipv6-badsource {
        value 30;
        description
          "IPv6 bad source address";
      }
      enum drop-ipv6-badhop {
        value 31;
        description
          "IPv6 bad hop count";
      }
      enum drop-ipv6-toobigpacket {
        value 32;
        description
          "IPv6 packet too big";
      }
      enum drop-ipv6-no-route {
        value 33;
        description
          "IPv6 no route";
      }
      enum drop-ipv6-acl-lookup-miss {
        value 34;
        description
          "IPv6 access control list (ACL) lookup miss";
      }
      enum drop-ipv6-acl {
        value 35;
        description
          "IPv6 access control list (ACL)";
      }
      enum drop-ip-acl-err {
        value 36;
        description
          "IP access control list (ACL) error";
      }
      enum drop-mac-acl {
        value 37;
        description
          "MAC access control list (ACL)";
      }
      enum drop-mac-acl-lookup-miss {
        value 38;
        description
          "MAC access control list (ACL) lookup miss";
      }
      enum drop-ipv4mc-no-route {
        value 39;
        description
          "IPv4 multicast no route";
      }
      enum drop-unknown-ext-header {
        value 40;
        description
          "Unknown extension header";
      }
      enum drop-ipv4mc-rpf-failed {
        value 41;
        description
          "IPv4 multicast reverse path forwarding failed";
      }
      enum drop-ipv4mc-invalid-replica-record {
        value 42;
        description
          "IPv4 multicast invalid replica record";
      }
      enum drop-ipv4mc-ttl-threshold-chk-failed {
        value 43;
        description
          "IPv4 multicast time to live (TTL) threshold check failed";
      }
      enum drop-ipv4mc-extra-replicae {
        value 44;
        description
          "IPv4 multicast extra replica";
      }
      enum drop-ipv4-mtr {
        value 45;
        description
          "IPv4 multi topology routing";
      }
      enum drop-internal-ctl {
        value 46;
        description
          "Internal control";
      }
      enum drop-bad-dist-fifo {
        value 47;
        description
          "Bad distribution first in first out (FIFO)";
      }
      enum drop-frfab-wred-drop {
        value 48;
        description
          "Frame Relay weighted random early detection (WRED) drop";
      }
      enum drop-firewall-nonsession {
        value 49;
        description
          "Firewall no session";
      }
      enum drop-firewall-invalid-zone {
        value 50;
        description
          "Firewall invalid zone";
      }
      enum drop-firewall-backpressure {
        value 51;
        description
          "Firewall backpressure";
      }
      enum drop-firewall-l4-insp {
        value 52;
        description
          "Firewall layer 4 insp";
      }
      enum drop-ip-frag-err {
        value 53;
        description
          "IP fragments error";
      }
      enum drop-no-gpm-memory-err {
        value 54;
        description
          "No global packet memory memory error";
      }
      enum drop-for-us {
        value 55;
        description
          "For us";
      }
      enum drop-ipsec-input {
        value 56;
        description
          "IPSEC input";
      }
      enum drop-ipsec-ike-indicate {
        value 57;
        description
          "IPSEC IKE indicate";
      }
      enum drop-ipsec-invalid-sa {
        value 58;
        description
          "IPSEC invalid security association (SA)";
      }
      enum drop-ipsec-tail-drop {
        value 59;
        description
          "IPSEC tail drop";
      }
      enum drop-layer2-no-route {
        value 60;
        description
          "Layer 2 no route";
      }
      enum drop-icmp {
        value 61;
        description
          "ICMP packet";
      }
      enum drop-ip-ttl-exceeded {
        value 62;
        description
          "IP time to live (TTL) exceeded";
      }
      enum drop-tunnel-bad-gre-checksum {
        value 63;
        description
          "Tunnel bad generic route encapsulation (GRE) checksum";
      }
      enum drop-tunnel-misconfiguration {
        value 64;
        description
          "Tunnel misconfiguration";
      }
      enum drop-gre-bad-options {
        value 65;
        description
          "Generic route encapsulation (GRE) bad options";
      }
      enum drop-frag-tail-drop {
        value 66;
        description
          "Fragments tail drop";
      }
      enum drop-unconfigured-fia {
        value 67;
        description
          "Unconfigured feature invocation array (FIA)";
      }
      enum drop-ipv4-fpm {
        value 68;
        description
          "IPv4 flexible packet match";
      }
      enum drop-nat-in2out {
        value 69;
        description
          "NAT in to out";
      }
      enum drop-nat-out2in {
        value 70;
        description
          "NAT out to in";
      }
      enum drop-pa-walk-err {
        value 71;
        description
          "Packet abstraction walk error";
      }
      enum drop-ipv4-routing-err {
        value 72;
        description
          "IPv4 routing error";
      }
      enum drop-ipv6-routing-err {
        value 73;
        description
          "IPv6 routing error";
      }
      enum drop-mpass-invalid-fs-vector {
        value 74;
        description
          "Multi pass invalid fs vector";
      }
      enum drop-reass-drop {
        value 75;
        description
          "Reassembly drop";
      }
      enum drop-reass-frag-too-big {
        value 76;
        description
          "Reassembly fragments too big";
      }
      enum drop-reass-no-frag-info {
        value 77;
        description
          "Reassembly no fragments information";
      }
      enum drop-reass-no-frag-info-low {
        value 78;
        description
          "Reassembly no fragments information low";
      }
      enum drop-reass-bad-len {
        value 79;
        description
          "Reassembly bad length";
      }
      enum drop-reass-too-many-frags {
        value 80;
        description
          "Reassembly too many fragments";
      }
      enum drop-reass-no-frags-left {
        value 81;
        description
          "Reassembly no fragments left";
      }
      enum drop-reass-overlap {
        value 82;
        description
          "Reassembly overlap";
      }
      enum drop-reass-timeout {
        value 83;
        description
          "Reassembly timeout";
      }
      enum drop-no-mem {
        value 84;
        description
          "No memory";
      }
      enum drop-vfr-err {
        value 85;
        description
          "Virtual forwarding and routing (VFR) error";
      }
      enum drop-vfr-tail-drop {
        value 86;
        description
          "Virtual forwarding and routing (VFR) tail drop";
      }
      enum drop-iphc {
        value 87;
        description
          "IP header compression";
      }
      enum drop-multilink-cfg {
        value 88;
        description
          "Multilink configuration";
      }
      enum drop-mlp {
        value 89;
        description
          "Multilink protocol (MLP)";
      }
      enum drop-min-tu {
        value 90;
        description
          "Minimum transfer unit";
      }
      enum drop-max-tu {
        value 91;
        description
          "Maximum transfer unit";
      }
      enum drop-ipv4-unclassified {
        value 92;
        description
          "IPv4 unclassified";
      }
      enum drop-ipv6-unclassified {
        value 93;
        description
          "IPv6 unclassified";
      }
      enum drop-ipv4-no-adj {
        value 94;
        description
          "IPv4 no adjacency";
      }
      enum drop-ipv4-null0 {
        value 95;
        description
          "IPv4 null0";
      }
      enum drop-ipv6-null0 {
        value 96;
        description
          "IPv6 null0";
      }
      enum drop-mpls-mismatch-linktype {
        value 97;
        description
          "Multiprotocol label switching (MPLS) mismatch linktype";
      }
      enum drop-mpls-frag-req {
        value 98;
        description
          "Multiprotocol label switching (MPLS) fragments request";
      }
      enum drop-choice-oce {
        value 99;
        description
          "Choice output chain element (OCE)";
      }
      enum drop-unsupported-oce {
        value 100;
        description
          "Unsupported output chain element (OCE)";
      }
      enum drop-attn-invalid-spid {
        value 101;
        description
          "Attention protocol invalid sync point identifier";
      }
      enum drop-inv-common-preamble {
        value 102;
        description
          "Invalid common preamble";
      }
      enum drop-ext-drop-path {
        value 103;
        description
          "Extension drop path";
      }
      enum drop-frr-oce-no-backup {
        value 104;
        description
          "Fast reroute (FRR) output chain element (OCE) no backup";
      }
      enum drop-frr-oce-invalid-state {
        value 105;
        description
          "Fast reroute (FRR) output chain element (OCE) invalid state";
      }
      enum drop-bqs-oor {
        value 106;
        description
          "Buffering, queuing and scheduling out of resources";
      }
      enum drop-ess-bad-sess-uidb {
        value 107;
        description
          "Edge switching services bad session interface";
      }
      enum drop-ess-pktsb-missed {
        value 108;
        description
          "Edge switching services packet sub block missed";
      }
      enum drop-ess-unsup-pkt-type {
        value 109;
        description
          "Edge switching services unsupported packet type";
      }
      enum drop-ess-no-encap-info {
        value 110;
        description
          "Edge switching services no encapsulation information";
      }
      enum drop-ess-inv-switch-mode {
        value 111;
        description
          "Edge switching services invalid switch mode";
      }
      enum drop-inv-ppp-cp-pkt {
        value 112;
        description
          "Invalid PPP control protocol packet";
      }
      enum drop-ppp-cxt-missed {
        value 113;
        description
          "PPP context missed";
      }
      enum drop-ess-unbound-session {
        value 114;
        description
          "Edge switching services unbound session";
      }
      enum drop-ess-pi-inv-subtype {
        value 115;
        description
          "Edge switching services platform independent invalid subtype";
      }
      enum drop-ess-pi-state-err {
        value 116;
        description
          "Edge switching services platform independent state error";
      }
      enum drop-ess-inject-bad-hdr {
        value 117;
        description
          "Edge switching services inject bad header";
      }
      enum drop-ess-l2-hdr-too-big {
        value 118;
        description
          "Edge switching services layer 2 header too big";
      }
      enum drop-pppox-unconfigured {
        value 119;
        description
          "PPP over any protocol (PPPoX) unconfigured";
      }
      enum drop-pppoe-pkt-inv-hdr {
        value 120;
        description
          "PPP over Ethernet (PPPoE) packet invalid header";
      }
      enum drop-pppoe-pkt-bad-len {
        value 121;
        description
          "PPP over Ethernet (PPPoE) packet bad length";
      }
      enum drop-pppoe-no-session {
        value 122;
        description
          "PPP over Ethernet (PPPoE) no session";
      }
      enum drop-pppoe-inv-encap-info {
        value 123;
        description
          "PPP over Ethernet (PPPoE) invalid encapsulation information";
      }
      enum drop-ess-cac {
        value 124;
        description
          "Edge switching services call admission control";
      }
      enum drop-l2tp-unconfigured {
        value 125;
        description
          "Layer 2 tunnelling protocol (L2TP) unconfigured";
      }
      enum drop-l2tp-pkt-inv-hdr {
        value 126;
        description
          "Layer 2 tunnelling protocol (L2TP) packet invalid header";
      }
      enum drop-l2tp-pkt-bad-len {
        value 127;
        description
          "Layer 2 tunnelling protocol (L2TP) packet bad length";
      }
      enum drop-l2tp-no-session {
        value 128;
        description
          "Layer 2 tunnelling protocol (L2TP) no session";
      }
      enum drop-l2tp-pktsb-missed {
        value 129;
        description
          "Layer 2 tunnelling protocol (L2TP) packet sub block missed";
      }
      enum drop-l2tp-security-check {
        value 130;
        description
          "Layer 2 tunnelling protocol (L2TP) security check";
      }
      enum drop-l2tp-bad-udp-chksum {
        value 131;
        description
          "Layer 2 tunnelling protocol (L2TP) bad UDP checksum";
      }
      enum drop-l2tp-ooo-rx-pkt {
        value 132;
        description
          "Layer 2 tunnelling protocol (L2TP) ooo receive packet";
      }
      enum drop-l2tp-exceed-tx-mtu {
        value 133;
        description
          "Layer 2 tunnelling protocol (L2TP) exceed transmit mtu";
      }
      enum drop-ipsec-output {
        value 134;
        description
          "IPSEC output";
      }
      enum drop-ipsec-ted-indicate {
        value 135;
        description
          "IPSEC tunnel end point discovery (TED) indicate";
      }
      enum drop-ipsec-deny-drop {
        value 136;
        description
          "IPSEC deny drop";
      }
      enum drop-l2tp-cxt-missed {
        value 137;
        description
          "Layer 2 tunnelling protocol (L2TP) context missed";
      }
      enum drop-l2tp-tx-seq-missed {
        value 138;
        description
          "Layer 2 tunnelling protocol (L2TP) transmit sequence missed";
      }
      enum drop-disabled {
        value 139;
        description
          "Disabled";
      }
      enum drop-ipv6-no-adj {
        value 140;
        description
          "IPv6 no adjacency";
      }
      enum drop-not-enabled {
        value 141;
        description
          "Not enabled";
      }
      enum drop-special-multicast-obj {
        value 142;
        description
          "Special multicast object";
      }
      enum drop-illegal-obj {
        value 143;
        description
          "Illegal object";
      }
      enum drop-unresolved {
        value 144;
        description
          "Unresolved";
      }
      enum drop-discard {
        value 145;
        description
          "Discard";
      }
      enum drop-ipv6mc-no-route {
        value 146;
        description
          "IPv6 multicast no route";
      }
      enum drop-ipv6mc-rpf-failed {
        value 147;
        description
          "IPv6 multicast reverse path forwarding failed";
      }
      enum drop-ipv6mc-invalid-replica-record {
        value 148;
        description
          "IPv6 multicast invalid replica record";
      }
      enum drop-ipv6mc-ttl-threshold-chk-failed {
        value 149;
        description
          "IPv6 multicast time to live (TTL) threshold check failed";
      }
      enum drop-ipv6mc-extra-replica {
        value 150;
        description
          "IPv6 multicast extra replica";
      }
      enum drop-layer2-switching {
        value 151;
        description
          "Layer 2 switching";
      }
      enum drop-internal-intf-err {
        value 152;
        description
          "Internal interface error";
      }
      enum drop-sbc-police-punt {
        value 153;
        description
          "Session border controller (SBC) police punt";
      }
      enum drop-sbc-uidb {
        value 154;
        description
          "Session border controller (SBC) interface";
      }
      enum drop-sbc-sess {
        value 155;
        description
          "Session border controller (SBC) session";
      }
      enum drop-sbc-mmoh-invalid-replica-record {
        value 156;
        description
          "Session border controller (SBC) music on hold invalid replica record";
      }
      enum drop-mpls-ipv6-frag-req {
        value 157;
        description
          "Multiprotocol label switching (MPLS) IPv6 fragments request";
      }
      enum drop-sw-mac-filter {
        value 158;
        description
          "Software MAC filter";
      }
      enum drop-tunnel-bad-pim-checksum {
        value 159;
        description
          "Tunnel bad protocol independent multicast (PIM) checksum";
      }
      enum drop-tunnel-unsupported-config {
        value 160;
        description
          "Tunnel unsupported config";
      }
      enum drop-firewall-no-forwarding {
        value 161;
        description
          "Firewall no forwarding";
      }
      enum drop-erspan {
        value 162;
        description
          "Extended reach SPAN (ERSPAN)";
      }
      enum drop-ipv4-urpf-null-path-list {
        value 163;
        description
          "IPv4 unicast reverse path forwarding null path list";
      }
      enum drop-mpls-unclassified {
        value 164;
        description
          "Multiprotocol label switching (MPLS) unclassified";
      }
      enum drop-mpls-eos-invalid {
        value 165;
        description
          "Multiprotocol label switching (MPLS) end of stack invalid";
      }
      enum drop-glean-adj-unsupport-linktype {
        value 166;
        description
          "Glean adjacency unsupported linktype";
      }
      enum drop-mpls-label-oce-ptr-null {
        value 167;
        description
          "Multiprotocol label switching (MPLS) label output chain element (OCE) pointer null";
      }
      enum drop-mpls-label-oce-invalid-label {
        value 168;
        description
          "Multiprotocol label switching (MPLS) label output chain element (OCE) invalid label";
      }
      enum drop-mpls-label-oce-unsup-linktype {
        value 169;
        description
          "Multiprotocol label switching (MPLS) label output chain element (OCE) unsupported linktype";
      }
      enum drop-lookup-oce-should-drop {
        value 170;
        description
          "Lookup output chain element (OCE) should drop";
      }
      enum drop-lookup-oce-unsupport-linktype {
        value 171;
        description
          "Lookup output chain element (OCE) unsupported linktype";
      }
      enum drop-unsupport-linktype-no-route {
        value 172;
        description
          "Unsupported linktype no route";
      }
      enum drop-unsupport-linktype-null0 {
        value 173;
        description
          "Unsupported linktype null0";
      }
      enum drop-sr-te-remote-error {
        value 174;
        description
          "Segment routing traffic engineering (TE) remote error";
      }
      enum drop-ipv4-pop-pipe-php-ttl-expire {
        value 175;
        description
          "IPv4 pop pipe penultimate hop pop time to live (TTL) expire";
      }
      enum drop-ipv4-pop-unf-uhp-ttl-expire {
        value 176;
        description
          "IPv4 pop uniform ultimate hop pop time to live (TTL) expire";
      }
      enum drop-ipv4-pop-unf-php-ttl-expire {
        value 177;
        description
          "IPv4 pop uniform penultimate hop pop time to live (TTL) expire";
      }
      enum drop-mpls-pop-pipe-ttl-expire {
        value 178;
        description
          "Multiprotocol label switching (MPLS) pop pipe time to live (TTL) expire";
      }
      enum drop-mpls-pop-unf-uhp-ttl-expire {
        value 179;
        description
          "Multiprotocol label switching (MPLS) pop uniform ultimate hop pop time to live (TTL) expire";
      }
      enum drop-mpls-pop-unf-php-ttl-expire {
        value 180;
        description
          "Multiprotocol label switching (MPLS) pop uniform penultimate hop pop time to live (TTL) expire";
      }
      enum drop-label-pop-unsupport-linktype {
        value 181;
        description
          "Label pop unsupported linktype";
      }
      enum drop-mpls-no-route {
        value 182;
        description
          "Multiprotocol label switching (MPLS) no route";
      }
      enum drop-mpls-icmp-invalid-hdr {
        value 183;
        description
          "Multiprotocol label switching (MPLS) ICMP invalid header";
      }
      enum drop-mpls-sanity-echo-req {
        value 184;
        description
          "Multiprotocol label switching (MPLS) sanity echo request";
      }
      enum drop-mpls-sanity-drop {
        value 185;
        description
          "Multiprotocol label switching (MPLS) sanity drop";
      }
      enum drop-ess-unprov-session {
        value 186;
        description
          "Edge switching services unprovisioned session";
      }
      enum drop-firewall-policy {
        value 187;
        description
          "Firewall policy";
      }
      enum drop-firewall-l4 {
        value 188;
        description
          "Firewall layer 4";
      }
      enum drop-firewall-l7 {
        value 189;
        description
          "Firewall layer 7";
      }
      enum drop-firewall-no-new-sessions {
        value 190;
        description
          "Firewall no new sessions";
      }
      enum drop-firewall-not-initiator {
        value 191;
        description
          "Firewall not initiator";
      }
      enum drop-firewall-not-from-init {
        value 192;
        description
          "Firewall not from init";
      }
      enum drop-gen-pkt-replication {
        value 193;
        description
          "Gen packet replication";
      }
      enum drop-esf-l4r-bad-config {
        value 194;
        description
          "Edge switching services feature (ESF) layer 4 redirect bad config";
      }
      enum drop-esf-l4r-trans-unavail {
        value 195;
        description
          "Edge switching services feature (ESF) layer 4 redirect trans unavailable";
      }
      enum drop-esf-pbhk-bad-config {
        value 196;
        description
          "Edge switching services feature (ESF) port-bundle host key bad config";
      }
      enum drop-esf-pbhk-unalloc {
        value 197;
        description
          "Edge switching services feature (ESF) port-bundle host key unallocated";
      }
      enum drop-esf-pbhk-port-unavail {
        value 198;
        description
          "Edge switching services feature (ESF) port-bundle host key port unavailable";
      }
      enum drop-esf-pbhk-port-notfound {
        value 199;
        description
          "Edge switching services feature (ESF) port-bundle host key port not found";
      }
      enum drop-esf-pbhk-port-removed {
        value 200;
        description
          "Edge switching services feature (ESF) port-bundle host key port removed";
      }
      enum drop-mpls-no-adj {
        value 201;
        description
          "Multiprotocol label switching (MPLS) no adjacency";
      }
      enum drop-ipv4-adj-drop {
        value 202;
        description
          "IPv4 adjacency drop";
      }
      enum drop-ipv6-adj-drop {
        value 203;
        description
          "IPv6 adjacency drop";
      }
      enum drop-mpls-adj-drop {
        value 204;
        description
          "Multiprotocol label switching (MPLS) adjacency drop";
      }
      enum drop-bad-adj {
        value 205;
        description
          "Bad adjacency";
      }
      enum drop-punt-policer-drop {
        value 206;
        description
          "Punt policer drop";
      }
      enum drop-punt-global-policer-drop {
        value 207;
        description
          "Punt global policer drop";
      }
      enum drop-esf-tc-drop {
        value 208;
        description
          "Edge switching services feature (ESF) traffic classification drop";
      }
      enum drop-esf-drl-drop {
        value 209;
        description
          "Edge switching services feature (ESF) dynamic rate limit drop";
      }
      enum drop-ess-ipsub-drop {
        value 210;
        description
          "Edge switching services IP subscriber drop";
      }
      enum drop-ess-ipsub-fsol-drop {
        value 211;
        description
          "Edge switching services IP subscriber first sign of life throttle drop";
      }
      enum drop-ess-ipsub-classifier-drop {
        value 212;
        description
          "Edge switching services IP subscriber classifier drop";
      }
      enum drop-ess-ipsub-ka-drop {
        value 213;
        description
          "Edge switching services IP subscriber keepalive drop";
      }
      enum drop-oam-loopback {
        value 214;
        description
          "Operations, administration and management (OAM) loopback";
      }
      enum drop-unconfigured-ipv4-fia {
        value 215;
        description
          "Unconfigured IPv4 feature invocation array (FIA)";
      }
      enum drop-unconfigured-ipv6-fia {
        value 216;
        description
          "Unconfigured IPv6 feature invocation array (FIA)";
      }
      enum drop-unconfigured-mpls-fia {
        value 217;
        description
          "Unconfigured multiprotocol label switching (MPLS) feature invocation array (FIA)";
      }
      enum drop-smi-disabled {
        value 218;
        description
          "Simple management interface disabled";
      }
      enum drop-oce-drop-adj {
        value 219;
        description
          "Output chain element (OCE) drop adjacency";
      }
      enum drop-internal {
        value 220;
        description
          "Internal";
      }
      enum drop-inv-spa-hdr {
        value 221;
        description
          "Invalid shared port adaptor (SPA) header";
      }
      enum drop-ppe-exception {
        value 222;
        description
          "Packet processing engine exception";
      }
      enum drop-internal-replication {
        value 223;
        description
          "Internal replication";
      }
      enum drop-internal-recycle-tail {
        value 224;
        description
          "Internal recycle tail";
      }
      enum drop-internal-no-gpm {
        value 225;
        description
          "Internal no global packet memory";
      }
      enum drop-internal-no-channel-mem {
        value 226;
        description
          "Internal no channel memory";
      }
      enum drop-ip-sia-hdr-err {
        value 227;
        description
          "IP service insertion architecture (SIA) header error";
      }
      enum drop-ip-sia-hop-limit-exceeded {
        value 228;
        description
          "IP service insertion architecture (SIA) hop limit exceeded";
      }
      enum drop-ip-sia-processing-err {
        value 229;
        description
          "IP service insertion architecture (SIA) processing error";
      }
      enum drop-sslvpn-svi-invalid-h {
        value 230;
        description
          "SSL VPN switched virtual interface (SVI) invalid header";
      }
      enum drop-esf-acct-exceed-drop {
        value 231;
        description
          "Edge switching services feature (ESF) accounting exceed drop";
      }
      enum drop-tcp {
        value 232;
        description
          "TCP packet";
      }
      enum drop-invalid-encap {
        value 233;
        description
          "Invalid encapsulation";
      }
      enum drop-dsp {
        value 234;
        description
          "Digital signal processing (DSP)";
      }
      enum drop-mpls-csc-drop {
        value 235;
        description
          "Multiprotocol label switching (MPLS) carrier supporting carrier drop";
      }
      enum drop-cstp-cdtp-inv-frame {
        value 236;
        description
          "Cisco SSL tunneling Protocol Cisco DTLS tunneling Protocol invalid frame";
      }
      enum drop-cstp-cdtp-no-tunnel {
        value 237;
        description
          "Cisco SSL tunneling Protocol Cisco DTLS tunneling Protocol no tunnel";
      }
      enum drop-cstp-cdtp-unsup-frame {
        value 238;
        description
          "Cisco SSL tunneling Protocol Cisco DTLS tunneling Protocol unsupported frame";
      }
      enum drop-esf-l4r-trans-sess-limit {
        value 239;
        description
          "Edge switching services feature (ESF) layer 4 redirect trans session limit";
      }
      enum drop-lisp-elig-oce {
        value 240;
        description
          "LISP eligible output chain element (OCE)";
      }
      enum drop-lisp-misconfiguration {
        value 241;
        description
          "LISP misconfiguration";
      }
      enum drop-lisp-disabled {
        value 242;
        description
          "LISP disabled";
      }
      enum drop-lisp-decap-failed {
        value 243;
        description
          "LISP deencapsulation failed";
      }
      enum drop-lisp-hash-lkup-failed {
        value 244;
        description
          "LISP hash lookup failed";
      }
      enum drop-lisp-failed-punt-lsb-mismatch {
        value 245;
        description
          "LISP failed to punt lsb mismatch";
      }
      enum drop-nat64-v6tov4 {
        value 246;
        description
          "NAT64 IPv6 to IPv4";
      }
      enum drop-nat64-v4tov6 {
        value 247;
        description
          "NAT64 IPv4 to IPv6";
      }
      enum drop-tunnel-sec-chk-fail {
        value 248;
        description
          "Tunnel security check fail";
      }
      enum drop-servicewire-hdr-err {
        value 249;
        description
          "Servicewire header error";
      }
      enum drop-servicewire-hop-limit-exceeded {
        value 250;
        description
          "Servicewire hop limit exceeded";
      }
      enum drop-servicewire-processing-err {
        value 251;
        description
          "Servicewire processing error";
      }
      enum drop-l2bd {
        value 252;
        description
          "Layer 2 Bridge Domain (L2BD)";
      }
      enum drop-tcp-bp-sslvpn {
        value 253;
        description
          "TCP back pressure SSL VPN";
      }
      enum drop-evc-efp-egress-filter {
        value 254;
        description
          "Ethernet virtual connection (EVC) ethernet flowpoint (EFP) egress filter";
      }
      enum drop-sslvpn-svi-if-err {
        value 255;
        description
          "SSL VPN switched virtual interface (SVI) interface error";
      }
      enum drop-sslvpn-ctx-null {
        value 256;
        description
          "SSL VPN ctx null";
      }
      enum drop-sslvpn-ctx-not-alive {
        value 257;
        description
          "SSL VPN ctx not alive";
      }
      enum drop-sslvpn-invalid-pkt {
        value 258;
        description
          "SSL VPN invalid packet";
      }
      enum drop-sslvpn-socket-wr-err {
        value 259;
        description
          "SSL VPN socket write error";
      }
      enum drop-sslvpn-pkt-rc-err {
        value 260;
        description
          "SSL VPN packet return code error";
      }
      enum drop-sslvpn-null-rc {
        value 261;
        description
          "SSL VPN null return code";
      }
      enum drop-sslvpn-wrong-pkt-type {
        value 262;
        description
          "SSL VPN wrong packet type";
      }
      enum drop-sslvpn-not-ssl-record {
        value 263;
        description
          "SSL VPN not ssl record";
      }
      enum drop-firewall-syncookie {
        value 264;
        description
          "Firewall syncookie";
      }
      enum drop-l2bd-mac-security-violation {
        value 265;
        description
          "Layer 2 Bridge Domain (L2BD) MAC security violation";
      }
      enum drop-l2bd-src-filter {
        value 266;
        description
          "Layer 2 Bridge Domain (L2BD) source filter";
      }
      enum drop-l2bd-policy {
        value 267;
        description
          "Layer 2 Bridge Domain (L2BD) policy";
      }
      enum drop-l2bd-repl-start {
        value 268;
        description
          "Layer 2 Bridge Domain (L2BD) replication start";
      }
      enum drop-l2bd-repl-end {
        value 269;
        description
          "Layer 2 Bridge Domain (L2BD) replication end";
      }
      enum drop-l2bd-recycle-tail {
        value 270;
        description
          "Layer 2 Bridge Domain (L2BD) recycle tail";
      }
      enum drop-l2bd-static-mac-move {
        value 271;
        description
          "Layer 2 Bridge Domain (L2BD) static MAC move";
      }
      enum drop-l2bd-bd-disabled {
        value 272;
        description
          "Layer 2 Bridge Domain (L2BD) bridge domain disabled";
      }
      enum drop-l2bd-inject-no-sb {
        value 273;
        description
          "Layer 2 Bridge Domain (L2BD) inject no sub block";
      }
      enum drop-l2bd-inject-invalid {
        value 274;
        description
          "Layer 2 Bridge Domain (L2BD) inject invalid";
      }
      enum drop-l2bd-stp-state {
        value 275;
        description
          "Layer 2 Bridge Domain (L2BD) spanning tree (STP) state";
      }
      enum drop-l2bd-storm-ctrl {
        value 276;
        description
          "Layer 2 Bridge Domain (L2BD) storm ctrl";
      }
      enum drop-sslvpn-coprocessor-err {
        value 277;
        description
          "SSL VPN coprocessor error";
      }
      enum drop-sslvpn-tail-drop {
        value 278;
        description
          "SSL VPN tail drop";
      }
      enum drop-ecfm {
        value 279;
        description
          "Ethernet connection fault management (ECFM)";
      }
      enum drop-ipv4mc-oif-rpf-failed {
        value 280;
        description
          "IPv4 multicast output interface reverse path forwarding failed";
      }
      enum drop-ipv6mc-oif-rpf-failed {
        value 281;
        description
          "IPv6 multicast output interface reverse path forwarding failed";
      }
      enum drop-ipv6-pbr {
        value 282;
        description
          "IPv6 policy based routing (PBR)";
      }
      enum drop-sslvpn-coproc-state-unset {
        value 283;
        description
          "SSL VPN coprocessor state not set";
      }
      enum drop-sslvpn-coproc-state-reply-unset {
        value 284;
        description
          "SSL VPN coprocessor state reply not set";
      }
      enum drop-sslvpn-neg-ssl-rec-pad-len {
        value 285;
        description
          "SSL VPN negotiated SSL record pad length";
      }
      enum drop-sslvpn-inv-ssl-rec {
        value 286;
        description
          "SSL VPN invalid SSL record";
      }
      enum drop-sslvpn-not-ssl-rec-rc {
        value 287;
        description
          "SSL VPN not SSL record return code";
      }
      enum drop-sslvpn-ssl-rec-not-pkt {
        value 288;
        description
          "SSL VPN SSL record not packet";
      }
      enum drop-sslvpn-add-ssl-rec-hdr-err {
        value 289;
        description
          "SSL VPN add SSL record header error";
      }
      enum drop-sslvpn-null-session {
        value 290;
        description
          "SSL VPN null session";
      }
      enum drop-sslvpn-invalid-session {
        value 291;
        description
          "SSL VPN invalid session";
      }
      enum drop-sslvpn-empty-pkt {
        value 292;
        description
          "SSL VPN empty packet";
      }
      enum drop-ipv4-reass-tail-drop {
        value 293;
        description
          "IPv4 reassembly tail drop";
      }
      enum drop-ipv6-reass-tail-drop {
        value 294;
        description
          "IPv6 reassembly tail drop";
      }
      enum drop-ipv4mc-nat-in2out {
        value 295;
        description
          "IPv4 multicast NAT in to out";
      }
      enum drop-ipv4mc-nat-out2in {
        value 296;
        description
          "IPv4 multicast NAT out to in";
      }
      enum drop-fia-error {
        value 297;
        description
          "Feature invocation array (FIA) error";
      }
      enum drop-firewall-syncookie-max-dst {
        value 298;
        description
          "Firewall syncookie maximum dst";
      }
      enum drop-ipv4-urpf-loose-failed {
        value 299;
        description
          "IPv4 unicast reverse path forwarding loose failed";
      }
      enum drop-ipv4-urpf-strict-failed {
        value 300;
        description
          "IPv4 unicast reverse path forwarding strict failed";
      }
      enum drop-ipv6-urpf-loose-failed {
        value 301;
        description
          "IPv6 unicast reverse path forwarding loose failed";
      }
      enum drop-ipv6-urpf-strict-failed {
        value 302;
        description
          "IPv6 unicast reverse path forwarding strict failed";
      }
      enum drop-ipv6-urpf-null-path-list {
        value 303;
        description
          "IPv6 unicast reverse path forwarding null path list";
      }
      enum drop-ipv6-urpf-no-fib {
        value 304;
        description
          "IPv6 unicast reverse path forwarding no fib";
      }
      enum drop-unknown-mcast-pkt-type {
        value 305;
        description
          "Unknown multicast packet type";
      }
      enum drop-l2v4mc-invalid-replica-record {
        value 306;
        description
          "Layer 2 IPv4 multicast invalid replica record";
      }
      enum drop-l2v6mc-invalid-replica-record {
        value 307;
        description
          "Layer 2 IPv6 multicast invalid replica record";
      }
      enum drop-l2mc-invalid-replica-record {
        value 308;
        description
          "Layer 2 multicast invalid replica record";
      }
      enum drop-lsm-invalid-replica-record {
        value 309;
        description
          "Label switch multicast invalid replica record";
      }
      enum drop-cts-format {
        value 310;
        description
          "Cisco trustsec format";
      }
      enum drop-cts-not-enable {
        value 311;
        description
          "Cisco trustsec not enable";
      }
      enum drop-idle-packet {
        value 312;
        description
          "Idle packet";
      }
      enum drop-mfr {
        value 313;
        description
          "Multilink frame relay";
      }
      enum drop-ar-tx {
        value 314;
        description
          "Asymmetric routing transmit";
      }
      enum drop-ar-rx {
        value 315;
        description
          "Asymmetric routing receive";
      }
      enum drop-ar-standby {
        value 316;
        description
          "Asymmetric routing standby";
      }
      enum drop-ar-fnf-clnup {
        value 317;
        description
          "Asymmetric routing flexible netflow cleanup";
      }
      enum drop-mac-mcast-ip-nonmcast {
        value 318;
        description
          "MAC multicast IP not multicast";
      }
      enum drop-bfd {
        value 319;
        description
          "Bidirectional fault detection (BFD)";
      }
      enum drop-bundle-oce {
        value 320;
        description
          "Bundle output chain element (OCE)";
      }
      enum drop-bqs-oor-pri {
        value 321;
        description
          "Buffering, queuing and scheduling out of resources priority";
      }
      enum drop-bqs-oor-pak-pri {
        value 322;
        description
          "Buffering, queuing and scheduling out of resources packet priority";
      }
      enum drop-bqs-oor-vital {
        value 323;
        description
          "Buffering, queuing and scheduling out of resources vital";
      }
      enum drop-epc {
        value 324;
        description
          "Embedded packet capture";
      }
      enum drop-lisp-failed-punt-dyn-eid-config {
        value 325;
        description
          "LISP failed to punt dynamic embedded identifier config";
      }
      enum drop-sv-match-fail {
        value 326;
        description
          "SV match fail";
      }
      enum drop-cblbf-null-repllist {
        value 327;
        description
          "Cable bundle flood null replication list";
      }
      enum drop-cblbf-repl-fail {
        value 328;
        description
          "Cable bundle flood replication fail";
      }
      enum drop-cblbf-repl-start {
        value 329;
        description
          "Cable bundle flood replication start";
      }
      enum drop-cblbf-repl-end {
        value 330;
        description
          "Cable bundle flood replication end";
      }
      enum drop-cblbf-recycle-tail {
        value 331;
        description
          "Cable bundle flood recycle tail";
      }
      enum drop-cblbf-fwdint-down {
        value 332;
        description
          "Cable bundle flood forwarding interface down";
      }
      enum drop-cable-p2pl-oce-ptr-null {
        value 333;
        description
          "Cable P2PL output chain element (OCE) pointer null";
      }
      enum drop-cable-mc-invalid-replica-record {
        value 334;
        description
          "Cable multicast invalid replica record";
      }
      enum drop-no-def-jib {
        value 335;
        description
          "No default JIB";
      }
      enum drop-no-inj-jib {
        value 336;
        description
          "No inj JIB";
      }
      enum drop-onefw {
        value 337;
        description
          "Firewall";
      }
      enum drop-ccm-tx {
        value 338;
        description
          "CCM transmit";
      }
      enum drop-appnav-sn-pkt-invalid {
        value 339;
        description
          "APPNAV Service Node (SN) packet invalid";
      }
      enum drop-appnav-internal-err {
        value 340;
        description
          "APPNAV internal error";
      }
      enum drop-appnav-badroute {
        value 341;
        description
          "APPNAV bad route";
      }
      enum drop-appnav-notunnel {
        value 342;
        description
          "APPNAV no tunnel";
      }
      enum drop-appnav-nosvcctx {
        value 343;
        description
          "APPNAV no SVC context";
      }
      enum drop-appnav-inv-flow-state {
        value 344;
        description
          "APPNAV invalid flow state";
      }
      enum drop-appnav-unexpected-pkt {
        value 345;
        description
          "APPNAV unexpected packet";
      }
      enum drop-rl2gp-non-tcb {
        value 346;
        description
          "Reverse layer 2 gateway protocol(R-L2GP) non topology change bridge protocol unit (TCB)";
      }
      enum drop-tunnel-pkt-sb-missed {
        value 347;
        description
          "Tunnel packet sub block missed";
      }
      enum drop-fhs-pkt-invalid {
        value 348;
        description
          "First hop security packet invalid";
      }
      enum drop-fhs-pkt-dropped {
        value 349;
        description
          "First hop security packet dropped";
      }
      enum drop-tunnel-sgre-virt-mac-mismatch {
        value 350;
        description
          "Tunnel secure generic routing encapsulation (sGRE) virtual MAC mismatch";
      }
      enum drop-tunnel-sgre-unsupported-proto {
        value 351;
        description
          "Tunnel secure generic routing encapsulation (sGRE) unsupported protocol";
      }
      enum drop-mpls-gal-check-non-gal-dropped {
        value 352;
        description
          "Multiprotocol label switching (MPLS) generic associated channel label (GAL) check non generic associated channel label (GAL) dropped";
      }
      enum drop-mpls-gal-check-non-eos-dropped {
        value 353;
        description
          "Multiprotocol label switching (MPLS) generic associated channel label (GAL) check non end of stack dropped";
      }
      enum drop-mpls-gal-check-invalid {
        value 354;
        description
          "Multiprotocol label switching (MPLS) generic associated channel label (GAL) check invalid";
      }
      enum drop-mpls-gal-exception-non-eos {
        value 355;
        description
          "Multiprotocol label switching (MPLS) generic associated channel label (GAL) exception non end of stack dropped";
      }
      enum drop-mpls-gal-exception-non-gach {
        value 356;
        description
          "Multiprotocol label switching (MPLS) generic associated channel label (GAL) exception non generic associated channel (GACH) dropped";
      }
      enum drop-conf-sw-sess {
        value 357;
        description
          "Configuration software session";
      }
      enum drop-tunnel-decap-too-many-times {
        value 358;
        description
          "Tunnel deencapsulation too many times";
      }
      enum drop-loadbalance-null0 {
        value 359;
        description
          "Load balance null0";
      }
      enum drop-gpm-tx-len-exceed {
        value 360;
        description
          "Global packet memory transmit length exceed";
      }
      enum drop-esf-ffr-drop {
        value 361;
        description
          "Edge switching services feature (ESF) ffr drop";
      }
      enum drop-ec-bundle-enq {
        value 362;
        description
          "Etherchannel bundle enqueue";
      }
      enum drop-ec-link-tx {
        value 363;
        description
          "Etherchannel link transmit";
      }
      enum drop-pfrv3-probe-err {
        value 364;
        description
          "Performance routing version 4 (pFRv3) probe error";
      }
      enum drop-ovl-bad-pkt {
        value 365;
        description
          "Overlay bad packet";
      }
      enum drop-ovl-l2-filter {
        value 366;
        description
          "Overlay layer 2 filter";
      }
      enum drop-dpss {
        value 367;
        description
          "Dataplane service set (DPSS)";
      }
      enum drop-tunnel-invalid-protocol {
        value 368;
        description
          "Tunnel invalid protocol";
      }
      enum drop-pfrv3-at-failure {
        value 369;
        description
          "Performance routing version 4 (pFRv3) at failure";
      }
      enum drop-ipv4-mcast-acl {
        value 370;
        description
          "IPv4 multicast access control list (ACL)";
      }
      enum drop-ipv6-mcast-acl {
        value 371;
        description
          "IPv6 multicast access control list (ACL)";
      }
      enum drop-pprl-sbrl-drop {
        value 372;
        description
          "PPRL source based rate limit drop";
      }
      enum drop-cbl-req-arl-drop {
        value 373;
        description
          "Cable request ARP drop";
      }
      enum drop-cbl-rep-arl-drop {
        value 374;
        description
          "Cable rep ARP drop";
      }
      enum drop-appnav-acgreloaddelay {
        value 375;
        description
          "APPNAV reload delay";
      }
      enum drop-ngfw-policy {
        value 376;
        description
          "Next generation firewall (NGFW) policy";
      }
      enum drop-ngfw-divert {
        value 377;
        description
          "Next generation firewall (NGFW) divert";
      }
      enum drop-pfrv3-blackhole {
        value 378;
        description
          "Performance routing version 4 (pFRv3) black hole";
      }
      enum drop-pppoe-fctl {
        value 379;
        description
          "PPP over Ethernet (PPPoE) flow control";
      }
      enum drop-lisp-sfltr {
        value 380;
        description
          "LISP filtering";
      }
      enum drop-flowspec {
        value 381;
        description
          "Flowspec";
      }
      enum drop-identity-cft-error {
        value 382;
        description
          "Identity common flow table error";
      }
      enum drop-bad-us-jib-hdr {
        value 383;
        description
          "Bad us JIB header";
      }
      enum drop-too-many-mpls-lookup-oce {
        value 384;
        description
          "Too many multiprotocol label switching (MPLS) lookup output chain element (OCE)";
      }
      enum drop-cable-prereg-not-cm {
        value 385;
        description
          "Cable pre registration not call manager";
      }
      enum drop-invalid-virtual-id {
        value 386;
        description
          "Invalid virtual identifier";
      }
      enum drop-flow-queue-failure-id {
        value 387;
        description
          "Flow queue failure identifier";
      }
      enum drop-l2es-input-invalid-tag {
        value 388;
        description
          "Layer 2 embedded ethernet switching input invalid tag";
      }
      enum drop-l2es-input-invalid-svi {
        value 389;
        description
          "Layer 2 embedded ethernet switching input invalid switched virtual interface (SVI)";
      }
      enum drop-svi-output-invalid-l2sb {
        value 390;
        description
          "Switched virtual interface (SVI) output invalid layer 2 sub block";
      }
      enum drop-svi-input-invalid-mac {
        value 391;
        description
          "Switched virtual interface (SVI) input invalid MAC";
      }
      enum drop-svi-output-recycle-tail {
        value 392;
        description
          "Switched virtual interface (SVI) output recycle tail";
      }
      enum drop-svi-output-repl {
        value 393;
        description
          "Switched virtual interface (SVI) output replication";
      }
      enum drop-svi-repl-end {
        value 394;
        description
          "Switched virtual interface (SVI) replication end";
      }
      enum drop-cws-ctx-id-not-found-mob {
        value 395;
        description
          "Cisco wire service (CWS) ctx identifier not found mobile";
      }
      enum drop-cws-ctx-id-not-found-conn {
        value 396;
        description
          "Cisco wire service (CWS) ctx identifier not found connection";
      }
      enum drop-l2cp-cfg-action {
        value 397;
        description
          "Layer 2 control process configuration action";
      }
      enum drop-perf-lic-policer-lo {
        value 398;
        description
          "Performance license policer lo";
      }
      enum drop-perf-lic-policer-hi {
        value 399;
        description
          "Performance license policer high";
      }
      enum drop-hqf-tx-error {
        value 400;
        description
          "Hierarchical queuing function transmit error";
      }
      enum drop-cmd-format {
        value 401;
        description
          "Command format";
      }
      enum drop-utd {
        value 402;
        description
          "Universal threat defense";
      }
      enum drop-nat66-in2out {
        value 403;
        description
          "NAT66 in to out";
      }
      enum drop-nat66-out2in {
        value 404;
        description
          "NAT66 out to in";
      }
      enum drop-dsa-no-ip {
        value 405;
        description
          "DNS snooping agent no IP";
      }
      enum drop-cws-inter-error {
        value 406;
        description
          "Cisco wire service (CWS) inter error";
      }
      enum drop-utd-sn {
        value 407;
        description
          "Universal threat defense Service Node (SN)";
      }
      enum drop-mpls-el-invalid-tag {
        value 408;
        description
          "Multiprotocol label switching (MPLS) entropy label invalid tag";
      }
      enum drop-lisp-failed-punt-gsmr-enabled {
        value 409;
        description
          "LISP failed to punt generalized solicit map request enabled";
      }
      enum drop-schain-flow-action {
        value 410;
        description
          "Service chain flow action";
      }
      enum drop-opendns {
        value 411;
        description
          "OpenDNS";
      }
      enum drop-capwap-err {
        value 412;
        description
          "CAPWAP error";
      }
      enum drop-capwap-no-uidb {
        value 413;
        description
          "CAPWAP no interface";
      }
      enum drop-dtls-err {
        value 414;
        description
          "DTLS error";
      }
      enum drop-wlclnt-err {
        value 415;
        description
          "Wireless client error";
      }
      enum drop-wlclnt-fnf-v9-report {
        value 416;
        description
          "Wireless client flexible netflow v9 report";
      }
      enum drop-wlclnt-fnf-v9-err {
        value 417;
        description
          "Wireless client flexible netflow v9 error";
      }
      enum drop-cgacl-err {
        value 418;
        description
          "CG Access Control List(CGACL) error";
      }
      enum drop-cgacl-lookup-miss {
        value 419;
        description
          "CG Access Control List(CGACL) lookup miss";
      }
      enum drop-cgacl-inv-stats {
        value 420;
        description
          "CG Access Control List(CGACL) invalid statistics";
      }
      enum drop-cgacl-match {
        value 421;
        description
          "CG Access Control List(CGACL) match";
      }
      enum drop-cgacl-action {
        value 422;
        description
          "CG Access Control List(CGACL) action";
      }
      enum drop-cgacl-pkt-type {
        value 423;
        description
          "CG Access Control List(CGACL) invalid packet type";
      }
      enum drop-cwfrag-err {
        value 424;
        description
          "Cisco wireservice fragment error";
      }
      enum drop-pathmgr-measurement-err {
        value 425;
        description
          "Path manager measurement error";
      }
      enum drop-pathmgr-select-err {
        value 426;
        description
          "Path manager select error";
      }
      enum drop-capwap-reass-frag-consm {
        value 427;
        description
          "CAPWAP reassembly fragments consumed";
      }
      enum drop-capwap-reass-alloc-err {
        value 428;
        description
          "CAPWAP reassembly allocation error";
      }
      enum drop-capwap-reass-frag-err {
        value 429;
        description
          "CAPWAP reassembly fragments error";
      }
      enum drop-redistrib-err-bad-dst {
        value 430;
        description
          "Redistribution error bad dst";
      }
      enum drop-redistrib-err-sb-trans-fail {
        value 431;
        description
          "Redistribution error sub block trans fail";
      }
      enum drop-redistrib-err-ph-alc-fail {
        value 432;
        description
          "Redistribution error ph allocation fail";
      }
      enum drop-redistrib-err-not-sup {
        value 433;
        description
          "Redistribution error not sup";
      }
      enum drop-redistrib-fifo-tail-drop {
        value 434;
        description
          "Redistribution first in first out (FIFO) tail drop";
      }
      enum drop-redistrib-no-credits {
        value 435;
        description
          "Redistribution no credits";
      }
      enum drop-max-indirect-exceeded {
        value 436;
        description
          "Maximum indirect exceeded";
      }
      enum drop-punt-intf-drop {
        value 437;
        description
          "Punt interface drop";
      }
      enum drop-srh-pkt-truncated-in-gpm {
        value 438;
        description
          "Segment routing header packet truncated in global packet memory";
      }
      enum drop-srh-invalid-extension {
        value 439;
        description
          "Segment routing header invalid extension";
      }
      enum drop-swport {
        value 440;
        description
          "Switch port";
      }
      enum drop-swport-disabled {
        value 441;
        description
          "Switch port disabled";
      }
      enum drop-swport-sanity-check {
        value 442;
        description
          "Switch port sanity check";
      }
      enum drop-swport-vp-state {
        value 443;
        description
          "Switch port virtual port state";
      }
      enum drop-swport-mac-conflict {
        value 444;
        description
          "Switch port MAC conflict";
      }
      enum drop-swport-stby {
        value 445;
        description
          "Switch port standby";
      }
      enum drop-swport-tx-stby {
        value 446;
        description
          "Switch port transmit standby";
      }
      enum drop-switch-l2m {
        value 447;
        description
          "Switch layer 2 multicast";
      }
      enum drop-switch-l2m-igmp {
        value 448;
        description
          "Switch layer 2 multicast internet group management protocol (IGMP)";
      }
      enum drop-switch-l2m-mld {
        value 449;
        description
          "Switch layer 2 multicast mld";
      }
      enum drop-switch-l2m-lookup-miss {
        value 450;
        description
          "Switch layer 2 multicast lookup miss";
      }
      enum drop-switch-l2m-sanity-check {
        value 451;
        description
          "Switch layer 2 multicast sanity check";
      }
      enum drop-bier-invalid-replica-record {
        value 452;
        description
          "Bit index explicit replication (BIER) invalid replica record";
      }
      enum drop-bier-snaity {
        value 453;
        description
          "Bit index explicit replication (BIER) sanity";
      }
      enum drop-cable-oob-us-sess-invalid {
        value 454;
        description
          "Cable out of band us session invalid";
      }
      enum drop-cable-oob-us-src-id-invalid {
        value 455;
        description
          "Cable out of band us source identifier invalid";
      }
      enum drop-cable-oob-us-pkt-invalid {
        value 456;
        description
          "Cable out of band us packet invalid";
      }
      enum drop-cbl-oob-null-repllist {
        value 457;
        description
          "Cable out of band null replication list";
      }
      enum drop-cbl-oob-repl-fail {
        value 458;
        description
          "Cable out of band replication fail";
      }
      enum drop-cbl-oob-add-hdr-fail {
        value 459;
        description
          "Cable out of band add header fail";
      }
      enum drop-cbl-oob-repl-end {
        value 460;
        description
          "Cable out of band replication end";
      }
      enum drop-cbl-oob-recycle-tail {
        value 461;
        description
          "Cable out of band recycle tail";
      }
      enum drop-cbl-oob-repl-uidb-invalid {
        value 462;
        description
          "Cable out of band replication interface invalid";
      }
      enum drop-cbl-oob-repl-sess-invalid {
        value 463;
        description
          "Cable out of band replication session invalid";
      }
      enum drop-cbl-oob-null-repl-info {
        value 464;
        description
          "Cable out of band null replication information";
      }
      enum drop-nid-vlan-mismatch {
        value 465;
        description
          "Network interface device VLAN mismatch";
      }
      enum drop-pfrv3-loop {
        value 466;
        description
          "Performance routing version 4 (pFRv3) loop";
      }
      enum drop-dialer-list {
        value 467;
        description
          "Dialer list";
      }
      enum drop-udp {
        value 468;
        description
          "UDP packet";
      }
      enum drop-tun-l2tpv3oipv6-cookie-mismatch {
        value 469;
        description
          "Tunnel layer 2 tunneling protocol version 3 over IPv6 (L2TPv3oIPv6) cookie mismatch";
      }
      enum drop-tun-l2tpv3oipv6-minmtu-err {
        value 470;
        description
          "Tunnel layer 2 tunneling protocol version 3 over IPv6 (L2TPv3oIPv6) minimum maximum transfer unit error";
      }
      enum drop-tun-l2tpv3oipv6-cookieflag-err {
        value 471;
        description
          "Tunnel layer 2 tunneling protocol version 3 over IPv6 (L2TPv3oIPv6) cookie flag error";
      }
      enum drop-tun-l2tpv3oipv6-mac-mismatch {
        value 472;
        description
          "Tunnel layer 2 tunneling protocol version 3 over IPv6 (L2TPv3oIPv6) MAC mismatch";
      }
      enum drop-tun-l2tpv3oipv6-vlanid-mismatch {
        value 473;
        description
          "Tunnel layer 2 tunneling protocol version 3 over IPv6 (L2TPv3oIPv6) VLAN identifier mismatch";
      }
      enum drop-tun-l2tpv3oipv6-unsup-proto {
        value 474;
        description
          "Tunnel layer 2 tunneling protocol version 3 over IPv6 (L2TPv3oIPv6) unsupported protocol";
      }
      enum drop-pfrv3-stickiness {
        value 475;
        description
          "Performance routing version 4 (pFRv3) stickiness";
      }
      enum drop-cbl-sid-exceed {
        value 476;
        description
          "Cable service identifier exceed";
      }
      enum drop-sdwan {
        value 477;
        description
          "Software defined WAN (SDWAN)";
      }
      enum drop-sdwan-generic {
        value 478;
        description
          "Software defined WAN (SDWAN) generic";
      }
      enum drop-sdwan-implicit-acl {
        value 479;
        description
          "Software defined WAN (SDWAN) implicit access control list (ACL)";
      }
      enum drop-sdwan-acl {
        value 480;
        description
          "Software defined WAN (SDWAN) access control list (ACL)";
      }
      enum drop-sdwan-bfd {
        value 481;
        description
          "Software defined WAN (SDWAN) bidirectional fault detection (BFD)";
      }
      enum drop-sdwan-app-route-policy {
        value 482;
        description
          "Software defined WAN (SDWAN) app route policy";
      }
      enum drop-sdwan-data-policy {
        value 483;
        description
          "Software defined WAN (SDWAN) data policy";
      }
      enum drop-sdwan-interface-policy {
        value 484;
        description
          "Software defined WAN (SDWAN) interface policy";
      }
      enum drop-sdwan-tunnel-lkup {
        value 485;
        description
          "Software defined WAN (SDWAN) tunnel lookup";
      }
      enum drop-sdwan-tloc-ext {
        value 486;
        description
          "Software defined WAN (SDWAN) tunnel locator extension";
      }
      enum drop-tunnel-vxlan-mismatch {
        value 487;
        description
          "Tunnel VxLAN mismatch";
      }
      enum drop-l2bd-mac-security-move {
        value 488;
        description
          "Layer 2 Bridge Domain (L2BD) MAC security move";
      }
      enum drop-l2bd-mac-security-unknown {
        value 489;
        description
          "Layer 2 Bridge Domain (L2BD) MAC security unknown";
      }
      enum drop-dapr-noroute {
        value 490;
        description
          "Dynamic application policy routing no route";
      }
      enum drop-epbr {
        value 491;
        description
          "Enhanced policy based routing";
      }
      enum drop-sdvt-sn {
        value 492;
        description
          "SDVT Service Node (SN)";
      }
      enum drop-sdvt {
        value 493;
        description
          "Service divert";
      }
      enum drop-tunnel-vxlan-policer {
        value 494;
        description
          "Tunnel VxLAN policer";
      }
      enum drop-tunnel-vrf-mux {
        value 495;
        description
          "Tunnel VRF multiplexed";
      }
      enum drop-tunnel-vrf-demux {
        value 496;
        description
          "Tunnel VRF demultiplexed";
      }
      enum drop-frag-invalid-pkt {
        value 497;
        description
          "Fragment invalid packet";
      }
      enum drop-frag-invalid-ip6pkt {
        value 498;
        description
          "Fragment invalid IPv6 packet";
      }
      enum drop-crypto-offload-output {
        value 499;
        description
          "Crypto offload output";
      }
      enum drop-cable-prng-expected-drops {
        value 500;
        description
          "Cable Pseudo Random Number Generator expected drops";
      }
      enum drop-ipv4-egress-intf-enforce {
        value 501;
        description
          "IPv4 egress interface enforce";
      }
      enum drop-ipv6-egress-intf-enforce {
        value 502;
        description
          "IPv6 egress interface enforce";
      }
      enum drop-cable-dhcp-bad-len {
        value 503;
        description
          "Cable DHCP bad length";
      }
      enum drop-l2bd-uuf-suppression {
        value 504;
        description
          "Layer 2 Bridge Domain (L2BD) unknown unicast flood suppression";
      }
      enum drop-wpan {
        value 505;
        description
          "Wireless Personal Area Network";
      }
      enum drop-l2bd-sisf-ctrl {
        value 506;
        description
          "Layer 2 Bridge Domain (L2BD) Switch Integrated Security Features control";
      }
      enum drop-cable-recycle-queue {
        value 507;
        description
          "Cable recycle queue";
      }
      enum drop-pcgw-pdu-sess-err {
        value 508;
        description
          "Packet Core Gateway PDU session error";
      }
      enum drop-pcgw-gtpu-err {
        value 509;
        description
          "Packet Core Gateway gtpu error";
      }
      enum drop-pcgw-punt-inject-err {
        value 510;
        description
          "Packet Core Gateway punt inject error";
      }
      enum drop-pcacl {
        value 511;
        description
          "Packet Core ACL";
      }
      enum drop-vtcp-err {
        value 512;
        description
          "Virtual TCP error";
      }
      enum drop-vtcp-invalid-tx {
        value 513;
        description
          "Virtual TCP invalid transmit";
      }
      enum drop-vtcp-pa-err {
        value 514;
        description
          "Virtual TCP packet abstraction error";
      }
      enum drop-vtcp-mem-err {
        value 515;
        description
          "Virtual TCP memory error";
      }
      enum drop-vtcp-punt-err {
        value 516;
        description
          "Virtual TCP punt error";
      }
      enum drop-fbd-oom-err {
        value 517;
        description
          "Flow based distribution out of memory error";
      }
      enum drop-memory-interface {
        value 518;
        description
          "Memory interface";
      }
      enum drop-no-interface-resources {
        value 519;
        description
          "No interface resources";
      }
      enum drop-dlep-unconfigured {
        value 520;
        description
          "Dynamic Link Exchange Protocol unconfigured";
      }
    }
    description
      "Drop causes";
  }

  typedef nwpi-domain-state {
    type enumeration {
      enum domain-state-invalid {
        value 0;
        description
          "Invalid domain";
      }
      enum domain-state-uncompleted {
        value 1;
        description
          "Domain uncompleted";
      }
      enum domain-state-completed {
        value 2;
        description
          "Domain completed";
      }
    }
    description
      "Domain type";
  }

  typedef nwpi-domain-dns-trans-type {
    type enumeration {
      enum domain-dns-trans-invalid {
        value 0;
        description
          "Invalid transport type";
      }
      enum domain-dns-trans-udp {
        value 1;
        description
          "DNS UDP transport";
      }
      enum domain-dns-trans-tcp {
        value 2;
        description
          "DNS TCP transport";
      }
      enum domain-dns-trans-udp2tcp {
        value 3;
        description
          "DNS transport from UDP to TCP";
      }
    }
    description
      "Domain transport type";
  }

  grouping nwpi-trace {
    description
      "Trace identifier, action and filters";
    leaf trace-id {
      type uint16 {
        range "1..65535";
      }
      description
        "Global unique trace identifier";
    }
    leaf action {
      type Cisco-IOS-XE-nwpi-types:nwpi-action-type;
      description
        "Trace start/stop/clean actions";
    }
    leaf target {
      when "(../action[.='action-start-trace' or .='action-stop-trace'])";
      type Cisco-IOS-XE-nwpi-types:nwpi-target-type;
      description
        "Target types";
    }
    leaf vpn-id {
      when "(../action[.='action-start-trace' or .= 'action-stop-trace']) and (../target = 'target-vpn-id')";
      type uint32 {
        range "0..65531";
      }
      description
        "SD-WAN VPN identifier";
    }
    leaf vrf-name {
      when "(../action[.='action-start-trace' or .= 'action-stop-trace']) and (../target = 'target-vrf-name')";
      type string;
      description
        "VRF name";
    }
    leaf src-ip {
      type inet:ip-address;
      description
        "Source IP to filter";
    }
    leaf dst-ip {
      type inet:ip-address;
      description
        "Destination IP to filter";
    }
    leaf app {
      type string;
      description
        "Application to filter";
    }
    leaf src-if {
      type string;
      description
        "Source interface to filter";
    }
    leaf protocol {
      type uint8;
      description
        "IP protocol field in IP header to filter";
    }
    leaf src-port {
      type uint16;
      description
        "Source port to filter";
    }
    leaf dst-port {
      type uint16;
      description
        "Destination port to filter";
    }
    leaf dscp-is-valid {
      type boolean;
      description
        "Indicate DSCP filter was configured";
    }
    leaf dscp {
      when "(../dscp-is-valid = 'true')";
      type uint8;
      description
        "DSCP value to filter";
    }
    leaf duration {
      type uint16;
      units "minutes";
      description
        "Trace remaining duration in minutes";
    }
    leaf src-pfx {
      type inet:ip-address;
      description
        "Source prefix to filter";
    }
    leaf src-pfx-len {
      type uint8;
      units "bits";
      description
        "Source prefix length to filter";
    }
    leaf dst-pfx {
      type inet:ip-address;
      description
        "Destination prefix to filter";
    }
    leaf dst-pfx-len {
      type uint8;
      units "bits";
      description
        "Destination prefix length to filter";
    }
    leaf app-grp {
      type string;
      description
        "Application grouped by vendors to filter";
    }
    leaf domain-mon {
      type boolean;
      description
        "Enable domain monitor";
    }
    leaf art-vis {
      type boolean;
      description
        "Enable ART visibility";
    }
    leaf app-vis {
      type boolean;
      description
        "Enable application visibility";
    }
    leaf dia-vis {
      type boolean;
      description
        "Enable direct internet access visibility";
    }
    leaf hub-wan-vis {
      type boolean;
      description
        "Enable HUB WAN ingress visibility";
    }
    leaf sampling {
      type boolean;
      description
        "Enable trace flow sampling";
    }
    leaf spl-intvl {
      type uint32;
      units "milliseconds";
      description
        "Trace one flow in each sample interval";
    }
    list domain {
      description
        "Domain list to filter";
      uses Cisco-IOS-XE-nwpi-types:nwpi-domain-filter;
    }
    container lcl-state {
      description
        "Local trace state";
      uses Cisco-IOS-XE-nwpi-types:nwpi-local-state;
    }
  }

  grouping nwpi-feature-trace {
    description
      "Feature trace";
    leaf name {
      type string;
      description
        "Feature name";
    }
    leaf feature-type {
      type Cisco-IOS-XE-nwpi-oper:nwpi-feature-type;
      description
        "Feature type";
    }
    leaf dir {
      type Cisco-IOS-XE-nwpi-oper:nwpi-feature-dir;
      description
        "Feature direction";
    }
    leaf policy {
      type string;
      description
        "Policy name";
    }
  }

  grouping nwpi-event-entry {
    description
      "Entry of a Network Wide Path Insight event";
    leaf event-type {
      type Cisco-IOS-XE-nwpi-oper:nwpi-event-type;
      description
        "Type of the event";
    }
    leaf packet-id {
      type uint32;
      description
        "Packet identifier";
    }
  }

  grouping packet-key {
    description
      "Key to index packet record";
    leaf trace-id {
      type uint16;
      description
        "Trace identifier";
    }
    leaf packet-id {
      type uint32;
      description
        "Packet identifier";
    }
  }

  grouping nwpi-packet {
    description
      "Packet record";
    leaf hostname {
      type string;
      description
        "Hostname";
    }
    leaf system-ip {
      type inet:ip-address;
      description
        "SD-WAN system IP";
    }
    leaf flow-id {
      type uint16;
      description
        "Flow identifier";
    }
    leaf dir {
      type Cisco-IOS-XE-nwpi-oper:nwpi-flow-dir;
      description
        "Flow direction this packet belongs to";
    }
    leaf hop-idx {
      type uint8;
      description
        "Hop index of flow";
    }
    leaf app-recognized {
      type boolean;
      description
        "Application recognized or not";
    }
    list trace {
      description
        "List of feature traces";
      uses Cisco-IOS-XE-nwpi-oper:nwpi-feature-trace;
    }
    leaf p-pkt-id {
      type uint32;
      description
        "Parent packet identifier";
    }
    list event {
      description
        "The flow event triggering capture of this packet record";
      uses Cisco-IOS-XE-nwpi-oper:nwpi-event-entry;
    }
    leaf ttl {
      type uint8;
      description
        "Time to live or hop limit value of this packet";
    }
  }

  grouping flow-key {
    description
      "Key to index flow record";
    leaf trace-id {
      type uint16;
      description
        "Trace identifier";
    }
    leaf flow-id {
      type uint16;
      description
        "Flow identifier";
    }
  }

  grouping nwpi-nexthop {
    description
      "Nexthop detail info";
    leaf nexthop-type {
      type Cisco-IOS-XE-nwpi-oper:nwpi-nexthop-type;
      description
        "Nexthop type";
    }
    leaf if-name {
      when "(../nexthop-type[.!='nexthop-local-consumed' and .!='nexthop-invalid'])";
      type string;
      description
        "Input or output interface name";
    }
    leaf local-color {
      when "(../nexthop-type[.='nexthop-sdwan-session' or .='nexthop-sdwan-session-tloc-extension' or .='nexthop-nat-dia'])";
      type Cisco-IOS-XE-nwpi-oper:nwpi-color-type;
      description
        "SD-WAN local color";
    }
    leaf remote-color {
      when "(../nexthop-type[.='nexthop-sdwan-session' or .='nexthop-sdwan-session-tloc-extension'])";
      type Cisco-IOS-XE-nwpi-oper:nwpi-color-type;
      description
        "SD-WAN remote color";
    }
    leaf encap {
      when "(../nexthop-type[.='nexthop-sdwan-session' or .='nexthop-sdwan-session-tloc-extension'])";
      type Cisco-IOS-XE-nwpi-oper:nwpi-encap-type;
      description
        "SD-WAN tunnel encap";
    }
    leaf remote-system-ip {
      when "(../nexthop-type[.='nexthop-sdwan-session' or .='nexthop-sdwan-session-tloc-extension'])";
      type inet:ip-address;
      description
        "SD-WAN remote peer system IP";
    }
  }

  grouping unicast-path {
    description
      "Network path info for unicast flows";
    leaf up-hop-idx {
      type uint8;
      description
        "Upstream hop index";
    }
    container up-ingress {
      description
        "Upstream ingress info";
      uses Cisco-IOS-XE-nwpi-oper:nwpi-nexthop;
    }
    container up-egress {
      description
        "Upstream egress info";
      uses Cisco-IOS-XE-nwpi-oper:nwpi-nexthop;
    }
    leaf down-hop-idx {
      type uint8;
      description
        "Downstream hop index";
    }
    container down-ingress {
      description
        "Downstream ingress info";
      uses Cisco-IOS-XE-nwpi-oper:nwpi-nexthop;
    }
    container down-egress {
      description
        "Downstream egress info";
      uses Cisco-IOS-XE-nwpi-oper:nwpi-nexthop;
    }
  }

  grouping nwpi-flow-metrics {
    description
      "Network metrics of a flow";
    leaf jitter-mean {
      type uint32;
      units "microseconds";
      description
        "Jitter mean value";
    }
    leaf delay-mean {
      type uint32;
      units "microseconds";
      description
        "Delay mean value";
    }
  }

  grouping nwpi-flow-base-stats {
    description
      "Basic statistics used in all cases";
    leaf total-pkts {
      type uint64;
      description
        "Total packets count";
    }
    leaf total-octets {
      type uint64;
      description
        "Total octets count";
    }
    leaf drop-pkts {
      type uint64;
      description
        "Drop packets count";
    }
    leaf drop-octets {
      type uint64;
      description
        "Drop octets count";
    }
  }

  grouping nwpi-flow-adv-stats {
    description
      "Advanced statistics only used in specific cases";
    leaf frag-pkts {
      type uint64;
      description
        "Fragment packets count";
    }
    leaf frag-octets {
      type uint64;
      description
        "Fragment octets count";
    }
    leaf punt-pkts {
      type uint64;
      description
        "Punt packets count";
    }
    leaf punt-octets {
      type uint64;
      description
        "Punt octets count";
    }
    leaf recycle-pkts {
      type uint64;
      description
        "Recycle packets count";
    }
    leaf recycle-octets {
      type uint64;
      description
        "Recycle octets count";
    }
    leaf repl-pkts {
      type uint64;
      description
        "Replicate packets count";
    }
    leaf repl-octets {
      type uint64;
      description
        "Replicate octets count";
    }
  }

  grouping nwpi-qos-stats {
    description
      "QoS statistics";
    leaf q-id {
      type uint32;
      description
        "QoS queue identifier";
    }
    leaf q-lim-pkts {
      type uint32;
      description
        "QoS queue limit in packets count";
    }
    leaf q-d-max-pkts {
      type uint32;
      description
        "QoS queue maximum depth in packets count";
    }
    leaf q-d-min-pkts {
      type uint32;
      description
        "QoS queue minimum depth in packets count";
    }
    leaf q-d-avg-pkts {
      type uint32;
      description
        "QoS queue average depth in packets count";
    }
  }

  grouping nwpi-drop-stats {
    description
      "Per cause drop statistics";
    leaf cause {
      type Cisco-IOS-XE-nwpi-oper:nwpi-drop-cause;
      description
        "Drop cause";
    }
    leaf per-cause-pkts {
      type uint64;
      description
        "Per cause drop packets count";
    }
  }

  grouping nwpi-flow-insight {
    description
      "Insight on flow status";
    leaf fif-dpi-not-classified {
      type boolean;
      description
        "First in flow packet not classified by DPI";
    }
    leaf sla-violated {
      type boolean;
      description
        "SLA criteria violated";
    }
    leaf qos-congested {
      type boolean;
      description
        "QoS queue congested";
    }
    leaf path-changed {
      type boolean;
      description
        "Flow forwarding next hop changed";
    }
    leaf tcp-flow-reset {
      type boolean;
      description
        "TCP flow received a packet with TCP reset flag in TCP header";
    }
    leaf nat-translated {
      type boolean;
      description
        "Flow tuple has been translated by NAT";
    }
    leaf policy-bypassed {
      type boolean;
      description
        "Flow bypassed SD-WAN policy configured action";
    }
    leaf wan-color-asym {
      type boolean;
      description
        "Flow egress WAN color asymmetric with return traffic ingress WAN color";
    }
    leaf dpi-policy-used {
      type boolean;
      description
        "SD-WAN policy used DPI classification to match flows";
    }
  }

  grouping nwpi-flow {
    description
      "Flow record";
    leaf hostname {
      type string;
      description
        "Hostname";
    }
    leaf system-ip {
      type inet:ip-address;
      description
        "SD-WAN system IP";
    }
    leaf src-ip {
      type inet:ip-address;
      description
        "Source IP";
    }
    leaf dst-ip {
      type inet:ip-address;
      description
        "Destination IP";
    }
    leaf src-port {
      type uint16;
      description
        "Source port";
    }
    leaf dst-port {
      type uint16;
      description
        "Destination port";
    }
    leaf protocol {
      type uint8;
      description
        "IP Protocol field in IP header";
    }
    leaf up-dscp {
      type uint8;
      description
        "Upstream DSCP";
    }
    leaf down-dscp {
      type uint8;
      description
        "Downstream DSCP";
    }
    leaf app-name {
      type string;
      description
        "Application name";
    }
    leaf app-group {
      type string;
      description
        "Application group";
    }
    leaf category {
      type Cisco-IOS-XE-nwpi-oper:nwpi-ms-category;
      description
        "Office 365 endpoint category";
    }
    leaf is-fin {
      type boolean;
      description
        "Is the flow in final state after aged out or trace stopped";
    }
    leaf flow-type {
      type Cisco-IOS-XE-nwpi-oper:nwpi-flow-type;
      description
        "Flow type";
    }
    list uni-path {
      when "(../flow-type = 'flow-unicast')";
      description
        "Unicast flow network path info";
      uses Cisco-IOS-XE-nwpi-oper:unicast-path;
    }
    leaf mcast-hop-idx {
      when "(../flow-type = 'flow-multicast')";
      type uint8;
      description
        "Multicast hop index";
    }
    container mcast-ingress {
      when "(../flow-type = 'flow-multicast')";
      description
        "Multicast ingress info";
      uses Cisco-IOS-XE-nwpi-oper:nwpi-nexthop;
    }
    list mcast-egress-nexthop {
      when "(../flow-type = 'flow-multicast')";
      description
        "Multicast egress info";
      uses Cisco-IOS-XE-nwpi-oper:nwpi-nexthop;
    }
    leaf asymmetry-detected {
      type boolean;
      description
        "Asymmetry routing detected or not";
    }
    leaf loop-detected {
      type boolean;
      description
        "Routing loop detected or not";
    }
    leaf-list up-pkt {
      type uint32;
      ordered-by user;
      description
        "Upstream packets belong to this flow";
    }
    leaf-list down-pkt {
      when "(../flow-type = 'flow-unicast')";
      type uint32;
      ordered-by user;
      description
        "Downstream packets belong to this flow";
    }
    leaf-list repl-pkt {
      when "(../flow-type = 'flow-multicast')";
      type uint32;
      ordered-by user;
      description
        "Multicast replicated packets belong to this flow";
    }
    container up-ingress-metrics {
      description
        "Upstream ingress metrics";
      uses Cisco-IOS-XE-nwpi-oper:nwpi-flow-metrics;
    }
    container down-ingress-metrics {
      when "(../flow-type = 'flow-unicast')";
      description
        "Downstream ingress metrics";
      uses Cisco-IOS-XE-nwpi-oper:nwpi-flow-metrics;
    }
    container up-local-metrics {
      description
        "Upstream local metrics";
      uses Cisco-IOS-XE-nwpi-oper:nwpi-flow-metrics;
    }
    container down-local-metrics {
      when "(../flow-type = 'flow-unicast')";
      description
        "Downstream local metrics";
      uses Cisco-IOS-XE-nwpi-oper:nwpi-flow-metrics;
    }
    container up-base-stats {
      description
        "Upstream base statistics";
      uses Cisco-IOS-XE-nwpi-oper:nwpi-flow-base-stats;
    }
    container down-base-stats {
      when "(../flow-type = 'flow-unicast')";
      description
        "Downstream base statistics";
      uses Cisco-IOS-XE-nwpi-oper:nwpi-flow-base-stats;
    }
    leaf stats-type {
      type Cisco-IOS-XE-nwpi-oper:nwpi-stats-type;
      description
        "Statistics type";
    }
    container up-adv-stats {
      when "(../stats-type = 'stats-advanced')";
      description
        "Upstream advanced statistics";
      uses Cisco-IOS-XE-nwpi-oper:nwpi-flow-adv-stats;
    }
    container down-adv-stats {
      when "(../flow-type = 'flow-unicast') and (../stats-type = 'stats-advanced')";
      description
        "Downstream advanced statistics";
      uses Cisco-IOS-XE-nwpi-oper:nwpi-flow-adv-stats;
    }
    leaf art-snd {
      type uint32;
      units "milliseconds";
      description
        "ART server network delay";
    }
    leaf art-cnd {
      type uint32;
      units "milliseconds";
      description
        "ART client network delay";
    }
    container up-qos-stats {
      description
        "Upstream QoS statistics";
      uses Cisco-IOS-XE-nwpi-oper:nwpi-qos-stats;
    }
    container down-qos-stats {
      description
        "Downstream QoS statistics";
      uses Cisco-IOS-XE-nwpi-oper:nwpi-qos-stats;
    }
    list up-drop {
      description
        "Upstream per cause drop statistics";
      uses Cisco-IOS-XE-nwpi-oper:nwpi-drop-stats;
    }
    list down-drop {
      description
        "Downstream per cause drop statistics";
      uses Cisco-IOS-XE-nwpi-oper:nwpi-drop-stats;
    }
    list up-last-event {
      description
        "Last event seen on upstream of this flow";
      uses Cisco-IOS-XE-nwpi-oper:nwpi-event-entry;
    }
    list down-last-event {
      description
        "Last event seen on downstream of this flow";
      uses Cisco-IOS-XE-nwpi-oper:nwpi-event-entry;
    }
    container up-insight {
      description
        "Insight on flow upstream status";
      uses Cisco-IOS-XE-nwpi-oper:nwpi-flow-insight;
    }
    container down-insight {
      description
        "Insight on flow downstream status";
      uses Cisco-IOS-XE-nwpi-oper:nwpi-flow-insight;
    }
    leaf is-first {
      type boolean;
      description
        "Is this device first to see this flow";
    }
    leaf-list domain {
      type uint16;
      ordered-by user;
      description
        "List of domains this flow potentially belongs to";
    }
    leaf up-mon-id {
      type uint8;
      description
        "Current upstream monitor identifier";
    }
    leaf down-mon-id {
      type uint8;
      description
        "Current downstream monitor identifier";
    }
    container up-mon-intvl-stats {
      description
        "Current upstream monitor interval statistics";
      uses Cisco-IOS-XE-nwpi-oper:nwpi-flow-base-stats;
    }
    container down-mon-intvl-stats {
      description
        "Current downstream monitor interval statistics";
      uses Cisco-IOS-XE-nwpi-oper:nwpi-flow-base-stats;
    }
    leaf-list up-ttl {
      type uint8;
      ordered-by user;
      description
        "Upstream time to live or hop limit value of this flow";
    }
    leaf-list down-ttl {
      type uint8;
      ordered-by user;
      description
        "Downstream time to live or hop limit value of this flow";
    }
  }

  grouping domain-key {
    description
      "Key to index domain record";
    leaf trace-id {
      type uint16;
      description
        "Trace identifier";
    }
    leaf domain-id {
      type uint16;
      description
        "Domain identifier";
    }
  }

  grouping nwpi-domain-res {
    description
      "Domain resolution from a certain path";
    container nexthop {
      description
        "DNS request egress nexthop";
      uses Cisco-IOS-XE-nwpi-oper:nwpi-nexthop;
    }
    leaf state {
      type Cisco-IOS-XE-nwpi-oper:nwpi-domain-state;
      description
        "DNS resolution state";
    }
    leaf-list addr {
      type inet:ip-address;
      ordered-by user;
      description
        "DNS resolved IP addresses list";
    }
    leaf trans-type {
      type Cisco-IOS-XE-nwpi-oper:nwpi-domain-dns-trans-type;
      description
        "DNS session transport type";
    }
    leaf req-times {
      type uint32;
      description
        "Count of DNS requests on this path in this report interval";
    }
    leaf ttl {
      type uint32;
      description
        "DNS resolution TTL";
    }
    leaf is-redi {
      type boolean;
      description
        "Is DNS request redirected on this path";
    }
    leaf redi-svr {
      type inet:ip-address;
      description
        "DNS server to redirect to";
    }
  }

  grouping nwpi-domain {
    description
      "Domain record";
    leaf hostname {
      type string;
      description
        "Hostname";
    }
    leaf system-ip {
      type inet:ip-address;
      description
        "SD-WAN system IP";
    }
    leaf domain-name {
      type string;
      description
        "Domain name";
    }
    leaf-list server {
      type inet:ip-address;
      ordered-by user;
      description
        "DNS servers list";
    }
    leaf total-req-times {
      type uint32;
      description
        "Count of DNS requests on all paths for all times";
    }
    leaf app-name {
      type string;
      description
        "Application name";
    }
    leaf app-group {
      type string;
      description
        "Application group name";
    }
    list last-event {
      description
        "Last event seen on this domain";
      uses Cisco-IOS-XE-nwpi-oper:nwpi-event-entry;
    }
    leaf app-mon-enabled {
      type boolean;
      description
        "Domain application monitor enabled";
    }
    list resolution {
      description
        "Domain per path resolutions list";
      uses Cisco-IOS-XE-nwpi-oper:nwpi-domain-res;
    }
  }

  grouping ip-domain-key {
    description
      "Key to index IP domain record";
    leaf trace-id {
      type uint16;
      description
        "Trace identifier";
    }
    leaf addr {
      type inet:ip-address;
      description
        "IP address";
    }
  }

  grouping nwpi-ip-domain {
    description
      "IP to domain mapping record";
    list domain {
      description
        "IP's domain identifier list";
      uses Cisco-IOS-XE-nwpi-types:nwpi-domain-info;
    }
  }

  grouping flow-agg-mtrs {
    description
      "Per path metrics to aggregated flows";
    container uni-path {
      description
        "Unicast path information";
      uses Cisco-IOS-XE-nwpi-oper:unicast-path;
    }
    leaf-list flow {
      type uint16;
      ordered-by user;
      description
        "Flows sharing this path";
    }
    leaf agg-snd {
      type uint32;
      units "milliseconds";
      description
        "ART server network delay";
    }
    leaf agg-cnd {
      type uint32;
      units "milliseconds";
      description
        "ART client network delay";
    }
  }

  grouping nwpi-flow-agg {
    description
      "Aggregated flows";
    leaf-list agg-flow {
      type uint16;
      ordered-by user;
      description
        "Aggregated flows id list";
    }
    list agg-metrics {
      description
        "Aggregated per path metrics list";
      uses Cisco-IOS-XE-nwpi-oper:flow-agg-mtrs;
    }
  }

  grouping domain-agg-key {
    description
      "Key to index domain aggregate record";
    leaf trace-id {
      type uint16;
      description
        "Trace identifier";
    }
    leaf domain-id {
      type uint16;
      description
        "Domain identifier";
    }
  }

  grouping nwpi-domain-agg {
    description
      "Aggregate record";
    leaf hostname {
      type string;
      description
        "Hostname";
    }
    leaf system-ip {
      type inet:ip-address;
      description
        "SD-WAN system IP";
    }
    leaf domain-name {
      type string;
      description
        "Domain name";
    }
    container domain-agg {
      description
        "Flow info aggregated by domain";
      uses Cisco-IOS-XE-nwpi-oper:nwpi-flow-agg;
    }
  }

  container nwpi-oper-data {
    config false;
    description
      "Network Wide Path Insight operational data";
    list location {
      key "fru slot bay chassis node";
      description
        "A list of data provider locations";
      uses common-types-ios-xe:extended-location;
      list nwpi-packet {
        key "trace-id packet-id";
        description
          "Network Wide Path Insight Packets";
        uses Cisco-IOS-XE-nwpi-oper:nwpi-packet;
        uses Cisco-IOS-XE-nwpi-oper:packet-key;
      }
      list nwpi-flow {
        key "trace-id flow-id";
        description
          "Network Wide Path Insight Flows";
        uses Cisco-IOS-XE-nwpi-oper:nwpi-flow;
        uses Cisco-IOS-XE-nwpi-oper:flow-key;
      }
      list nwpi-trace {
        key "trace-id";
        description
          "Network Wide Path Insight Traces";
        uses Cisco-IOS-XE-nwpi-oper:nwpi-trace;
      }
      list nwpi-domain {
        key "trace-id domain-id";
        description
          "Network Wide Path Insight Domains";
        uses Cisco-IOS-XE-nwpi-oper:nwpi-domain;
        uses Cisco-IOS-XE-nwpi-oper:domain-key;
      }
      list nwpi-ip-domain {
        key "trace-id addr";
        description
          "Network Wide Path Insight IP to domain mapping";
        uses Cisco-IOS-XE-nwpi-oper:nwpi-ip-domain;
        uses Cisco-IOS-XE-nwpi-oper:ip-domain-key;
      }
      list nwpi-domain-agg {
        key "trace-id domain-id";
        description
          "Network Wide Path Insight aggregate flows by domain";
        uses Cisco-IOS-XE-nwpi-oper:nwpi-domain-agg;
        uses Cisco-IOS-XE-nwpi-oper:domain-agg-key;
      }
    }
  }
}
