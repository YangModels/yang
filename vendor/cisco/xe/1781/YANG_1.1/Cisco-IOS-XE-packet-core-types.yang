module Cisco-IOS-XE-packet-core-types {
  yang-version 1.1;
  namespace "http://cisco.com/ns/yang/Cisco-IOS-XE-packet-core-types";
  prefix packet-core-types;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains common type definitions used by
     other Packet-Core yang modules.
     Copyright (c) 2021 by Cisco Systems, Inc.
     All rights reserved.";

  revision 2021-11-01 {
    description
      "Initial revision";
    reference
      "1.0.0";
    cisco-semver:module-version "1.0.0";
  }

  typedef nid-assignment-mode {
    type enumeration {
      enum nid-global-unique {
        value 0;
        description
          "Coordinated assignment mode option 1.
           NID is assigned such that it is globally unique
           independent of the PLMN ID used";
      }
      enum nid-self-assign {
        value 1;
        description
          "Self assignment mode.
           NID is chosen individually by SNPNs at deployment time.
           Therefore this may not be unique, but use a different
           numbering space than the coordinated assignment NIDs";
      }
      enum nid-global-plmn-unique {
        value 2;
        description
          "Coordinated assignment mode option 2.
           NID is assigned such that the combination of the NID
           and the PLMN ID is globally unique";
      }
    }
    description
      "SNPN Network Identifier assignment mode";
  }

  typedef userplane-int-protection {
    type enumeration {
      enum up-int-protect-not-required {
        value 0;
        description
          "User plane integrity protection not required";
      }
      enum up-int-protect-preferred {
        value 1;
        description
          "User plane integrity protection is preferred";
      }
      enum up-int-protect-required {
        value 2;
        description
          "User plane integrity protection is required";
      }
    }
    description
      "User plane integrity protection types";
  }

  typedef userplane-cipher-protection {
    type enumeration {
      enum up-cipher-protect-not-required {
        value 0;
        description
          "User plane cipher protection not required";
      }
      enum up-cipher-protect-preferred {
        value 1;
        description
          "User plane cipher protection is preferred";
      }
      enum up-cipher-protect-required {
        value 2;
        description
          "User plane cipher protection is required";
      }
    }
    description
      "User plane cipher protection types";
  }

  typedef ciphering-algorithm {
    type enumeration {
      enum encr-alg-nea0 {
        value 0;
        description
          "Null ciphering algorithm";
      }
      enum encr-alg-128-nea1 {
        value 1;
        description
          "128-bit SNOW 3G based ciphering algorithm";
      }
      enum encr-alg-128-nea2 {
        value 2;
        description
          "128-bit AES based ciphering algorithm";
      }
      enum encr-alg-128-nea3 {
        value 3;
        description
          "128-bit ZUC based ciphering algorithm";
      }
    }
    description
      "Cipher algorithms";
  }

  typedef integrity-algorithm {
    type enumeration {
      enum int-alg-nia0 {
        value 0;
        description
          "Null integrity protection algorithm";
      }
      enum int-alg-128-nia1 {
        value 1;
        description
          "128-bit SNOW 3G based integrity protection algorithm";
      }
      enum int-alg-128-nia2 {
        value 2;
        description
          "128-bit AES based integrity protection algorithm";
      }
      enum int-alg-128-nia3 {
        value 3;
        description
          "128-bit ZUC based integrity protection algorithm";
      }
    }
    description
      "Integrity protection algorithms";
  }

  typedef preemption-vulnerability {
    type enumeration {
      enum preemption-vulnerable {
        value 0;
        description
          "Vulnerable to preemption";
      }
      enum preemption-not-vulnerable {
        value 1;
        description
          "Not vulnerable to preemption";
      }
    }
    description
      "Preemption vulnerability";
  }

  typedef preemption-capability {
    type enumeration {
      enum preemption-capable {
        value 0;
        description
          "Capable of preemption";
      }
      enum preemption-not-capable {
        value 1;
        description
          "Not capable of preemption";
      }
    }
    description
      "Preemption capability";
  }

  grouping amf {
    description
      "AMF name and identifiers";
    leaf name {
      type string {
        length "0..32" {
          error-message "AMF name must be between 0 and 32 characters";
          error-app-tag "must-violation";
        }
        pattern '([!-~]([ -~]*[!-~])?)?' {
          error-message "Please use ASCII 32-126 characters and avoid leading/trailing spaces";
          error-app-tag "must-violation";
        }
      }
      default "";
      description
        "AMF name";
    }
    leaf set-id {
      type uint16 {
        range "0 .. 1023";
      }
      default "0";
      description
        "AMF set identifier";
    }
    leaf pointer {
      type uint8 {
        range "0 .. 63";
      }
      default "0";
      description
        "AMF pointer";
    }
    leaf region-id {
      type uint8 {
        range "0 .. 255";
      }
      default "0";
      description
        "AMF region identifier";
    }
  }

  grouping bitrate {
    description
      "Uplink and downlink bit rates";
    leaf downlink {
      type uint64 {
        range "1 .. 2500000";
      }
      units "kbps";
      default "2500000";
      description
        "Downlink bit rate";
    }
    leaf uplink {
      type uint64 {
        range "1 .. 2500000";
      }
      units "kbps";
      default "2500000";
      description
        "Uplink bit rate";
    }
  }

  grouping arp {
    description
      "Allocation and retention priority (ARP)";
    leaf priority {
      type uint8 {
        range "1 .. 15";
      }
      default "1";
      description
        "Priority level";
    }
    leaf capability {
      type packet-core-types:preemption-capability;
      default "preemption-not-capable";
      description
        "Preemption capability";
    }
    leaf vulnerability {
      type packet-core-types:preemption-vulnerability;
      default "preemption-vulnerable";
      description
        "Preemption vulnerability";
    }
  }

  grouping v4-dns-addrs {
    description
      "IPv4 DNS server addresses";
    leaf primary {
      type inet:ipv4-address;
      default "0.0.0.0";
      description
        "Primary DNS server";
    }
    leaf secondary {
      type inet:ipv4-address;
      default "0.0.0.0";
      description
        "Secondary DNS server";
    }
  }

  grouping v6-dns-addrs {
    description
      "IPv6 DNS server addresses";
    leaf primary {
      type inet:ipv6-address;
      description
        "Primary DNS server";
    }
    leaf secondary {
      type inet:ipv6-address;
      description
        "Secondary DNS server";
    }
  }

  grouping plmn-id {
    description
      "PLMN Identifier consisting of an MCC and an MNC";
    leaf mcc {
      type string {
        length "3";
        pattern '[0-9][0-9][0-9]';
      }
      mandatory true;
      description
        "Mobile Country Code (MCC) consisting of three decimal digits";
    }
    leaf mnc {
      type string {
        length "2|3";
        pattern '[0-9]{2,3}';
      }
      mandatory true;
      description
        "Mobile Network Code (MNC) consisting of two or three decimal
         digits. Note that an MNC of '001' is not same as an MNC of '01'";
    }
  }

  grouping snpn-nid {
    description
      "SNPN Network Identifier (NID)
       consisting of NID Assignment mode and NID value,
       which eventually becomes a 44 bit Network Identifier
       in NGAP Signaling";
    leaf assign-mode {
      type packet-core-types:nid-assignment-mode;
      description
        "SNPN NID assignment mode";
    }
    leaf value {
      type uint64 {
        range "0 .. 1099511627775";
      }
      description
        "SNPN NID value (10 hex digits)";
    }
  }

  grouping s-nssai {
    description
      "Single - Network Slice Selection Assistance Information";
    leaf sst {
      type uint16 {
        range "0 .. 256";
      }
      default "256";
      description
        "Network Slice Service Type";
    }
    leaf sd {
      type uint32 {
        range "0 .. 16777215";
      }
      default "16777215";
      description
        "Network Slice Differentiator";
    }
  }
}
