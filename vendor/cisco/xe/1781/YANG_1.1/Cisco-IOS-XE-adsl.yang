module Cisco-IOS-XE-adsl {
  yang-version 1.1;
  namespace "http://cisco.com/ns/yang/Cisco-IOS-XE-adsl";
  prefix ios-adsl;

  import Cisco-IOS-XE-native {
    prefix ios;
  }
  import Cisco-IOS-XE-controller {
    prefix ios-ctrl;
  }
  import cisco-semver {
    prefix cisco-semver;
  }
  import Cisco-IOS-XE-types {
    prefix ios-types;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native ADSL (Asymmetric Digital Subscriber Line) Yang model
     to support Titan DSL controller commands.
     Copyright (c) 2020-2021 by Cisco Systems, Inc.
     All rights reserved.";

  revision 2022-03-01 {
    description
      "- Add Annex-B support";
  }
  revision 2021-07-01 {
    description
      "- Add rx-padding node";
  }
  revision 2020-08-01 {
    description
      "- Initial revision";
    cisco-semver:module-version "1.0.0";
  }

  grouping adsl-pvc-grouping {
    container carrier-set {
      description
        "Set carrier tonal frequency value";
      presence "true";
      leaf carrier-set-values {
        description
          "Carrier-set values";
        type enumeration {
          enum a43 {
            description
              "Carrier set A43";
          }
          enum a43c {
            description
              "Carrier set A43C";
          }
          enum b43 {
            description
              "Carrier set B43";
          }
          enum v43 {
            description
              "Carrier set V43";
          }
        }
      }
    }
    container capability {
      description
        "Set annex specification";
      presence "true";
      leaf capability-values {
        description
          "Capability values";
        type enumeration {
          enum annex-b {
            description
              "Annex-B Support";
          }
          enum annex-j {
            description
              "Annex-J Support";
          }
        }
      }
    }
    leaf mac-address {
      description
        "Set DSL SFP MAC address";
      type ios-types:cisco-mac-address-type;
    }
    leaf rx-padding {
      description
        "Enable padding of received packets";
      type boolean;
      default "false";
    }
    list adsl-pvc {
      description
        "Configure ADSL PVC (Permanent Virtual Circuit) parameters";
      key "vpi-vci";
      leaf vpi-vci {
        description
          "Enter VPI/VCI value (slash required)";
        type string;
      }
      leaf bridge-dot1q {
        description
          "802.1Q VLAN ID to PVC mapping";
        type uint16 {
          range "1..4094";
        }
      }
      leaf encapsulation {
        description
          "Configure ADSL PVC Encapsulation";
        type enumeration {
          enum llcsnap {
            description
              "LLC/SNAP Encapsulation";
          }
          enum vcmux {
            description
              "VCMux Encapsulation";
          }
        }
      }
      container pvc-qos {
        description
          "Configure PVC QoS parameters";
        choice pvc-qos-choice {
          case cbr {
            container cbr {
              description
                "Configure Constant Bit Rate (CBR) Service";
              leaf pcr {
                description
                  "PCR (Peak Cell Rate)";
                type uint16 {
                  range "0..5500";
                }
              }
            }
          }
          case ubr {
            container ubr {
              description
                "Configure Unspecified Bit Rate (UBR) Service";
              leaf pcr {
                description
                  "PCR (Peak Cell Rate)";
                type uint16 {
                  range "0..5500";
                }
              }
            }
          }
          case vbr-nrt {
            container vbr-nrt {
              description
                "Configure Non Real-time Variable Bit Rate Service";
              leaf pcr {
                description
                  "PCR (Peak Cell Rate)";
                type uint16 {
                  range "0..5500";
                }
              }
              leaf scr {
                description
                  "SCR (Sustainable Cell Rate)";
                when '../pcr';
                must 'current() <= ../pcr' {
                  error-message "Please ensure pcr >= scr for vbr-nrt";
                }
                type uint16 {
                  range "0..5500";
                }
              }
            }
          }
          case vbr-rt {
            container vbr-rt {
              description
                "Configure Real-time Variable Bit Rate Service";
              leaf pcr {
                description
                  "PCR (Peak Cell Rate)";
                type uint16 {
                  range "0..5500";
                }
              }
              leaf scr {
                description
                  "SCR (Sustainable Cell Rate)";
                when '../pcr';
                must 'current() <= ../pcr' {
                  error-message "Please ensure pcr >= scr for vbr-rt";
                }
                type uint16 {
                  range "0..5500";
                }
              }
            }
          }
        }
      }
      leaf vlanid-rx {
        description
          "PVC VLAN Receive ID";
        type uint16 {
          range "1..4094";
        }
      }
      leaf vlanid-tx {
        description
          "PVC VLAN Transmit ID";
        type uint16 {
          range "1..4094";
        }
      }
      leaf vlanop-rx {
        description
          "PVC VLAN Receive ID Operation";
        type enumeration {
          enum pass-through {
            description
              "Pass-through VLAN ID Operation";
          }
          enum remove {
            description
              "Remove VLAN ID Operation";
          }
          enum replace {
            description
              "Replace VLAN ID Operation (default)";
          }
        }
      }
      leaf vlanop-tx {
        description
          "PVC VLAN Transmit ID Operation";
        type enumeration {
          enum pass-through {
            description
              "Pass-through VLAN ID Operation";
          }
          enum remove {
            description
              "Remove VLAN ID Operation";
          }
          enum replace {
            description
              "Replace VLAN ID Operation (default)";
          }
        }
      }
    }
  }

  augment "/ios:native/ios:controller/ios-ctrl:VDSL" {
    uses adsl-pvc-grouping;
  }
}
