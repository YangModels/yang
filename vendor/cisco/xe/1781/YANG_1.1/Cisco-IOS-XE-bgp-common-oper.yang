module Cisco-IOS-XE-bgp-common-oper {
  yang-version 1.1;
  namespace "http://cisco.com/ns/yang/Cisco-IOS-XE-bgp-common-oper";
  prefix bgp-common-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     common for all bgp operational data.
     Copyright (c) 2016-2017, 2019 by Cisco Systems, Inc.
     All rights reserved.";

  revision 2019-05-01 {
    description
      "Added semantic version";
    reference
      "1.1.0";
    cisco-semver:module-version "1.1.0";
  }
  revision 2017-02-07 {
    description
      "Initial revision";
    reference
      "1.0.0";
    cisco-semver:module-version "1.0.0";
  }

  typedef afi-safi {
    type enumeration {
      enum ipv4-mdt {
        value 0;
        description
          "IPv4 MDT address family";
      }
      enum ipv4-multicast {
        value 1;
        description
          "IPv4 Multicast address family";
      }
      enum ipv4-unicast {
        value 2;
        description
          "IPv4 Unicast address family";
      }
      enum ipv4-mvpn {
        value 3;
        description
          "IPV4 MVPN address family";
      }
      enum ipv4-flowspec {
        value 4;
        description
          "IPv4 Flowspec address family";
      }
      enum ipv6-multicast {
        value 5;
        description
          "IPv6 Multicast address family";
      }
      enum ipv6-unicast {
        value 6;
        description
          "IPv6 Unicast address family";
      }
      enum ipv6-mvpn {
        value 7;
        description
          "IPv6 MVPN address family";
      }
      enum ipv6-flowspec {
        value 8;
        description
          "IPv6 Flowspec address family";
      }
      enum l2vpn-vpls {
        value 9;
        description
          "L2VPN VPLS address family";
      }
      enum l2vpn-e-vpn {
        value 10;
        description
          "L2VPN EVPN address family";
      }
      enum nsap-unicast {
        value 11;
        description
          "NSAP Unicast address family";
      }
      enum rtfilter-unicast {
        value 12;
        description
          "RT Filter Unicast address family";
      }
      enum vpnv4-multicast {
        value 13;
        description
          "VPNv4 Multicast address family";
      }
      enum vpnv4-unicast {
        value 14;
        description
          "VPNv4 Unicast address family";
      }
      enum vpnv6-unicast {
        value 15;
        description
          "VPNv6 Unicast address family";
      }
      enum vpnv6-multicast {
        value 16;
        description
          "VPNv6 Multicast address family";
      }
      enum vpnv4-flowspec {
        value 17;
        description
          "VPNv4 Flowspec address family";
      }
      enum vpnv6-flowspec {
        value 18;
        description
          "VPNv6 Flowspec address family";
      }
    }
    description
      "Base identity from which identities
       describing address families are derived.
       This identity represents IPv4 address family";
  }

  typedef tcp-fsm-state {
    type enumeration {
      enum closed {
        value 0;
        description
          "no connection";
      }
      enum listen {
        value 1;
        description
          "Waiting for a connection request from any remote TCP";
      }
      enum synsent {
        value 2;
        description
          "Waiting for a matching connection request
           after having sent a connection request";
      }
      enum synrcvd {
        value 3;
        description
          "Waiting for a confirming connection request acknowledgment
           after having both received and sent a connection request";
      }
      enum established {
        value 4;
        description
          "connection established";
      }
      enum finwait1 {
        value 5;
        description
          "Waiting for a connection termination request
           from the remote TCP, or an acknowledgment of
           the connection termination request previously sent";
      }
      enum finwait2 {
        value 6;
        description
          "Waiting for a connection termination request from the
           remote TCP";
      }
      enum closewait {
        value 7;
        description
          "Waiting for a connection termination request from
           the local use";
      }
      enum lastack {
        value 8;
        description
          "Waiting for an acknowledgment of the connection termination
           request previously sent to the remote TCP";
      }
      enum closing {
        value 9;
        description
          "Waiting for a connection termination request acknowledgment
           from the remote";
      }
      enum timewait {
        value 10;
        description
          "waiting for enough time to pass to be sure the remote TCP
           received the acknowledgment of its connection termination request";
      }
    }
    description
      "TCP state machine states";
  }
}
