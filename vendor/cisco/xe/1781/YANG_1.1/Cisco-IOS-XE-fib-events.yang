module Cisco-IOS-XE-fib-events {
  yang-version 1.1;
  namespace "http://cisco.com/ns/yang/Cisco-IOS-XE-fib-events";
  prefix fib-ios-xe-events;

  import Cisco-IOS-XE-ios-common-oper {
    prefix ios-common-ios-xe-oper;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for FIB status change notification.
     Copyright (c) 2021 by Cisco Systems, Inc.
     All rights reserved.";

  revision 2022-03-01 {
    description
      "Initial revision";
    reference
      "1.0.0";
    cisco-semver:module-version "1.0.0";
  }

  typedef fib-af-type {
    type enumeration {
      enum fib-af-unknown {
        value 0;
        description
          "Unknown address family";
      }
      enum fib-af-ipv4 {
        value 1;
        description
          "IPv4 address family";
      }
      enum fib-af-ipv6 {
        value 2;
        description
          "IPv6 address family";
      }
    }
    description
      "FIB address family types";
  }

  typedef fib-updates-af-type {
    type enumeration {
      enum fib-updates-af-unknown {
        value 0;
        description
          "Unknown address family";
      }
      enum fib-updates-af-ipv4 {
        value 1;
        description
          "IPv4 address family";
      }
      enum fib-updates-af-ipv6 {
        value 2;
        description
          "IPv6 address family";
      }
    }
    description
      "FIB updates AF type";
  }

  grouping fib-notif-default-route-state {
    description
      "FIB default route state";
    leaf table-name {
      type string;
      description
        "FIB table name";
    }
    leaf vrf-name {
      type string;
      description
        "VRF name";
    }
    leaf af {
      type fib-ios-xe-events:fib-af-type;
      description
        "Address family";
    }
    leaf drh-override {
      type boolean;
      description
        "Default route handler over";
    }
  }

  grouping fib-update {
    description
      "FIB update notifications";
    leaf severity-level {
      type ios-common-ios-xe-oper:notification-severity;
      description
        "Event severity";
    }
    leaf host-name {
      type string;
      description
        "Host name";
    }
    leaf system-ip {
      type inet:ip-address;
      description
        "IP address";
    }
    leaf vrf-name {
      type string;
      description
        "Last updated VRF";
    }
    leaf address-family-type {
      type fib-ios-xe-events:fib-updates-af-type;
      description
        "Last updated address family";
    }
    leaf fib-last-update-time {
      type yang:date-and-time;
      description
        "Last update time";
    }
  }

  notification fib-updates {
    description
      "FIB update notification. This notification should be used instead of the older FIB notifications from namespace ios-events-ios-xe-oper.";
    uses fib-ios-xe-events:fib-update;
  }

  notification fib-default-route-state-change {
    description
      "FIB default route state change notification";
    uses fib-ios-xe-events:fib-notif-default-route-state;
  }
}
