module Cisco-IOS-XE-umbrella {
  yang-version 1.1;
  namespace "http://cisco.com/ns/yang/Cisco-IOS-XE-umbrella";
  prefix ios-umbrella;

  import cisco-semver {
    prefix cisco-semver;
  }
  import ietf-inet-types {
    prefix inet;
  }
  import Cisco-IOS-XE-native {
    prefix ios;
  }
  import Cisco-IOS-XE-policy {
    prefix ios-policy;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Umbrella Yang model.
     Copyright (c) 2017-2020 by Cisco Systems, Inc.
     All rights reserved.";

  revision 2020-11-01 {
    description
      "- Obsolete interface augment";
    cisco-semver:module-version "2.2.0";
  }
  revision 2020-07-01 {
    description
      "- Added local-resolver support in global parameter-map
       - Added local-domain support in non-global parameter-map
       - Removed local-resolver support in global parameter-map
       - Removed local-domain support in non-global parameter-map";
    cisco-semver:module-version "2.1.0";
  }
  revision 2020-03-01 {
    description
      "- Added constraints to resolver
       - Added default to udp-timeout";
    cisco-semver:module-version "2.0.0";
  }
  revision 2019-11-01 {
    description
      "- Added non-global parameter-map type umbrella";
    cisco-semver:module-version "1.1.0";
  }
  revision 2019-07-01 {
    description
      "- Establish semantic version baseline
       - Adding api-key, secret and org id CLI under parameter-map umbrella";
    cisco-semver:module-version "1.0.0";
  }
  revision 2019-01-25 {
    description
      "Added leaf for App-hosting Gigabit Ethernet interface";
  }
  revision 2018-12-06 {
    description
      "Change non-strict-leafref's to leafref's for threat-defense features";
  }
  revision 2018-11-11 {
    description
      "Show default values under parameter-map construct";
  }
  revision 2018-11-06 {
    description
      "Remove instances of max string length of 128/256/512";
  }
  revision 2018-10-12 {
    description
      "interface config of umbrella with dca";
  }
  revision 2018-06-26 {
    description
      "Changed match-local-domain to match-local-domain-to-bypass";
  }
  revision 2018-05-18 {
    description
      "Add support for sdwan platforms";
  }
  revision 2018-05-14 {
    description
      "Limit string lengths for threat-defense features";
  }
  revision 2018-02-22 {
    description
      "Add threat-defense support for Ethernet interfaces";
  }
  revision 2018-02-06 {
    description
      "Refactor parameter-map";
  }
  revision 2017-11-27 {
    description
      "Added Change 25GE name";
  }
  revision 2017-11-14 {
    description
      "Added Two GE Interface";
  }
  revision 2017-08-30 {
    description
      "Initial revision";
  }

  grouping config-umbrella-grouping {
    container umbrella {
      description
        "Umbrella mode";
      container global {
        description
          "umbrella global parameter-map";
        presence "true";
        leaf token {
          description
            "Config umbrella token";
          type string {
            length "1..64";
          }
        }
        leaf local-domain {
          description
            "Local domain processing";
          type leafref {
            path "/ios:native/ios:parameter-map/ios:type/ios-policy:regex/ios-policy:name";
          }
        }
        leaf dnscrypt {
          description
            "Enable DNSCrypt";
          type boolean;
          default "true";
        }
        leaf public-key {
          description
            "DNSCrypt provider public key";
          type string {
            length "1..80";
          }
        }
        leaf udp-timeout {
          description
            "Config timeout value for UDP sessions";
          type uint8 {
            range "1..30";
          }
          default "5";
        }
        container resolver {
          description
            "Anycast address";
          list ipv4 {
            description
              "IPv4 anycast address";
            key "address";
            leaf address {
              type inet:ipv4-address;
            }
            must "not(/ios:native/ios:parameter-map/ios:type/ios-umbrella:umbrella/ios-umbrella:global/ios-umbrella:resolver/ios-umbrella:ipv4[ios-umbrella:address='208.67.222.222'] or
                      /ios:native/ios:parameter-map/ios:type/ios-umbrella:umbrella/ios-umbrella:global/ios-umbrella:resolver/ios-umbrella:ipv4[ios-umbrella:address='208.67.220.220'])" {
              error-message "Config not allowed for default umbrella resolver addresses 208.67.222.222 and 208.67.220.220";
            }
          }
          list ipv6 {
            description
              "IPv6 anycast address";
            key "address";
            leaf address {
              type inet:ipv6-address;
            }
            must "not(/ios:native/ios:parameter-map/ios:type/ios-umbrella:umbrella/ios-umbrella:global/ios-umbrella:resolver/ios-umbrella:ipv6[ios-umbrella:address='2620:119:53::53'] or
                      /ios:native/ios:parameter-map/ios:type/ios-umbrella:umbrella/ios-umbrella:global/ios-umbrella:resolver/ios-umbrella:ipv6[ios-umbrella:address='2620:119:35::35'])" {
              error-message "Config not allowed for default umbrella resolver addresses 2620:119:53::53 and 2620:119:35::35";
            }
          }
        }
        leaf orgid {
          description
            "Config umbrella org id";
          type uint32 {
            range "1..2147483647";
          }
        }
        leaf api-key {
          description
            "Config umbrella api-key";
          type string {
            length "1..64";
          }
        }
        container secret {
          description
            "Secret";
          leaf encryption {
            type enumeration {
              enum 0;
              enum 6;
            }
          }
          leaf secret-key {
            type string;
          }
        }
        leaf registration-vrf {
          description
            "Exit VRF for Umbrella Registrations";
          must '/ios:native/ios:ip/ios:vrf[ios:name = current()] or /ios:native/ios:vrf/ios:definition[ios:name = current()]' {
            error-message "Please create vrf first, and delete vrf last";
          }
          type string {
            length "1..32";
          }
        }
        list vrf {
          description
            "Umbrella per-VRF Config Parameters";
          key "name";
          leaf name {
            description
              "VRF name";
            must '/ios:native/ios:ip/ios:vrf[ios:name = current()] or /ios:native/ios:vrf/ios:definition[ios:name = current()]' {
              error-message "Please create vrf first, and delete vrf last";
            }
            type string {
              length "1..32";
            }
          }
          leaf dns-resolver {
            description
              "Config DNS resolver";
            type union {
              type inet:ipv4-address;
              type enumeration {
                enum umbrella;
              }
            }
          }
          leaf match-local-domain-to-bypass {
            description
              "Match local domain list (if configured) and bypass from redirection";
            type boolean;
            default "true";
          }
        }
      }
      list non-global-parameter-map {
        description
          "non-global parameter-map name";
        key "name";
        leaf name {
          description
            "parameter-map name maximum 32 chars";
          must '/ios:native/ios:parameter-map/ios:type/ios-umbrella:umbrella/ios-umbrella:global' {
            error-message "Global Umbrella parameter-map must be created first and deleted last";
          }
          type string {
            length "1..32";
          }
        }
      }
    }
  }

  grouping config-interface-umbrella-grouping {
    container umbrella {
      description
        "Umbrella interface commands";
      leaf out {
        description
          "Umbrella Out direction";
        type empty;
      }
      container in {
        description
          "Umbrella In direction";
        choice tag_or_dca {
          leaf tag {
            description
              "Umbrella interface tag";
            type string {
              length "1..49";
            }
          }
          container direct-cloud-access {
            description
              "Umbrella direct cloud access";
            leaf policy {
              description
                "Umbrella policy map name";
              must "/ios:native/ios:policy/ios-policy:policy-map[ios-policy:name=current()] or .='default'" {
                error-message "user-defined policy or default policy must be configured";
              }
              type string {
                length "1..512";
              }
            }
            leaf tag {
              description
                "Umbrella interface tag";
              type string {
                length "1..49";
              }
            }
          }
        }
      }
    }
  }

  augment "/ios:native/ios:parameter-map/ios:type" {
    uses config-umbrella-grouping;
  }

  augment "/ios:native/ios:interface/ios:Ethernet" {
    uses config-interface-umbrella-grouping;
  }

  augment "/ios:native/ios:interface/ios:FastEthernet" {
    uses config-interface-umbrella-grouping;
  }

  augment "/ios:native/ios:interface/ios:GigabitEthernet" {
    uses config-interface-umbrella-grouping;
  }

  augment "/ios:native/ios:interface/ios:TenGigabitEthernet" {
    uses config-interface-umbrella-grouping;
  }

  augment "/ios:native/ios:interface/ios:FiveGigabitEthernet" {
    uses config-interface-umbrella-grouping;
  }

  augment "/ios:native/ios:interface/ios:AppGigabitEthernet" {
    uses config-interface-umbrella-grouping;
  }

  augment "/ios:native/ios:interface/ios:TwentyFiveGigabitEthernet" {
    status obsolete;
    uses config-interface-umbrella-grouping {
      status obsolete;
    }
  }

  augment "/ios:native/ios:interface/ios:TwentyFiveGigE" {
    uses config-interface-umbrella-grouping;
  }

  augment "/ios:native/ios:interface/ios:FortyGigabitEthernet" {
    uses config-interface-umbrella-grouping;
  }

  augment "/ios:native/ios:interface/ios:HundredGigE" {
    uses config-interface-umbrella-grouping;
  }

  augment "/ios:native/ios:interface/ios:TwoGigabitEthernet" {
    uses config-interface-umbrella-grouping;
  }

  augment "/ios:native/ios:interface/ios:LISP" {
    uses config-interface-umbrella-grouping;
  }

  augment "/ios:native/ios:interface/ios:Loopback" {
    uses config-interface-umbrella-grouping;
  }

  augment "/ios:native/ios:interface/ios:Tunnel" {
    uses config-interface-umbrella-grouping;
  }

  augment "/ios:native/ios:interface/ios:Virtual-Template" {
    uses config-interface-umbrella-grouping;
  }

  augment "/ios:native/ios:interface/ios:Vlan" {
    uses config-interface-umbrella-grouping;
  }

  augment "/ios:native/ios:interface/ios:vasileft" {
    uses config-interface-umbrella-grouping;
  }

  augment "/ios:native/ios:interface/ios:vasiright" {
    uses config-interface-umbrella-grouping;
  }
}
