module Cisco-IOS-XE-vrrp-events {
  yang-version 1.1;
  namespace "http://cisco.com/ns/yang/Cisco-IOS-XE-vrrp-events";
  prefix vrrp-ios-xe-events;

  import Cisco-IOS-XE-common-types {
    prefix common-types-ios-xe;
  }
  import Cisco-IOS-XE-ios-common-oper {
    prefix ios-common-ios-xe-oper;
  }
  import Cisco-IOS-XE-vrrp-types {
    prefix vrrp-ios-xe-types;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for VRRP BFD State change Notification.
     Copyright (c) 2020 by Cisco Systems, Inc.
     All rights reserved.";

  revision 2021-03-01 {
    description
      "Initial revision";
    reference
      "1.0.0";
    cisco-semver:module-version "1.0.0";
  }

  grouping vrrp-bfd-state-update-data {
    description
      "VRRP BFD state change Notification";
    leaf severity {
      type ios-common-ios-xe-oper:notification-severity;
      description
        "Event severity";
    }
    leaf host-name {
      type string;
      description
        "Host name";
    }
    leaf system-ip {
      type inet:ip-address;
      description
        "System IP address";
    }
    leaf group-id {
      type uint16;
      description
        "VRRP Group ID";
    }
    leaf addr-type {
      type common-types-ios-xe:addr-type;
      description
        "Address family of VRRP group";
    }
    leaf if-name {
      type string;
      description
        "Name for the interface where VRRP group is hosted";
    }
    leaf bfd-state {
      type vrrp-ios-xe-types:vrrp-bfd-state-type;
      description
        "VRRP BFD state";
    }
  }

  notification vrrp-bfd-state-update {
    description
      "VRRP BFD state change Notification";
    uses vrrp-ios-xe-events:vrrp-bfd-state-update-data;
  }
}
