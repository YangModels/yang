module Cisco-IOS-XE-packet-core-policy-cfg {
  yang-version 1.1;
  namespace "http://cisco.com/ns/yang/Cisco-IOS-XE-packet-core-policy-cfg";
  prefix packet-core-policy-cfg;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Packet-Core policy configuration.
     Copyright (c) 2021 by Cisco Systems, Inc.
     All rights reserved.";

  revision 2021-11-01 {
    description
      "Initial revision";
    reference
      "1.0.0";
    cisco-semver:module-version "1.0.0";
  }

  grouping class-map-5qi {
    description
      "Class-map to 5QI association";
    leaf class-map-name {
      type string {
        length "1..80" {
          error-message "Class-map name must be between 1 and 80 characters";
          error-app-tag "must-violation";
        }
        pattern '[!-~]([ -~]*[!-~])?' {
          error-message "Class-map name must use ASCII 32-126 characters and must not contain leading or trailing spaces";
          error-app-tag "pattern-violation";
        }
      }
      description
        "Class-map to be applied to QoS Flows";
    }
    leaf qos-flow-5qi {
      type uint8 {
        range "1 .. 86";
      }
      must "((current() <= 9) or
            (current() >= 65) and (current() <= 67) or
            (current() >= 69) and (current() <= 76) or
            (current() >= 79) and (current() <= 80) or
            (current() >= 82))" {
        error-message "5QI value must be within 1-9 or 65-67 or 69-76 or 79-80 or 82-86";
        error-app-tag "must-violation";
      }
      default "9";
      description
        "5QI value associated with the class-map";
    }
  }

  grouping policy-profile {
    description
      "Policy profile configuration";
    leaf status {
      type boolean;
      default "false";
      description
        "Administrative status of policy profile";
    }
    leaf profile-name {
      type string {
        length "1..32" {
          error-message "Policy profile name must be between 1 and 32 characters";
          error-app-tag "must-violation";
        }
        pattern '[!-~]([ -~]*[!-~])?' {
          error-message "Policy profile name must use ASCII 32-126 characters and must not contain leading or trailing spaces";
          error-app-tag "pattern-violation";
        }
      }
      description
        "Policy profile name";
    }
    leaf policy-map-name {
      type string {
        length "0..80";
        pattern '([!-~]([ -~]*[!-~])?)?' {
          error-message "Policy map name must use ASCII 32-126 characters and must not contain leading or trailing spaces";
          error-app-tag "pattern-violation";
        }
      }
      default "";
      description
        "Policy map name";
    }
    leaf ipv4-acl-name {
      type string {
        length "0..80";
        pattern '([!-~]([ -~]*[!-~])?)?' {
          error-message "ACL name must use ASCII 32-126 characters and must not contain leading or trailing spaces";
          error-app-tag "pattern-violation";
        }
      }
      default "";
      description
        "IPv4 ACL name";
    }
    leaf ipv6-acl-name {
      type string {
        length "0..80";
        pattern '([!-~]([ -~]*[!-~])?)?' {
          error-message "ACL name must use ASCII 32-126 characters and must not contain leading or trailing spaces";
          error-app-tag "pattern-violation";
        }
      }
      default "";
      description
        "IPv6 ACL name";
    }
    container class-map-5qis {
      description
        "A list of class-maps and associated 5QI values";
      list class-map-5qi {
        key "class-map-name";
        description
          "Class-map to 5QI association";
        uses packet-core-policy-cfg:class-map-5qi;
      }
    }
  }

  container packet-core-policy-cfg-data {
    description
      "Packet-Core policy configuration data model";
    container packet-core-policies {
      description
        "A list of policy profile configuration";
      list packet-core-policy {
        key "profile-name";
        description
          "Policy profile configuration";
        uses packet-core-policy-cfg:policy-profile;
      }
    }
  }
}
