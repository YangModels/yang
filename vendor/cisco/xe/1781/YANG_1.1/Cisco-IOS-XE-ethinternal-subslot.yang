module Cisco-IOS-XE-ethinternal-subslot {
  yang-version 1.1;
  namespace "http://cisco.com/ns/yang/Cisco-IOS-XE-ethinternal-subslot";
  prefix ios-ethinternal-subslot;

  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Synchronous Ethernet Yang Model.
     Copyright (c) 2020 by Cisco Systems, Inc.
     All rights reserved.";

  revision 2020-11-01 {
    description
      "Initial revision";
  }

  grouping config-ethinternal-subslot-svi-grouping {
    description
      "SM-X module configuration";
    container ethernet-internal {
      list subslot {
        description
          "Subslot information";
        key "subslot-number";
        leaf subslot-number {
          type string {
            pattern '[1-2/0]*';
          }
        }
        container platform {
          leaf switchport {
            description
              "Select ethernet internal interface work mode";
            type enumeration {
              enum svi {
                description
                  "The ethernet internal interface with SVI interface";
              }
              enum bdi {
                description
                  "The ethernet internal interface with BDI interface";
              }
            }
          }
        }
      }
    }
  }

  augment "/ios:native" {
    uses config-ethinternal-subslot-svi-grouping;
  }
}
