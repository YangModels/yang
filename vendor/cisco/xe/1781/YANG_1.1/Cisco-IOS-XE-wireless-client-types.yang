module Cisco-IOS-XE-wireless-client-types {
  yang-version 1.1;
  namespace "http://cisco.com/ns/yang/Cisco-IOS-XE-wireless-client-types";
  prefix wireless-client-types;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for wireless client data types.
     Copyright (c) 2016-2019, 2021 by Cisco Systems, Inc.
     All rights reserved.";

  revision 2022-03-01 {
    description
      "- Added support for stats of delete reasons related to the maximum clients limit
       - Added new client delete reason for device PMK timeout in client delete reason stats";
    reference
      "4.5.0";
    cisco-semver:module-version "4.5.0";
  }
  revision 2021-07-01 {
    description
      "- Added Station/Device manufacturers enum
       - Added enum for 6 GHz radio type and protocol type
       - Added support for client delete reason stats";
    reference
      "4.4.0";
    cisco-semver:module-version "4.4.0";
  }
  revision 2021-03-01 {
    description
      "- Added RSN Cipher GMAC-256 enum";
    reference
      "4.3.0";
    cisco-semver:module-version "4.3.0";
  }
  revision 2020-03-01 {
    description
      " - Added OSEN enum values in dot11 EAP WPA version.";
    reference
      "4.2.0";
    cisco-semver:module-version "4.2.0";
  }
  revision 2019-05-01 {
    description
      "- Added enum value SAE for authentication algorithm.
       - Added semantic version";
    reference
      "4.1.0";
    cisco-semver:module-version "4.1.0";
  }
  revision 2018-12-17 {
    description
      "- Insertion of an enumeration for wired guest
       - Cleaned up spelling errors in descriptions
       - Removed explicit MAX from CO state enum";
    reference
      "4.0.0";
    cisco-semver:module-version "4.0.0";
  }
  revision 2018-08-08 {
    description
      "- Add 11ax client physical type enumeration
       - Add WPA3 support";
    reference
      "3.1.0";
    cisco-semver:module-version "3.1.0";
  }
  revision 2018-03-22 {
    description
      "Insertion of an enumeration";
    reference
      "3.0.0";
    cisco-semver:module-version "3.0.0";
  }
  revision 2018-01-24 {
    description
      "The first generally available version";
    reference
      "2.0.0";
    cisco-semver:module-version "2.0.0";
  }
  revision 2017-05-05 {
    description
      "Initial revision";
    reference
      "1.0.0";
    cisco-semver:module-version "1.0.0";
  }

  typedef client-co-state {
    type enumeration {
      enum client-status-idle {
        value 0;
        description
          "Represents the client in idle state";
      }
      enum client-status-associating {
        value 1;
        description
          "Used to indicate that the client is trying to associate";
      }
      enum client-status-associated {
        value 2;
        description
          "Used to indicate that the client has associated to the Access point";
      }
      enum client-status-authenticating {
        value 3;
        description
          "Used to indicate that the client is in the the process of authenticating";
      }
      enum client-status-authenticated {
        value 4;
        description
          "Used to indicate that the client has been Authenticated";
      }
      enum client-status-mobility-discovery {
        value 5;
        description
          "Used to indicate that the client is in mobility discovery state";
      }
      enum client-status-mobility-complete {
        value 6;
        description
          "Used to indicate that the client is in mobility complete state";
      }
      enum client-status-ip-learning {
        value 7;
        description
          "Used to indicate that the client is in the state of learning the IP";
      }
      enum client-status-ip-learn-complete {
        value 8;
        description
          "Used to indicate that the client has completed the IP learn process";
      }
      enum client-status-webauth-required {
        value 9;
        description
          "Used to indicate that the client web authentication is pending";
      }
      enum client-status-static-ip-anchor-discovery {
        value 10;
        description
          "Used to indicate that the client is in static ip anchor discovery state";
      }
      enum client-status-run {
        value 11;
        description
          "Used to indicate that the client has moved to run state";
      }
      enum client-status-delete-in-progress {
        value 12;
        description
          "Used to indicate that the client delete is in progress";
      }
      enum client-status-deleted {
        value 13;
        description
          "Used to indicate that the client has been deleted";
      }
    }
    description
      "represents the client orchestrator state";
  }

  typedef ms-radio-type {
    type enumeration {
      enum dot11-radio-type-none {
        value 0;
        description
          "Used to indicate that the radio is not of type BG or A";
      }
      enum dot11-radio-type-bg {
        value 1;
        description
          "Used to indicate that the radio is of type BG";
      }
      enum dot11-radio-type-a {
        value 2;
        description
          "Used to indicate that the radio is of type A";
      }
      enum dot11-radio-type-6ghz {
        value 16;
        description
          "Used to indicate that the radio is of type 6 GHz Band";
      }
    }
    description
      "Used to indicate whether the radio type is BG or A";
  }

  typedef ms-phy-radio-type {
    type enumeration {
      enum client-unknown-prot {
        value 0;
        description
          "The client protocol is unknown";
      }
      enum client-dot11b {
        value 1;
        description
          "The client is using 802.11b standard to connect to the access point (AP)";
      }
      enum client-dot11g {
        value 2;
        description
          "The client is using 802.11g standard to connect to the access point (AP)";
      }
      enum client-dot11a {
        value 3;
        description
          "The client is using 802.11a standard to connect to the access point (AP)";
      }
      enum client-dot11n-24-ghz-prot {
        value 4;
        description
          "The client is using 802.11n standard with 2.4 GHz frequency to connect to the access point (AP)";
      }
      enum client-dot11n-5-ghz-prot {
        value 5;
        description
          "The client is using 802.11n standard with 5 GHz frequency to connect to the access point (AP)";
      }
      enum client-dot11ac {
        value 6;
        description
          "The client is using dot11ac standard to connect to the access point (AP).";
      }
      enum client-phy-type-notappl {
        value 7;
        description
          "Radio type is not applicable to WGB wired client";
      }
      enum client-ethernet {
        value 8;
        description
          "Radio type is not applicable to rlan client";
      }
      enum client-dot11ax-5ghz-prot {
        value 9;
        description
          "The client is using dot11ax standard on 5 GHz radio to connect to the access point (AP)";
      }
      enum client-dot11ax-24ghz-prot {
        value 10;
        description
          "The client is using dot11ax standard on 2.4 GHz radio to connect to the access point (AP)";
      }
      enum client-802-3 {
        value 11;
        description
          "The client is a wired guest client, protocol 802.3";
      }
      enum client-dot11ax-6ghz-prot {
        value 12;
        description
          "The client is using dot11ax standard on 6 GHz radio to connect to the access point (AP)";
      }
    }
    description
      "The 802.11 protocol type of the client";
  }

  typedef ms-type {
    type enumeration {
      enum ms-type-local {
        value 0;
        description
          "Mobile station type is local";
      }
      enum ms-type-anchor {
        value 1;
        description
          "Mobile station type is Anchor";
      }
      enum ms-type-flex-central-auth {
        value 2;
        description
          "Mobile station is centrally authenticated in flex mode";
      }
      enum ms-type-flex-local-auth {
        value 3;
        description
          "Mobile station is locally authenticated in flex mode";
      }
      enum ms-type-guest {
        value 4;
        description
          "Mobile station type is guest";
      }
    }
    description
      "Mobile station entry type";
  }

  typedef ms-client-type {
    type enumeration {
      enum dot11-client-normal {
        value 0;
        description
          "wireless client";
      }
      enum dot11-client-wgb {
        value 1;
        description
          "workgroup bridge";
      }
      enum dot11-client-wired {
        value 2;
        description
          "wired client";
      }
      enum dot11-client-rlan {
        value 3;
        description
          "rlan client";
      }
      enum client-802-3-guest-lan {
        value 4;
        description
          "Wired Guest client connected through 802.3 protocol";
      }
    }
    description
      "client type";
  }

  typedef dot11-eap-wpa-version {
    type enumeration {
      enum dot1x-wpa-version {
        value 0;
        description
          "The WPA version of the client is 802.1x";
      }
      enum wpa1 {
        value 1;
        description
          "The WPA version of the client is WPA1";
      }
      enum wpa2 {
        value 2;
        description
          "The WPA version of the client is WPA2";
      }
      enum wpa-version-wpa2-v3 {
        value 3;
        description
          "The WPA version of the client is WPA wVFF";
      }
      enum wpa-version-not-def {
        value 4;
        description
          "The WPA version of the client is Not Defined";
      }
      enum wpa-version-wpa3 {
        value 5;
        description
          "The WPA version of the client is WPA3";
      }
      enum wpa-osen {
        value 6;
        description
          "The WPA client encryption type is OSEN";
      }
      enum wpa-osen-within-rsn {
        value 7;
        description
          "The WPA client encryption type is OSEN within RSN";
      }
    }
    description
      "Enumeration for the WPA versions that can be used in a client connection";
  }

  typedef client-wep-policy-type {
    type enumeration {
      enum client-policy-type-none {
        value 0;
        description
          "The client's WEP State is None";
      }
      enum client-policy-type-static-wep {
        value 1;
        description
          "The client's WEP State is Static WEP";
      }
      enum client-policy-type-dynamic-wep {
        value 2;
        description
          "The client's WEP State is Dynamic WEP";
      }
    }
    description
      "This data type tells us about the WEP state of the client";
  }

  typedef dot11-state {
    type enumeration {
      enum idle {
        value 0;
        description
          "The current client state is Idle";
      }
      enum associating {
        value 1;
        description
          "The current client state is Associating";
      }
      enum associated {
        value 2;
        description
          "The current client state is Associated";
      }
      enum deleting {
        value 3;
        description
          "The current client state is Deleting";
      }
      enum deleted {
        value 4;
        description
          "The current client state is Deleted";
      }
    }
    description
      "Enumeration for the client current status";
  }

  typedef auth-algo {
    type enumeration {
      enum open-system {
        value 0;
        description
          "The client joined through Open Authentication";
      }
      enum shared-key {
        value 1;
        description
          "The client joined through Shared WEP Authentication";
      }
      enum open-and-eap {
        value 128;
        description
          "The client joined through Open and EAP Authentication";
      }
      enum auth-algo-none {
        value 129;
        description
          "The authentication algorithm is NA";
      }
      enum simultaneous-authentication-of-equals {
        value 130;
        description
          "The client joined through Simultaneous Authentication Of Equals";
      }
    }
    description
      "Enumeration for the authentication algorithms used by the client";
  }

  typedef dot11i-cipher-suite {
    type enumeration {
      enum rsn-cipher-suite-use-group {
        value 0;
        description
          "The Cipher suite used by the client is the same as group cipher";
      }
      enum wep-40-bits {
        value 1;
        description
          "The Cipher suite used by the client is WEP (40 bits)";
      }
      enum tkip-mic {
        value 2;
        description
          "The Cipher Suite used by the client is TKIP";
      }
      enum reserved {
        value 3;
        description
          "The Cipher suite used by the client is Reserved";
      }
      enum ccmp-aes {
        value 4;
        description
          "The Cipher suite used by the client is CCMP";
      }
      enum wep-104-bits {
        value 5;
        description
          "The Cipher suite used by the client is WEP (104 bits)";
      }
      enum bip {
        value 6;
        description
          "The Cipher suite used by the client is BIP";
      }
      enum traffic-not-allowed {
        value 7;
        description
          "Traffic not allowed on cipher suite used by client";
      }
      enum gcmp128 {
        value 8;
        description
          "The Cipher suite used by the client is GCMP128";
      }
      enum gcmp256 {
        value 9;
        description
          "The Cipher suite used by the client is GCMP256";
      }
      enum ccmp256 {
        value 10;
        description
          "The Cipher suite used by the client is CCMP256";
      }
      enum wep-128-bits {
        value 127;
        description
          "The Cipher suite used by the client is WEP (128 bits)";
      }
      enum rsn-cipher-suite-invalid {
        value 255;
        description
          "The Cipher suite used by the client is Invalid";
      }
      enum gmac256 {
        value 12;
        description
          "The Cipher suite used by the client is GMAC-256";
      }
    }
    description
      "Enumeration for the 802.11i encryption protocols that can be employed by the client";
  }

  typedef reason-code {
    type enumeration {
      enum reason-none {
        value 0;
        description
          "The reason for disassocdeauth is None";
      }
      enum reason-unspecified {
        value 1;
        description
          "The reason for disassocdeauth is Unspecified";
      }
      enum reason-prev-auth-not-valid {
        value 2;
        description
          "The reason for disassocdeauth was invalid previous authentication";
      }
      enum reason-deauth-leaving {
        value 3;
        description
          "The reason for disassocdeauth was a deauthentication received";
      }
      enum reason-disassoc-due-to-inactivity {
        value 4;
        description
          "The reason for disassocdeauth was disassociation due to inactivity";
      }
      enum reason-disassoc-ap-busy {
        value 5;
        description
          "The reason for disassocdeauth was disassociation because AP is busy";
      }
      enum reason-class2-frame-from-nonauth-sta {
        value 6;
        description
          "The reason for disassocdeauth was a Class 2 Frame received from Non Authenticated AP";
      }
      enum reason-class2-frame-from-nonassoc-sta {
        value 7;
        description
          "The reason for disassocdeauth was a Class 2 Frame received from Non Associated AP";
      }
      enum reason-disassoc-sta-has-left {
        value 8;
        description
          "The reason for disassocdeauth was the AP left the controller";
      }
      enum reason-sta-req-assoc-without-auth {
        value 9;
        description
          "The reason for disassocdeauth was the AP requested association without authentication";
      }
      enum reason-invalid-ie {
        value 13;
        description
          "The reason for disassocdeauth was invalid Information Element";
      }
      enum reason-micheal-failure {
        value 14;
        description
          "The reason for disassocdeauth was a Micheal failure";
      }
      enum reason-4-way-handshake-timeout {
        value 15;
        description
          "The reason for disassocdeauth was a 4 way Handshake Timeout";
      }
      enum reason-group-key-update-timeout {
        value 16;
        description
          "The reason for disassocdeauth was a Group key update Timeout";
      }
      enum reason-invalid-rsn-ie {
        value 17;
        description
          "The reason for disassocdeauth was invalid RSN Information Element";
      }
      enum reason-group-cipher-invalid {
        value 18;
        description
          "The reason for disassocdeauth was invalid Group cipher";
      }
      enum reason-unicast-cipher-invalid {
        value 19;
        description
          "The reason for disassocdeauth was invalid Unicast Cipher";
      }
      enum reason-akmp-invalid {
        value 20;
        description
          "The reason for disassocdeauth was invalid AKMP";
      }
      enum reason-unsupported-rsn-version {
        value 21;
        description
          "The reason for disassocdeauth was unsupported RSN version";
      }
      enum reason-invalid-rsn-ie-capabilities {
        value 22;
        description
          "The reason for disassocdeauth was invalid RSN information element capabilities";
      }
      enum reason-8021-x-auth-failed {
        value 23;
        description
          "The reason for disassocdeauth was a 802.1x authentication failure";
      }
      enum reason-cipher-suite-rejected {
        value 24;
        description
          "The reason for disassocdeauth was the Cipher suite was rejected";
      }
      enum reason-unspec-qos-related-reason {
        value 32;
        description
          "The reason for disassocdeauth was an unspecified QOS related failure";
      }
      enum reason-insufficient-bandwidth {
        value 33;
        description
          "The reason for disassocdeauth was insufficient bandwidth";
      }
      enum reason-poor-channel-conditions {
        value 34;
        description
          "The reason for disassocdeauth was the channel conditions were poor";
      }
      enum reason-sta-violating-txop {
        value 35;
        description
          "The reason for disassocdeauth was the AP violated TXOP (Transmission Opportunity)";
      }
      enum reason-voice-sta-reanchoring {
        value 36;
        description
          "The reason for disassocdeauth was voice AP reanchoring";
      }
      enum reason-probing-sta-in-loc-calib {
        value 37;
        description
          "The reason for disassocdeauth was a Probing AP in LOC Calibration";
      }
      enum reason-guest-anchor-down {
        value 98;
        description
          "The reason for disassocdeauth was Guest Anchor being down";
      }
      enum reason-missing-reason-code {
        value 99;
        description
          "The reason for disassocdeauth is NA";
      }
      enum reason-client-access-to-quarantine {
        value 100;
        description
          "The reason for disassocdeauth was the client accessed Quarantine";
      }
      enum reason-max-associated-clients-reached {
        value 101;
        description
          "The reason for disassocdeauth was exceeding the limit of maximum associated clients";
      }
      enum reason-max-clients-reached-on-ap {
        value 102;
        description
          "The reason for disassocdeauth was exceeding the limit of maximum clients on the AP";
      }
      enum reason-webauth-reqd-timeout {
        value 103;
        description
          "The reason for disassocdeauth was a Webauth required timeout";
      }
      enum reason-webauth-async-timeout {
        value 104;
        description
          "The reason for disassocdeauth was a Webauth asynchronous timeout";
      }
      enum reason-max-clients-reached-on-ap-radio {
        value 105;
        description
          "The reason for disassocdeauth was exceeding the limit of maximum clients on the AP radio";
      }
      enum reason-max-clients-reached-on-ap-wlan {
        value 106;
        description
          "The reason for disassocdeauth was exceeding the limit of maximum clients on the AP WLAN";
      }
      enum reason-max-clients-reached-on-ap-radio-wlan {
        value 107;
        description
          "The reason for disassocdeauth was exceeding the limit of maximum clients on the AP Radio WLAN";
      }
      enum reason-sta-no-ip {
        value 108;
        description
          "The reason for disassocdeauth was that the AP had no IP";
      }
      enum reason-ccx-qos-unspecified-failure {
        value 200;
        description
          "The reason for disassocdeauth was a CCX QOS unspecified failure";
      }
      enum reason-ccx-qos-policy {
        value 201;
        description
          "The reason for disassocdeauth was CCX QOS policy failure";
      }
      enum reason-ccx-insufficient-bandwidth {
        value 202;
        description
          "The reason for disassocdeauth was CCX insufficient bandwidth";
      }
      enum reason-ccx-invalid-qos-parameter {
        value 203;
        description
          "The reason for disassocdeauth was CCX QOS parameters being invalid";
      }
      enum reason-tunnel-eogre-roam-fail {
        value 204;
        description
          "The reason for disassocdeauth was a Tunnel EOGRE roam failure";
      }
      enum reason-sta-roam-without-auth {
        value 205;
        description
          "The reason for disassocdeauth was the AP roamed without authentication";
      }
      enum reason-authz-fail {
        value 250;
        description
          "The reason for disassocdeauth was the authorization failed";
      }
      enum reason-logout {
        value 251;
        description
          "The reason for disassocdeauth was the user has logged out";
      }
      enum reason-admin-reset {
        value 252;
        description
          "The reason for disassocdeauth was an Admin reset";
      }
      enum reason-anchor-close {
        value 253;
        description
          "The reason for disassocdeauth was an Anchor close";
      }
      enum reason-common-enum-end {
        value 300;
        description
          "The reason for disassocdeauth was a Common Enumeration end";
      }
    }
    description
      "Enumeration for the Reason Codes for disassociation deauthentication as defined by 802.11 standards";
  }

  typedef ip-binding-learn-type {
    type enumeration {
      enum ip-learn-type-unknown {
        value 0;
        description
          "The method used to learn the IP Address is unknown";
      }
      enum ip-learn-type-dhcp {
        value 1;
        description
          "The method used to learn the IP Address is DHCP";
      }
      enum ip-learn-type-arp {
        value 2;
        description
          "The method used to learn the IP Address is ARP";
      }
      enum ip-learn-type-ip-snooping {
        value 3;
        description
          "The method used to learn the IP Address is IP Snooping";
      }
      enum ip-learn-type-roaming {
        value 4;
        description
          "The method used to learn the IP Address is Roaming";
      }
      enum ip-learn-type-ip-theft {
        value 5;
        description
          "The method used to learn the IP Address is IP Theft";
      }
      enum ip-learn-type-static {
        value 6;
        description
          "The method used to learn the IP Address is Static";
      }
      enum ipv6-learn-type-unknown {
        value 7;
        description
          "The method used to learn the IPv6 Address is Unknown";
      }
      enum ipv6-learn-type-ndp {
        value 8;
        description
          "The method used to learn the IPv6 Address is NDP";
      }
      enum ipv6-learn-type-dhcp {
        value 9;
        description
          "The method used to learn the IPv6 Address is DHCP";
      }
      enum ipv6-learn-type-packet {
        value 10;
        description
          "The method used to learn the IPv6 Address is Packet";
      }
      enum ipv6-learn-type-local {
        value 11;
        description
          "The method used to learn the IPv6 Address is Local";
      }
      enum ipv6-learn-type-static {
        value 12;
        description
          "The method used to learn the IPv6 Address is Static";
      }
    }
    description
      "This data type enumerates the various methods used for learning the IP of the client";
  }

  typedef sta-type {
    type enumeration {
      enum sta-unknown {
        value 0;
        description
          "The STA/device type is Unknown";
      }
      enum sta-apple {
        value 1;
        description
          "The STA/device type is Apple";
      }
      enum sta-samsung {
        value 2;
        description
          "The STA/device type is Samsung";
      }
      enum sta-intel {
        value 3;
        description
          "The STA/device type is Intel";
      }
    }
    description
      "This data type enumerates the various Station/Device manufacturers";
  }

  grouping co-delete-reason {
    description
      "Client delete reasons";
    leaf invalid-operation {
      type uint32;
      description
        "Invalid delete reason";
    }
    leaf internal-generic-err {
      type uint32;
      description
        "Default delete reason";
    }
    leaf deauth-or-disassoc-req {
      type uint32;
      description
        "Deauthentication or disassociation request received from client";
    }
    leaf auth-fail {
      type uint32;
      description
        "Authentication or authorization failure";
    }
    leaf webauth-fail {
      type uint32;
      description
        "Web authentication failure";
    }
    leaf ap-delete {
      type uint32;
      description
        "AP initiated client delete";
    }
    leaf bssid-down {
      type uint32;
      description
        "BSSID down";
    }
    leaf capwap-down {
      type uint32;
      description
        "AP down";
    }
    leaf connect-timeout {
      type uint32;
      description
        "Client connection timeout";
    }
    leaf mab-fail {
      type uint32;
      description
        "MAC authentication by-pass failed";
    }
    leaf datapath-fail {
      type uint32;
      description
        "Failure during data path plumbing";
    }
    leaf wlan-change {
      type uint32;
      description
        "WLAN change";
    }
    leaf vlan-change {
      type uint32;
      description
        "VLAN change";
    }
    leaf admin-reset {
      type uint32;
      description
        "Admin reset due to manual deauthentication";
    }
    leaf qos-fail {
      type uint32;
      description
        "QoS failure";
    }
    leaf key-exchange-timeout {
      type uint32;
      description
        "Key exchange process timeout";
    }
    leaf group-key-update {
      type uint32;
      description
        "Group key update timeout";
    }
    leaf max-sa-queries {
      type uint32;
      description
        "Maximum secure association queries reached";
    }
    leaf restart-purge {
      type uint32;
      description
        "Delete due to system restart";
    }
    leaf client-block-list {
      type uint32;
      description
        "Default client block listed";
    }
    leaf inter-instance-roam-succ {
      type uint32;
      description
        "Inter instance roam success";
    }
    leaf intra-instance-roam-fail {
      type uint32;
      description
        "Intra instance roam failure";
    }
    leaf mobility-roam-succ {
      type uint32;
      description
        "Inter controller roam success";
    }
    leaf mobility-roam-fail {
      type uint32;
      description
        "Inter controller roam failure";
    }
    leaf client-session-timeout {
      type uint32;
      description
        "Client session timeout";
    }
    leaf client-idle-timeout {
      type uint32;
      description
        "Client idle timeout";
    }
    leaf user-req {
      type uint32;
      description
        "User requested client delete";
    }
    leaf nas-err {
      type uint32;
      description
        "Network access server identifier error";
    }
    leaf aaa-service-unavailable {
      type uint32;
      description
        "AAA Service unavailable";
    }
    leaf mobility-bssid-down {
      type uint32;
      description
        "Mobility BSSID down";
    }
    leaf mobility-tunnel-down {
      type uint32;
      description
        "Mobility tunnel down";
    }
    leaf dot11v-smart-roam-fail {
      type uint32;
      description
        "802.11v smart roam failed";
    }
    leaf dot11v-timer-timeout {
      type uint32;
      description
        "802.11v disassociation imminent timeout";
    }
    leaf dot11v-assoc-fail {
      type uint32;
      description
        "802.11v association failed";
    }
    leaf ft-auth-response-fail {
      type uint32;
      description
        "Fast transition authentication response failure";
    }
    leaf sae-auth-fail {
      type uint32;
      description
        "Simultaneous authentication of equals failure";
    }
    leaf dot11-unspecified-fail {
      type uint32;
      description
        "802.11 unspecified failure";
    }
    leaf dot11-fail-ignore-req {
      type uint32;
      description
        "802.11 failure due to ignore request";
    }
    leaf dot11-ccx-qos-add-ts-no-bw {
      type uint32;
      description
        "802.11 failure due to addition of CCX QoS traffic stream with no bandwidth";
    }
    leaf dot11-caps-unsupported {
      type uint32;
      description
        "802.11 capabilities not supported";
    }
    leaf dot11-assoc-deny-unspec {
      type uint32;
      description
        "802.11 association denied due to unspecified reason";
    }
    leaf dot11-max-client {
      type uint32;
      description
        "Maximum stations limit reached on AP";
    }
    leaf dot11-denied-rates {
      type uint32;
      description
        "802.11 denied data rates";
    }
    leaf dot11-poor-channel {
      type uint32;
      description
        "Poor channel conditions";
    }
    leaf dot11-invalid-qos-param {
      type uint32;
      description
        "Invalid 802.11 QoS parameter";
    }
    leaf dot11-invalid-ie {
      type uint32;
      description
        "Invalid 802.11 information element";
    }
    leaf dot11-group-cipher-invalid {
      type uint32;
      description
        "802.11 group cipher invalid";
    }
    leaf dot11-ucast-cipher-invalid {
      type uint32;
      description
        "802.11 unicast cipher invalid";
    }
    leaf dot11-akmp-invalid {
      type uint32;
      description
        "802.11 authentication key management protocol invalid";
    }
    leaf dot11-rsn-ver-no-supported {
      type uint32;
      description
        "802.11 unsupported robust secure network version";
    }
    leaf dot11-invalid-rsn-ie {
      type uint32;
      description
        "802.11 invalid robust secure network information element ";
    }
    leaf dot11-cipher-suite-reject {
      type uint32;
      description
        "802.11 cipher suite rejected";
    }
    leaf dot11-deny-ht-capab {
      type uint32;
      description
        "802.11 denied high throughput capabilities";
    }
    leaf dot11-invalid-ft-frame {
      type uint32;
      description
        "Invalid 802.11 fast transition action frame count";
    }
    leaf dot11-invalid-pmkid {
      type uint32;
      description
        "Invalid 802.11 pairwise master key identifier";
    }
    leaf dot11-invalid-mdie {
      type uint32;
      description
        "Invalid 802.11 mobility domain information element";
    }
    leaf dot11-invalid-ftie {
      type uint32;
      description
        "Invalid 802.11 fast transition information element";
    }
    leaf dot11-ccx-qos-policy {
      type uint32;
      description
        "802.11 CCX QoS policy failure";
    }
    leaf dot11-bandwidth-fail {
      type uint32;
      description
        "802.11 CCX insufficient bandwidth failure";
    }
    leaf dot11-ccx-invalidqos-param {
      type uint32;
      description
        "802.11 CCX invalid QoS parameter";
    }
    leaf dot11-ccx-non-opt-choice {
      type uint32;
      description
        "802.11 CCX non optimal association choice";
    }
    leaf wired-iapp-disassoc {
      type uint32;
      description
        "Wired client deleted due to disassociation from AP";
    }
    leaf wired-wgb-change {
      type uint32;
      description
        "Wired client deleted due to WGB change";
    }
    leaf wired-vlan-change {
      type uint32;
      description
        "Wired client deleted due to VLAN change";
    }
    leaf wired-wgb-delete {
      type uint32;
      description
        "Wired client deleted as WGB is removed";
    }
    leaf avc-reanchoring {
      type uint32;
      description
        "Application visibility and control reanchoring";
    }
    leaf wgb-client-direct-assoc {
      type uint32;
      description
        "WGB client direct association";
    }
    leaf ap-upgrade {
      type uint32;
      description
        "Client deleted due to AP upgrade";
    }
    leaf client-dhcp-fail {
      type uint32;
      description
        "Client DHCP failure";
    }
    leaf eap-timeout-fail {
      type uint32;
      description
        "EAP timeout failure from client";
    }
    leaf client-8021x-fail {
      type uint32;
      description
        "802.1x failure from client";
    }
    leaf client-device-idle-timeout {
      type uint32;
      description
        "Client device idle state timeout";
    }
    leaf captive-portal-sec-fail {
      type uint32;
      description
        "Captive portal security failure from client";
    }
    leaf client-decrypt-fail {
      type uint32;
      description
        "Decryption failure from client";
    }
    leaf client-intf-disable {
      type uint32;
      description
        "Client interface disabled";
    }
    leaf client-disassociated {
      type uint32;
      description
        "User triggered disassociation from client";
    }
    leaf client-misc-reason {
      type uint32;
      description
        "Miscellaneous reason from client";
    }
    leaf client-unknown-reason {
      type uint32;
      description
        "Unknown reason from client";
    }
    leaf client-peer-triggered {
      type uint32;
      description
        "Client peer triggered";
    }
    leaf client-beacon-loss {
      type uint32;
      description
        "Beacon loss at client";
    }
    leaf client-eap-id-timeout {
      type uint32;
      description
        "EAP identifier timeout from client";
    }
    leaf client-dot1x-timeout {
      type uint32;
      description
        "802.1x timeout from client";
    }
    leaf recv-eap-key-invalid-frame {
      type uint32;
      description
        "Invalid frame during key management";
    }
    leaf recv-eap-key-install-bit {
      type uint32;
      description
        "Install bit received during key management";
    }
    leaf recv-eap-key-err-bit {
      type uint32;
      description
        "Error bit during key management";
    }
    leaf recv-eap-key-ack-bit {
      type uint32;
      description
        "Acknowledgement bit during key management";
    }
    leaf recv-eap-key-invalid-key {
      type uint32;
      description
        "Invalid key during key management";
    }
    leaf recv-eap-key-secure-bit {
      type uint32;
      description
        "Secure bit during key management";
    }
    leaf recv-eap-key-desc-ver {
      type uint32;
      description
        "Key description version during key management";
    }
    leaf recv-eapkey-wr-replay-cnt {
      type uint32;
      description
        "Wrong replay counter received during key management";
    }
    leaf recv-eap-key-no-mic-bit {
      type uint32;
      description
        "MIC bit not set during key management";
    }
    leaf recv-eap-key-mic-validate {
      type uint32;
      description
        "MIC validation failed during key management";
    }
    leaf recv-eap-key-ptk-compute {
      type uint32;
      description
        "Pairwise transient key computation failure during key management";
    }
    leaf client-credential-fail {
      type uint32;
      description
        "Client credential failure";
    }
    leaf lost-carrier {
      type uint32;
      description
        "Client lost carrier";
    }
    leaf reauth-fail {
      type uint32;
      description
        "Client reauthentication failure";
    }
    leaf port-admin-disable {
      type uint32;
      description
        "Port admin disabled";
    }
    leaf supplicant-restart {
      type uint32;
      description
        "Supplicant restarted";
    }
    leaf ip-down-no-ip {
      type uint32;
      description
        "Client IP is invalid and IP is down";
    }
    leaf anchor-throttled {
      type uint32;
      description
        "Anchor controller is throttled";
    }
    leaf anchor-no-memory {
      type uint32;
      description
        "Anchor controller has no memory";
    }
    leaf anchor-invalid-mbssid {
      type uint32;
      description
        "Client on anchor controller used invalid mobility BSSID";
    }
    leaf anchor-create-req-fail {
      type uint32;
      description
        "Client create request failed on anchor";
    }
    leaf db-populate-fail {
      type uint32;
      description
        "Failure during database populate";
    }
    leaf dangling-cleanup-timer {
      type uint32;
      description
        "Client cleanup after dangling timer expiry";
    }
    leaf exclude-static-config {
      type uint32;
      description
        "Client excluded based on static configuration";
    }
    leaf exclude-assoc-fail {
      type uint32;
      description
        "Client excluded due to association failure";
    }
    leaf exclude-dot11-auth-fail {
      type uint32;
      description
        "Client excluded due to 802.11 authentication failure";
    }
    leaf exclude-dot1x-timeout {
      type uint32;
      description
        "Client excluded due to 802.1x authentication timeout";
    }
    leaf exclude-dot1x-auth-fail {
      type uint32;
      description
        "Client excluded due to 802.1x authentication failure";
    }
    leaf exclude-web-auth-fail {
      type uint32;
      description
        "Client excluded due to web authentication failure";
    }
    leaf exclude-policy-bind-fail {
      type uint32;
      description
        "Client excluded due to policy bind failure";
    }
    leaf exclude-ip-theft {
      type uint32;
      description
        "Client excluded due to IP theft";
    }
    leaf exclude-mac-theft {
      type uint32;
      description
        "Client excluded due to MAC theft";
    }
    leaf exclude-mac-and-ip-theft {
      type uint32;
      description
        "Client excluded due to MAC and IP theft";
    }
    leaf exclude-qos-policy-fail {
      type uint32;
      description
        "Client excluded due to failure in QoS policy";
    }
    leaf exclude-qospol-apsend-fail {
      type uint32;
      description
        "Client excluded due to failure in sending QoS policy to AP";
    }
    leaf exclude-qospol-bind-fail {
      type uint32;
      description
        "Client excluded due to failure in binding QoS policy to AP";
    }
    leaf exclude-qospol-unbind-fail {
      type uint32;
      description
        "Client excluded due to failure in un-bind QoS policy to AP";
    }
    leaf exclude-sta-ip-anchor-fail {
      type uint32;
      description
        "Client excluded due to static IP failure at anchor";
    }
    leaf exclude-vlan-fail {
      type uint32;
      description
        "Client excluded due to VLAN failure";
    }
    leaf exclude-acl-fail {
      type uint32;
      description
        "Client excluded due to access control list failure";
    }
    leaf exclude-punt-acl-fail {
      type uint32;
      description
        "Client excluded due to punt access control list failure";
    }
    leaf exclude-accounting-fail {
      type uint32;
      description
        "Client excluded due to accounting failure";
    }
    leaf exclude-cts-fail {
      type uint32;
      description
        "Client excluded due to Cisco TrustSec failure";
    }
    leaf exclude-fqdn-no-def-fail {
      type uint32;
      description
        "Client excluded due to missing of FQDN access control list definition";
    }
    leaf exclude-fqdn-poauth-fail {
      type uint32;
      description
        "Client excluded due to mismatch in FQDN access control list configuration for post authentication";
    }
    leaf exclude-fqdn-preauth-fail {
      type uint32;
      description
        "Client excluded due to mismatch in FQDN access control list configuration for pre authentication";
    }
    leaf exclude-fqdnzero-gid-fail {
      type uint32;
      description
        "Client excluded due to FQDN zero group identifier fail";
    }
    leaf exclude-misc-fail {
      type uint32;
      description
        "Client excluded due to miscellaneous reason";
    }
    leaf exclude-reauth-fail {
      type uint32;
      description
        "Client excluded due to reauthentication failure";
    }
    leaf exclude-wrong-psk {
      type uint32;
      description
        "Client excluded due to wrong PSK";
    }
    leaf exclude-policy-fail {
      type uint32;
      description
        "Client excluded due to policy failure";
    }
    leaf ap-idle-timeout {
      type uint32;
      description
        "AP initiated delete due to client idle timeout";
    }
    leaf ap-client-acl-mismatch {
      type uint32;
      description
        "AP initiated delete due to access control list mismatch";
    }
    leaf ap-auth-stop {
      type uint32;
      description
        "AP stopped authentication";
    }
    leaf ap-assoc-expired-at-ap {
      type uint32;
      description
        "Association expired at AP";
    }
    leaf fourway-handshake-fail {
      type uint32;
      description
        "Four-way handshake failed at AP";
    }
    leaf ap-dhcp-timeout {
      type uint32;
      description
        "AP initiated delete due to DHCP timeout";
    }
    leaf ap-reassoc-timeout {
      type uint32;
      description
        "AP initiated delete due to reassociation timeout";
    }
    leaf ap-sa-query-timeout {
      type uint32;
      description
        "AP initiated delete due to security association query timeout";
    }
    leaf ap-intra-ap-roam {
      type uint32;
      description
        "Intra access point roam";
    }
    leaf ap-channel-switch-at-ap {
      type uint32;
      description
        "AP initiated delete due to channel switch at access point";
    }
    leaf ap-del-bad-aid {
      type uint32;
      description
        "AP initiated delete due to invalid association identifier";
    }
    leaf ap-del-req {
      type uint32;
      description
        "AP initiated request to delete client";
    }
    leaf ap-del-intf-reset {
      type uint32;
      description
        "AP initiated delete due to interface reset";
    }
    leaf ap-del-all-on-slot {
      type uint32;
      description
        "AP initiated delete for all clients on radio slot";
    }
    leaf ap-del-link-change-reaper {
      type uint32;
      description
        "AP initiated delete as link to client has changed and uplink can be reaper";
    }
    leaf ap-del-slot-disable {
      type uint32;
      description
        "AP initiated client delete as radio slot is disabled";
    }
    leaf ap-del-mic-fail {
      type uint32;
      description
        "Message integrity check failure at access point";
    }
    leaf ap-del-vlan-del {
      type uint32;
      description
        "AP initiated delete due to VLAN delete at access point";
    }
    leaf ap-del-channel-change {
      type uint32;
      description
        "AP initiated delete due to channel change at access point";
    }
    leaf ap-del-stop-reassoc {
      type uint32;
      description
        "AP initiated delete due to reassociation stop";
    }
    leaf ap-del-pak-max-retry {
      type uint32;
      description
        "AP initiated delete due to maximum packet retry";
    }
    leaf ap-del-tx-deauth {
      type uint32;
      description
        "AP initiated delete due to transmission of deauthentication frame";
    }
    leaf ap-sensor-sta-timeout {
      type uint32;
      description
        "AP initiated client delete due to sensor station timeout";
    }
    leaf ap-del-age-timeout {
      type uint32;
      description
        "AP initiated delete due to age timeout";
    }
    leaf ap-del-tx-fail-thold {
      type uint32;
      description
        "AP initiated delete due to transmission failure threshold";
    }
    leaf ap-uplink-recv-timeout {
      type uint32;
      description
        "AP initiated delete due to uplink receive timeout";
    }
    leaf ap-snsrscan-nxtradio {
      type uint32;
      description
        "AP initiated delete due to sensor scan next radio";
    }
    leaf ap-snsrscan-otherbssid {
      type uint32;
      description
        "AP initiated delete due to sensor scan with another BSSID";
    }
    leaf aaa-server-unavailable {
      type uint32;
      description
        "AAA server unavailable";
    }
    leaf aaa-not-ready {
      type uint32;
      description
        "AAA not ready";
    }
    leaf no-dot1x-auth-config {
      type uint32;
      description
        "802.1x authentication configuration not available";
    }
    leaf abort-recv {
      type uint32;
      description
        "Client deleted due to abort received";
    }
    leaf assoc-connect-timeout {
      type uint32;
      description
        "Association connect timeout";
    }
    leaf macauth-connect-timeout {
      type uint32;
      description
        "MAC authentication connect timeout";
    }
    leaf l2auth-connect-timeout {
      type uint32;
      description
        "L2 authentication connect timeout";
    }
    leaf webauth-connect-timeout {
      type uint32;
      description
        "Web authentication connect timeout";
    }
    leaf mobility-connect-timeout {
      type uint32;
      description
        "Mobility connect timeout";
    }
    leaf static-anchor-timeout {
      type uint32;
      description
        "Static IP anchor connection timeout";
    }
    leaf sm-session-connect-timeout {
      type uint32;
      description
        "State machine session connection timeout";
    }
    leaf iplearn-connect-timeout {
      type uint32;
      description
        "Client deleted due to timeout during IP learn";
    }
    leaf datapath-ifid-exists {
      type uint32;
      description
        "Another client exists with same interface identifier";
    }
    leaf radio-down {
      type uint32;
      description
        "Radio down";
    }
    leaf fabric-reject {
      type uint32;
      description
        "Rejected due to fabric configuration";
    }
    leaf guest-lan-invalid-mbssid {
      type uint32;
      description
        "Invalid mobility BSSID in guest LAN";
    }
    leaf guest-lan-no-memory {
      type uint32;
      description
        "No memory on guest LAN controller";
    }
    leaf guest-lan-create-req-fail {
      type uint32;
      description
        "Guest LAN create request fail";
    }
    leaf tunnel-eogre-reset {
      type uint32;
      description
        "Tunnel ethernet over GRE reset";
    }
    leaf tunnel-eogre-join-fail {
      type uint32;
      description
        "Tunnel ethernet over GRE join failure";
    }
    leaf tun-eogre-reconcile {
      type uint32;
      description
        "Tunnel ethernet over GRE reconciliation";
    }
    leaf wired-idle-timeout {
      type uint32;
      description
        "Wired client delete due to idle timeout";
    }
    leaf ip-update-timeout {
      type uint32;
      description
        "IP update timeout";
    }
    leaf remote-mobility-delete {
      type uint32;
      description
        "Remote mobility delete";
    }
    leaf sae-auth-in-assoced-st {
      type uint32;
      description
        "Simultaneous authentication of equals authentication in association state";
    }
    leaf nack-ifid-mismatch {
      type uint32;
      description
        "NACK interface identifier mismatch";
    }
    leaf tunnnel-eogre-invalid-vlan {
      type uint32;
      description
        "Tunnel ethernet over GRE invalid VLAN";
    }
    leaf tunnnel-eogre-empty-domain {
      type uint32;
      description
        "Tunnel ethernet over GRE empty domain";
    }
    leaf tunnel-eogre-inv-domain {
      type uint32;
      description
        "Tunnel ethernet over GRE invalid domain";
    }
    leaf tunnel-eogre-domain-shut {
      type uint32;
      description
        "Tunnel ethernet over GRE domain shut";
    }
    leaf tunnel-eogre-invalid-gway {
      type uint32;
      description
        "Tunnel ethernet over GRE invalid gateway";
    }
    leaf tunnel-eogre-gway-down {
      type uint32;
      description
        "Tunnel ethernet over GRE gateway down";
    }
    leaf tunnel-eogreflex-no-actgw {
      type uint32;
      description
        "Tunnel ethernet over GRE flex no active gateway";
    }
    leaf tunnel-eogre-rule-match {
      type uint32;
      description
        "Tunnel ethernet over GRE rule match";
    }
    leaf tunnel-eogre-aaa-override {
      type uint32;
      description
        "Tunnel ethernet over GRE AAA override";
    }
    leaf tunnel-eogre-mspayload {
      type uint32;
      description
        "Tunnel ethernet over GRE ms-payload";
    }
    leaf tunnel-eogre-handoff-err {
      type uint32;
      description
        "Tunnel ethernet over GRE handoff error";
    }
    leaf invalid-pmk-len {
      type uint32;
      description
        "Invalid pairwise master key length";
    }
    leaf l3-vlan-oride-conn-timeout {
      type uint32;
      description
        "Web authentication VLAN override connection timeout";
    }
    leaf user-trigger-unspecified {
      type uint32;
      description
        "User triggered unspecified";
    }
    leaf usr-trigger-pwrof-wifiof {
      type uint32;
      description
        "User triggered power down turns Wi-Fi off";
    }
    leaf connect-to-other-ssid {
      type uint32;
      description
        "User triggered connection to another SSID";
    }
    leaf usr-trigger-remove-ssid {
      type uint32;
      description
        "User triggered to remove SSID";
    }
    leaf usr-trigger-airplane-mode {
      type uint32;
      description
        "User triggered airplane mode";
    }
    leaf l2connection-unspecify {
      type uint32;
      description
        "L2 connection unspecified";
    }
    leaf l2connection-assoc {
      type uint32;
      description
        "L2 connection association";
    }
    leaf fourway-handshake-unspec {
      type uint32;
      description
        "Unspecified four-way handshake";
    }
    leaf eap-key-m1-fail {
      type uint32;
      description
        "EAP key message-1 failure";
    }
    leaf eap-key-m3-fail {
      type uint32;
      description
        "EAP key message-3 failure";
    }
    leaf eapkey-m3-m4-xchng-timeout {
      type uint32;
      description
        "EAP key Message-3 message-4 key exchange timeout";
    }
    leaf dhcp-fail-unspecified {
      type uint32;
      description
        "Client deleted due to unspecified DHCP failure";
    }
    leaf dhcp-fail-timeout {
      type uint32;
      description
        "Client deleted due to DHCP timeout fail";
    }
    leaf dhcp-fail-timeout-roam {
      type uint32;
      description
        "Client deleted due to DHCP timeout failure after roaming";
    }
    leaf dhcp-fail-lease-expired {
      type uint32;
      description
        "Client deleted due to DHCP lease expired failure";
    }
    leaf dhcp-fail-nak-in-renew {
      type uint32;
      description
        "Client deleted due to DHCP negative acknowledgment during renew";
    }
    leaf dhcpfail-ren-lease-ip {
      type uint32;
      description
        "Client deleted due to DHCP renew lease wrong IP failure";
    }
    leaf dhcp-fail-int-err {
      type uint32;
      description
        "Client deleted due to DHCP internal error";
    }
    leaf eap-fail-unspecified {
      type uint32;
      description
        "EAP unspecified failure";
    }
    leaf eap-fail-code-fail {
      type uint32;
      description
        "EAP code failure";
    }
    leaf eap-fail-infonot-enter {
      type uint32;
      description
        "EAP failed as information not entered";
    }
    leaf eap-fail-mschap-err {
      type uint32;
      description
        "EAP fail due MS CHAP error";
    }
    leaf eap-fail-sim-auth-fail {
      type uint32;
      description
        "EAP-SIM authentication failure";
    }
    leaf eap-fail-timeout {
      type uint32;
      description
        "EAP failure due to timeout";
    }
    leaf eap-fail-tls-cert-err {
      type uint32;
      description
        "EAP failure due to TLS certificate error";
    }
    leaf no-internet-unspecified {
      type uint32;
      description
        "Client deleted due to no internet, unspecified issue";
    }
    leaf no-internet-dns {
      type uint32;
      description
        "Client deleted due to no internet, DNS issue";
    }
    leaf no-internet-arp {
      type uint32;
      description
        "Client deleted due to ARP error";
    }
    leaf exclude-pol-template-fail {
      type uint32;
      description
        "Exclusion policy template fail";
    }
    leaf ap-del-auth-expired {
      type uint32;
      description
        "AP initiated delete due to authentication expiry";
    }
    leaf ap-del-disassoc {
      type uint32;
      description
        "AP initiated delete due to disassociation";
    }
    leaf ap-del-tx-disassoc {
      type uint32;
      description
        "AP initiated delete due to transmission disassociation";
    }
    leaf fastroam-mobility-fail {
      type uint32;
      description
        "Fast roam mobility failure";
    }
    leaf policy-profile-deny {
      type uint32;
      description
        "Roam across policy profile deny";
    }
    leaf dot11-aid-alloc-req {
      type uint32;
      description
        "802.11 association identifier allocation conflict request";
    }
    leaf zone-change {
      type uint32;
      description
        "Client deleted due to IP zone change";
    }
    leaf wlan-id-attr-mismatch {
      type uint32;
      description
        "WLAN-ID mismatch in access accept failures";
    }
    leaf epsk-aaa-unknown-err {
      type uint32;
      description
        "Easy PSK AAA unknown error";
    }
    leaf epsk-unspec-err {
      type uint32;
      description
        "Easy PSK unspecified error";
    }
    leaf epsk-psk-mismatch {
      type uint32;
      description
        "PSK mismatch error with easy PSK";
    }
    leaf easy-psk-radius-busy {
      type uint32;
      description
        "Easy PSK radius busy error";
    }
    leaf easy-psk-limit-reached {
      type uint32;
      description
        "Easy PSK limit reached error";
    }
    leaf easy-psk-bad-8021x-frame {
      type uint32;
      description
        "Easy PSK bad 802.1X frame error";
    }
    leaf epsk-missing-param {
      type uint32;
      description
        "Easy PSK missing parameter error";
    }
    leaf exclude-supp-name-fail {
      type uint32;
      description
        "Client exclusion due to supplicant name failure";
    }
    leaf exclude-user-name-fail {
      type uint32;
      description
        "Client exclusion due to user name failure";
    }
    leaf exclude-service-setid-fail {
      type uint32;
      description
        "Client exclusion due to SSID failure";
    }
    leaf exclude-anch-vlanid-fail {
      type uint32;
      description
        "Client exclusion due to anchor VLAN ID failure";
    }
    leaf exclude-psk-fail {
      type uint32;
      description
        "Client exclusion due to PSK failure";
    }
    leaf exclude-psk-mode-fail {
      type uint32;
      description
        "Client exclusion due to PSK mode failure";
    }
    leaf exclude-int-interval-fail {
      type uint32;
      description
        "Client exclusion due to interim interval failure";
    }
    leaf random-mac {
      type uint32;
      description
        "Access denied due to locally administered MAC address";
    }
    leaf ap-iplearn-timeout {
      type uint32;
      description
        "AP initiated client delete due to AP IP learn timeout";
    }
    leaf ap-flexgroup-change {
      type uint32;
      description
        "AP initiated client delete due to flex group change";
    }
    leaf ap-eapol-logoff {
      type uint32;
      description
        "AP initiated client delete due to EAPOL log off";
    }
    leaf ap-eap-req-timeout {
      type uint32;
      description
        "AP initiated client delete due to EAP request timeout";
    }
    leaf ap-fourway-handshake-fail {
      type uint32;
      description
        "AP initiated delete due four way handshake failure";
    }
    leaf ap-mic-validation {
      type uint32;
      description
        "AP initiated delete due message integrity check failure";
    }
    leaf ap-wrong-replay-counter {
      type uint32;
      description
        "AP initiated delete due wrong replay counter";
    }
    leaf ap-tunnel-down {
      type uint32;
      description
        "AP initiated delete due to AP tunnel being down";
    }
    leaf inter-ap-roam {
      type uint32;
      description
        "AP initiated delete due to inter AP roam failure";
    }
    leaf ap-unknown-client {
      type uint32;
      description
        "AP initiated delete due to unknown client";
    }
    leaf ap-reauth-timeout {
      type uint32;
      description
        "AP initiated delete due to reauthentication timeout";
    }
    leaf ap-cont-idle-timeout {
      type uint32;
      description
        "AP initiated delete due to continuous idle timeout";
    }
    leaf ap-rldp-cleanup {
      type uint32;
      description
        "AP initiated delete due to RLDP cleanup";
    }
    leaf ap-intra-switch-roam {
      type uint32;
      description
        "AP initiated delete due to intra-switch roam";
    }
    leaf ap-pem-cleanup {
      type uint32;
      description
        "AP initiated delete due to PEM cleanup";
    }
    leaf ap-rlan-central-switch {
      type uint32;
      description
        "AP initiated delete due to RLAN central switch";
    }
    leaf ap-rlan-dp-add-fail {
      type uint32;
      description
        "AP initiated delete due to RLAN data path add failure";
    }
    leaf ap-rlan-delete {
      type uint32;
      description
        "AP initiated delete due to RLAN Delete";
    }
    leaf ap-rlan-inactive-timeout {
      type uint32;
      description
        "AP initiated delete due to RLAN inactive timeout";
    }
    leaf ap-rlan-mab-fail {
      type uint32;
      description
        "AP initiated delete due to RLAN MAB failure";
    }
    leaf ap-no-memory {
      type uint32;
      description
        "AP initiated client delete as the memory is exhausted on AP side";
    }
    leaf ap-bssid-mismatch {
      type uint32;
      description
        "AP initiated delete as client state machine has BSSID mismatch";
    }
    leaf ap-delete-no-acl {
      type uint32;
      description
        "AP initiated delete as client state machine has no ACL found";
    }
    leaf ap-del-no-parent-wgb {
      type uint32;
      description
        "AP initiated delete as client state machine has no parent WGB";
    }
    leaf ap-key-plumb-fail {
      type uint32;
      description
        "AP initiated delete as client state machine has key plumb failure";
    }
    leaf ap-mesh-keyplumb-fail {
      type uint32;
      description
        "AP initiated delete as client state machine has mesh key plumb failure";
    }
    leaf ap-datapath-add-fail {
      type uint32;
      description
        "AP initiated delete as client state machine has adding data path failure";
    }
    leaf ap-auth-resp-reject {
      type uint32;
      description
        "AP initiated delete as client state machine authentication response got rejected";
    }
    leaf ap-auth-resp-send-fail {
      type uint32;
      description
        "AP initiated delete due to client state machine authentication response send failure";
    }
    leaf ap-assoc-resp-send-fail {
      type uint32;
      description
        "AP initiated delete due to client state machine association response send failure";
    }
    leaf ap-assoc-resp-fail-stat {
      type uint32;
      description
        "AP initiated delete due to client state machine association response failure with status";
    }
    leaf ap-webauth-timer-exp {
      type uint32;
      description
        "AP initiated delete due to client state machine webauth timer expired";
    }
    leaf ap-dot1x-timer-exp {
      type uint32;
      description
        "AP initiated delete due to client state machine has 802.1x timer expired";
    }
    leaf ap-deauth-disassoc-fail {
      type uint32;
      description
        "AP initiated delete due to client state machine has deauthentication and disassociation send failure";
    }
    leaf ap-dvr-evt-class3-recv {
      type uint32;
      description
        "Driver initiated delete due to class three event received on AP";
    }
    leaf ap-dvr-evt-psp-unauth {
      type uint32;
      description
        "Driver initiated delete due to power sleep event when not authenticated on AP";
    }
    leaf ap-dvr-evt-ioctl-err {
      type uint32;
      description
        "Driver initiated delete due to input output control event error at AP";
    }
    leaf ap-flex-ft-fail {
      type uint32;
      description
        "AP initiated delete due to flex fast transition failure";
    }
    leaf ap-dvr-add-fail {
      type uint32;
      description
        "Driver initiated delete due to client state machine add failure at AP";
    }
    leaf ap-dvr-client-not-found {
      type uint32;
      description
        "Driver initiated delete as client not found on AP";
    }
    leaf ap-dvr-mgmtpkt-alloc-fail {
      type uint32;
      description
        "Driver initiated delete due to management packet allocation failure at AP";
    }
    leaf ap-dvr-invalid-cipher {
      type uint32;
      description
        "Driver initiated delete due to invalid cipher on AP";
    }
    leaf ap-dvr-invalid-aid {
      type uint32;
      description
        "Driver initiated delete due to invalid association identifier on AP";
    }
    leaf ap-dvr-invalid-key {
      type uint32;
      description
        "Driver initiated delete due to invalid key at AP";
    }
    leaf ap-dvr-fw-key-set-fail {
      type uint32;
      description
        "Driver initiated delete due to firmware set key failure at AP";
    }
    leaf ap-dvr-invalid-htvht-rates {
      type uint32;
      description
        "Driver initiated delete due to invalid high throughput and very high throughput rates on AP";
    }
    leaf ap-dvr-invalid-leg-rates {
      type uint32;
      description
        "Driver initiated delete due to invalid legacy rates on AP";
    }
    leaf ap-dvr-no-olap-leg-rates {
      type uint32;
      description
        "Driver initiated delete due to no overlapping legacy rates at AP";
    }
    leaf ap-dvr-max-vht-streams {
      type uint32;
      description
        "Driver initiated delete due to maximum very high throughput streams at AP";
    }
    leaf ap-driver-aid-inuse {
      type uint32;
      description
        "Driver initiated delete due to association identifier in use at AP";
    }
    leaf ap-dvr-assoc-too-many {
      type uint32;
      description
        "Driver initiated delete due to too many association requests at AP";
    }
    leaf ap-dvr-cipher-attach-fail {
      type uint32;
      description
        "Driver initiated delete due to cipher attach failure at AP";
    }
    leaf ap-dvr-algo-mismatch {
      type uint32;
      description
        "Driver initiated delete due to algorithm mismatch on AP";
    }
    leaf ap-dvr-invalid-keylen {
      type uint32;
      description
        "Driver initiated delete due to invalid key length at AP";
    }
    leaf ap-dvr-invalid-key-index {
      type uint32;
      description
        "Driver initiated delete due to invalid key index at AP";
    }
    leaf ap-dvr-assoc-scb-noauth {
      type uint32;
      description
        "Driver initiated delete due to rejected association due to authentication failure at AP";
    }
    leaf ap-dvr-stadb-init-fail {
      type uint32;
      description
        "Driver initiated delete due to client addition to internal records failure at AP";
    }
    leaf ap-dvr-add-entry-fail {
      type uint32;
      description
        "Driver initiated delete due to client association entry failure at AP";
    }
    leaf ap-dvr-add-ent-fw-fail {
      type uint32;
      description
        "Driver initiated delete due to addition of client entry in firmware failure at AP";
    }
    leaf ap-reason-internal-fail {
      type uint32;
      description
        "Driver related internal failure at AP";
    }
    leaf link-localbridge-vlan-fail {
      type uint32;
      description
        "Client exclusion due to link-local VLAN failure";
    }
    leaf max-sta-on-ap {
      type uint32;
      description
        "Maximum number of clients reached per AP";
    }
    leaf max-sta-on-vap {
      type uint32;
      description
        "Maximum number of clients reached per AP per WLAN";
    }
    leaf max-sta-on-bssid {
      type uint32;
      description
        "Maximum number of clients reached per AP radio per WLAN";
    }
    leaf max-sta-on-radio {
      type uint32;
      description
        "Maximum number of clients reached per AP radio";
    }
    leaf ap-max-sta-on-ap {
      type uint32;
      description
        "AP initiated delete due to maximum number of clients per AP limit reached";
    }
    leaf ap-max-sta-on-bssid {
      type uint32;
      description
        "AP initiated delete due to maximum number of clients per AP radio per WLAN limit reached";
    }
    leaf ap-max-sta-on-radio {
      type uint32;
      description
        "AP initiated delete due to maximum number of clients per AP radio limit reached";
    }
    leaf sta-triggered-pmk-timeout {
      type uint32;
      description
        "STA triggered delete due to the PMK timeout occurred on the client device";
    }
  }
}
