module Cisco-IOS-XE-eta {
  yang-version 1.1;
  namespace "http://cisco.com/ns/yang/Cisco-IOS-XE-eta";
  prefix ios-eta;

  import cisco-semver {
    prefix cisco-semver;
  }
  import ietf-inet-types {
    prefix inet;
  }
  import Cisco-IOS-XE-native {
    prefix ios;
  }
  import Cisco-IOS-XE-types {
    prefix ios-types;
  }
  import Cisco-IOS-XE-features {
    prefix ios-features;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Encrypted Traffic Analytics Yang model.
     Copyright (c) 2017-2019 by Cisco Systems, Inc.
     All rights reserved.";

  revision 2021-03-01 {
    description
      "- Replaced deprecated diff-dependency annotations";
    cisco-semver:module-version "2.0.1";
  }
  revision 2019-11-01 {
    description
      "Added if-feature statement";
    cisco-semver:module-version "2.0.0";
  }
  revision 2019-07-01 {
    description
      "- Establish semantic version baseline
       - Added IPv6 flow-export destination support
       - Moved whitelist must constraint from container to leaf
       - Add must constraints for inactive-timeout and whitelist on at least one ip flow-export entry";
    cisco-semver:module-version "1.0.0";
  }
  revision 2019-01-22 {
    description
      "Added leaf for App-hosting Gigabit Ethernet interface";
  }
  revision 2018-11-28 {
    description
      "Add source-interface and ipfix option support to ip flow-export";
  }
  revision 2018-09-18 {
    description
      "Add diff-dependency from inactive-timeout to ip flow-export";
  }
  revision 2018-06-28 {
    description
      "added must constraints for deleting vrf";
  }
  revision 2018-05-14 {
    description
      "Limit string lengths for threat-defense features";
  }
  revision 2018-02-22 {
    description
      "Add threat-defense support for Ethernet interfaces";
  }
  revision 2017-11-27 {
    description
      "Added Change 25GE name";
  }
  revision 2017-11-14 {
    description
      "Add 100GE interface support";
  }
  revision 2017-10-16 {
    description
      "Initial revision";
  }

  grouping eta-ip-flow-export-dest-grouping {
    leaf source-interface {
      description
        "Optional source-interface";
      type string;
    }
    leaf ipfix {
      description
        "Export in ipfix format";
      type empty;
    }
  }

  grouping config-eta-grouping {
    container et-analytics {
      description
        "Encrypted Traffic Analytics";
      must '(count(/ios:native/ios-eta:et-analytics/ios-eta:ip/ios-eta:flow-export/ios-eta:destination) + count(/ios:native/ios-eta:et-analytics/ios-eta:ip/ios-eta:flow-export/ios-eta:destination-vrf/ios-eta:destination) + count(/ios:native/ios-eta:et-analytics/ios-eta:ipv6/ios-eta:flow-export/ios-eta:destination) + count(/ios:native/ios-eta:et-analytics/ios-eta:ipv6/ios-eta:flow-export/ios-eta:destination-vrf/ios-eta:destination)) <= 4' {
        error-message "ET-Analytics can only config upto 4 different destination combinations";
      }
      presence "true";
      container ip {
        description
          "Specify netflow record export destination ip address and port";
        container flow-export {
          description
            "netflow record export";
          list destination {
            description
              "netflow record export destination";
            key "address port";
            leaf address {
              description
                "IP address";
              type inet:ipv4-address;
            }
            leaf port {
              description
                "Valid Port Number";
              type uint16 {
                range "1..65535";
              }
            }
            uses eta-ip-flow-export-dest-grouping;
          }
          container destination-vrf {
            list destination {
              description
                "netflow record export destination";
              key "address port vrf";
              leaf address {
                description
                  "IP address";
                type inet:ipv4-address;
              }
              leaf port {
                description
                  "Valid Port Number";
                type uint16 {
                  range "1..65535";
                }
              }
              leaf vrf {
                description
                  "Optional VRF label";
                must '/ios:native/ios:vrf/ios:definition[ios:name=current()] or /ios:native/ios:ip/ios:vrf[ios:name=current()]' {
                  error-message "VRF must be created 1st, deleted last";
                }
                type string {
                  length "1..32";
                }
              }
              uses eta-ip-flow-export-dest-grouping;
            }
          }
        }
      }
      container ipv6 {
        description
          "Specify netflow record export destination ipv6 address and port";
        container flow-export {
          description
            "netflow record export";
          list destination {
            description
              "netflow record export destination";
            key "address port";
            leaf address {
              description
                "IPV6 address";
              type inet:ipv6-address;
            }
            leaf port {
              description
                "Valid Port Number";
              type uint16 {
                range "1..65535";
              }
            }
            uses eta-ip-flow-export-dest-grouping;
          }
          container destination-vrf {
            list destination {
              description
                "netflow record export destination";
              key "address port vrf";
              leaf address {
                description
                  "IPV6 address";
                type inet:ipv6-address;
              }
              leaf port {
                description
                  "Valid Port Number";
                type uint16 {
                  range "1..65535";
                }
              }
              leaf vrf {
                description
                  "Optional VRF label";
                must '/ios:native/ios:vrf/ios:definition[ios:name=current()] or /ios:native/ios:ip/ios:vrf[ios:name=current()]' {
                  error-message "VRF must be created 1st, deleted last";
                }
                type string {
                  length "1..32";
                }
              }
              uses eta-ip-flow-export-dest-grouping;
            }
          }
        }
      }
      leaf inactive-timeout {
        description
          "Specify Inactive flow timeout value";
        must '(count(/ios:native/ios-eta:et-analytics/ios-eta:ip/ios-eta:flow-export/ios-eta:destination) + count(/ios:native/ios-eta:et-analytics/ios-eta:ip/ios-eta:flow-export/ios-eta:destination-vrf/ios-eta:destination) + count(/ios:native/ios-eta:et-analytics/ios-eta:ipv6/ios-eta:flow-export/ios-eta:destination) + count(/ios:native/ios-eta:et-analytics/ios-eta:ipv6/ios-eta:flow-export/ios-eta:destination-vrf/ios-eta:destination)) != 0' {
          error-message "Must create at least one 'ip/ipv6 flow-export' entry first";
        }
        type uint32 {
          range "1..604800";
        }
      }
      container whitelist {
        description
          "Whitelist traffic";
        if-feature "ios-features:routing-platform";
        leaf acl {
          description
            "Access list";
          must '(count(/ios:native/ios-eta:et-analytics/ios-eta:ip/ios-eta:flow-export/ios-eta:destination) + count(/ios:native/ios-eta:et-analytics/ios-eta:ip/ios-eta:flow-export/ios-eta:destination-vrf/ios-eta:destination) + count(/ios:native/ios-eta:et-analytics/ios-eta:ipv6/ios-eta:flow-export/ios-eta:destination) + count(/ios:native/ios-eta:et-analytics/ios-eta:ipv6/ios-eta:flow-export/ios-eta:destination-vrf/ios-eta:destination)) != 0' {
            error-message "Must create at least one 'ip/ipv6 flow-export' entry first";
          }
          type union {
            type ios-types:access-list-type;
            type string {
              length "1..64";
            }
          }
        }
      }
    }
  }

  grouping config-interface-eta-grouping {
    container et-analytics {
      description
        "et-analytics support on this interface";
      leaf enable {
        description
          "Enable et-analytics on this interface";
        must '(count(/ios:native/ios-eta:et-analytics/ios-eta:ip/ios-eta:flow-export/ios-eta:destination) + count(/ios:native/ios-eta:et-analytics/ios-eta:ip/ios-eta:flow-export/ios-eta:destination-vrf/ios-eta:destination) + count(/ios:native/ios-eta:et-analytics/ios-eta:ipv6/ios-eta:flow-export/ios-eta:destination) + count(/ios:native/ios-eta:et-analytics/ios-eta:ipv6/ios-eta:flow-export/ios-eta:destination-vrf/ios-eta:destination)) != 0' {
          error-message "Must create at least one 'ip/ipv6 flow-export' entry first";
        }
        type empty;
      }
    }
  }

  augment "/ios:native" {
    uses config-eta-grouping;
  }

  augment "/ios:native/ios:interface/ios:Ethernet" {
    uses config-interface-eta-grouping;
  }

  augment "/ios:native/ios:interface/ios:FastEthernet" {
    uses config-interface-eta-grouping;
  }

  augment "/ios:native/ios:interface/ios:GigabitEthernet" {
    uses config-interface-eta-grouping;
  }

  augment "/ios:native/ios:interface/ios:TenGigabitEthernet" {
    uses config-interface-eta-grouping;
  }

  augment "/ios:native/ios:interface/ios:FiveGigabitEthernet" {
    uses config-interface-eta-grouping;
  }

  augment "/ios:native/ios:interface/ios:AppGigabitEthernet" {
    uses config-interface-eta-grouping;
  }

  augment "/ios:native/ios:interface/ios:TwentyFiveGigE" {
    uses config-interface-eta-grouping;
  }

  augment "/ios:native/ios:interface/ios:FortyGigabitEthernet" {
    uses config-interface-eta-grouping;
  }

  augment "/ios:native/ios:interface/ios:HundredGigE" {
    uses config-interface-eta-grouping;
  }

  augment "/ios:native/ios:interface/ios:TwoGigabitEthernet" {
    uses config-interface-eta-grouping;
  }

  augment "/ios:native/ios:interface/ios:LISP" {
    uses config-interface-eta-grouping;
  }

  augment "/ios:native/ios:interface/ios:Loopback" {
    uses config-interface-eta-grouping;
  }

  augment "/ios:native/ios:interface/ios:Tunnel" {
    uses config-interface-eta-grouping;
  }

  augment "/ios:native/ios:interface/ios:Virtual-Template" {
    uses config-interface-eta-grouping;
  }

  augment "/ios:native/ios:interface/ios:Vlan" {
    uses config-interface-eta-grouping;
  }

  augment "/ios:native/ios:interface/ios:vasileft" {
    uses config-interface-eta-grouping;
  }

  augment "/ios:native/ios:interface/ios:vasiright" {
    uses config-interface-eta-grouping;
  }
}
