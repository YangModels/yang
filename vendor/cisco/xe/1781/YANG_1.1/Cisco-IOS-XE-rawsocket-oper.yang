module Cisco-IOS-XE-rawsocket-oper {
  yang-version 1.1;
  namespace "http://cisco.com/ns/yang/Cisco-IOS-XE-rawsocket-oper";
  prefix raw-socket-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Rawsocket operational data.
     Copyright (c) 2019 by Cisco Systems, Inc.
     All rights reserved.";

  revision 2020-03-01 {
    description
      "Initial revision";
    reference
      "1.0.0";
    cisco-semver:module-version "1.0.0";
  }

  typedef rs-mode {
    type enumeration {
      enum rs-mode-server {
        value 0;
        description
          "Server mode";
      }
      enum rs-mode-client {
        value 1;
        description
          "Client mode";
      }
    }
    description
      "Mode of operation for the connection";
  }

  typedef rs-state {
    type enumeration {
      enum rs-state-down {
        value 0;
        description
          "State DOWN";
      }
      enum rs-state-up {
        value 1;
        description
          "State UP";
      }
    }
    description
      "State of the connection";
  }

  grouping connection-stats {
    description
      "Connection statistics for a line";
    leaf async-line {
      type string;
      description
        "Name of the async line";
    }
    leaf tty {
      type uint32;
      description
        "TTY ID";
    }
    leaf vrf {
      type string;
      description
        "VRF name";
    }
    leaf num-sessions {
      type uint32;
      description
        "Number of active sessions";
    }
    leaf tcp-in-bytes {
      type uint64;
      description
        "Total input bytes";
    }
    leaf tcp-out-bytes {
      type uint64;
      description
        "Total output bytes";
    }
    leaf tcp-to-tty-frames {
      type uint64;
      description
        "Total TCP frames sent to TTY";
    }
    leaf tty-to-tcp-frames {
      type uint64;
      description
        "Total TCP frames received from TTY";
    }
  }

  grouping rs-session-info-key {
    description
      "Session information list key";
    leaf async-line {
      type string;
      description
        "Name of the async line";
    }
    leaf destination-ip {
      type inet:ip-address;
      description
        "Destination IP for the connection";
    }
    leaf destination-port {
      type uint16;
      description
        "Destination port for the connection";
    }
  }

  grouping rs-session-info-params {
    description
      "Session information parameters";
    leaf tty {
      type uint32;
      description
        "TTY ID";
    }
    leaf vrf {
      type string;
      description
        "VRF name";
    }
    leaf idle-timeout {
      type uint32;
      description
        "Idle timeout for the connection (in minutes)";
    }
    leaf mode {
      type raw-socket-ios-xe-oper:rs-mode;
      description
        "Mode of operation";
    }
    leaf local-ip {
      type inet:ip-address;
      description
        "Local IP for the connection";
    }
    leaf local-port {
      type uint16;
      description
        "Local port for the connection";
    }
    leaf socket {
      type uint32;
      description
        "Data socket associated with the connection";
    }
    leaf start-time {
      type yang:date-and-time;
      description
        "Start Time";
    }
    leaf last-active-time {
      type yang:date-and-time;
      description
        "Last Active Time";
    }
  }

  grouping rs-client-state-key {
    description
      "Client state key";
    leaf async-line {
      type string;
      description
        "Name of the async line";
    }
    leaf destination-ip {
      type inet:ip-address;
      description
        "Destination IP for the connection";
    }
    leaf destination-port {
      type uint16;
      description
        "Destination port for the connection";
    }
  }

  grouping rs-client-state-params {
    description
      "Client state parameters";
    leaf tty {
      type uint32;
      description
        "TTY ID";
    }
    leaf local-ip {
      type inet:ip-address;
      description
        "Local IP for the connection";
    }
    leaf local-port {
      type uint16;
      description
        "Local port for the connection";
    }
    leaf state {
      type raw-socket-ios-xe-oper:rs-state;
      description
        "State the connection";
    }
  }

  grouping tcp {
    description
      "Rawsocket TCP Operational Data";
    list rs-tcp-stats {
      key "async-line";
      description
        "Rawsocket TCP Statistics";
      uses raw-socket-ios-xe-oper:connection-stats;
    }
    list rs-tcp-sessions {
      key "async-line destination-ip destination-port";
      description
        "Rawsocket TCP Sessions";
      uses raw-socket-ios-xe-oper:rs-session-info-key;
      uses raw-socket-ios-xe-oper:rs-session-info-params;
    }
    list rs-tcp-clients-state {
      key "async-line destination-ip destination-port";
      description
        "Rawsocket TCP Clients State";
      uses raw-socket-ios-xe-oper:rs-client-state-key;
      uses raw-socket-ios-xe-oper:rs-client-state-params;
    }
  }

  grouping udp {
    description
      "Rawsocket UDP Operational Data";
    list rs-udp-stats {
      key "async-line";
      description
        "Rawsocket UDP Statistics";
      uses raw-socket-ios-xe-oper:connection-stats;
    }
    list rs-udp-sessions {
      key "async-line destination-ip destination-port";
      description
        "Rawsocket UDP Sessions";
      uses raw-socket-ios-xe-oper:rs-session-info-key;
      uses raw-socket-ios-xe-oper:rs-session-info-params;
    }
    list rs-udp-clients-state {
      key "async-line destination-ip destination-port";
      description
        "Rawsocket UDP Clients State";
      uses raw-socket-ios-xe-oper:rs-client-state-key;
      uses raw-socket-ios-xe-oper:rs-client-state-params;
    }
  }

  container rawsocket-oper-data {
    config false;
    description
      "Operational state of Rawsocket";
    container rs-udp {
      presence "rs-udp";
      description
        "Rawsocket UDP Operational Data";
      uses raw-socket-ios-xe-oper:udp;
    }
    container rs-tcp {
      presence "rs-tcp";
      description
        "Rawsocket TCP Operational Data";
      uses raw-socket-ios-xe-oper:tcp;
    }
  }
}
