module Cisco-IOS-XE-trace-events {
  yang-version 1.1;
  namespace "http://cisco.com/ns/yang/Cisco-IOS-XE-trace-events";
  prefix trace-ios-xe-events;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for trace action notification for trace decoder events.
     Copyright (c) 2021 by Cisco Systems, Inc.
     All rights reserved.";

  revision 2021-07-01 {
    description
      "Initial revision";
    reference
      "1.0.0";
    cisco-semver:module-version "1.0.0";
  }

  grouping trace-event-fields {
    description
      "Trace action progress events";
    leaf unique-id {
      type uint32;
      description
        "The Unique ID (Identifier) is a number and represents the
         decoder instance. Its is used to uniquely identify the
         current trace action invoked via RPC and it is replayed
         back in the progress notifications from decoder, to
         correlate them back to the specific trace action operation.";
    }
    leaf percentage {
      type uint8;
      units "percent";
      description
        "Percent of completion for trace action.
         If the value is 0, the field is not applicable";
    }
  }

  notification trace-status {
    description
      "Trace event status notification";
    uses trace-ios-xe-events:trace-event-fields;
  }
}
