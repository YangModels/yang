module Cisco-IOS-XE-nat-events {
  yang-version 1.1;
  namespace "http://cisco.com/ns/yang/Cisco-IOS-XE-nat-events";
  prefix nat-ios-xe-events;

  import Cisco-IOS-XE-ios-common-oper {
    prefix ios-common-ios-xe-oper;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for NAT event notification.
     Copyright (c) 2021 by Cisco Systems, Inc.
     All rights reserved.";

  revision 2022-03-01 {
    description
      "Initial revision";
    reference
      "1.0.0";
    cisco-semver:module-version "1.0.0";
  }

  typedef ip-nat-route-type {
    type enumeration {
      enum route-type-unknown {
        value 0;
        description
          "Unknown NAT route";
      }
      enum route-type-inside {
        value 1;
        description
          "Inside NAT route";
      }
      enum route-type-outside {
        value 2;
        description
          "Outside NAT route";
      }
      enum route-type-dia {
        value 3;
        description
          "DIA NAT route";
      }
    }
    description
      "NAT route type";
  }

  typedef ip-nat-route-update {
    type enumeration {
      enum route-update-added {
        value 0;
        description
          "NAT route added";
      }
      enum route-update-removed {
        value 1;
        description
          "NAT route removed";
      }
    }
    description
      "NAT route update";
  }

  grouping ip-nat-route-change {
    description
      "IP NAT route change";
    leaf severity-level {
      type ios-common-ios-xe-oper:notification-severity;
      description
        "Event severity";
    }
    leaf host-name {
      type string;
      description
        "Host name";
    }
    leaf system-ip {
      type inet:ip-address;
      description
        "System IP address";
    }
    leaf vrf-name {
      type string;
      description
        "VRF name";
    }
    leaf object-tracker {
      type uint16;
      description
        "Object tracker number";
    }
    leaf address {
      type inet:ip-address;
      description
        "NAT IP address";
    }
    leaf mask {
      type inet:ip-address;
      description
        "NAT IP address mask";
    }
    leaf route-type {
      type nat-ios-xe-events:ip-nat-route-type;
      description
        "NAT route type";
    }
    leaf update {
      type nat-ios-xe-events:ip-nat-route-update;
      description
        "NAT route update";
    }
  }

  notification nat-route-change {
    description
      "NAT route change notification";
    uses nat-ios-xe-events:ip-nat-route-change;
  }
}
