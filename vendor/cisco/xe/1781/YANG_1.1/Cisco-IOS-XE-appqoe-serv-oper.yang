module Cisco-IOS-XE-appqoe-serv-oper {
  yang-version 1.1;
  namespace "http://cisco.com/ns/yang/Cisco-IOS-XE-appqoe-serv-oper";
  prefix appqoe-xe-serv-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Application Quality of Experience (APPQOE) serviceability
     operational data. This includes overall and individual
     services status information, registered statistics for monitoring,
     and flows getting closed due to errors in different services.
     Copyright (c) 2020-2021 by Cisco Systems, Inc.
     All rights reserved.";

  revision 2022-03-01 {
    description
      " - Added AppQoE active, expired and summary flow operational data.";
    reference
      "1.1.0";
    cisco-semver:module-version "1.1.0";
  }
  revision 2021-07-01 {
    description
      "Initial revision";
    reference
      "1.0.0";
    cisco-semver:module-version "1.0.0";
  }

  typedef appqoe-module {
    type enumeration {
      enum appqoe-module-invalid {
        value 0;
        description
          "APPQOE module is invalid";
      }
      enum appqoe-module-tcpproxy {
        value 1;
        description
          "APPQOE module is TCP proxy";
      }
      enum appqoe-module-sslproxy {
        value 2;
        description
          "APPQOE module is SSL proxy";
      }
      enum appqoe-module-rm {
        value 3;
        description
          "APPQOE module is Resource Manager(RM)";
      }
      enum appqoe-module-sc {
        value 4;
        description
          "APPQOE module is service chain";
      }
    }
    description
      "APPQOE services or modules";
  }

  typedef appqoe-module-status {
    type enumeration {
      enum appqoe-status-invalid {
        value 0;
        description
          "APPQOE status type invalid";
      }
      enum appqoe-status-green {
        value 1;
        description
          "APPQOE status type green";
      }
      enum appqoe-status-yellow {
        value 2;
        description
          "APPQOE status type yellow";
      }
      enum appqoe-status-red {
        value 3;
        description
          "APPQOE status type red";
      }
    }
    description
      "APPQOE overall status and each module status";
  }

  typedef appqoe-status-err {
    type enumeration {
      enum appqoe-err-undef {
        value 0;
        description
          "Error is undefined";
      }
      enum appqoe-err-ocsp-init-fail {
        value 1;
        description
          "SSL error: Online Certificate Status Protocol(OCSP) initialization fail";
      }
      enum appqoe-err-sign-ca-exp {
        value 2;
        description
          "SSL error: Certificate Authority(CA) signing certificate expired";
      }
      enum appqoe-err-ocsp-fail-ca-exp {
        value 3;
        description
          "SSL error: OCSP init fail and CA sign certificate expired";
      }
      enum appqoe-err-ca-tp-cfg {
        value 4;
        description
          "SSL error: CA Trust Point(TP) is not configured";
      }
      enum appqoe-err-ocsp-fail-ca-tp-cfg {
        value 5;
        description
          "SSL error: OCSP init fail and CA TP is not configured";
      }
      enum appqoe-err-ca-exp-ca-tp-cfg {
        value 6;
        description
          "SSL error: CA sign cert expired and CA TP is not configured";
      }
      enum appqoe-err-ocsp-fail-ca-exp-tp-cfg {
        value 7;
        description
          "SSL error: OCSP init fail, CA sign cert expired and CA TP is not configured";
      }
      enum appqoe-err-ca-bund-cfg {
        value 8;
        description
          "SSL error: CA bundle not configured";
      }
      enum appqoe-err-ocsp-fail-ca-bund-cfg {
        value 9;
        description
          "SSL error: OCSP init fail and CA bundle not configured";
      }
      enum appqoe-err-ca-exp-bund-cfg {
        value 10;
        description
          "SSL error: CA sign cert expired and CA bundle not configured";
      }
      enum appqoe-err-ocsp-fail-ca-exp-bund-cfg {
        value 11;
        description
          "SSL error: OCSP init fail, CA sign cert expired and CA bundle not configured";
      }
      enum appqoe-err-ca-tp-bund-cfg {
        value 12;
        description
          "SSL error: CA TP and CA bundle not configured";
      }
      enum appqoe-err-ocsp-fail-ca-tp-bund-cfg {
        value 13;
        description
          "SSL error: OCSP init fail, CA TP and CA bundle not configured";
      }
      enum appqoe-err-ca-exp-tp-bund-cfg {
        value 14;
        description
          "SSL error: CA sign cert expired, CA TP and CA bundle not configured";
      }
      enum appqoe-err-ocsp-ca-exp-tp-bund-cfg {
        value 15;
        description
          "SSL error: OCSP init fail, CA sign cert expired, CA TP and CA bundle not configured";
      }
      enum appqoe-err-ism-init-fail {
        value 16;
        description
          "SSL error: Interposer Session Manager(ISM) initialization fail";
      }
      enum appqoe-err-cert-mgr-init-fail {
        value 17;
        description
          "SSL error: Certificate manager initialization fail";
      }
      enum appqoe-err-rm-mem-limit-reach {
        value 18;
        description
          "RM error: Memory usage reached beyond allowed limit";
      }
      enum appqoe-err-rm-sess-limit-reach {
        value 19;
        description
          "RM error: Number of sessions reached beyond allowed limit";
      }
      enum appqoe-err-sc-channel-down {
        value 20;
        description
          "SC error: One or more communication channel is down";
      }
      enum appqoe-err-ssl-status-disabled {
        value 21;
        description
          "SSL proxy is disabled";
      }
    }
    description
      "Error details of APPQOE service or module when status is not green";
  }

  typedef tcpproxy-flow-err-tag {
    type enumeration {
      enum tcp-flow-err-tag-invalid {
        value 0;
        description
          "TCP-Proxy flow error is invalid";
      }
      enum tcp-flow-err-tag-accpt-conn-fail {
        value 1;
        description
          "TCP-Proxy accept conn fail";
      }
      enum tcp-flow-err-tag-rx-thr-fail {
        value 2;
        description
          "TCP-Proxy receive thread fail";
      }
      enum tcp-flow-err-tag-aoim-sync-fail {
        value 3;
        description
          "TCP-Proxy application optimiser information manager sync fail";
      }
      enum tcp-flow-err-tag-dre-resp-fail {
        value 4;
        description
          "TCP-Proxy DRE response create fail";
      }
      enum tcp-flow-err-tag-snort-resp-fail {
        value 5;
        description
          "TCP-Proxy SNORT response create fail";
      }
      enum tcp-flow-err-tag-utd-resp-fail {
        value 6;
        description
          "TCP-Proxy UTD response create fail";
      }
      enum tcp-flow-err-tag-close-by-utd {
        value 7;
        description
          "TCP-Proxy flow closed by UTD";
      }
      enum tcp-flow-err-tag-close-by-dre {
        value 8;
        description
          "TCP-Proxy flow closed by DRE";
      }
      enum tcp-flow-err-tag-close-by-ssl {
        value 9;
        description
          "TCP-Proxy flow closed by SSL";
      }
      enum tcp-flow-err-tag-reset-by-aoim {
        value 10;
        description
          "TCP-Proxy flow reset by application optimiser information manager";
      }
      enum tcp-flow-err-tag-create-dre-fail {
        value 11;
        description
          "TCP-Proxy flow create fail by DRE";
      }
      enum tcp-flow-err-tag-create-utd-fail {
        value 12;
        description
          "TCP-Proxy flow create fail by UTD";
      }
      enum tcp-flow-err-tag-create-ssl-fail {
        value 13;
        description
          "TCP-Proxy flow create fail by SSL";
      }
      enum tcp-flow-err-tag-syn-cache-purge {
        value 14;
        description
          "TCP-Proxy flow fail as syn cache purged";
      }
      enum tcp-flow-err-tag-ctimer-expire {
        value 15;
        description
          "TCP-Proxy flow cleanup timer expired";
      }
      enum tcp-flow-err-tag-cleanup-other {
        value 16;
        description
          "TCP-Proxy flow cleanup due to other reasons";
      }
      enum tcp-flow-err-tag-accept-failed {
        value 17;
        description
          "TCP-Proxy flow accept failed";
      }
      enum tcp-flow-err-tag-remote-conn-failed {
        value 18;
        description
          "TCP-Proxy flow remote connection failed";
      }
    }
    description
      "Error tag for flows which are closed by
       TCP-Proxy to indicate appropriate error message.";
  }

  typedef sslproxy-flow-err-tag {
    type enumeration {
      enum ssl-ism-err-none {
        value 0;
        description
          "SSL-Proxy ISM error invalid.";
      }
      enum ssl-ism-err-mem-alloc {
        value 1;
        description
          "Memory allocation fail at ISM.";
      }
      enum ssl-ism-err-pool {
        value 2;
        description
          "Unable to get memory from pool at ISM.";
      }
      enum ssl-ism-err-unsupp-cipher {
        value 3;
        description
          "Unsupported cipher.";
      }
      enum ssl-ism-err-hs-unsupported {
        value 4;
        description
          "Handshake unsupported at ISM.";
      }
      enum ssl-ism-err-vertverif-fail {
        value 5;
        description
          "Certificate verification fail at ISM.";
      }
      enum ssl-ism-err-endp-alert {
        value 6;
        description
          "End point alert in ISM.";
      }
      enum ssl-ism-err-close-before-hs {
        value 7;
        description
          "TCP close received before handshake complete.";
      }
      enum ssl-ism-err-proxy-cert {
        value 8;
        description
          "Unable to get proxy certificate.";
      }
      enum ssl-ism-err-expiered-cert {
        value 9;
        description
          "Certificate expired.";
      }
      enum ssl-ism-err-untrusted-cert {
        value 10;
        description
          "Untrusted certificate.";
      }
      enum ssl-ism-err-mem-access {
        value 11;
        description
          "Unable to access memory in ISM.";
      }
      enum ssl-lwssl-err-de-close {
        value 12;
        description
          "Received close request from DE.";
      }
      enum ssl-lwssl-err-de-flush-done {
        value 13;
        description
          "Flush done failed for DE.";
      }
      enum ssl-lwssl-err-nop-read {
        value 14;
        description
          "No operation read function called.";
      }
      enum ssl-lwssl-err-invalid-fsm-evt {
        value 15;
        description
          "Received invalid FSM event.";
      }
      enum ssl-lwssl-err-key-pkt-snd-fail {
        value 16;
        description
          "Failed to send key packet to ISM.";
      }
      enum ssl-lwssl-err-invalid-de-msg {
        value 17;
        description
          "Invalid message received from DE.";
      }
      enum ssl-lwssl-err-null-flow-ptr {
        value 18;
        description
          "Flow pointer is NULL";
      }
      enum ssl-lwssl-err-pd-reset {
        value 19;
        description
          "Reset due to push down";
      }
      enum ssl-lwssl-err-flush-done-fail {
        value 20;
        description
          "ISM flush done event handling is failed";
      }
      enum ssl-lwssl-err-ism-key-pkt-hdl-fail {
        value 21;
        description
          "ISM key packet handling is failed";
      }
      enum ssl-lwssl-err-invalid-ism-msg {
        value 22;
        description
          "Invalid message from ISM";
      }
      enum ssl-lwssl-err-invalid-peer {
        value 23;
        description
          "Invalid peer";
      }
      enum ssl-lwssl-err-min-tls-ver-act-rst {
        value 24;
        description
          "Unsupported protocol version action drop";
      }
      enum ssl-lwssl-err-null-ch-buf {
        value 25;
        description
          "Client hello buffer is null";
      }
      enum ssl-lwssl-err-snd-de-data-fail {
        value 26;
        description
          "Send DE data failed";
      }
      enum ssl-lwssl-err-fin-rst-pd {
        value 27;
        description
          "FIN or RST received during handshake";
      }
      enum ssl-lwssl-err-evt-in-inv-fsm-state {
        value 28;
        description
          "Invalid event in FSM state";
      }
      enum ssl-lwssl-err-evt-wrng-fsm-state {
        value 29;
        description
          "Event received in wrong FSM state";
      }
      enum ssl-lwssl-err-wrng-evt-in-de {
        value 30;
        description
          "Invalid event in DE init done state";
      }
      enum ssl-lwssl-err-snd-flush-fail {
        value 31;
        description
          "ISM send flush failed";
      }
      enum ssl-lwssl-err-evt-trig-rst {
        value 32;
        description
          "Trigger reset";
      }
      enum ssl-lwssl-err-one-side-key-pdg {
        value 33;
        description
          "One side key pending from ISM";
      }
      enum ssl-lwssl-err-null-ssl-rec {
        value 34;
        description
          "NULL SSL record in encrypted services buffer";
      }
      enum ssl-lwssl-err-ch-buf-alloc-fail {
        value 35;
        description
          "Buffer allocation failed for client hello";
      }
      enum ssl-lwssl-err-hs-parse-abort {
        value 36;
        description
          "Parse abort during handshake";
      }
      enum ssl-lwssl-err-hs-parse-incomp {
        value 37;
        description
          "Incomplete message during handshake";
      }
      enum ssl-lwssl-err-data-parse-abort {
        value 38;
        description
          "Data parse abort";
      }
      enum ssl-lwssl-err-data-parse-incomp {
        value 39;
        description
          "Incomplete message for data";
      }
      enum ssl-lwssl-err-invalid-ssl-rec {
        value 40;
        description
          "Invalid SSL record";
      }
      enum ssl-lwssl-err-fail-mode-rst {
        value 41;
        description
          "Failure mode reset";
      }
      enum ssl-lwssl-err-sslv2-fail-mode-rst {
        value 42;
        description
          "SSLv2 failure mode reset";
      }
      enum ssl-lwssl-err-peer-nop-read-fn {
        value 43;
        description
          "Peer no operation read function called";
      }
      enum ssl-lwssl-err-ssl-aut-trig-rst {
        value 44;
        description
          "SSL AUT triggering reset";
      }
      enum ssl-lwssl-err-send-ism-msg-fail {
        value 45;
        description
          "Unable to send handshake message to ISM";
      }
    }
    description
      "Error tag for flows which are closed by
       SSL-Proxy to indicate appropriate error message.";
  }

  typedef appqoe-stats-label {
    type enumeration {
      enum appqoe-stat-undef {
        value 0;
        description
          "APPQOE statistics label is not defined";
      }
      enum appqoe-stat-ssl-drop-untrusted-cert {
        value 1;
        description
          "APPQOE statistics label SSL drop due to untrusted certificate";
      }
      enum appqoe-stat-ssl-drop-no-proxy-cert {
        value 2;
        description
          "APPQOE statistics label SSL drop as unable to get proxy certificate";
      }
      enum appqoe-stat-ssl-drop-expired-cert {
        value 3;
        description
          "APPQOE statistics label SSL drop due to certificate expired";
      }
      enum appqoe-stat-ssl-drop-ocsp-cert-verif {
        value 4;
        description
          "APPQOE statistics label SSL due to OCSP certificate verification fail";
      }
      enum appqoe-stat-ssl-drop-endpoint-alert {
        value 5;
        description
          "APPQOE statistics label SSL drop due to endpoint alert";
      }
      enum appqoe-stat-ssl-drop-tcp-close-hs {
        value 6;
        description
          "APPQOE statistics label SSL drop due to TCP close received";
      }
      enum appqoe-stat-ssl-session-alloc-fail {
        value 7;
        description
          "APPQOE statistics label SSL could not allocate sessions";
      }
      enum appqoe-stat-ssl-c2s-wcapi-deny-pkt {
        value 8;
        description
          "APPQOE statistics label SSL client to server packet denied";
      }
      enum appqoe-stat-ssl-s2c-wcapi-deny-pkt {
        value 9;
        description
          "APPQOE statistics label SSL server to client packet denied";
      }
      enum appqoe-stat-rm-res-tcp-used-sess {
        value 10;
        description
          "APPQOE statistics label RM number of sessions used by TCP";
      }
      enum appqoe-stat-rm-res-ssl-used-sess {
        value 11;
        description
          "APPQOE statistics label RM number of sessions used by SSL";
      }
      enum appqoe-stat-rm-health-yellow {
        value 12;
        description
          "APPQOE statistics label RM number of times health status changed to yellow";
      }
      enum appqoe-stat-rm-health-green {
        value 13;
        description
          "APPQOE statistics label RM number of times health status changed to green";
      }
      enum appqoe-stat-rm-tcp-sess-alloc {
        value 14;
        description
          "APPQOE statistics label RM number of sessions allocated by TCP";
      }
      enum appqoe-stat-rm-tcp-sess-free {
        value 15;
        description
          "APPQOE statistics label RM number of sessions freed by TCP";
      }
      enum appqoe-stat-rm-ssl-sess-alloc {
        value 16;
        description
          "APPQOE statistics label RM number of sessions allocated by SSL";
      }
      enum appqoe-stat-rm-ssl-sess-free {
        value 17;
        description
          "APPQOE statistics label RM number of sessions freed by SSL";
      }
      enum appqoe-stat-tcp-tot-conn {
        value 18;
        description
          "APPQOE statistics label TCP total number of connections";
      }
      enum appqoe-stat-tcp-tot-flow-create {
        value 19;
        description
          "APPQOE statistics label TCP total number of flows created";
      }
      enum appqoe-stat-tcp-tot-flow-delete {
        value 20;
        description
          "APPQOE statistics label TCP total number of flows deleted";
      }
      enum appqoe-stat-tcp-tot-curr-conn {
        value 21;
        description
          "APPQOE statistics label TCP total number of current connections";
      }
      enum appqoe-stat-tcp-tot-fail-conn {
        value 22;
        description
          "APPQOE statistics label TCP total number of failed connections";
      }
      enum appqoe-stat-tcp-tot-syncache-add {
        value 23;
        description
          "APPQOE statistics label TCP total number of SYN cache added";
      }
      enum appqoe-stat-vp-tot-syn-drop-pps {
        value 24;
        description
          "APPQOE statistics label transport channel total SYN dropped due to packet per second limit reached";
      }
      enum appqoe-stat-vp-tot-new-conn-fail {
        value 25;
        description
          "APPQOE statistics label transport channel total new connection failed";
      }
      enum appqoe-stat-bbr-act-conn {
        value 26;
        description
          "APPQOE statistics label Bottleneck Bandwidth and Round-trip propagation time(BBR) total active connections";
      }
      enum appqoe-stat-bbr-tot-sendmap-fail {
        value 27;
        description
          "APPQOE statistics label BBR total send map allocation failed";
      }
      enum appqoe-stat-sppi-pkt-avail {
        value 28;
        description
          "APPQOE statistics label Service Plane Packet Interface(SPPI) total available packets";
      }
      enum appqoe-stat-sppi-rx-fail {
        value 29;
        description
          "APPQOE statistics label SPPI failed received packets";
      }
      enum appqoe-stat-sppi-tx-fail {
        value 30;
        description
          "APPQOE statistics label SPPI failed transmit packets";
      }
      enum appqoe-stat-sppi-pipe-disconnect {
        value 31;
        description
          "APPQOE statistics label SPPI pipe disconnected";
      }
      enum appqoe-stat-hput-sys-callout-del {
        value 32;
        description
          "APPQOE statistics label system timer call-out deleted";
      }
      enum appqoe-stat-hput-hpt-callout-del {
        value 33;
        description
          "APPQOE statistics label HPTS(high precision timers) timer call-out deleted";
      }
      enum appqoe-stat-hput-sys-timer-del {
        value 34;
        description
          "APPQOE statistics label system timer deleted";
      }
      enum appqoe-stat-hput-hpt-timer-del {
        value 35;
        description
          "APPQOE statistics label high precision timer deleted";
      }
      enum appqoe-stat-hput-sys-node-empty {
        value 36;
        description
          "APPQOE statistics label system timer node is empty";
      }
      enum appqoe-stat-hput-hpt-node-empty {
        value 37;
        description
          "APPQOE statistics label high precision timer node is empty";
      }
    }
    description
      "APPQOE services registered statistics label";
  }

  typedef appqoe-flow-services {
    type bits {
      bit appqoe-flow-services-tcpproxy {
        position 0;
        description
          "Flow was handled by TCP-Proxy";
      }
      bit appqoe-flow-services-sslproxy {
        position 1;
        description
          "Flow was handled by SSL-Proxy";
      }
      bit appqoe-flow-services-utd {
        position 2;
        description
          "Flow was handled by UTD";
      }
      bit appqoe-flow-services-dreopt {
        position 3;
        description
          "Flow was handled by DRE Optimization";
      }
    }
    description
      "Services involved in flow optimization";
  }

  grouping appqoe-modules {
    description
      "Status of each APPQOE service or module.";
    leaf module {
      type appqoe-xe-serv-oper:appqoe-module;
      description
        "Service or module name";
    }
    leaf status {
      type appqoe-xe-serv-oper:appqoe-module-status;
      description
        "Service or module status";
    }
    leaf err-tag {
      type appqoe-xe-serv-oper:appqoe-status-err;
      description
        "Error details when service or module status is not green";
    }
  }

  grouping appqoe-status-details {
    description
      "APPQOE overall status along with
       each service or module registered status.
       Also displays error details when a service or module
       is inactive";
    leaf appqoe-status {
      type appqoe-xe-serv-oper:appqoe-module-status;
      description
        "APPQOE overall status";
    }
    list module-status {
      description
        "Status of APPQOE module registered
         with status infra";
      uses appqoe-xe-serv-oper:appqoe-modules;
    }
  }

  grouping appqoe-flow-brief-key {
    description
      "Active flow unique identifier attributes.";
    leaf vpn-id {
      type uint32;
      description
        "Flow VPN identifier.";
    }
    leaf client-ip {
      type inet:ip-address;
      description
        "Flow client IP address.";
    }
    leaf client-port {
      type uint16;
      description
        "Flow client port number.";
    }
    leaf server-ip {
      type inet:ip-address;
      description
        "Flow server IP address.";
    }
    leaf server-port {
      type uint16;
      description
        "Flow server port number.";
    }
    leaf index {
      type uint32;
      description
        "The index when combined with the other key fields ensures flow uniqueness.";
    }
  }

  grouping appqoe-flow-brief {
    description
      "Brief AppQoE flow attributes and statistics.";
    leaf flow-id {
      type uint64;
      description
        "Unique Flow identifier. This field should be used to retrieve the detailed attributes of a specific flow";
    }
    leaf services {
      type appqoe-xe-serv-oper:appqoe-flow-services;
      description
        "Bitmap representing services that handled the flow";
    }
    leaf start-time {
      type yang:date-and-time;
      description
        "Time of flow commencement.";
    }
    leaf end-time {
      type yang:date-and-time;
      description
        "Time of flow expiry (when applicable).";
    }
    leaf rx-bytes {
      type uint64;
      units "bytes";
      description
        "Total number of bytes received";
    }
    leaf tx-bytes {
      type uint64;
      units "bytes";
      description
        "Total number of bytes sent";
    }
  }

  grouping appqoe-flow-error-entry {
    description
      "Flows closed due to errors in any of APPQOE services.";
    leaf flow-id {
      type uint64;
      description
        "Flow identifier.";
    }
    leaf vpn-id {
      type uint32;
      description
        "Flow VPN identifier.";
    }
    leaf client-ip {
      type inet:ip-address;
      description
        "Flow client IP address.";
    }
    leaf client-port {
      type uint16;
      description
        "Flow client port number.";
    }
    leaf server-ip {
      type inet:ip-address;
      description
        "Flow server IP address.";
    }
    leaf server-port {
      type uint16;
      description
        "Flow server port number.";
    }
    leaf services {
      type appqoe-xe-serv-oper:appqoe-flow-services;
      description
        "Bitmap representing services that handled the flow.";
    }
    leaf start-time {
      type yang:date-and-time;
      description
        "Timestamp of when flow was started.";
    }
    leaf tx-bytes {
      type uint64;
      units "bytes";
      description
        "Total number of bytes sent.";
    }
    leaf rx-bytes {
      type uint64;
      units "bytes";
      description
        "Total number of bytes received.";
    }
    leaf tcpproxy-err-tag {
      type appqoe-xe-serv-oper:tcpproxy-flow-err-tag;
      description
        "Error details set by TCP-Proxy service.";
    }
    leaf sslproxy-err-tag {
      type appqoe-xe-serv-oper:sslproxy-flow-err-tag;
      description
        "Error details set by SSL-Proxy service.";
    }
  }

  grouping appqoe-flow-error {
    description
      "Flows closed due to errors in any of APPQOE services.";
    leaf flow-count {
      type uint32;
      description
        "Current number of flows closed due to error.";
    }
    list appqoe-flow-error-entry {
      key "flow-id";
      description
        "List of flows closed due to error.";
      uses appqoe-xe-serv-oper:appqoe-flow-error-entry;
    }
  }

  grouping appqoe-flow-summary {
    description
      "Summary of aggregated flow statistics.";
    leaf total-flows {
      type uint64;
      description
        "Total number of flows handled by AppQoE services.";
    }
    leaf active-flows {
      type uint32;
      description
        "Current active optimized flow count.";
    }
    leaf expired-flows {
      type uint64;
      description
        "Total number of flows that have been successfully optimized since last clear or AppQoE service restart.";
    }
    leaf error-flows {
      type uint64;
      description
        "Total number of flows that were not optimized due to an error since last clear or AppQoE service restart.";
    }
    leaf max-concurrent-flows {
      type uint32;
      description
        "The maximum number of flows handled concurrently by AppQoE Services.";
    }
    leaf flows-in-progress {
      type uint32;
      description
        "Total number of flows in connection establishment/initialisation state.";
    }
  }

  grouping appqoe-stats-recent {
    description
      "APPQOE statistics holding the current value, 30 and 60 sec prior values";
    leaf stat-current {
      type uint64;
      description
        "APPQOE current value of statistics";
    }
    leaf stat-30s {
      type uint64;
      description
        "APPQOE statistics updated 30 seconds ago";
    }
    leaf stat-60s {
      type uint64;
      description
        "APPQOE statistics updated 60 seconds ago";
    }
    leaf label {
      type appqoe-xe-serv-oper:appqoe-stats-label;
      description
        "APPQOE services registered statistics label";
    }
  }

  grouping appqoe-stats-recent-db {
    description
      "APPQOE services registered statistics database";
    list stats-rec {
      description
        "Registered statistics at different time intervals";
      uses appqoe-xe-serv-oper:appqoe-stats-recent;
    }
  }

  container appqoe-serv-oper-data {
    config false;
    description
      "APPQOE serviceability operational data, such as
          APPQOE overall status along with individual service status,
          flows closed due to error with reason,
          statistics for monitoring failure.";
    container appqoe-status-details {
      presence "appqoe-status-details";
      description
        "APPQOE overall status along with individual service status,
         also displays the reason if any services is inactive";
      uses appqoe-xe-serv-oper:appqoe-status-details;
    }
    list appqoe-flow-active-brief {
      key "vpn-id client-ip client-port server-ip server-port index";
      description
        "Brief attributes and metrics of current real-time active flows handled by SD-WAN AppQoE services.";
      uses appqoe-xe-serv-oper:appqoe-flow-brief-key;
      uses appqoe-xe-serv-oper:appqoe-flow-brief;
    }
    list appqoe-flow-expired-brief {
      key "vpn-id client-ip client-port server-ip server-port index";
      description
        "Brief attributes and metrics of the most recent expired flows handled by SD-WAN AppQoE services.";
      uses appqoe-xe-serv-oper:appqoe-flow-brief-key;
      uses appqoe-xe-serv-oper:appqoe-flow-brief;
    }
    container appqoe-flow-error {
      presence "appqoe-flow-error";
      description
        "Flows closed due to errors by respective services are listed.
            Flows closed without errors are excluded.";
      uses appqoe-xe-serv-oper:appqoe-flow-error;
    }
    container appqoe-flow-summary {
      presence "appqoe-flow-summary";
      description
        "Summary of aggregated SD-WAN AppQoE flow statistics.";
      uses appqoe-xe-serv-oper:appqoe-flow-summary;
    }
    container appqoe-stats-recent {
      presence "appqoe-stats-recent";
      description
        "APPQOE services registered counters that helps in abnormal
            behavior is seen with connections or flows.";
      uses appqoe-xe-serv-oper:appqoe-stats-recent-db;
    }
  }
}
