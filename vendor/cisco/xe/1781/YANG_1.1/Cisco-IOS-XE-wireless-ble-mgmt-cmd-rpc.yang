module Cisco-IOS-XE-wireless-ble-mgmt-cmd-rpc {
  yang-version 1.1;
  namespace "http://cisco.com/ns/yang/Cisco-IOS-XE-wireless-ble-mgmt-cmd-rpc";
  prefix wireless-ble-mgmt-cmd-rpc;

  import Cisco-IOS-XE-wireless-enum-types {
    prefix wireless-enum-types;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Copyright (c) 2019-2020 by Cisco Systems, Inc.
     All rights reserved.";

  revision 2021-11-01 {
    description
      "- Added range for iBeacon & vibeacon frequency, transmit power and advertised transmit power";
    reference
      "2.0.0";
    cisco-semver:module-version "2.0.0";
  }
  revision 2020-07-01 {
    description
      "Initial revision";
    reference
      "1.0.0";
    cisco-semver:module-version "1.0.0";
  }

  typedef ap-identifier {
    type enumeration {
      enum ap-identifier-name {
        value 0;
        description
          "AP name";
      }
      enum ap-identifier-mac-address {
        value 1;
        description
          "AP MAC address";
      }
    }
    description
      "Access point identifier";
  }

  grouping ble-scan-req {
    description
      "Command to configure BLE scan role";
    leaf interval-sec {
      type uint32;
      units "seconds";
      mandatory true;
      description
        "Scan interval";
    }
    leaf window-msec {
      type uint16;
      units "milliseconds";
      description
        "Scan window";
    }
    leaf max-value {
      type uint8;
      description
        "Scan max value";
    }
    leaf filter {
      type wireless-enum-types:ble-ltx-scan-filter;
      description
        "Scan filter";
    }
    leaf state {
      type wireless-enum-types:ble-ltx-scan-state;
      mandatory true;
      description
        "Scan state";
    }
    choice ap-identifier-choice {
      mandatory true;
      description
        "AP identifier";
      case ap-identifier-name {
        leaf ap-name {
          type string;
          mandatory true;
          description
            "AP name";
        }
      }
      case ap-identifier-mac-address {
        leaf mac-addr {
          type yang:mac-address;
          mandatory true;
          description
            "MAC address";
        }
      }
    }
  }

  grouping ble-sync-req {
    description
      "Command to send a BLE sync request";
    leaf ble-mac {
      type yang:mac-address;
      mandatory true;
      description
        "BLE MAC address";
    }
    choice ap-identifier-choice {
      mandatory true;
      description
        "AP identifier";
      case ap-identifier-name {
        leaf ap-name {
          type string;
          mandatory true;
          description
            "AP name";
        }
      }
      case ap-identifier-mac-address {
        leaf mac-addr {
          type yang:mac-address;
          mandatory true;
          description
            "MAC address";
        }
      }
    }
  }

  grouping ble-ibeacon-req {
    description
      "Command to configure BLE beacon of type iBeacon";
    leaf uuid {
      type string {
        pattern '[0-9a-fA-F]{8}-[0-9a-fA-F]{4}-[0-9a-fA-F]{4}-[0-9a-fA-F]{4}-[0-9a-fA-F]{12}';
      }
      mandatory true;
      description
        "UUID to be chirped by the beacon of type iBeacon";
    }
    leaf major {
      type uint16;
      mandatory true;
      description
        "Major value to be chirped by the beacon of type iBeacon";
    }
    leaf minor {
      type uint16;
      mandatory true;
      description
        "Minor value to be chirped by the beacon of type iBeacon";
    }
    leaf tx-power {
      type uint8 {
        range "0..12";
      }
      mandatory true;
      description
        "Power to chirp with for the beacon of type iBeacon";
    }
    leaf frequency-msec {
      type uint16 {
        range "100..1000";
      }
      units "milliseconds";
      mandatory true;
      description
        "Frequency to chirp with for the beacon of type iBeacon";
    }
    leaf adv-tx-power {
      type uint8 {
        range "1..127";
      }
      units "dbm";
      mandatory true;
      description
        "Power to advertise when chirping beacon of type iBeacon";
    }
    choice ap-identifier-choice {
      mandatory true;
      description
        "AP identifier";
      case ap-identifier-name {
        leaf ap-name {
          type string;
          mandatory true;
          description
            "AP name";
        }
      }
      case ap-identifier-mac-address {
        leaf mac-addr {
          type yang:mac-address;
          mandatory true;
          description
            "MAC address";
        }
      }
    }
  }

  grouping ble-eddy-uid-req {
    description
      "Command to configure BLE Eddystone UID beacon";
    leaf instance-id {
      type string {
        pattern '[0-9a-fA-F]{12}';
      }
      mandatory true;
      description
        "Instance ID to be chirped by the Eddystone UID beacon";
    }
    leaf namespace {
      type string {
        pattern '[0-9a-fA-F]{20}';
      }
      mandatory true;
      description
        "Namespace to be chirped by the Eddystone UID beacon";
    }
    choice ap-identifier-choice {
      mandatory true;
      description
        "AP identifier";
      case ap-identifier-name {
        leaf ap-name {
          type string;
          mandatory true;
          description
            "AP name";
        }
      }
      case ap-identifier-mac-address {
        leaf mac-addr {
          type yang:mac-address;
          mandatory true;
          description
            "MAC address";
        }
      }
    }
  }

  grouping ble-eddy-url-req {
    description
      "Command to configure BLE Eddystone URL beacon";
    leaf url {
      type string;
      mandatory true;
      description
        "URL to be chirped by the Eddystone URL beacon";
    }
    choice ap-identifier-choice {
      mandatory true;
      description
        "AP identifier";
      case ap-identifier-name {
        leaf ap-name {
          type string;
          mandatory true;
          description
            "AP name";
        }
      }
      case ap-identifier-mac-address {
        leaf mac-addr {
          type yang:mac-address;
          mandatory true;
          description
            "MAC address";
        }
      }
    }
  }

  grouping ble-mgt-admin-req {
    description
      "Command to enable or disable BLE functionality";
    leaf state {
      type wireless-enum-types:ble-ltx-admin-state;
      mandatory true;
      description
        "BLE admin flag";
    }
    choice ap-identifier-choice {
      mandatory true;
      description
        "AP identifier";
      case ap-identifier-name {
        leaf ap-name {
          type string;
          mandatory true;
          description
            "AP name";
        }
      }
      case ap-identifier-mac-address {
        leaf mac-addr {
          type yang:mac-address;
          mandatory true;
          description
            "MAC address";
        }
      }
    }
  }

  grouping ble-vibeacon-req {
    description
      "Command to configure BLE beacon of type viBeacon";
    leaf beacon-id {
      type uint8;
      mandatory true;
      description
        "Id of the viBeacon being configured";
    }
    leaf status {
      type wireless-enum-types:ble-ltx-vibeacon-status;
      mandatory true;
      description
        "Status of the viBeacon being configured";
    }
    leaf uuid {
      type string {
        pattern '[0-9a-fA-F]{8}-[0-9a-fA-F]{4}-[0-9a-fA-F]{4}-[0-9a-fA-F]{4}-[0-9a-fA-F]{12}';
      }
      mandatory true;
      description
        "UUID to be chirped by the beacon of type viBeacon";
    }
    leaf major {
      type uint16;
      mandatory true;
      description
        "Type (major value) to be chirped by the beacon of type viBeacon";
    }
    leaf minor {
      type uint16;
      mandatory true;
      description
        "Subtype (minor value) to be chirped by the beacon of type viBeacon";
    }
    leaf tx-power {
      type uint8 {
        range "0..12";
      }
      mandatory true;
      description
        "Power to chirp with for the beacon of type viBeacon";
    }
    leaf interval-msec {
      type uint16 {
        range "100..1000";
      }
      units "milliseconds";
      mandatory true;
      description
        "Interval to chirp with for the beacon of type viBeacon";
    }
    leaf adv-tx-power {
      type uint8 {
        range "1..127";
      }
      units "dbm";
      mandatory true;
      description
        "Power to advertise when chirping beacon of type viBeacon";
    }
    choice ap-identifier-choice {
      mandatory true;
      description
        "AP identifier";
      case ap-identifier-name {
        leaf ap-name {
          type string;
          mandatory true;
          description
            "AP name";
        }
      }
      case ap-identifier-mac-address {
        leaf mac-addr {
          type yang:mac-address;
          mandatory true;
          description
            "MAC address";
        }
      }
    }
  }

  grouping ble-no-adv-profile-req {
    description
      "RPC to configure BLE no advertisement profile";
    leaf state {
      type wireless-enum-types:ble-no-adv-profile-state;
      mandatory true;
      description
        "No advertisement profile state";
    }
    choice ap-identifier-choice {
      mandatory true;
      description
        "AP identifier";
      case ap-identifier-name {
        leaf ap-name {
          type string;
          mandatory true;
          description
            "AP name";
        }
      }
      case ap-identifier-mac-address {
        leaf mac-addr {
          type yang:mac-address;
          mandatory true;
          description
            "MAC address";
        }
      }
    }
  }

  rpc ble-sync-req {
    description
      "Command to send a BLE sync request";
    input {
      uses wireless-ble-mgmt-cmd-rpc:ble-sync-req;
    }
  }

  rpc ble-scan-req {
    description
      "Command to configure BLE scan role";
    input {
      uses wireless-ble-mgmt-cmd-rpc:ble-scan-req;
    }
  }

  rpc ble-ibeacon-req {
    description
      "Command to configure BLE beacon of type iBeacon";
    input {
      uses wireless-ble-mgmt-cmd-rpc:ble-ibeacon-req;
    }
  }

  rpc ble-eddy-uid-req {
    description
      "Command to configure BLE Eddystone UID beacon";
    input {
      uses wireless-ble-mgmt-cmd-rpc:ble-eddy-uid-req;
    }
  }

  rpc ble-eddy-url-req {
    description
      "Command to configure BLE Eddystone URL beacon";
    input {
      uses wireless-ble-mgmt-cmd-rpc:ble-eddy-url-req;
    }
  }

  rpc ble-mgt-admin-req {
    description
      "Command to enable or disable BLE functionality";
    input {
      uses wireless-ble-mgmt-cmd-rpc:ble-mgt-admin-req;
    }
  }

  rpc ble-vibeacon-req {
    description
      "Command to configure BLE beacon of type viBeacon";
    input {
      uses wireless-ble-mgmt-cmd-rpc:ble-vibeacon-req;
    }
  }

  rpc ble-no-adv-profile-req {
    description
      "RPC to configure BLE no advertisement profile";
    input {
      uses wireless-ble-mgmt-cmd-rpc:ble-no-adv-profile-req;
    }
  }
}
