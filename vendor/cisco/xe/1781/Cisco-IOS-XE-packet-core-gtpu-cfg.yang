module Cisco-IOS-XE-packet-core-gtpu-cfg {
  yang-version 1;
  namespace "http://cisco.com/ns/yang/Cisco-IOS-XE-packet-core-gtpu-cfg";
  prefix packet-core-gtpu-cfg;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Packet-Core GTPU profile configuration.
     Copyright (c) 2021 by Cisco Systems, Inc.
     All rights reserved.";

  revision 2021-11-01 {
    description
      "Initial revision";
    reference
      "1.0.0";
    cisco-semver:module-version "1.0.0";
  }

  grouping gtpu-profile {
    description
      "GTPU Profile config";
    leaf profile-name {
      type string {
        length "1..32" {
          error-message "Invalid length for GTPU Profile name: Valid length is 1 to 32 ASCII characters";
          error-app-tag "must-violation";
        }
        pattern '[!-~]([ -~]*[!-~])?' {
          error-message "Please use ASCII 32-126 characters and avoid leading/trailing spaces";
          error-app-tag "must-violation";
        }
      }
      description
        "GTPU Profile Name";
    }
    leaf status {
      type boolean;
      default "false";
      description
        "Administrative status of GTPU Profile";
    }
    leaf if-name {
      type string;
      default "";
      description
        "Interface Name (eg. (Ten)GigabitEthernet1/Loopback1/Port-channel1)";
    }
    leaf keep-alive-enable {
      type boolean;
      default "false";
      description
        "Enable GTPU path management echo request/response handling";
    }
    leaf keep-alive-intrvl {
      type uint32 {
        range "60 .. 86400";
      }
      units "seconds";
      default "120";
      description
        "Keep-alive packet transmission interval (secs)";
    }
    leaf msg-retrans-intrvl {
      type uint16 {
        range "3 .. 30";
      }
      units "seconds";
      default "5";
      description
        "Keep-alive retransmit timeout (secs)";
    }
    leaf max-msg-retries {
      type uint16 {
        range "1 .. 15";
      }
      default "3";
      description
        "Keep-alive maximum retries";
    }
  }

  container packet-core-gtpu-cfg-data {
    description
      "Packet-Core GTPU profile configuration data";
    container gtpu-profiles {
      description
        "GTPU profiles configuration";
      list gtpu-profile {
        key "profile-name";
        description
          "GTPU profile config for Packet-Core";
        uses packet-core-gtpu-cfg:gtpu-profile;
      }
    }
  }
}
