module Cisco-IOS-XE-nat {
  namespace "http://cisco.com/ns/yang/Cisco-IOS-XE-nat";
  prefix ios-nat;

  import cisco-semver {
    prefix cisco-semver;
  }
  import ietf-inet-types {
    prefix inet;
  }
  import Cisco-IOS-XE-types {
    prefix ios-types;
  }
  import Cisco-IOS-XE-native {
    prefix ios;
  }
  import Cisco-IOS-XE-interface-common {
    prefix ios-ifc;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Network Address Translation (NAT) Yang model.
     Copyright (c) 2016-2021 by Cisco Systems, Inc.
     All rights reserved.";

  revision 2022-03-01 {
    description
      "-Added new leaf track for static nat and dynamic nat with vrf
       -Refined leaf mask in list nat-static-transport-list-with-vrf to support CLI with vrf
       -Deprecated leaf network and created a new leaf with type enumeration
       -Marking leaves proto, local-port and global-port as Obsolete in the grouping
        config-ip-nat-source-static-transport-common-part-one-grouping
       -Added must constraint for ip nat inside source list interface";
    cisco-semver:module-version "6.0.0";
  }
  revision 2021-11-01 {
    description
      "-Added CLI for nat66";
    cisco-semver:module-version "5.1.0";
  }
  revision 2021-07-01 {
    description
      "-Marking vrf leaf from nat64 prefix stateful CLI under interface as Obsolete";
    cisco-semver:module-version "5.0.0";
  }
  revision 2021-03-01 {
    description
      "-Added pool support for inside/outside static NAT";
    cisco-semver:module-version "4.0.0";
  }
  revision 2020-11-01 {
    description
      "17.4 unification";
    cisco-semver:module-version "3.1.0";
  }
  revision 2020-07-01 {
    description
      "- Added new NAT config: ip nat settings non PAT log-disable
       - Added new NAT config: ip nat settings trans-err-limit per-ip-pool <number>
       - Created new model, added the older leaf node dns-v6 back and marked it as deprecated";
    cisco-semver:module-version "3.0.0";
  }
  revision 2020-03-01 {
    description
      "- Added new NAT config: ip nat settings high-performance for call setup rate";
    cisco-semver:module-version "2.1.0";
  }
  revision 2019-11-01 {
    description
      "- Added new NAT config";
    cisco-semver:module-version "2.0.0";
  }
  revision 2019-07-01 {
    description
      "- Establish semantic version baseline
       - Implementation of NAT64 DIA route support
       - Implementation of create, switchover, settings, service and missing
         parts of translation max-entries
       - Add ip nat to interface BD-VIF";
    cisco-semver:module-version "1.0.0";
  }
  revision 2019-02-04 {
    description
      "fixed issue with config for ip nat source list interface to allow
       more than one config";
  }
  revision 2019-01-22 {
    description
      "Added leaf for App-hosting Gigabit Ethernet interface";
  }
  revision 2018-12-18 {
    description
      "fix ip nat inside static with multiple vrf get-config missing config issue";
  }
  revision 2018-12-07 {
    description
      "Move nat64 timeout configuration for protocols into timeout container";
  }
  revision 2018-11-21 {
    description
      "Cleanup spelling errors in description statements";
  }
  revision 2018-11-15 {
    description
      "Add correct dependencies on VRF to 'ip nat route'";
  }
  revision 2018-10-04 {
    description
      "fix to allow multiple pool/interface under different vrf";
  }
  revision 2018-08-31 {
    description
      "add nat inside/outside to Vlan interfaces";
  }
  revision 2018-08-22 {
    description
      "fix the deletion of ip nat inside source static <ip> <ip> vrf";
  }
  revision 2018-08-18 {
    description
      "Changed source inside source list to use only one pool/interface";
  }
  revision 2018-08-08 {
    description
      "force overload to 'ip nat inside source list interface/vrf' and 'ip
       nat inside source route-map interface/vrf'";
  }
  revision 2018-07-07 {
    description
      "Added ip nat to interface Multilink";
  }
  revision 2018-06-30 {
    description
      "fixing source list pool/interface and source route-map pool/interface
       issues";
  }
  revision 2018-06-28 {
    description
      "Added must constraints for deleting vrf";
  }
  revision 2018-05-29 {
    description
      "Add ip nat inside source static <ip> <interface>";
  }
  revision 2018-05-18 {
    description
      "Add NAT models under ATM interface and sub interface";
  }
  revision 2018-05-17 {
    description
      "Added ip nat to interface Dialer";
  }
  revision 2018-04-03 {
    description
      "Added ip nat to interface Serial";
  }
  revision 2018-03-21 {
    description
      "Make ip nat inside source list interface/pool vrf list";
  }
  revision 2018-03-14 {
    description
      "Added ip nat to interface VirtualPortGroup";
  }
  revision 2018-02-22 {
    description
      "Added ip nat to interface Cellular";
  }
  revision 2018-01-25 {
    description
      "Added model for ip nat translation max-entries host";
  }
  revision 2017-11-27 {
    description
      "Added Change 25GE name";
  }
  revision 2017-11-14 {
    description
      "Add 40 and 100GE support";
  }
  revision 2017-11-10 {
    description
      "Add translation timeout support";
  }
  revision 2017-11-06 {
    description
      "Add ip nat to interface BDI";
  }
  revision 2017-10-06 {
    description
      "Model for ip nat route vrf <vrfname> <ipaddr> <netmask> global";
  }
  revision 2017-09-15 {
    description
      "This revison has changes for new 2gig interface addition";
  }
  revision 2017-08-16 {
    description
      "This revision has changes for new 5gig and 25gig interfaces addition";
  }
  revision 2017-08-03 {
    description
      " Static NAT with VRF and route-map results in incorrect CLI order";
  }
  revision 2017-06-16 {
    description
      "Native Yang Support for NATv6";
  }
  revision 2017-03-14 {
    description
      "Add Container node Pool, Oer and Overload
       under node Route-map.";
  }
  revision 2017-02-07 {
    description
      "Initial revision";
  }

  grouping config-interface-ip-nat-grouping {
    container nat {
      description
        "NAT interface commands";
      leaf allow-static-host {
        description
          "Allow static-ip clients";
        type empty;
      }
      leaf enable {
        description
          "Enable Address Translation (NVI)";
        type empty;
      }
      leaf stick {
        description
          "Stick(Hairpin) interface for address translations";
        type empty;
      }
      choice nat-choice {
        leaf inside {
          description
            "Inside interface for address translation";
          type empty;
        }
        leaf outside {
          description
            "Outside interface for address translation";
          type empty;
        }
      }
    }
  }

  grouping config-ip-nat-source-route-map-pool-base-grouping {
    leaf overload {
      description
        "Overload an address translation";
      type empty;
    }
    leaf extended {
      description
        "Overload extended";
      when '../overload';
      type empty;
    }
    leaf oer {
      description
        "Use with vtemplate only. On new translation, if OER BR is UP,
         OER will select IP from outgoing Interface.
         All packets matching translation are forwarded over Interface
         for duration of translation.";
      type empty;
    }
    leaf reversible {
      description
        "Allow out->in traffic";
      type empty;
    }
  }

  grouping config-ip-nat-source-pool-vrf-base-grouping {
    list vrf {
      description
        "Specify vrf";
      key "name";
      leaf name {
        must '/ios:native/ios:vrf/ios:definition[ios:name=current()] or /ios:native/ios:ip/ios:vrf[ios:name=current()]' {
          error-message "VRF must be created 1st, deleted last";
        }
        type string;
      }
      leaf match-in-vrf {
        description
          "Match incoming vrf";
        type empty;
      }
      leaf overload {
        description
          "Overload an address translation";
        type empty;
      }
    }
  }

  grouping old-ip-nat-source-pool-vrf-base-grouping {
    list vrf {
      status deprecated;
      description
        "Specify vrf";
      key "name";
      leaf name {
        status deprecated;
        must '/ios:native/ios:vrf/ios:definition[ios:name=current()] or /ios:native/ios:ip/ios:vrf[ios:name=current()]' {
          error-message "VRF must be created 1st, deleted last";
        }
        type string;
      }
      leaf match-in-vrf {
        status deprecated;
        description
          "Match incoming vrf";
        type empty;
      }
      leaf overload {
        status deprecated;
        description
          "Overload an address translation";
        type empty;
      }
    }
  }

  grouping config-ip-nat-source-route-map-pool-option-grouping {
    list redundancy {
      key "name";
      leaf name {
        type uint8 {
          range "1..2";
        }
      }
      list mapping-id {
        description
          "Associate a mapping id to this mapping";
        key "name";
        leaf name {
          type uint32 {
            range "1..2147483647";
          }
        }
        uses config-ip-nat-source-route-map-pool-base-grouping;
      }
    }
    uses config-ip-nat-source-route-map-pool-base-grouping;
  }

  grouping config-ip-nat-source-pool-vrf-grouping {
    list redundancy {
      key "name";
      leaf name {
        type uint8 {
          range "1..2";
        }
      }
      list mapping-id {
        description
          "Associate a mapping id to this mapping";
        key "name";
        leaf name {
          type uint32 {
            range "1..2147483647";
          }
        }
        uses config-ip-nat-source-pool-vrf-base-grouping;
      }
    }
    uses config-ip-nat-source-pool-vrf-base-grouping;
  }

  grouping old-ip-nat-source-pool-vrf-grouping {
    list redundancy {
      status deprecated;
      key "name";
      leaf name {
        status deprecated;
        type uint8 {
          range "1..2";
        }
      }
      list mapping-id {
        status deprecated;
        description
          "Associate a mapping id to this mapping";
        key "name";
        leaf name {
          status deprecated;
          type uint32 {
            range "1..2147483647";
          }
        }
        uses old-ip-nat-source-pool-vrf-base-grouping {
          status deprecated;
        }
      }
    }
    uses old-ip-nat-source-pool-vrf-base-grouping {
      status deprecated;
    }
  }

  grouping config-ip-nat-source-interface-base-grouping {
    leaf overload {
      description
        "Overload an address translation";
      mandatory true;
      type empty;
    }
    leaf extended {
      description
        "Overload extended";
      when '../overload';
      type empty;
    }
    leaf oer {
      description
        "Use with vtemplate only.  On new translation,
         if OER BR is UP, OER will select IP from outgoing
         Interface.  All packets matching translation are
         forwarded over Interface for duration of translation.";
      type empty;
    }
  }

  grouping old-ip-nat-source-interface-base-grouping {
    leaf overload {
      status deprecated;
      description
        "Overload an address translation";
      mandatory true;
      type empty;
    }
    leaf extended {
      status deprecated;
      description
        "Overload extended";
      when '../overload';
      type empty;
    }
    leaf oer {
      status deprecated;
      description
        "Use with vtemplate only.  On new translation,
         if OER BR is UP, OER will select IP from outgoing
         Interface.  All packets matching translation are
         forwarded over Interface for duration of translation.";
      type empty;
    }
  }

  grouping config-ip-nat-source-interface-vrf-grouping {
    list vrf {
      description
        "Specify vrf";
      key "vrf-name";
      leaf vrf-name {
        description
          "vrf name";
        type string;
      }
      uses config-ip-nat-source-interface-base-grouping;
    }
  }

  grouping old-ip-nat-source-interface-vrf-grouping {
    list vrf {
      status deprecated;
      description
        "Specify vrf";
      key "vrf-name";
      leaf vrf-name {
        status deprecated;
        description
          "vrf name";
        type string;
      }
      uses old-ip-nat-source-interface-base-grouping {
        status deprecated;
      }
    }
  }

  grouping config-ip-nat-source-list-pool-base-grouping {
    leaf overload {
      description
        "Overload an address translation";
      type empty;
    }
    leaf extended {
      description
        "Overload extended";
      when '../overload';
      type empty;
    }
    leaf oer {
      description
        "Use with vtemplate only. On new translation, if OER BR is UP,
         OER will select IP from outgoing Interface.
         All packets matching translation are forwarded over Interface
         for duration of translation.";
      type empty;
    }
  }

  grouping old-ip-nat-source-list-pool-base-grouping {
    leaf overload {
      status deprecated;
      description
        "Overload an address translation";
      type empty;
    }
    leaf extended {
      status deprecated;
      description
        "Overload extended";
      when '../overload';
      type empty;
    }
    leaf oer {
      status deprecated;
      description
        "Use with vtemplate only. On new translation, if OER BR is UP,
         OER will select IP from outgoing Interface.
         All packets matching translation are forwarded over Interface
         for duration of translation.";
      type empty;
    }
  }

  grouping config-ip-nat-source-list-pool-option-grouping {
    list redundancy {
      key "name";
      leaf name {
        type uint8 {
          range "1..2";
        }
      }
      list mapping-id {
        description
          "Associate a mapping id to this mapping";
        key "name";
        leaf name {
          type uint32 {
            range "1..2147483647";
          }
        }
        uses config-ip-nat-source-list-pool-base-grouping;
      }
    }
    uses config-ip-nat-source-list-pool-base-grouping;
  }

  grouping old-ip-nat-source-list-pool-option-grouping {
    list redundancy {
      status deprecated;
      key "name";
      leaf name {
        status deprecated;
        type uint8 {
          range "1..2";
        }
      }
      list mapping-id {
        status deprecated;
        description
          "Associate a mapping id to this mapping";
        key "name";
        leaf name {
          status deprecated;
          type uint32 {
            range "1..2147483647";
          }
        }
        uses old-ip-nat-source-list-pool-base-grouping {
          status deprecated;
        }
      }
    }
    uses old-ip-nat-source-list-pool-base-grouping {
      status deprecated;
    }
  }

  grouping config-ip-nat-inside-source-pool-with-vrf-grouping {
    container pool-with-vrf {
      list pool {
        description
          "Name pool of global addresses";
        key "name";
        leaf name {
          type string;
        }
        uses config-ip-nat-source-pool-vrf-grouping;
      }
    }
  }

  grouping old-ip-nat-inside-source-pool-with-vrf-grouping {
    container pool-with-vrf {
      status deprecated;
      list pool {
        status deprecated;
        description
          "Name pool of global addresses";
        key "name";
        leaf name {
          status deprecated;
          type string;
        }
        uses old-ip-nat-source-pool-vrf-grouping {
          status deprecated;
        }
      }
    }
  }

  grouping config-ip-nat-inside-source-interface-grouping {
    list interface {
      description
        "Specify interface for global address";
      key "name";
      leaf name {
        type string;
      }
      uses config-ip-nat-source-interface-base-grouping;
    }
    container interface-with-vrf {
      list interface {
        description
          "Specify interface for global address";
        key "name";
        leaf name {
          type string;
        }
        uses config-ip-nat-source-interface-vrf-grouping;
      }
    }
  }

  grouping old-ip-nat-inside-source-interface-grouping {
    list interface {
      status deprecated;
      description
        "Specify interface for global address";
      key "name";
      leaf name {
        status deprecated;
        type string;
      }
      uses old-ip-nat-source-interface-base-grouping {
        status deprecated;
      }
    }
    container interface-with-vrf {
      status deprecated;
      list interface {
        status deprecated;
        description
          "Specify interface for global address";
        key "name";
        leaf name {
          status deprecated;
          type string;
        }
        uses old-ip-nat-source-interface-vrf-grouping {
          status deprecated;
        }
      }
    }
  }

  grouping config-ip-nat-source-route-map-pool-interface-grouping {
    choice pool-or-interface {
      case pool-choice {
        list pool {
          description
            "Name pool of global addresses";
          max-elements 1;
          key "pool-name";
          leaf pool-name {
            description
              "Pool name for global addresses";
            type string;
          }
          uses config-ip-nat-source-route-map-pool-option-grouping;
        }
        uses config-ip-nat-inside-source-pool-with-vrf-grouping;
      }
      case interface-choice {
        uses config-ip-nat-inside-source-interface-grouping;
      }
    }
  }

  grouping config-ip-nat-source-list-pool-interface-grouping {
    choice pool-or-interface {
      status deprecated;
      case pool-choice {
        status deprecated;
        list pool {
          status deprecated;
          description
            "Name pool of global addresses";
          max-elements 1;
          key "name";
          leaf name {
            status deprecated;
            description
              "Pool name for global addresses";
            type string;
          }
          uses old-ip-nat-source-list-pool-option-grouping {
            status deprecated;
          }
        }
        uses old-ip-nat-inside-source-pool-with-vrf-grouping {
          status deprecated;
        }
      }
      case interface-choice {
        status deprecated;
        uses old-ip-nat-inside-source-interface-grouping {
          status deprecated;
        }
      }
    }
  }

  grouping ip-nat-translation-port-number-grouping {
    container protocol {
      leaf port-numer {
        description
          "Port number";
        type uint16 {
          range "1..63535";
        }
      }
      leaf time-val {
        description
          "Timeout in seconds";
        type uint32 {
          range "0..536870";
        }
      }
      leaf never {
        description
          "Never timeout";
        type empty;
      }
    }
  }

  grouping ip-nat-translation-timeout-grouping {
    leaf time-val {
      description
        "Timeout in seconds";
      type uint32 {
        range "0..536870";
      }
    }
    leaf never {
      description
        "Never timeout";
      type empty;
    }
  }

  grouping port-fwd-grouping {
    leaf mask {
      type union {
        type inet:ipv4-address;
        type string;
      }
    }
    container egress-interface {
      description
        "Specify interface for global address";
      uses ios-ifc:interface-grouping;
    }
    leaf extendable {
      description
        "Extend this translation when used";
      type empty;
    }
    leaf no-alias {
      description
        "Do not create an alias for the global address";
      type empty;
    }
    leaf no-payload {
      description
        "No translation of embedded address/port in the payload";
      type empty;
    }
    leaf route-map {
      description
        "Specify route-map";
      type string;
    }
    leaf reversible {
      when '../route-map';
      type empty;
    }
    leaf redundancy {
      description
        "NAT redundancy operation";
      type union {
        type uint8;
        type string;
      }
    }
    leaf mapping-id {
      description
        "Associate a mapping id to this mapping";
      when '../redundancy';
      type uint32 {
        range "1..2147483647";
      }
    }
    leaf stateless {
      description
        "No flow entries (session) for mapping";
      type empty;
    }
  }

  grouping config-ip-nat-source-static-transport-common-part-one-grouping {
    leaf proto {
      status obsolete;
      type enumeration {
        enum tcp;
        enum udp;
      }
    }
    leaf network-config {
      description
        "Subnet translation";
      type enumeration {
        enum network;
      }
    }
    leaf network {
      description
        "Subnet translation";
      status deprecated;
      type empty;
    }
    leaf local-port {
      status obsolete;
      type uint16 {
        range "1..65535";
      }
    }
    leaf mask {
      type union {
        type inet:ipv4-address;
        type string;
      }
    }
    leaf global-port {
      status obsolete;
      type uint16 {
        range "1..65535";
      }
    }
    container egress-interface {
      description
        "Specify interface for global address";
      uses ios-ifc:interface-grouping;
    }
    leaf extendable {
      description
        "Extend this translation when used";
      type empty;
    }
    leaf no-alias {
      description
        "Do not create an alias for the global address";
      type empty;
    }
    leaf no-payload {
      description
        "No translation of embedded address/port in the payload";
      type empty;
    }
    leaf route-map {
      description
        "Specify route-map";
      type string;
    }
    leaf reversible {
      when '../route-map';
      type empty;
    }
    leaf redundancy {
      description
        "NAT redundancy operation";
      type union {
        type uint8;
        type string;
      }
    }
    leaf mapping-id {
      description
        "Associate a mapping id to this mapping";
      when '../redundancy';
      type uint32 {
        range "1..2147483647";
      }
    }
    leaf stateless {
      description
        "No flow entries (session) for mapping";
      type empty;
    }
  }

  grouping config-ip-nat-source-static-transport-common-part-two-grouping {
    leaf forced {
      description
        "Delete this entry and its children, even if in use";
      type empty;
    }
    leaf overload {
      description
        "Overload an address translation";
      type empty;
    }
  }

  grouping nat-log-dest-grouping {
    container source {
      description
        "Specify source interface for DNS resolver";
      uses ios-ifc:interface-grouping;
    }
    leaf bind-only {
      description
        "Log NAT binding translations only";
      type empty;
    }
  }

  grouping ip-nat-pool-option-grouping {
    list redundancy-new {
      key "name";
      leaf name {
        type uint8 {
          range "1..2";
        }
      }
      list mapping-id-new {
        description
          "Associate a mapping id to this mapping";
        key "name";
        leaf name {
          type uint32 {
            range "1..2147483647";
          }
        }
        uses ip-nat-pool-base-grouping;
      }
    }
    uses ip-nat-pool-base-grouping;
  }

  grouping ip-nat-pool-base-grouping {
    list vrf-new {
      description
        "Specify vrf";
      key "name";
      leaf name {
        type string;
      }
      leaf match-in-vrf-new {
        description
          "Match incoming vrf";
        type empty;
      }
      leaf overload-new {
        description
          "Overload an address translation";
        type empty;
      }
      container egress-interface {
        description
          "Specify interface for global address";
        uses ios-ifc:interface-grouping;
      }
      leaf track {
        description
          "Object tracker";
        type uint16 {
          range "1..1000";
        }
      }
    }
    leaf overload-new {
      description
        "Overload an address translation";
      type empty;
    }
    container egress-interface {
      description
        "Specify interface for global address";
      uses ios-ifc:interface-grouping;
    }
    leaf match-in-vrf-new {
      description
        "Match incoming vrf";
      type empty;
    }
    leaf extended-new {
      description
        "Overload extended";
      when '../overload-new';
      type empty;
    }
    leaf oer-new {
      description
        "Use with vtemplate only. On new translation, if OER BR is UP,
         OER will select IP from outgoing Interface.
         All packets matching translation are forwarded over Interface
         for duration of translation.";
      type empty;
    }
    leaf reversible-new {
      description
        "Allow out->in traffic";
      type empty;
    }
  }

  grouping ip-nat-interface-option-grouping {
    list vrf-new {
      description
        "Specify vrf";
      key "name";
      leaf name {
        type string;
      }
      uses ip-nat-interface-base-grouping;
    }
    uses ip-nat-interface-base-grouping;
  }

  grouping ip-nat-interface-base-grouping {
    leaf overload-new {
      description
        "Overload an address translation";
      type empty;
    }
    container egress-interface {
      description
        "Specify interface for global address";
      uses ios-ifc:interface-grouping;
    }
    leaf extended-new {
      description
        "Overload extended";
      when '../overload-new';
      type empty;
    }
    leaf oer-new {
      description
        "Use with vtemplate only. On new translation, if OER BR is UP,
         OER will select IP from outgoing Interface.
         All packets matching translation are forwarded over Interface
         for duration of translation.";
      when '../overload-new';
      type empty;
    }
  }

  grouping config-ip-nat-grouping {
    container nat {
      description
        "NAT configuration commands";
      list pool {
        description
          "Define pool of addresses";
        key "id";
        leaf id {
          type string;
        }
        leaf start-address {
          type inet:ipv4-address;
        }
        leaf end-address {
          when '../start-address';
          type inet:ipv4-address;
        }
        choice prefix-choice {
          leaf netmask {
            description
              "Specify the network mask";
            type inet:ipv4-address;
          }
          leaf prefix-length {
            description
              "Specify the prefix length";
            type uint8 {
              range "1..32";
            }
          }
        }
        leaf accounting {
          description
            "Specify the accounting";
          type string;
        }
        choice nat-choice {
          leaf arp-ping {
            description
              "WLAN ARP Ping";
            type empty;
          }
          leaf type {
            description
              "Specify the pool type";
            type enumeration {
              enum match-host;
              enum rotary;
            }
          }
          leaf add-route {
            description
              "Add special route to Virtual Interface";
            type empty;
          }
        }
      }
      container inside {
        description
          "Inside address translation";
        container source {
          description
            "Source address translation";
          container list-pool {
            list list {
              description
                "Specify access list describing local addresses";
              key "id";
              leaf id {
                type union {
                  type uint16 {
                    range "1..2699";
                  }
                  type string;
                }
              }
              list pool {
                description
                  "Name pool of global addresses";
                key "name";
                leaf name {
                  type string;
                }
                uses ip-nat-pool-option-grouping;
              }
            }
          }
          container list-interface {
            list list {
              description
                "Specify access list describing local addresses";
              key "id";
              leaf id {
                type union {
                  type uint16 {
                    range "1..2699";
                  }
                  type string;
                }
              }
              list interface {
                description
                  "Specify interface for global address";
                key "name";
                leaf name {
                  type string;
                  must "not (starts-with(., 'Dialer')) or/ios:native/ios:interface/*[concat(local-name(), ios:name) = current()]" {
                    error-message "Dialer interface must be created first and deleted last.";
                  }
                  must "not (starts-with(., 'Loopback')) or/ios:native/ios:interface/*[concat(local-name(), ios:name) = current()]" {
                    error-message "Loopback interface must be created first and deleted last.";
                  }
                  must "not (starts-with(., 'Tunnel')) or/ios:native/ios:interface/*[concat(local-name(), ios:name) = current()]" {
                    error-message "Tunnel interface must be created first and deleted last.";
                  }
                  must "not (starts-with(., 'Port-channel')) or/ios:native/ios:interface/*[concat(local-name(), ios:name) = current()]" {
                    error-message "Port-channel interface must be created first and deleted last.";
                  }
                  must "not (starts-with(., 'Vlan')) or/ios:native/ios:interface/*[concat(local-name(), ios:name) = current()]" {
                    error-message "Vlan interface must be created first and deleted last.";
                  }
                  must "not (starts-with(., 'LISP')) or/ios:native/ios:interface/*[concat(local-name(), ios:name) = current()]" {
                    error-message "LISP interface must be created first and deleted last.";
                  }
                  must "not (starts-with(., 'Virtual-Template')) or/ios:native/ios:interface/*[concat(local-name(), ios:name) = current()]" {
                    error-message "Virtual-Template interface must be created first and deleted last.";
                  }
                  must "not (starts-with(., 'BDI')) or/ios:native/ios:interface/*[concat(local-name(), ios:name) = current()]" {
                    error-message "BDI interface must be created first and deleted last.";
                  }
                  must "not (starts-with(., 'Ethernet')) or/ios:native/ios:interface/*[concat(local-name(), ios:name) = current()]" {
                    error-message "Ethernet interface must be created first and deleted last.";
                  }
                  must "not (starts-with(., 'FastEthernet')) or/ios:native/ios:interface/*[concat(local-name(), ios:name) = current()]" {
                    error-message "FastEthernet interface must be created first and deleted last.";
                  }
                  must "not (starts-with(., 'GigabitEthernet')) or/ios:native/ios:interface/*[concat(local-name(), ios:name) = current()]" {
                    error-message "GigabitEthernet interface must be created first and deleted last.";
                  }
                  must "not (starts-with(., 'TenGigabitEthernet')) or/ios:native/ios:interface/*[concat(local-name(), ios:name) = current()]" {
                    error-message "TenGigabitEthernet interface must be created first and deleted last.";
                  }
                  must "not (starts-with(., 'FiveGigabitEthernet')) or/ios:native/ios:interface/*[concat(local-name(), ios:name) = current()]" {
                    error-message "FiveGigabitEthernet interface must be created first and deleted last.";
                  }
                  must "not (starts-with(., 'TwentyFiveGigE')) or/ios:native/ios:interface/*[concat(local-name(), ios:name) = current()]" {
                    error-message "TwentyFiveGigE interface must be created first and deleted last.";
                  }
                  must "not (starts-with(., 'TwoGigabitEthernet')) or/ios:native/ios:interface/*[concat(local-name(), ios:name) = current()]" {
                    error-message "TwoGigabitEthernet interface must be created first and deleted last.";
                  }
                  must "not (starts-with(., 'FortyGigabitEthernet')) or/ios:native/ios:interface/*[concat(local-name(), ios:name) = current()]" {
                    error-message "FortyGigabitEthernet interface must be created first and deleted last.";
                  }
                  must "not (starts-with(., 'HundredGigE')) or/ios:native/ios:interface/*[concat(local-name(), ios:name) = current()]" {
                    error-message "HundredGigE interface must be created first and deleted last.";
                  }
                }
                uses ip-nat-interface-option-grouping;
              }
            }
          }
          list list {
            status deprecated;
            description
              "Specify access list describing local addresses";
            key "id";
            leaf id {
              status deprecated;
              type union {
                type uint16 {
                  range "1..2699";
                }
                type string;
              }
            }
            uses config-ip-nat-source-list-pool-interface-grouping {
              status deprecated;
            }
          }
          list route-map {
            description
              "Specify route-map";
            key "route-map-name";
            leaf route-map-name {
              description
                "Route-map name";
              type string;
            }
            uses config-ip-nat-source-route-map-pool-interface-grouping;
          }
          container static {
            description
              "Specify static local->global mapping";
            list nat-static-transport-list-with-vrf {
              key "local-ip global-ip vrf";
              leaf local-ip {
                type inet:ipv4-address;
              }
              leaf global-ip {
                type inet:ipv4-address;
              }
              leaf vrf {
                description
                  "Specify vrf";
                type string;
              }
              uses config-ip-nat-source-static-transport-common-part-one-grouping {
                refine "mask";
              }
              leaf match-in-vrf {
                description
                  "Match incoming vrf";
                when '../vrf';
                type empty;
              }
              uses config-ip-nat-source-static-transport-common-part-two-grouping;
              leaf pool {
                description
                  "Name pool of local addresses";
                type string;
              }
              leaf track {
                description
                  "Object tracker";
                type uint16 {
                  range "1..1000";
                }
              }
            }
            list nat-static-transport-list-port-fwd {
              key "protocol local-ip local-port global-ip global-port";
              leaf protocol {
                type enumeration {
                  enum tcp;
                  enum udp;
                }
              }
              leaf local-ip {
                type inet:ipv4-address;
              }
              leaf local-port {
                type uint16 {
                  range "1..65535";
                }
              }
              leaf global-ip {
                type inet:ipv4-address;
              }
              leaf global-port {
                type uint16 {
                  range "1..65535";
                }
              }
              leaf network {
                description
                  "Subnet translation";
                type empty;
              }
              uses port-fwd-grouping;
              uses config-ip-nat-source-static-transport-common-part-two-grouping;
              leaf pool {
                description
                  "Name pool of local addresses";
                type string;
              }
            }
            list nat-static-transport-list-with-vrf-port-fwd {
              key "protocol local-ip local-port global-ip global-port vrf";
              leaf protocol {
                type enumeration {
                  enum tcp;
                  enum udp;
                }
              }
              leaf local-ip {
                type inet:ipv4-address;
              }
              leaf local-port {
                type uint16 {
                  range "1..65535";
                }
              }
              leaf global-ip {
                type inet:ipv4-address;
              }
              leaf global-port {
                type uint16 {
                  range "1..65535";
                }
              }
              leaf vrf {
                description
                  "Specify vrf";
                type string;
              }
              leaf network {
                description
                  "Subnet translation";
                type empty;
              }
              uses port-fwd-grouping;
              leaf match-in-vrf {
                description
                  "Match incoming vrf";
                when '../vrf';
                type empty;
              }
              uses config-ip-nat-source-static-transport-common-part-two-grouping;
              leaf pool {
                description
                  "Name pool of local addresses";
                type string;
              }
            }
            list nat-static-transport-list {
              key "local-ip global-ip";
              leaf local-ip {
                type inet:ipv4-address;
              }
              leaf global-ip {
                type inet:ipv4-address;
              }
              uses config-ip-nat-source-static-transport-common-part-one-grouping;
              uses config-ip-nat-source-static-transport-common-part-two-grouping;
              leaf pool {
                description
                  "Name pool of local addresses";
                type string;
              }
            }
            list nat-static-proto-transport-interface-list {
              key "proto local-ip local-port";
              leaf proto {
                type enumeration {
                  enum tcp;
                  enum udp;
                }
              }
              leaf local-ip {
                type inet:ipv4-address;
              }
              leaf local-port {
                type uint16 {
                  range "1..65535";
                }
              }
              container interface {
                description
                  "Specify interface for global address";
                uses ios-ifc:interface-grouping;
              }
              leaf global-port {
                type uint16 {
                  range "1..65535";
                }
              }
            }
            list nat-static-transport-interface-list {
              key "local-ip";
              leaf local-ip {
                type inet:ipv4-address;
              }
              container interface {
                description
                  "Specify interface for global address";
                uses ios-ifc:interface-grouping;
              }
            }
          }
        }
        container destination {
          description
            "Destination address translation";
          list list {
            description
              "Specify access list describing global addresses";
            key "id";
            leaf id {
              type union {
                type uint16 {
                  range "1..2699";
                }
                type string;
              }
            }
            leaf pool {
              description
                "Name pool of local addresses";
              type string;
            }
            leaf redundancy {
              description
                "NAT redundancy operation";
              type uint8 {
                range "1..2";
              }
            }
            leaf mapping-id {
              description
                "Associate a mapping id to this mapping";
              type uint32 {
                range "1..2147483647";
              }
            }
          }
        }
      }
      container outside {
        description
          "Outside address translation";
        container source {
          description
            "Source address translation";
          container static {
            description
              "Specify static global->local mapping";
            list nat-static-transport-list-no-vrf {
              key "global-ip local-ip";
              leaf global-ip {
                type inet:ipv4-address;
              }
              leaf local-ip {
                type inet:ipv4-address;
              }
              leaf extendable {
                description
                  "Extend this translation when used";
                type empty;
              }
              leaf no-payload {
                description
                  "No translation of embedded address/port in the payload";
                type empty;
              }
              leaf match-in-vrf {
                description
                  "Match incoming vrf";
                type empty;
              }
              leaf pool {
                description
                  "Name pool of local addresses";
                type string;
              }
            }
            list nat-static-transport-list-with-vrf {
              key "global-ip local-ip vrf";
              leaf global-ip {
                type inet:ipv4-address;
              }
              leaf local-ip {
                type inet:ipv4-address;
              }
              leaf vrf {
                type string;
              }
              leaf extendable {
                description
                  "Extend this translation when used";
                type empty;
              }
              leaf no-payload {
                description
                  "No translation of embedded address/port in the payload";
                type empty;
              }
              leaf match-in-vrf {
                description
                  "Match incoming vrf";
                type empty;
              }
              leaf pool {
                description
                  "Name pool of local addresses";
                type string;
              }
            }
            list nat-static-transport-list {
              status deprecated;
              key "global-ip local-ip";
              leaf global-ip {
                status deprecated;
                type inet:ipv4-address;
              }
              leaf local-ip {
                status deprecated;
                type inet:ipv4-address;
              }
              leaf vrf {
                status deprecated;
                description
                  "Specify vrf";
                type string;
              }
              leaf extendable {
                status deprecated;
                description
                  "Extend this translation when used";
                type empty;
              }
              leaf no-payload {
                status deprecated;
                description
                  "No translation of embedded address/port in the payload";
                type empty;
              }
              leaf match-in-vrf {
                status deprecated;
                description
                  "Match incoming vrf";
                type empty;
              }
            }
          }
          container list-pool {
            list list {
              description
                "Specify access list describing global addresses";
              key "id";
              leaf id {
                type union {
                  type uint16 {
                    range "1..2699";
                  }
                  type string;
                }
              }
              list pool {
                description
                  "Name pool of global addresses";
                key "name";
                leaf name {
                  type leafref {
                    path "/ios:native/ios:ip/ios-nat:nat/ios-nat:pool/ios-nat:id";
                  }
                }
                leaf mapping-id {
                  description
                    "Associate a mapping id to this mapping";
                  type uint32 {
                    range "1..2147483647";
                  }
                }
                leaf vrf {
                  description
                    "Specify vrf";
                  type string;
                }
                leaf overload {
                  description
                    "overload an address translation";
                  type empty;
                }
                leaf match-in-vrf {
                  description
                    "Match incoming vrf";
                  type empty;
                }
                leaf add-route {
                  description
                    "Add a static route for outside local address";
                  type empty;
                }
              }
            }
          }
        }
        list list {
          description
            "Specify access list describing global addresses";
          key "id";
          leaf id {
            type union {
              type uint16 {
                range "1..2699";
              }
              type string;
            }
          }
          leaf pool {
            description
              "Name pool of local addresses";
            type string;
          }
          leaf mapping-id {
            description
              "Associate a mapping id to this mapping";
            type uint32 {
              range "1..2147483647";
            }
          }
          leaf vrf {
            description
              "Specify vrf";
            type string;
          }
          leaf add-route {
            description
              "Add a static route for outside local address";
            type empty;
          }
        }
        list route-map {
          description
            "Specify route-map";
          key "id";
          leaf id {
            type string;
          }
          leaf pool {
            description
              "Name pool of local addresses";
            type string;
          }
          leaf mapping-id {
            description
              "Associate a mapping id to this mapping";
            type uint32 {
              range "1..2147483647";
            }
          }
          leaf vrf {
            description
              "Specify vrf";
            type string;
          }
          leaf add-route {
            description
              "Add a static route for outside local address";
            type empty;
          }
        }
      }
      container translation {
        container dns-timeout {
          description
            "Specify timeout for NAT DNS flows";
          uses ip-nat-translation-timeout-grouping;
        }
        container finrst-timeout {
          description
            "Specify timeout for NAT TCP flows after a FIN or RST";
          uses ip-nat-translation-timeout-grouping;
        }
        container icmp-timeout {
          description
            "Specify timeout for NAT ICMP flows";
          uses ip-nat-translation-timeout-grouping;
        }
        container routemap-entry-timeout {
          description
            "Specify timeout for routemap created half entry";
          uses ip-nat-translation-timeout-grouping;
        }
        container syn-timeout {
          description
            "Specify timeout for NAT TCP flows after a SYNand no further data";
          uses ip-nat-translation-timeout-grouping;
        }
        container tcp-timeout {
          description
            "Specify timeout for NAT TCP/UDP port specific flows";
          uses ip-nat-translation-timeout-grouping;
        }
        container timeout {
          description
            "Specify timeout for dynamic NAT translations";
          uses ip-nat-translation-timeout-grouping;
        }
        container udp-timeout {
          description
            "Specify timeout for NAT UDP flows";
          uses ip-nat-translation-timeout-grouping;
        }
        container port-timeout {
          description
            "Specify timeout for NAT TCP/UDP port specific flows";
          container tcp {
            description
              "TCP protocol";
            uses ip-nat-translation-port-number-grouping;
          }
          container udp {
            description
              "UDP protocol";
            uses ip-nat-translation-port-number-grouping;
          }
        }
        container max-entries {
          description
            "Specify maximum number of NAT entries";
          list host {
            description
              "Specify per-host NAT entry limit";
            key "host-ip";
            leaf host-ip {
              type inet:ipv4-address;
            }
            leaf number-of-entries {
              description
                "Number of entries";
              type uint32 {
                range "1..2147483647";
              }
            }
          }
          leaf num-entries {
            description
              "Number of entries";
            type uint32 {
              range "1..2147483637";
            }
          }
          leaf all-host {
            description
              "Specify maximum number of NAT entries for each host";
            type uint32 {
              range "1..2147483637";
            }
          }
          leaf all-vrf {
            description
              "Specify maximum number of NAT entries for each vrf";
            type uint32 {
              range "1..2147483637";
            }
          }
          list redundancy {
            description
              "Specify maximum number of NAT entries for RG";
            ordered-by user;
            key "id";
            leaf id {
              type enumeration {
                enum 1;
                enum 2;
              }
            }
            leaf num-entries {
              description
                "Number of entries";
              type uint32 {
                range "1..2147483637";
              }
            }
          }
          list list {
            description
              "Specify access list based NAT entry limit";
            key "id";
            leaf id {
              type union {
                type uint32 {
                  range "1..199";
                }
                type string;
              }
            }
            leaf num-entries {
              description
                "Number of entries";
              type uint32 {
                range "1..2147483637";
              }
            }
          }
          list vrf {
            description
              "Specify per-VRF NAT entry limit";
            key "id";
            leaf id {
              must '/ios:native/ios:vrf/ios:definition[ios:name=current()] or /ios:native/ios:ip/ios:vrf[ios:name=current()]' {
                error-message "VRF must be created 1st, deleted last";
              }
              type string;
            }
            leaf num-entries {
              description
                "Number of entries";
              type uint32 {
                range "1..2147483637";
              }
            }
          }
        }
      }
      list route {
        description
          "Establish NAT static routes";
        ordered-by user;
        key "vrf ipaddr mask";
        leaf vrf {
          description
            "Configure NAT static route for a VPN Routing/Forwarding instance";
          must "(/ios:native/ios:vrf/ios:definition[ios:name=current()] and (/ios:native/ios:vrf/ios:definition[ios:name=current()]/ios:address-family/ios:ipv4) or
                (/ios:native/ios:vrf/ios:definition[ios:name=current()]/ios:address-family/ios:ipv6)) or /ios:native/ios:ip/ios:vrf[ios:name=current()]" {
            error-message "VRF must be created first, deleted last";
          }
          type string;
        }
        leaf ipaddr {
          description
            "IP address";
          type inet:ipv4-address;
        }
        leaf mask {
          description
            "Network mask";
          type inet:ipv4-address;
        }
        leaf global {
          description
            "Next hop address is global";
          type empty;
        }
      }
      container settings {
        description
          "NAT general settings";
        leaf central-policy {
          description
            "centralized policy";
          type empty;
        }
        container mode {
          description
            "NAT operating mode";
          choice choice-mode {
            leaf cgn {
              description
                "The carrier grade NAT operating mode";
              type empty;
            }
            leaf default {
              description
                "The default NAT operating mode";
              type empty;
            }
          }
        }
        container cfg-check {
          description
            "NAT setting for configuration removal check";
          leaf static-map-removal {
            description
              "static map removal";
            type empty;
          }
        }
        leaf gatekeeper-size {
          description
            "Gatekeeper cache size";
          type uint32 {
            range "512..262144";
          }
        }
        leaf nonpatdrop {
          description
            "Drop non PAT packets";
          type empty;
        }
        leaf high-performance {
          description
            "enable NAT high performance call setup rate";
          type empty;
        }
        leaf nonpatlog-disable {
          description
            "Disable non PAT log";
          type empty;
        }
        container trans-err-limit {
          description
            "Log rate limit for translation error";
          leaf per-ip-pool {
            description
              "per client address and pool";
            type uint16 {
              range "1..10080";
            }
          }
        }
        container pool {
          description
            "Pool related settings";
          container watermark {
            description
              "Specify high/low watermark";
            leaf high {
              description
                "high watermark percentage";
              type uint32 {
                range "1..100";
              }
            }
            leaf low {
              description
                "low watermark percentage";
              type uint32 {
                range "1..100";
              }
            }
          }
        }
        container scale {
          description
            "Increase NAT scale";
          leaf bind {
            description
              "Scale bind";
            type empty;
          }
        }
        container support {
          description
            "NAT configuration support";
          container mapping {
            description
              "NAT mapping configuration support";
            leaf outside {
              description
                "NAT outside mapping configuration support.";
              type empty;
            }
          }
        }
        container pap {
          description
            "NAT paired address pooling";
          presence "true";
          leaf limit {
            description
              "Limit of the number of local addresses per global address";
            type enumeration {
              enum 1000;
              enum 120;
              enum 250;
              enum 30;
              enum 500;
              enum 60;
            }
          }
          choice bpa-pool-choice {
            case bpa-case {
              leaf bpa {
                description
                  "NAT bulk port allocation";
                type empty;
              }
              leaf set-size {
                description
                  "Number of ports in each port block";
                when '../bpa';
                type enumeration {
                  enum 128;
                  enum 256;
                  enum 512;
                  enum 64;
                  enum 1024;
                }
              }
              leaf step-size {
                description
                  "Port step size";
                type enumeration {
                  enum 1;
                  enum 2;
                  enum 4;
                  enum 8;
                  enum 16;
                }
              }
              leaf single-set {
                description
                  "Indicates that a user is restricted to a single port set";
                type empty;
              }
            }
            case pool-case {
              leaf pool {
                description
                  "Indicates that a user is restricted to a pool PAP";
                type empty;
              }
            }
          }
        }
        container interface-overload {
          description
            "Port setting for interface overload mappings";
          container block {
            description
              "Block a Port";
            container port {
              description
                "High port";
              leaf-list tcp {
                description
                  "Transmission Control Protocol";
                type uint32 {
                  range "1024..65535";
                }
              }
              leaf-list udp {
                description
                  "User Datagram Protocol";
                type uint32 {
                  range "1024..65535";
                }
              }
            }
          }
          container port {
            description
              "Block a Port";
            container range {
              description
                "High port range";
              leaf start {
                type uint32 {
                  range "1024..65536";
                }
              }
              leaf end {
                type uint32 {
                  range "1024..65536";
                }
              }
            }
          }
        }
      }
      container create {
        description
          "Create flow entries";
        leaf flow-entries {
          description
            "NAT create flow based entries";
          type empty;
        }
      }
      container switchover {
        description
          "Session replication";
        container replication {
          description
            "Session replication";
          container http {
            description
              "HTTP session replication";
            presence "true";
            leaf port {
              description
                "port";
              type uint32 {
                range "1..65535";
              }
            }
          }
        }
      }
      container service {
        description
          "Special translation for application using non-standard port";
        leaf H225 {
          description
            "H.225  protocol";
          type empty;
        }
        leaf all-algs {
          description
            "Enable all NAT Application Level Gateways";
          type empty;
        }
        container dns {
          description
            "DNS protocol";
          leaf tcp {
            description
              "TCP protocol";
            type empty;
          }
          leaf udp {
            description
              "UDP protocol";
            type empty;
          }
        }
        leaf dns-reset-ttl {
          description
            "Reset dns canonical name ttl value";
          type empty;
        }
        container dns-v6-config {
          description
            "dns v6 packet processing";
          presence "true";
          leaf list {
            description
              "Specify IPv6 access list describing DNS server addresses";
            type string;
          }
        }
        leaf dns-v6 {
          status deprecated;
          description
            "dns v6 packet processing";
          type empty;
        }
        leaf ftp {
          description
            "ftp protocol";
          type empty;
        }
        container fullrange {
          description
            "allocate all available port of 1024 to 65535";
          container tcp {
            description
              "TCP protocol";
            leaf-list port {
              description
                "TCP port number";
              type uint16 {
                range "1..511";
              }
            }
          }
          container udp {
            description
              "UDP protocol";
            leaf-list port {
              description
                "UDP port number";
              type uint16 {
                range "1..511";
              }
            }
          }
        }
        leaf gatekeeper {
          description
            "Gatekeeper protocol";
          type empty;
        }
        container ipsec-esp {
          description
            "ipsec esp packet processing options";
          leaf enable {
            description
              "enable esp processing";
            type empty;
          }
        }
        leaf ldap {
          description
            "LDAP protocol";
          type empty;
        }
        container modify-in-progress {
          description
            "Packet processing options when config is being modified and/or cleared";
          leaf drop {
            description
              "Drop all NAT packets when a modify is in progress";
            type empty;
          }
        }
        container list {
          list esp-ike-list {
            description
              "Specify access list describing global addresses";
            key "type";
            leaf type {
              type enumeration {
                enum ESP;
                enum IKE;
              }
            }
            leaf acl {
              mandatory true;
              type union {
                type uint32 {
                  range "1..2699";
                }
                type string;
              }
            }
            leaf spi-match {
              when "../type = 'ESP'";
              description
                "SPI matching IPsec passthrough";
              type empty;
            }
            leaf preserve-port {
              when "../type = 'IKE'";
              description
                "preserve IKE port, as required by some IPsec servers";
              type empty;
            }
          }
          list ftp-list {
            description
              "Specify access list describing global addresses";
            key "id";
            leaf id {
              type union {
                type uint32 {
                  range "1..2699";
                }
                type string;
              }
            }
            container ftp {
              description
                "ftp protocol";
              container tcp {
                description
                  "TCP protocol";
                leaf-list port {
                  description
                    "TCP port number";
                  type uint32 {
                    range "1..65535";
                  }
                }
              }
            }
          }
        }
        container msrpc {
          description
            "MS-RPC protocol";
          leaf tcp {
            description
              "TCP protocol";
            type empty;
          }
        }
        leaf multi-wan-link {
          description
            "multiple wan link support for outside interface";
          type empty;
        }
        leaf netbios-dgm {
          description
            "NetBios datagram protocol";
          type empty;
        }
        container netbios-ns {
          description
            "NetBios name protocol";
          leaf tcp {
            description
              "TCP protocol";
            type empty;
          }
          leaf udp {
            description
              "UDP protocol";
            type empty;
          }
        }
        leaf netbios-ssn {
          description
            "NetBios session protocol";
          type empty;
        }
        leaf pptp {
          description
            "Point-to-Point Tunneling protocol";
          type empty;
        }
        leaf ras {
          description
            "H323-RAS protocol";
          type empty;
        }
        leaf rcmd {
          description
            "RCMD protocol";
          type empty;
        }
        container rtsp {
          description
            "RTSP protocol";
          leaf tcp {
            description
              "TCP protocol";
            type empty;
          }
          leaf udp {
            description
              "UDP protocol";
            type empty;
          }
        }
        container sip {
          description
            "SIP protocol";
          container tcp {
            description
              "TCP protocol";
            leaf-list port {
              description
                "TCP port number";
              type uint32 {
                range "1..65535";
              }
            }
          }
          container udp {
            description
              "UDP protocol";
            leaf-list port {
              description
                "UDP port number";
              type uint32 {
                range "1..65535";
              }
            }
          }
        }
        container skinny {
          description
            "skinny protocol";
          container tcp {
            description
              "TCP protocol";
            leaf-list port {
              description
                "TCP port number";
              type uint32 {
                range "1..65535";
              }
            }
          }
        }
        leaf tftp {
          description
            "TFTP Protocol";
          type empty;
        }
        container sunrpc {
          description
            "Enable SUN RPC protocol";
          leaf tcp {
            description
              "TCP protocol";
            type empty;
          }
          leaf udp {
            description
              "UDP protocol";
            type empty;
          }
        }
      }
      container log {
        description
          "NAT Logging";
        must '(count(/ios:native/ios:ip/ios-nat:nat/ios-nat:log/ios-nat:translations/ios-nat:flow-export/ios-nat:v9/ios-nat:udp/ios-nat:destination) + count(/ios:native/ios:ip/ios-nat:nat/ios-nat:log/ios-nat:translations/ios-nat:flow-export/ios-nat:v9/ios-nat:udp/ios-nat:destination-vrf/ios-nat:destination) + count(/ios:native/ios:ip/ios-nat:nat/ios-nat:log/ios-nat:translations/ios-nat:flow-export/ios-nat:v9/ios-nat:udp/ios-nat:ipv6-destination) + count(/ios:native/ios:ip/ios-nat:nat/ios-nat:log/ios-nat:translations/ios-nat:flow-export/ios-nat:v9/ios-nat:udp/ios-nat:ipv6-destination-vrf/ios-nat:ipv6-destination) ) <= 4' {
          error-message "ip nat log translations flow-export can only configure upto 4 different destination combinations";
        }
        container translations {
          description
            "NAT Logging Translations";
          choice syslog-or-flow-export {
            case syslog-choice {
              container syslog {
                description
                  "NAT log translations using syslog";
                presence "true";
                leaf bind-only {
                  description
                    "Log NAT binding translations only";
                  type empty;
                }
              }
            }
            case flow-export-choice {
              container flow-export {
                description
                  "NAT log translations using flow export";
                container v9 {
                  description
                    "Exporter version 9 format";
                  container udp {
                    description
                      "UDP protocol";
                    list destination {
                      description
                        "netflow record export destination";
                      key "address port";
                      leaf address {
                        description
                          "IP address";
                        type inet:ipv4-address;
                      }
                      leaf port {
                        description
                          "Valid Port Number";
                        type uint16 {
                          range "1..65535";
                        }
                      }
                      uses nat-log-dest-grouping;
                    }
                    container destination-vrf {
                      list destination {
                        description
                          "netflow record export destination";
                        key "address port vrf";
                        leaf address {
                          description
                            "IP address";
                          type inet:ipv4-address;
                        }
                        leaf port {
                          description
                            "Valid Port Number";
                          type uint16 {
                            range "1..65535";
                          }
                        }
                        leaf vrf {
                          description
                            "Optional VRF label";
                          must '/ios:native/ios:vrf/ios:definition[ios:name=current()] or /ios:native/ios:ip/ios:vrf[ios:name=current()]' {
                            error-message "VRF must be created 1st, deleted last";
                          }
                          type string {
                            length "1..32";
                          }
                        }
                        uses nat-log-dest-grouping;
                      }
                    }
                    list ipv6-destination {
                      description
                        "netflow record export destination";
                      key "address port";
                      leaf address {
                        description
                          "IP address";
                        type inet:ipv6-address;
                      }
                      leaf port {
                        description
                          "Valid Port Number";
                        type uint16 {
                          range "1..65535";
                        }
                      }
                      uses nat-log-dest-grouping;
                    }
                    container ipv6-destination-vrf {
                      list ipv6-destination {
                        description
                          "netflow record export destination";
                        key "address port vrf";
                        leaf address {
                          description
                            "IP address";
                          type inet:ipv6-address;
                        }
                        leaf port {
                          description
                            "Valid Port Number";
                          type uint16 {
                            range "1..65535";
                          }
                        }
                        leaf vrf {
                          description
                            "Optional VRF label";
                          must '/ios:native/ios:vrf/ios:definition[ios:name=current()] or /ios:native/ios:ip/ios:vrf[ios:name=current()]' {
                            error-message "VRF must be created 1st, deleted last";
                          }
                          type string {
                            length "1..32";
                          }
                        }
                        uses nat-log-dest-grouping;
                      }
                    }
                  }
                }
              }
            }
          }
        }
      }
    }
  }

  grouping config-nat66-grouping {
    container nat66 {
      description
        "NAT66 configuration commands";
      container prefix {
        description
          "NAT66 prefix";
        container inside-no-vrf {
          list inside {
            description
              "inside prefix";
            key "inside-pfx";
            leaf inside-pfx {
              description
                "IPv6 prefix";
              type ios-types:ipv6-prefix;
            }
            leaf outside {
              description
                "outside prefix";
              type union {
                type ios-types:ipv6-prefix;
                type string;
              }
            }
          }
        }
        container inside-with-vrf {
          list inside {
            description
              "inside prefix";
            key "inside-pfx vrf";
            leaf inside-pfx {
              description
                "IPv6 prefix";
              type ios-types:ipv6-prefix;
            }
            leaf vrf {
              description
                "Optional VRF label";
              must '/ios:native/ios:vrf/ios:definition[ios:name=current()] or /ios:native/ios:ip/ios:vrf[ios:name=current()]' {
                error-message "VRF must be created 1st, deleted last";
              }
              type string {
                length "1..32";
              }
            }
            leaf outside {
              description
                "outside prefix";
              type union {
                type ios-types:ipv6-prefix;
                type string;
              }
            }
          }
        }
        list inside {
          status deprecated;
          description
            "inside prefix";
          key "inside-pfx";
          leaf inside-pfx {
            status deprecated;
            description
              "IPv6 prefix";
            type ios-types:ipv6-prefix;
          }
          leaf outside {
            status deprecated;
            description
              "outside prefix";
            type ios-types:ipv6-prefix;
          }
        }
      }
      list route {
        description
          "Establish NAT64 DIA routes";
        key "vrf ipv6-prefix";
        leaf vrf {
          description
            "Configure NAT64 DIA route for a VPN Routing/Forwarding instance";
          must "(/ios:native/ios:vrf/ios:definition[ios:name=current()] and
                 /ios:native/ios:vrf/ios:definition[ios:name=current()]/ios:address-family/ios:ipv6)" {
            error-message "IPV6 VRF must be created first, deleted last";
          }
          type string;
        }
        leaf ipv6-prefix {
          description
            "IPV6 prefix";
          type ios-types:ipv6-prefix;
        }
        leaf global {
          description
            "Next hop address is global";
          type empty;
        }
      }
      container nd {
        leaf enable {
          type boolean;
          default "true";
        }
      }
      leaf max-vpn {
        type uint8 {
          range "1..250";
        }
      }
      leaf outside {
        status deprecated;
        type empty;
      }
    }
  }

  grouping config-interface-nat66-grouping {
    leaf nat66 {
      description
        "NAT66 interface commands";
      type enumeration {
        enum inside;
        enum outside;
      }
    }
  }

  grouping config-interface-nat64-grouping {
    container nat64 {
      description
        "NAT64 interface commands";
      leaf enable {
        description
          "Enable NAT64 on interface";
        type empty;
      }
      container prefix {
        description
          "NAT64 stateful prefix";
        container stateful {
          description
            "NAT64 prefix stateful";
          leaf ipv6-prefix {
            description
              "IPv6 prefix";
            type ios-types:ipv6-prefix;
          }
          leaf vrf {
            status obsolete;
            description
              "Configure NAT static route for a VPN Routing/Forwarding instance";
            must "(/ios:native/ios:vrf/ios:definition[ios:name=current()] and (/ios:native/ios:vrf/ios:definition[ios:name=current()]/ios:address-family/ios:ipv4) or
                  (/ios:native/ios:vrf/ios:definition[ios:name=current()]/ios:address-family/ios:ipv6)) or /ios:native/ios:ip/ios:vrf[ios:name=current()]" {
              error-message "VRF must be created first, deleted last";
            }
            type string;
          }
        }
      }
    }
  }

  grouping config-nat64-v6v4-map-base-grouping {
    list vrf {
      description
        "Specify vrf";
      key "name";
      leaf name {
        must "(/ios:native/ios:vrf/ios:definition[ios:name=current()] and (/ios:native/ios:vrf/ios:definition[ios:name=current()]/ios:address-family/ios:ipv4) or
              (/ios:native/ios:vrf/ios:definition[ios:name=current()]/ios:address-family/ios:ipv6)) or /ios:native/ios:ip/ios:vrf[ios:name=current()]" {
          error-message "VRF must be created first, deleted last";
        }
        type string;
      }
      leaf overload {
        description
          "Overload an address translation";
        type empty;
      }
    }
    leaf overload {
      description
        "Overload an address translation";
      type empty;
    }
  }

  grouping config-nat64-v6v4-map-grouping {
    choice pool-or-interface {
      case pool-choice {
        list pool {
          description
            "Name pool of global addresses";
          key "name";
          leaf name {
            type string;
          }
          uses config-nat64-v6v4-map-base-grouping;
        }
      }
      case interface-choice {
        list interface {
          description
            "Specify interface for global address";
          key "name";
          leaf name {
            type string;
          }
          list vrf {
            status deprecated;
            description
              "Specify vrf";
            key "name";
            leaf name {
              status deprecated;
              type string;
            }
            leaf overload {
              status deprecated;
              description
                "Overload an address translation";
              type empty;
            }
          }
          leaf overload {
            description
              "Overload an address translation";
            type empty;
          }
        }
      }
    }
  }

  grouping config-nat64-grouping {
    container nat64 {
      description
        "NAT64 configuration commands";
      container v4 {
        description
          "IPv4 configuration";
        list pool {
          description
            "Define pool of addresses";
          key "pool-name";
          leaf pool-name {
            description
              "NAT64 pool";
            type string;
          }
          leaf start-address {
            description
              "Starting address of pool address range";
            type inet:ipv4-address;
          }
          leaf end-address {
            description
              "Ending address of pool address range";
            when '../start-address';
            type inet:ipv4-address;
          }
        }
      }
      container v6v4 {
        description
          "IPv6 to IPv4 mapping";
        container list {
          description
            "Specify access list describing local addresses";
          list list {
            key "id";
            leaf id {
              type union {
                type uint16 {
                  range "1..2699";
                }
                type string;
              }
            }
            uses config-nat64-v6v4-map-grouping;
          }
        }
        container static {
          container ipv6address {
            list ipv6address {
              key "ipv6-address";
              leaf ipv6-address {
                description
                  "IPv6 Address";
                type inet:ipv6-address;
              }
              leaf ipv4-address {
                description
                  "IPv4 Address";
                type inet:ipv4-address;
              }
            }
          }
          container tcp {
            list tcp {
              key "ipv6-address";
              leaf ipv6-address {
                description
                  "IPv6 Address";
                type inet:ipv6-address;
              }
              leaf v6-port-number {
                description
                  "TCP v6 port";
                type uint16 {
                  range "1..65535";
                }
              }
              leaf ipv4-address {
                description
                  "IPv4 Address";
                type inet:ipv4-address;
              }
              leaf v4-port-number {
                description
                  "TCP v4 port";
                type uint16 {
                  range "1..65535";
                }
              }
            }
          }
          container udp {
            list udp {
              key "ipv6-address";
              leaf ipv6-address {
                description
                  "IPv6 Address";
                type inet:ipv6-address;
              }
              leaf v6-port-number {
                description
                  "UDP v6 port";
                type uint16 {
                  range "1..65535";
                }
              }
              leaf ipv4-address {
                description
                  "IPv4 Address";
                type inet:ipv4-address;
              }
              leaf v4-port-number {
                description
                  "UDP v4 port";
                type uint16 {
                  range "1..65535";
                }
              }
            }
          }
        }
      }
      container v4v6 {
        description
          "IPv4 to IPv6 mapping";
        container static {
          container ipv4address {
            list ipv4address {
              key "ipv4-address";
              leaf ipv4-address {
                description
                  "IPv4 Address";
                type inet:ipv4-address;
              }
              leaf ipv6-address {
                description
                  "IPv6 Address";
                type inet:ipv6-address;
              }
            }
          }
          container tcp {
            list tcp {
              key "ipv4-address";
              leaf ipv4-address {
                description
                  "IPv4 Address";
                type inet:ipv4-address;
              }
              leaf v4-port-number {
                description
                  "TCP v4 port";
                type uint16 {
                  range "1..65535";
                }
              }
              leaf ipv6-address {
                description
                  "IPv6 Address";
                type inet:ipv6-address;
              }
              leaf v6-port-number {
                description
                  "TCP v6 port";
                type uint16 {
                  range "1..65535";
                }
              }
            }
          }
          container udp {
            list udp {
              key "ipv4-address";
              leaf ipv4-address {
                description
                  "IPv6 Address";
                type inet:ipv4-address;
              }
              leaf v4-port-number {
                description
                  "UDP v4 port";
                type uint16 {
                  range "1..65535";
                }
              }
              leaf ipv6-address {
                description
                  "IPv6 Address";
                type inet:ipv6-address;
              }
              leaf v6-port-number {
                description
                  "UDP v6 port";
                type uint16 {
                  range "1..65535";
                }
              }
            }
          }
        }
      }
      container prefix {
        description
          "NAT64 prefix";
        container stateful {
          description
            "NAT64 stateful prefix";
          leaf ipv6-prefix {
            description
              "IPv6 prefix";
            type ios-types:ipv6-prefix;
          }
        }
        container stateful-with-vrf {
          list stateful {
            description
              "NAT64 stateful prefix";
            key "vrf";
            leaf vrf {
              description
                "Specify vrf";
              must "(/ios:native/ios:vrf/ios:definition[ios:name=current()] and (/ios:native/ios:vrf/ios:definition[ios:name=current()]/ios:address-family/ios:ipv4) or
                    (/ios:native/ios:vrf/ios:definition[ios:name=current()]/ios:address-family/ios:ipv6)) or /ios:native/ios:ip/ios:vrf[ios:name=current()]" {
                error-message "VRF must be created first, deleted last";
              }
              type string;
            }
            leaf ipv6-prefix {
              description
                "IPv6 prefix";
              type ios-types:ipv6-prefix;
            }
          }
        }
        container stateless {
          description
            "NAT64 stateless prefix";
          leaf ipv6-prefix {
            description
              "IPv6 prefix";
            type inet:ipv6-prefix;
          }
        }
        container stateless-with-vrf {
          list stateless {
            description
              "NAT64 stateless prefix";
            key "ipv4-prefix vrf";
            leaf ipv4-prefix {
              description
                "IPv4 prefix";
              type inet:ipv4-prefix;
            }
            leaf vrf {
              description
                "Specify vrf";
              must "(/ios:native/ios:vrf/ios:definition[ios:name=current()] and (/ios:native/ios:vrf/ios:definition[ios:name=current()]/ios:address-family/ios:ipv4) or
                          (/ios:native/ios:vrf/ios:definition[ios:name=current()]/ios:address-family/ios:ipv6)) or /ios:native/ios:ip/ios:vrf[ios:name=current()]" {
                error-message "VRF must be created first, deleted last";
              }
              type string;
            }
            leaf ipv6-prefix {
              description
                "IPv6 prefix";
              type inet:ipv6-prefix;
            }
            leaf add-route {
              description
                "Add IPV4 prefix to routing table";
              type empty;
            }
            leaf global {
              description
                "IPV6 global routing table";
              type empty;
            }
          }
        }
      }
      container translation {
        container timeout {
          container bind {
            description
              "Specify the timeout for NAT64 binds";
            uses ip-nat-translation-timeout-grouping;
          }
          container icmp {
            description
              "Specify the timeout for NAT64 ICMP flows";
            uses ip-nat-translation-timeout-grouping;
          }
          container tcp {
            description
              "Specify the timeout for NAT64 TCP flows";
            uses ip-nat-translation-timeout-grouping;
          }
          container tcp-transient {
            description
              "Specify the timeout for NAT64 transient TCP flows";
            uses ip-nat-translation-timeout-grouping;
          }
          container udp {
            description
              "Specify the timeout for NAT64 UDP flows";
            uses ip-nat-translation-timeout-grouping;
          }
        }
        container max-entries {
          description
            "Specify maximum number of NAT entries";
          leaf max-entries {
            type uint32 {
              range "1..2147483647";
            }
          }
        }
      }
      list route {
        description
          "Establish NAT64 DIA routes";
        key "vrf ipv6-prefix";
        leaf vrf {
          description
            "Configure NAT64 DIA route for a VPN Routing/Forwarding instance";
          must "(/ios:native/ios:vrf/ios:definition[ios:name=current()] and
                 /ios:native/ios:vrf/ios:definition[ios:name=current()]/ios:address-family/ios:ipv6)" {
            error-message "IPV6 VRF must be created first, deleted last";
          }
          type string;
        }
        leaf ipv6-prefix {
          description
            "IPV6 prefix";
          type ios-types:ipv6-prefix;
        }
        leaf global {
          description
            "Next hop address is global";
          type empty;
        }
      }
    }
  }

  augment "/ios:native/ios:ip" {
    uses config-ip-nat-grouping;
  }

  augment "/ios:native/ios:interface/ios:Ethernet/ios:ip" {
    uses config-interface-ip-nat-grouping;
  }

  augment "/ios:native/ios:interface/ios:FastEthernet/ios:ip" {
    uses config-interface-ip-nat-grouping;
  }

  augment "/ios:native/ios:interface/ios:GigabitEthernet/ios:ip" {
    uses config-interface-ip-nat-grouping;
  }

  augment "/ios:native/ios:interface/ios:TenGigabitEthernet/ios:ip" {
    uses config-interface-ip-nat-grouping;
  }

  augment "/ios:native/ios:interface/ios:FiveGigabitEthernet/ios:ip" {
    uses config-interface-ip-nat-grouping;
  }

  augment "/ios:native/ios:interface/ios:AppGigabitEthernet/ios:ip" {
    uses config-interface-ip-nat-grouping;
  }

  augment "/ios:native/ios:interface/ios:TwentyFiveGigE/ios:ip" {
    uses config-interface-ip-nat-grouping;
  }

  augment "/ios:native/ios:interface/ios:TwoGigabitEthernet/ios:ip" {
    uses config-interface-ip-nat-grouping;
  }

  augment "/ios:native/ios:interface/ios:FortyGigabitEthernet/ios:ip" {
    uses config-interface-ip-nat-grouping;
  }

  augment "/ios:native/ios:interface/ios:HundredGigE/ios:ip" {
    uses config-interface-ip-nat-grouping;
  }

  augment "/ios:native/ios:interface/ios:Port-channel/ios:ip" {
    uses config-interface-ip-nat-grouping;
  }

  augment "/ios:native/ios:interface/ios:Port-channel-subinterface/ios:Port-channel/ios:ip" {
    uses config-interface-ip-nat-grouping;
  }

  augment "/ios:native/ios:interface/ios:Loopback/ios:ip" {
    uses config-interface-ip-nat-grouping;
  }

  augment "/ios:native/ios:interface/ios:BDI/ios:ip" {
    uses config-interface-ip-nat-grouping;
  }

  augment "/ios:native/ios:interface/ios:Cellular/ios:ip" {
    uses config-interface-ip-nat-grouping;
  }

  augment "/ios:native/ios:interface/ios:Dialer/ios:ip" {
    uses config-interface-ip-nat-grouping;
  }

  augment "/ios:native/ios:interface/ios:VirtualPortGroup/ios:ip" {
    uses config-interface-ip-nat-grouping;
  }

  augment "/ios:native/ios:interface/ios:Serial/ios:ip" {
    uses config-interface-ip-nat-grouping;
  }

  augment "/ios:native/ios:interface/ios:Multilink/ios:ip" {
    uses config-interface-ip-nat-grouping;
  }

  augment "/ios:native/ios:interface/ios:ATM/ios:ip" {
    uses config-interface-ip-nat-grouping;
  }

  augment "/ios:native/ios:interface/ios:ATM-subinterface/ios:ATM/ios:ip" {
    uses config-interface-ip-nat-grouping;
  }

  augment "/ios:native/ios:interface/ios:Vlan/ios:ip" {
    uses config-interface-ip-nat-grouping;
  }

  augment "/ios:native/ios:interface/ios:Tunnel/ios:ip" {
    uses config-interface-ip-nat-grouping;
  }

  augment "/ios:native/ios:interface/ios:vasileft/ios:ip" {
    uses config-interface-ip-nat-grouping;
  }

  augment "/ios:native/ios:interface/ios:vasiright/ios:ip" {
    uses config-interface-ip-nat-grouping;
  }

  augment "/ios:native" {
    uses config-nat66-grouping;
  }

  augment "/ios:native" {
    uses config-nat64-grouping;
  }

  augment "/ios:native/ios:interface/ios:FastEthernet" {
    uses config-interface-nat66-grouping;
  }

  augment "/ios:native/ios:interface/ios:GigabitEthernet" {
    uses config-interface-nat66-grouping;
  }

  augment "/ios:native/ios:interface/ios:TenGigabitEthernet" {
    uses config-interface-nat66-grouping;
  }

  augment "/ios:native/ios:interface/ios:FiveGigabitEthernet" {
    uses config-interface-nat66-grouping;
  }

  augment "/ios:native/ios:interface/ios:AppGigabitEthernet" {
    uses config-interface-nat66-grouping;
  }

  augment "/ios:native/ios:interface/ios:TwentyFiveGigE" {
    uses config-interface-nat66-grouping;
  }

  augment "/ios:native/ios:interface/ios:TwoGigabitEthernet" {
    uses config-interface-nat66-grouping;
  }

  augment "/ios:native/ios:interface/ios:FortyGigabitEthernet" {
    uses config-interface-nat66-grouping;
  }

  augment "/ios:native/ios:interface/ios:HundredGigE" {
    uses config-interface-nat66-grouping;
  }

  augment "/ios:native/ios:interface/ios:Port-channel" {
    uses config-interface-nat66-grouping;
  }

  augment "/ios:native/ios:interface/ios:Loopback" {
    uses config-interface-nat66-grouping;
  }

  augment "/ios:native/ios:interface/ios:Tunnel" {
    uses config-interface-nat66-grouping;
  }

  augment "/ios:native/ios:interface/ios:ATM" {
    uses config-interface-nat66-grouping;
  }

  augment "/ios:native/ios:interface/ios:ATM-subinterface" {
    uses config-interface-nat66-grouping;
  }

  augment "/ios:native/ios:interface/ios:Vlan" {
    uses config-interface-nat66-grouping;
  }

  augment "/ios:native/ios:interface/ios:ucse" {
    uses config-interface-nat66-grouping;
  }

  augment "/ios:native/ios:interface/ios:FastEthernet" {
    uses config-interface-nat64-grouping;
  }

  augment "/ios:native/ios:interface/ios:GigabitEthernet" {
    uses config-interface-nat64-grouping;
  }

  augment "/ios:native/ios:interface/ios:TenGigabitEthernet" {
    uses config-interface-nat64-grouping;
  }

  augment "/ios:native/ios:interface/ios:FiveGigabitEthernet" {
    uses config-interface-nat64-grouping;
  }

  augment "/ios:native/ios:interface/ios:AppGigabitEthernet" {
    uses config-interface-nat64-grouping;
  }

  augment "/ios:native/ios:interface/ios:TwentyFiveGigE" {
    uses config-interface-nat64-grouping;
  }

  augment "/ios:native/ios:interface/ios:TwoGigabitEthernet" {
    uses config-interface-nat64-grouping;
  }

  augment "/ios:native/ios:interface/ios:FortyGigabitEthernet" {
    uses config-interface-nat64-grouping;
  }

  augment "/ios:native/ios:interface/ios:HundredGigE" {
    uses config-interface-nat64-grouping;
  }

  augment "/ios:native/ios:interface/ios:Port-channel" {
    uses config-interface-nat64-grouping;
  }

  augment "/ios:native/ios:interface/ios:Loopback" {
    uses config-interface-nat64-grouping;
  }

  augment "/ios:native/ios:interface/ios:Tunnel" {
    uses config-interface-nat64-grouping;
  }

  augment "/ios:native/ios:interface/ios:ATM" {
    uses config-interface-nat64-grouping;
  }

  augment "/ios:native/ios:interface/ios:ATM-subinterface" {
    uses config-interface-nat64-grouping;
  }

  augment "/ios:native/ios:interface/ios:BD-VIF/ios:ip" {
    uses config-interface-ip-nat-grouping;
  }

  augment "/ios:native/ios:interface/ios:ucse" {
    uses config-interface-nat64-grouping;
  }
}
