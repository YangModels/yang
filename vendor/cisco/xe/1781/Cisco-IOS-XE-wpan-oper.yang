module Cisco-IOS-XE-wpan-oper {
  yang-version 1;
  namespace "http://cisco.com/ns/yang/Cisco-IOS-XE-wpan-oper";
  prefix wpan-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for WPAN (Wireless Personal Area Network)
     operational data. WPAN implements Field Area
     Network support based on the IEEE 802.15.4 standard
     including support for RPL (IPv6 Routing Protocol for
     Low-Power and Lossy Networks described in RFC 6550).
     Copyright (c) 2021 by Cisco Systems, Inc.
     All rights reserved.";

  revision 2022-03-01 {
    description
      "Initial revision";
    reference
      "1.0.0";
    cisco-semver:module-version "1.0.0";
  }

  typedef wpan-module-type {
    type enumeration {
      enum wpan-module-invalid {
        value 0;
        description
          "The WPAN module is unknown/invalid.";
      }
      enum wpan-module-irmh-900 {
        value 1;
        description
          "IP67 rated WPAN module operating in the
           900 MHz band";
      }
    }
    description
      "Type of WPAN module";
  }

  typedef wpan-service-state {
    type enumeration {
      enum wpan-state-invalid {
        value 0;
        description
          "The WPAN module is in an invalid state";
      }
      enum wpan-state-no-mod {
        value 1;
        description
          "No WPAN module detected";
      }
      enum wpan-state-not-running {
        value 2;
        description
          "The WPAN module is not running. The module will
           be in this state when it has been stopped
           (powered off).";
      }
      enum wpan-state-starting {
        value 3;
        description
          "The WPAN module is in the process of starting
           and is expected to be fully operational within
           10-15 seconds";
      }
      enum wpan-state-running {
        value 4;
        description
          "The WPAN module is fully operational.";
      }
    }
    description
      "Service state of the WPAN (Wireless Personal Area
       Network) module";
  }

  typedef meshsec-state {
    type enumeration {
      enum meshsec-sess-init {
        value 0;
        description
          "Initialized but has not been authenticated";
      }
      enum meshsec-sess-auth {
        value 1;
        description
          "Authenticated but does not have keys";
      }
      enum meshsec-sess-enc-enabled {
        value 2;
        description
          "Completed key exchange and has keys";
      }
      enum meshsec-sess-handshake {
        value 3;
        description
          "Key exchange handshake in progress";
      }
      enum meshsec-sess-key-update {
        value 4;
        description
          "Key update in progress";
      }
      enum meshsec-sess-invalid {
        value 5;
        description
          "Invalid state";
      }
    }
    description
      "State of mesh security session";
  }

  grouping wpan-hw-info {
    description
      "WPAN hardware information and configuration of
       layer 1 and layer 2 parameters";
    leaf if-name {
      type string;
      description
        "The interface name";
    }
    leaf module-type {
      type wpan-ios-xe-oper:wpan-module-type;
      description
        "Module Type";
    }
    leaf state {
      type wpan-ios-xe-oper:wpan-service-state;
      description
        "Service state of the WPAN module";
    }
    leaf fw-ver {
      type string;
      description
        "firmware version";
    }
    leaf pan-id {
      type uint16;
      description
        "PAN (Personal Area Network) identifier";
    }
    leaf wisun {
      type empty;
      description
        "Wi-SUN mode is enabled";
    }
    leaf band-id {
      type uint8;
      description
        "Radio-Frequency Band identifier";
    }
    leaf ssid {
      type string;
      description
        "SSID (Network Name)";
    }
    leaf eui64 {
      type string;
      description
        "64-bit MAC address of the interface";
    }
    leaf txpower {
      type int8;
      units "dBm";
      description
        "Transmit Power (dBm)";
    }
    leaf-list phy-mode {
      type uint8;
      max-elements 8;
      ordered-by user;
      description
        "RF PHY Mode";
    }
    leaf channel {
      type uint8;
      description
        "Channel Number";
    }
    leaf dwell-window {
      type uint32;
      units "milliseconds";
      description
        "Dwell Window";
    }
    leaf dwell-max {
      type uint32;
      units "milliseconds";
      description
        "Dwell Maximum";
    }
    leaf disc-imin {
      type uint32;
      units "seconds";
      description
        "Discovery trickle timer Imin parameter
         (used for PAN Advertisements)";
    }
    leaf disc-imax {
      type uint32;
      units "seconds";
      description
        "Discovery trickle timer Imax parameter
         (used for PAN Advertisements)";
    }
    leaf disc-k {
      type uint32;
      description
        "Discovery trickle timer suppression constant
         (used for PAN Advertisements)";
    }
    leaf security-enabled {
      type boolean;
      description
        "Security is enabled. This includes 802.1x EAP-TLS
         for mutual authentication, 802.11i for key exchange
         and 802.15.4 MAC layer encryption and integrity.";
    }
    leaf admin-up {
      type boolean;
      description
        "Indicates that the WPAN module is enabled";
    }
    leaf beacon-ver {
      type uint32;
      description
        "Beacon version";
    }
    leaf beacon-ver-inc-time {
      type uint32;
      units "seconds";
      description
        "Beacon version increment time";
    }
    leaf ucast-dwell-interval {
      when 'boolean(../wisun)';
      type uint32;
      units "milliseconds";
      description
        "Unicast dwell interval";
    }
    leaf bcast-dwell-interval {
      when 'boolean(../wisun)';
      type uint32;
      units "milliseconds";
      description
        "Broadcast dwell interval";
    }
    leaf bcast-interval {
      when 'boolean(../wisun)';
      type uint32;
      units "milliseconds";
      description
        "Broadcast interval";
    }
    leaf edfe-enabled {
      when 'boolean(../wisun)';
      type boolean;
      description
        "EDFE mode is enabled";
    }
  }

  grouping wpan-conf {
    description
      "WPAN configuration (parameters related to layer 3
       and above functionality)";
    leaf if-name {
      type string;
      description
        "The interface name";
    }
    leaf outage-server {
      type inet:ip-address;
      description
        "Outage server address where Power Outage Notifications and
         Power Restoration Notifications are forwarded to";
    }
    leaf dtls-relay {
      type inet:ip-address;
      description
        "DTLS relay address (used during certificate enrollment)";
    }
    leaf-list mcast-group {
      type inet:ip-address;
      max-elements 3;
      ordered-by user;
      description
        "Unicast-Prefix-based IPv6 Multicast Address
         (RFC 3306) enabled on the interface";
    }
    leaf-list mcast-port {
      type uint16;
      max-elements 16;
      ordered-by user;
      description
        "UDP port allowed for multicast traffic";
    }
    leaf peer-to-peer {
      type boolean;
      description
        "Forward packets from mesh endpoints which have
         other mesh endpoints as destination";
    }
  }

  grouping wpan-rpl-config-info {
    description
      "WPAN RPL (IPv6 Routing Protocol for Low-Power and
       Lossy Networks: RFC 6550) configuration information";
    leaf if-name {
      type string;
      description
        "The interface name";
    }
    leaf dodag-id {
      type inet:ip-address;
      description
        "RPL DODAG Identifier (this is always set to the
         first IPv6 address of the WPAN interface)";
    }
    leaf dodag-lifetime {
      type uint8;
      units "minutes";
      description
        "RPL DODAG lifetime";
    }
    leaf dio-imin {
      type uint8;
      description
        "RPL DIO trickle timer Imin parameter exponent";
    }
    leaf dio-imax {
      type uint8;
      description
        "RPL DIO trickle timer Imax parameter (number of doublings)";
    }
    leaf rpl-ver {
      type uint8;
      units "minutes";
      description
        "RPL version increment time";
    }
    leaf ver-incr-time {
      type uint16;
      units "minutes";
      description
        "RPL version increment time";
    }
    leaf route-poisoning {
      type empty;
      description
        "RPL route poisoning is enabled";
    }
    leaf pon-instance {
      type empty;
      description
        "RPL PON (Power Outage Notification)
         instance is enabled";
    }
    leaf pon-dio-imin {
      when 'boolean(../pon-instance)';
      type uint8;
      description
        "RPL PON instance DIO trickle timer Imin parameter exponent";
    }
    leaf pon-dio-imax {
      when 'boolean(../pon-instance)';
      type uint8;
      description
        "RPL PON instance DIO trickle timer Imax parameter
         (number of doublings)";
    }
    leaf dodag-version {
      type uint8;
      description
        "RPL DODAG version";
    }
    leaf route-auto-poisoning {
      type empty;
      description
        "RPL route auto poisoning is enabled";
    }
    leaf rpl-opt-metric-container {
      type boolean;
      description
        "RPL option metric container is enabled";
    }
    leaf cisco-option {
      type uint8;
      description
        "Controls usage of the cisco option in DAO messages";
    }
  }

  grouping wpan-ipv6-key {
    description
      "Key for the WPAN tables based on IPv6 address";
    leaf if-name {
      type string;
      description
        "The Interface name.";
    }
    leaf ip {
      type inet:ip-address;
      description
        "The IPv6 address of the node.";
    }
  }

  grouping wpan-rpl {
    description
      "WPAN RPL (IPv6 Routing Protocol for Low-Power and
       Lossy Networks: RFC 6550) entry general information.";
    leaf num-parents {
      type uint8;
      description
        "Number of parents";
    }
    leaf external {
      type uint8;
      description
        "Whether the route is external";
    }
    leaf last-heard {
      type yang:date-and-time;
      description
        "Last time a RPL DAO was received from the node";
    }
    leaf-list mcast-group {
      type inet:ip-address;
      max-elements 8;
      ordered-by user;
      description
        "Multicast group joined by the node";
    }
    leaf-list mcast-domain {
      type inet:ip-address;
      max-elements 8;
      ordered-by user;
      description
        "MPL domain joined by the node";
    }
    leaf has-cisco-info {
      type empty;
      description
        "Cisco info present. This is a Cisco-specific
         option in the DAO messages to provide additional
         information about the node. Availability depends
         on configuration and support from the nodes";
    }
    leaf eui64 {
      when 'boolean(../has-cisco-info)';
      type string;
      description
        "The node's 64-bit MAC address";
    }
    leaf rank {
      when 'boolean(../has-cisco-info)';
      type uint16;
      description
        "The node's RPL rank";
    }
    leaf version {
      when 'boolean(../has-cisco-info)';
      type uint8;
      description
        "The node's RPL version";
    }
  }

  grouping wpan-rpl-parent-key {
    description
      "Key for the WPAN RPL table";
    leaf if-name {
      type string;
      description
        "The Interface name.";
    }
    leaf ip {
      type inet:ip-address;
      description
        "The IPv6 address of the node.";
    }
    leaf parent-ip {
      type inet:ip-address;
      description
        "The IPv6 address of the node's parent.";
    }
  }

  grouping wpan-rpl-parent {
    description
      "Parent-specific information for each node in the
       RPL table";
    leaf reachable {
      type boolean;
      description
        "The node can be reached via this parent";
    }
    leaf priority {
      type uint8;
      description
        "Priority of this parent (lower number means higher
         priority)";
    }
    leaf hops {
      when '(../priority = 1) or boolean(../has-cisco-info)';
      type uint8;
      description
        "Number of hops to the root via this parent";
    }
    leaf has-cisco-info {
      type empty;
      description
        "Cisco info present. This is a Cisco-specific
         option in the DAO messages to provide additional
         information about the node. Availability depends
         on configuration and support from the nodes";
    }
    leaf eui64 {
      when 'boolean(../has-cisco-info)';
      type string;
      description
        "The parent's 64-bit MAC address";
    }
    leaf etx-path {
      when 'boolean(../has-cisco-info)';
      type uint16;
      description
        "Path cost for expected transmission count metric";
    }
    leaf etx-link {
      when 'boolean(../has-cisco-info)';
      type uint16;
      description
        "Link cost for expected transmission count metric";
    }
    leaf rssi-reverse {
      when 'boolean(../has-cisco-info)';
      type int8;
      units "dBm";
      description
        "Received signal strength indicator based on packets
         received by the node from the parent";
    }
    leaf rssi-forward {
      when 'boolean(../has-cisco-info)';
      type int8;
      units "dBm";
      description
        "Received signal strength indicator based on packets
         received by the parent from the node";
    }
    leaf lqi-reverse {
      when 'boolean(../has-cisco-info)';
      type uint8;
      description
        "Link quality index based on packets
         received by the node from the parent";
    }
    leaf lqi-forward {
      when 'boolean(../has-cisco-info)';
      type uint8;
      description
        "Link quality index based on packets
         received by the parent from the node";
    }
  }

  grouping wpan-mpl-seed-info {
    description
      "MPL seed-specific information";
    leaf id {
      type inet:ip-address;
      description
        "Seed identifier for MPL messages forwarded by
         the border router. This is an IPv6 address, and is
         normally set to the first unicast IPv6 address of
         the WPAN interface";
    }
    leaf seq-hb {
      type uint8;
      description
        "MPL sequence high bound";
    }
    leaf seq-lb {
      type uint8;
      description
        "MPL sequence low bound";
    }
    leaf min-seq {
      type uint8;
      description
        "MPL sequence minimum value";
    }
    leaf num-msgs {
      type uint8;
      description
        "Number of messages in the MPL buffer";
    }
  }

  grouping wpan-mpl {
    description
      "WPAN MPL (Multicast Protocol for Low-Power and Lossy Networks: RFC 7731)
       information for each enabled MPL domain. The key is the IPv6 address of
       the MPL domain";
    leaf data-imin {
      type uint32;
      units "milliseconds";
      description
        "MPL trickle timer Imin parameter";
    }
    leaf data-imax {
      type uint32;
      units "milliseconds";
      description
        "MPL trickle timer Imax parameter";
    }
    leaf expire {
      type uint8;
      description
        "MPL trickle timer expiration parameter
         (number of messages)";
    }
    list seed {
      max-elements 5;
      description
        "MPL seed-specific information";
      uses wpan-ios-xe-oper:wpan-mpl-seed-info;
    }
  }

  grouping wpan-eui64-key {
    description
      "Key for the WPAN tables based on MAC address";
    leaf if-name {
      type string;
      description
        "The Interface name.";
    }
    leaf eui64 {
      type string;
      description
        "The node's 64-bit MAC address";
    }
  }

  grouping wpan-nbr {
    description
      "Neighbor entry for the WPAN interface";
    leaf first-heard {
      type yang:date-and-time;
      description
        "First time that a neighbor solicit message was received
         by the WPAN module from the node";
    }
    leaf last-heard {
      type yang:date-and-time;
      description
        "Last time that a neighbor solicit message was received
         by the WPAN module from the node";
    }
    leaf rssi-reverse {
      type int8;
      units "dBm";
      description
        "Received signal strength indicator based on packets
         received by the WPAN module from the node";
    }
    leaf rssi-forward {
      type int8;
      units "dBm";
      description
        "Received signal strength indicator based on packets
         received by the node from the WPAN module";
    }
    leaf lqi-reverse {
      type uint8;
      description
        "Link quality index based on packets
         received by the WPAN module from the node";
    }
    leaf lqi-forward {
      type uint8;
      description
        "Link quality index based on packets
         received by the node from the WPAN module";
    }
    leaf phy-mode-reverse {
      type uint8;
      description
        "Link quality index based on packets
         received by the WPAN module from the node";
    }
    leaf phy-mode-forward {
      type uint8;
      description
        "Link quality index based on packets
         received by the node from the WPAN module";
    }
    leaf ipv6-reg {
      type empty;
      description
        "The WPAN module has received a neighbor solicit with
         an address registration option from the node.
         This means that the node's address is considered on-link
         and IPv6 packets can be sent to it directly.";
    }
    leaf ip {
      when 'boolean(../ipv6-reg)';
      type inet:ip-address;
      description
        "The IPv6 address of the node.";
    }
    leaf ip-expiry {
      when 'boolean(../ipv6-reg)';
      type yang:date-and-time;
      description
        "Expiry time of the IPv6 registration if not refreshed.";
    }
  }

  grouping wpan-pon {
    description
      "Power Outage Notification entry";
    leaf outage-reported {
      type yang:date-and-time;
      description
        "The time when the outage occurred as reported by the node";
    }
    leaf first-received {
      type yang:date-and-time;
      description
        "The first time this power outage notification (for this node)
         was received. This is used to track performance of the outage
         notification protocols and for troubleshooting";
    }
    leaf last-received {
      type yang:date-and-time;
      description
        "The last time this power outage notification (for this node)
         was received. This is used to track performance of the outage
         notification protocols and for troubleshooting";
    }
  }

  grouping wpan-prn {
    description
      "Power Restoration Notification entry";
    leaf outage-reported {
      type yang:date-and-time;
      description
        "The time when the outage corresponding to this restoration
         occurred as reported by the node";
    }
    leaf restoration-reported {
      type yang:date-and-time;
      description
        "The time when the restoration occurred as reported by the node";
    }
    leaf first-received {
      type yang:date-and-time;
      description
        "The first time this power restoration notification (for this node)
         was received. This is used to track performance of the restoration
         notification protocols and for troubleshooting";
    }
    leaf last-received {
      type yang:date-and-time;
      description
        "The last time this power restoration notification (for this node)
         was received. This is used to track performance of the restoration
         notification protocols and for troubleshooting";
    }
  }

  grouping wpan-eap {
    description
      "Table used to keep track of EAP (Extensible Authentication Protocol) information";
    leaf last-heard {
      type yang:date-and-time;
      description
        "Last time an EAP packet was received from the supplicant";
    }
    leaf relayed {
      type empty;
      description
        "The last EAP packet for this supplicant was relayed via another node";
    }
    leaf relay-ip-addr {
      when 'boolean(../relayed)';
      type inet:ip-address;
      description
        "IPv6 address of the node that relayed the last EAP packet from this supplicant";
    }
  }

  grouping wpan-dtls-relay {
    description
      "DTLS relay information (used when nodes perform certificate enrollment)";
    leaf start-time {
      type yang:date-and-time;
      description
        "The start of the current session";
    }
    leaf num-rx {
      type uint32;
      description
        "Number of packets received in the current session";
    }
    leaf num-tx {
      type uint32;
      description
        "Number of packets transmitted in the current session";
    }
  }

  grouping meshsec-gtk {
    description
      "Global Transient Key";
    leaf key-id {
      type uint8;
      description
        "Key identifier";
    }
    leaf expiry {
      type yang:date-and-time;
      description
        "Key expiry time";
    }
  }

  grouping meshsec-info {
    description
      "Mesh security information about WPAN interface";
    leaf if-name {
      type string;
      description
        "The interface name";
    }
    leaf sess-total {
      type uint32;
      description
        "Total number of sessions";
    }
    leaf sess-with-keys {
      type uint32;
      description
        "Number of sessions with keys";
    }
    leaf max-active-auth {
      type uint32;
      description
        "Maximum active authentications";
    }
    leaf cur-active-auth {
      type uint32;
      description
        "Current active authentications";
    }
    leaf queued-auth {
      type uint32;
      description
        "Queued authentications";
    }
    leaf max-active-ke {
      type uint32;
      description
        "Maximum active key exchanges";
    }
    leaf cur-ke {
      type uint32;
      description
        "Current key exchanges";
    }
    leaf queued-ke {
      type uint32;
      description
        "Queued key exchanges";
    }
    leaf dot1x-cleanup {
      type boolean;
      description
        "Dot1x cleanup enabled on interface. When enabled, dot1x sessions will be automatically removed when no longer needed.";
    }
    leaf pmk-lifetime {
      type uint32;
      units "seconds";
      description
        "Lifetime of Pairwise Master Key";
    }
    leaf ptk-lifetime {
      type uint32;
      units "seconds";
      description
        "Lifetime of Pairwise Temporal key";
    }
    leaf gtk-lifetime {
      type uint32;
      units "seconds";
      description
        "Lifetime of Group Transient Key";
    }
    list gtk {
      max-elements 4;
      description
        "Information about currently installed Group Transient Keys";
      uses wpan-ios-xe-oper:meshsec-gtk;
    }
    leaf cur-key-id {
      type uint8;
      description
        "The ID of the current key";
    }
  }

  grouping meshsec-sess {
    description
      "Information about mesh security session for a supplicant";
    leaf state {
      type wpan-ios-xe-oper:meshsec-state;
      description
        "State of the session";
    }
    leaf has-pmk {
      type empty;
      description
        "The supplicant has a Pairwise Master Key";
    }
    leaf pmk-expiry {
      when 'boolean(../has-pmk)';
      type yang:date-and-time;
      description
        "Expiry time of the Pairwise Master Key";
    }
    leaf has-ptk {
      type empty;
      description
        "The supplicant has a Pairwise Temporal Key";
    }
    leaf ptk-expiry {
      when 'boolean(../has-ptk)';
      type yang:date-and-time;
      description
        "Expiry of the Pairwise Temporal Key";
    }
    leaf-list gtk {
      type uint8;
      max-elements 4;
      ordered-by user;
      description
        "Key IDs for each Group Transient Key that the supplicant has";
    }
  }

  container wpan-oper-data {
    config false;
    description
      "This is a top level container for WPAN information";
    list wpan-hw-info {
      key "if-name";
      description
        "WPAN hardware information";
      uses wpan-ios-xe-oper:wpan-hw-info;
    }
    list wpan-conf {
      key "if-name";
      description
        "WPAN configuration";
      uses wpan-ios-xe-oper:wpan-conf;
    }
    list wpan-rpl-config-info {
      key "if-name";
      description
        "RPL Configuration Information";
      uses wpan-ios-xe-oper:wpan-rpl-config-info;
    }
    list wpan-rpl {
      key "if-name ip";
      description
        "Contains RPL (RFC 6550) routing entries maintained
         by the RPL root. This table contains general information
         for each node.";
      uses wpan-ios-xe-oper:wpan-ipv6-key;
      uses wpan-ios-xe-oper:wpan-rpl;
    }
    list wpan-rpl-parent {
      key "if-name ip parent-ip";
      description
        "Contains the parent information for each node in
         the RPL table.";
      uses wpan-ios-xe-oper:wpan-rpl-parent-key;
      uses wpan-ios-xe-oper:wpan-rpl-parent;
    }
    list wpan-mpl {
      key "if-name ip";
      description
        "WPAN MPL (RFC 7731) information";
      uses wpan-ios-xe-oper:wpan-ipv6-key;
      uses wpan-ios-xe-oper:wpan-mpl;
    }
    list wpan-nbr {
      key "if-name eui64";
      description
        "Neighbor entry for the WPAN interface";
      uses wpan-ios-xe-oper:wpan-eui64-key;
      uses wpan-ios-xe-oper:wpan-nbr;
    }
    list wpan-pon {
      key "if-name eui64";
      description
        "Power Outage Notification entry";
      uses wpan-ios-xe-oper:wpan-eui64-key;
      uses wpan-ios-xe-oper:wpan-pon;
    }
    list wpan-prn {
      key "if-name eui64";
      description
        "Power Restoration Notification entry";
      uses wpan-ios-xe-oper:wpan-eui64-key;
      uses wpan-ios-xe-oper:wpan-prn;
    }
    list wpan-eap {
      key "if-name eui64";
      description
        "Table used to keep track of EAP (Extensible Authentication Protocol) information";
      uses wpan-ios-xe-oper:wpan-eui64-key;
      uses wpan-ios-xe-oper:wpan-eap;
    }
    list wpan-dtls-relay {
      key "if-name eui64";
      description
        "DTLS relay information (used when nodes perform certificate enrollment)";
      uses wpan-ios-xe-oper:wpan-eui64-key;
      uses wpan-ios-xe-oper:wpan-dtls-relay;
    }
    list meshsec-info {
      key "if-name";
      description
        "Mesh security information about WPAN interface";
      uses wpan-ios-xe-oper:meshsec-info;
    }
    list meshsec-sess {
      key "if-name eui64";
      description
        "Information about mesh security session for a supplicant";
      uses wpan-ios-xe-oper:wpan-eui64-key;
      uses wpan-ios-xe-oper:meshsec-sess;
    }
  }
}
