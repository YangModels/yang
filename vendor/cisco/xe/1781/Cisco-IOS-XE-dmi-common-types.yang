module Cisco-IOS-XE-dmi-common-types {
  yang-version 1;
  namespace "http://cisco.com/ns/yang/Cisco-IOS-XE-dmi-common-types";
  prefix dmi-common-types;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of common YANG definitions
     for DMI configuration and operational data.
     Copyright (c) 2021 by Cisco Systems, Inc.
     All rights reserved.";

  revision 2021-07-01 {
    description
      "Initial revision";
    reference
      "1.0.0";
    cisco-semver:module-version "1.0.0";
  }

  typedef enm-local-vrf-name {
    type enumeration {
      enum vrf-guestshell {
        value 0;
        description
          "Configure NETCONF access on guest-shell VRF.";
      }
    }
    description
      "The enumeration with all possible VRF names for local host NETCONF access configuration.";
  }
}
