module Cisco-IOS-XE-isdn-oper {
  yang-version 1;
  namespace "http://cisco.com/ns/yang/Cisco-IOS-XE-isdn-oper";
  prefix isdn-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for ISDN operational data.
     Copyright (c) 2019 by Cisco Systems, Inc.
     All rights reserved.";

  revision 2019-11-01 {
    description
      "Initial revision";
    reference
      "1.0.0";
    cisco-semver:module-version "1.0.0";
  }

  typedef isdn-switch-type {
    type enumeration {
      enum no-isdn-switch-type {
        value 0;
        description
          "No global ISDN switch type currently configured";
      }
      enum bri-net3-switch-type {
        value 1;
        description
          "BRI NET3 switch type";
      }
      enum pri-4ess-switch-type {
        value 2;
        description
          "PRI 4ESS switch type";
      }
      enum pri-5ess-switch-type {
        value 3;
        description
          "PRI 5ESS switch type";
      }
      enum bri-5ess-switch-type {
        value 4;
        description
          "BRI 5ESS switch type";
      }
      enum pri-dms100-switch-type {
        value 5;
        description
          "PRI DMS100 switch type";
      }
      enum bri-dms100-switch-type {
        value 6;
        description
          "BRI DMS100 switch type";
      }
      enum vn2-switch-type {
        value 7;
        description
          "VN2 switch type";
      }
      enum vn3-switch-type {
        value 8;
        description
          "VN3 switch type";
      }
      enum ntt-switch-type {
        value 9;
        description
          "BRI NTT switch type";
      }
      enum bri-1tr6-switch-type {
        value 10;
        description
          "BRI 1TR6 switch type";
      }
      enum bri-old-ni1-switch-type {
        value 11;
        description
          "BRI old national ISDN-1 switch type";
      }
      enum bri-ni1-switch-type {
        value 12;
        description
          "BRI generic national ISDN-1 switch type";
      }
      enum pri-ni-switch-type {
        value 13;
        description
          "PRI generic national ISDN switch type";
      }
      enum bri-ts013-switch-type {
        value 14;
        description
          "BRI Australia switch type";
      }
      enum bri-nznet3-switch-type {
        value 15;
        description
          "BRI New Zealand NET3 switch type";
      }
      enum bri-nwnet3-switch-type {
        value 16;
        description
          "BRI Norway NET3 switch type";
      }
      enum pri-ntt-switch-type {
        value 17;
        description
          "PRI NTT switch type";
      }
      enum pri-net5-switch-type {
        value 18;
        description
          "PRI NET5 switch type";
      }
      enum pri-ts014-switch-type {
        value 19;
        description
          "PRI TS014 switch type";
      }
      enum pri-qsig-master-switch-type {
        value 20;
        description
          "PRI QSIG Master switch type";
      }
      enum pri-qsig-slave-switch-type {
        value 21;
        description
          "PRI QSIG Slave switch type";
      }
      enum pri-qsig-switch-type {
        value 22;
        description
          "PRI QSIG switch type";
      }
      enum bri-qsig-switch-type {
        value 23;
        description
          "BRI QSIG switch type";
      }
      enum pri-qsigp-switch-type {
        value 24;
        description
          "PRI QSIGP switch type";
      }
      enum pri-ni2c-switch-type {
        value 25;
        description
          "PRI NI2C switch type";
      }
      enum pri-dpnss-switch-type {
        value 26;
        description
          "PRI DPNSS switch type";
      }
    }
    description
      "Enumeration for ISDN switch type";
  }

  typedef isdn-protocol-emul-config {
    type enumeration {
      enum isdn-protocol-emulation-user {
        value 0;
        description
          "ISDN user protocol emulation";
      }
      enum isdn-protocol-emulation-network {
        value 1;
        description
          "ISDN network protocol emulation";
      }
    }
    description
      "Enumeration for ISDN protocol emulation configuration";
  }

  typedef isdn-l1-status {
    type enumeration {
      enum l1-deactivated {
        value 0;
        description
          "ISDN layer 1 is in deactivated status";
      }
      enum l1-going-down {
        value 1;
        description
          "ISDN layer 1 is in going down status";
      }
      enum l1-init {
        value 2;
        description
          "ISDN layer 1 is in initializing status";
      }
      enum l1-testing {
        value 3;
        description
          "ISDN layer 1 is in in testing status";
      }
      enum l1-active {
        value 4;
        description
          "ISDN layer 1 is in active status";
      }
      enum l1-reset {
        value 5;
        description
          "ISDN layer 1 is in reset status";
      }
      enum l1-shutdown {
        value 6;
        description
          "ISDN layer 1 is in shut down status";
      }
      enum l1-deleted {
        value 7;
        description
          "ISDN layer 1 is in deleted status";
      }
      enum l1-unknown {
        value 8;
        description
          "ISDN layer 1 is in unknown status";
      }
    }
    description
      "ISDN Layer 1 status";
  }

  typedef isdn-l2-status {
    type enumeration {
      enum l2-not-activated {
        value 0;
        description
          "ISDN layer 2 is in not activated status";
      }
      enum l2-tei-unassigned {
        value 1;
        description
          "ISDN layer 2 is in TEI unassigned status";
      }
      enum l2-assign-awaiting-tei {
        value 2;
        description
          "ISDN layer 2 is in TEI assign awaiting status";
      }
      enum l2-establish-awaiting-tei {
        value 3;
        description
          "ISDN layer 2 is in TEI establish awaiting status";
      }
      enum l2-tei-assigned {
        value 4;
        description
          "ISDN layer 2 is in TEI assigned status";
      }
      enum l2-awaiting-establishment {
        value 5;
        description
          "ISDN layer 2 is in awaiting establishment status";
      }
      enum l2-awaiting-release {
        value 6;
        description
          "ISDN layer 2 is in awaiting release status";
      }
      enum l2-multiple-frame-established {
        value 7;
        description
          "ISDN layer 2 is in multiple frame established status";
      }
      enum l2-timer-recovery {
        value 8;
        description
          "ISDN layer 2 is in timer recovery status";
      }
      enum l2-not-applicable {
        value 9;
        description
          "ISDN layer 2 is not applicable to NFAS none";
      }
    }
    description
      "ISDN Layer 2 status";
  }

  typedef isdn-active-call-type {
    type enumeration {
      enum isdn-call-none {
        value 0;
        description
          "No call type assigned yet";
      }
      enum isdn-call-data {
        value 1;
        description
          "ISDN data call";
      }
      enum isdn-call-voice {
        value 2;
        description
          "ISDN voice call";
      }
      enum isdn-call-v110 {
        value 3;
        description
          "ISDN V110 call";
      }
      enum isdn-call-v120 {
        value 4;
        description
          "ISDN V120 call";
      }
      enum isdn-call-packet {
        value 5;
        description
          "ISDN packet switched data call";
      }
      enum isdn-call-internal {
        value 6;
        description
          "ISDN call for internal use";
      }
      enum isdn-call-signaling {
        value 7;
        description
          "ISDN QSIG signaling call";
      }
      enum isdn-call-modem {
        value 8;
        description
          "ISDN modem call";
      }
      enum isdn-call-facility {
        value 9;
        description
          "ISDN facility call";
      }
      enum isdn-call-data-over-voice {
        value 10;
        description
          "ISDN data over voice call";
      }
      enum isdn-call-piafs {
        value 11;
        description
          "ISDN piafs call";
      }
      enum isdn-call-cot {
        value 12;
        description
          "ISDN call with continuity tone test";
      }
      enum isdn-call-bumped {
        value 13;
        description
          "ISDN data call being bumped";
      }
      enum isdn-call-woken {
        value 14;
        description
          "ISDN voice call woken up";
      }
      enum isdn-call-unknown {
        value 15;
        description
          "Unknown ISDN call type value";
      }
      enum isdn-call-voice-over-data {
        value 16;
        description
          "ISDN clear channel voice over data call";
      }
    }
    description
      "ISDN active call type";
  }

  grouping isdn-active-call-entry {
    description
      "ISDN active call entry";
    leaf key-id {
      type uint32;
      description
        "Key to the entry";
    }
    leaf call-id {
      type uint64;
      description
        "Call ID";
    }
    leaf sapi {
      type uint32;
      description
        "ISDN Service Access Point Identifier";
    }
    leaf ces {
      type uint32;
      description
        "ISDN connection end-point suffix";
    }
    leaf b-channel-num {
      type uint32;
      description
        "ISDN B channel number";
    }
    leaf call-type {
      type isdn-ios-xe-oper:isdn-active-call-type;
      description
        "ISDN call type";
    }
  }

  grouping isdn-intf-entry {
    description
      "ISDN interface entry";
    leaf key-id {
      type uint32;
      description
        "Key to the entry";
    }
    leaf intf-name {
      type string;
      description
        "ISDN interface name";
    }
    leaf proto-emul-config {
      type isdn-ios-xe-oper:isdn-protocol-emul-config;
      description
        "ISDN protocol emulation configuration";
    }
    leaf dsl-number {
      type uint32;
      description
        "ISDN DSL number";
    }
    leaf switch-type {
      type isdn-ios-xe-oper:isdn-switch-type;
      description
        "ISDN switch type configured on this ISDN interface";
    }
    leaf l1-status {
      type isdn-ios-xe-oper:isdn-l1-status;
      description
        "ISDN L1 status on this ISDN interface";
    }
    leaf l2-status {
      type isdn-ios-xe-oper:isdn-l2-status;
      description
        "ISDN L2 status on this ISDN interface";
    }
    leaf l2-tei-config {
      type uint32;
      description
        "ISDN L2 terminal end-point identifier";
    }
    leaf l2-ces-config {
      type uint32;
      description
        "ISDN L2 connection end-point suffix";
    }
    leaf l2-sapi-config {
      type uint32;
      description
        "ISDN L2 service access point identifier";
    }
    leaf free-channel-mask {
      type uint32;
      description
        "Free channel mask on this interface";
    }
    leaf num-active-calls {
      type uint32;
      description
        "Number of ISDN active calls on this interface";
    }
    list isdn-active-call-entry {
      key "key-id";
      description
        "A list of ISDN active call entry";
      uses isdn-ios-xe-oper:isdn-active-call-entry;
    }
  }

  grouping isdn-status {
    description
      "ISDN status";
    leaf global-switch-type {
      type isdn-ios-xe-oper:isdn-switch-type;
      description
        "Global ISDN switch type configuration";
    }
    leaf total-intf {
      type uint32;
      description
        "Total ISDN interface configured";
    }
    list isdn-intf-entry {
      key "key-id";
      description
        "A list of ISDN interface entry";
      uses isdn-ios-xe-oper:isdn-intf-entry;
    }
  }

  container isdn-oper-data {
    config false;
    description
      "ISDN operational data";
    container isdn-status {
      presence "isdn-status";
      description
        "ISDN interface status";
      uses isdn-ios-xe-oper:isdn-status;
    }
  }
}
