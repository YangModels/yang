module Cisco-IOS-XE-packet-core-timer-cfg {
  yang-version 1;
  namespace "http://cisco.com/ns/yang/Cisco-IOS-XE-packet-core-timer-cfg";
  prefix packet-core-timer-cfg;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Packet-Core Timer profile configuration.
     Copyright (c) 2021 by Cisco Systems, Inc.
     All rights reserved.";

  revision 2021-11-01 {
    description
      "Initial revision";
    reference
      "1.0.0";
    cisco-semver:module-version "1.0.0";
  }

  grouping timer-profile {
    description
      "Timer Profile configuration";
    leaf profile-name {
      type string {
        length "1..32" {
          error-message "Invalid length for Timer Profile name: Valid length is 1 to 32 ASCII characters";
          error-app-tag "must-violation";
        }
        pattern '[!-~]([ -~]*[!-~])?' {
          error-message "Timer profile name must use ASCII 32-126 characters and must not contain leading or trailing spaces";
          error-app-tag "must-violation";
        }
      }
      description
        "Timer Profile Name";
    }
    leaf status {
      type boolean;
      default "false";
      description
        "Administrative state of Timer Profile";
    }
    leaf mobile-reachable-tmr {
      type uint32 {
        range "300 .. 12000";
      }
      units "seconds";
      default "3480";
      description
        "Mobile reachable timer interval";
    }
    leaf implicit-detach-tmr {
      type uint32 {
        range "300 .. 12000";
      }
      units "seconds";
      default "3480";
      description
        "UE implicit detach timer interval";
    }
    leaf purge-tmr {
      type uint32 {
        range "1 .. 20160";
      }
      units "minutes";
      default "10080";
      description
        "UE purge timer interval";
    }
    leaf qos-flow-inact-tmr-enable {
      type boolean;
      default "true";
      description
        "Enable QoS flow inactivity timer";
    }
    leaf qos-flow-inact-tmr {
      type uint32 {
        range "180 .. 86400";
      }
      units "seconds";
      default "300";
      description
        "QoS flow inactivity timer interval";
    }
    leaf usr-plane-inact-tmr-enable {
      type boolean;
      default "false";
      description
        "Enable user plane inactivity timer";
    }
    leaf usr-plane-inact-tmr {
      type uint32 {
        range "300 .. 86400";
      }
      units "seconds";
      default "300";
      description
        "User plane PDU session inactivity timer interval";
    }
    leaf stats-monitoring-enable {
      type boolean;
      default "true";
      description
        "Enable statistics monitoring timer";
    }
    leaf stats-monitoring-tmr {
      type uint32 {
        range "300 .. 86400";
      }
      units "seconds";
      default "300";
      description
        "Statistics monitoring timer interval at which UPF control plane polls data plane for statistics";
    }
  }

  container packet-core-timer-cfg-data {
    description
      "Packet-Core Timer profile configuration data";
    container timer-profiles {
      description
        "Timer profiles configuration";
      list timer-profile {
        key "profile-name";
        description
          "Timer profile configuration for Packet-Core";
        uses packet-core-timer-cfg:timer-profile;
      }
    }
  }
}
