module Cisco-IOS-XE-stack-oper {
  yang-version 1;
  namespace "http://cisco.com/ns/yang/Cisco-IOS-XE-stack-oper";
  prefix stack-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Stack operational data.
     Copyright (c) 2018-2021 by Cisco Systems, Inc.
     All rights reserved.";

  revision 2022-03-01 {
    description
      "Added HA related information";
    reference
      "1.6.0";
    cisco-semver:module-version "1.6.0";
  }
  revision 2021-03-01 {
    description
      "Added Stack and per-member  boot time information";
    reference
      "1.5.0";
    cisco-semver:module-version "1.5.0";
  }
  revision 2020-11-01 {
    description
      "Added stack info list";
    reference
      "1.4.0";
    cisco-semver:module-version "1.4.0";
  }
  revision 2020-07-01 {
    description
      "Added stack port counters.";
    reference
      "1.3.0";
    cisco-semver:module-version "1.3.0";
  }
  revision 2020-03-01 {
    description
      "Added reload reason leaf for 17.2.1";
    reference
      "1.2.0";
    cisco-semver:module-version "1.2.0";
  }
  revision 2019-06-06 {
    description
      "- Added node role, state and stacking mode information.
       - Added high availability interface MTU value.
       - Added standby SSO flag.
       - Added stacking port state.
       - Added semantic version";
    reference
      "1.1.0";
    cisco-semver:module-version "1.1.0";
  }
  revision 2018-05-01 {
    description
      "Initial revision";
    reference
      "1.0.0";
    cisco-semver:module-version "1.0.0";
  }

  typedef stack-node-role-id {
    type enumeration {
      enum role-unknown {
        value 0;
        description
          "Role Unknown";
      }
      enum role-active {
        value 1;
        description
          "Role Active";
      }
      enum role-standby {
        value 2;
        description
          "Role Standby";
      }
      enum role-member {
        value 3;
        description
          "Role Member";
      }
    }
    description
      "Stack Node Role";
  }

  typedef stack-node-state {
    type enumeration {
      enum state-configured {
        value 0;
        description
          "State Configured";
      }
      enum state-waiting {
        value 1;
        description
          "State Waiting";
      }
      enum state-progressing {
        value 2;
        description
          "State Progressing";
      }
      enum state-initializing {
        value 3;
        description
          "State Initializing";
      }
      enum state-ready {
        value 4;
        description
          "State Ready";
      }
      enum state-master-reinit {
        value 5;
        description
          "State Master Re-initializing";
      }
      enum state-feature-mismatch {
        value 6;
        description
          "State Feature Mismatch";
      }
      enum state-version-mismatch {
        value 7;
        description
          "State Version Mismatch";
      }
      enum state-license-mismatch {
        value 8;
        description
          "State License Mismatch";
      }
      enum state-platform-mismatch {
        value 9;
        description
          "State Platform Mismatch";
      }
      enum state-platform-and-license-mismatch {
        value 10;
        description
          "State Platform and License Mismatch";
      }
      enum state-invalid {
        value 11;
        description
          "State Invalid";
      }
      enum state-provisioned {
        value 12;
        description
          "State Provisioned";
      }
      enum state-removed {
        value 13;
        description
          "State Removed";
      }
      enum state-unprovisioned {
        value 14;
        description
          "State Un-provisioned";
      }
      enum state-os-mismatch {
        value 15;
        description
          "State OS Mismatch";
      }
      enum state-unknown {
        value 16;
        description
          "State Unknown";
      }
    }
    description
      "Stack Node State";
  }

  typedef stacking-mode {
    type enumeration {
      enum mode-stackwise-rear {
        value 0;
        description
          "Mode Stackwise Rear";
      }
      enum mode-active-standby {
        value 1;
        description
          "Mode Active Standby";
      }
      enum mode-stackwise-geo {
        value 2;
        description
          "Mode Stackwise Geo";
      }
      enum mode-stackwise-virtual {
        value 3;
        description
          "Mode Stackwise Virtual";
      }
      enum mode-unknown {
        value 4;
        description
          "Mode Unknown";
      }
    }
    description
      "Stack Mode";
  }

  typedef stacking-port-state {
    type enumeration {
      enum link-down {
        value 0;
        description
          "Port State Down";
      }
      enum link-up {
        value 1;
        description
          "Port State Up";
      }
      enum link-no-cable {
        value 2;
        description
          "Port State No Cable";
      }
    }
    description
      "Stack Port State";
  }

  typedef stack-ring-status {
    type enumeration {
      enum half-ring {
        value 0;
        description
          "Ring is Half";
      }
      enum full-ring {
        value 1;
        description
          "Ring is Full";
      }
      enum standalone {
        value 2;
        description
          "Ring is Standalone";
      }
    }
    description
      "Stack Ring State";
  }

  typedef stack-type {
    type enumeration {
      enum stack-type-stacking {
        value 0;
        description
          "Type Stacking";
      }
      enum stack-type-remote-ha {
        value 1;
        description
          "Type Remote HA";
      }
      enum stack-type-unknown {
        value 2;
        description
          "Type Unknown";
      }
    }
    description
      "Type of Stack";
  }

  typedef stack-mode-config {
    type enumeration {
      enum stack-mode-config-active {
        value 0;
        description
          "Mode configured as Active";
      }
      enum stack-mode-config-standby {
        value 1;
        description
          "Mode configured as Standby";
      }
      enum stack-mode-config-member {
        value 2;
        description
          "Mode configured as Member";
      }
      enum stack-mode-config-none {
        value 3;
        description
          "Mode not configured";
      }
    }
    description
      "Configured Stack Mode";
  }

  grouping stack-node-keepalive {
    description
      "Stack Node Keepalive Counters";
    leaf sent {
      type uint64;
      description
        "Keepalive Request Sent";
    }
    leaf received {
      type uint64;
      description
        "Keepalive Response Received";
    }
    leaf sent-failure {
      type uint64;
      description
        "Keepalive Request Sent Failure";
    }
    leaf receive-failure {
      type uint64;
      description
        "Keepalive Response Failure";
    }
    leaf consecutive-losses {
      type uint64;
      description
        "Keepalive Consecutive Losses";
    }
  }

  grouping stack-ports-stats {
    description
      "Stack port statistics";
    leaf rac-inserted {
      type uint64;
      units "bytes";
      description
        "Ring access controller ingress count";
    }
    leaf rac-copied {
      type uint64;
      units "bytes";
      description
        "Ring access controller egress count";
    }
    leaf rac-data-crc-err {
      type uint64;
      units "packets";
      description
        "Ring access controller data CRC error count";
    }
    leaf rac-invalid-ringword-err {
      type uint64;
      units "packets";
      description
        "Ring access controller invalid ring word received error count";
    }
    leaf rac-pcs-codeword-err {
      type uint64;
      units "packets";
      description
        "Ring access controller invalid physical coding sublayer code word received error count";
    }
    leaf rac-rwcrc-err {
      type uint64;
      units "packets";
      description
        "Ring access controller ring word CRC error count";
    }
  }

  grouping stack-port-info {
    description
      "Stack port information";
    leaf port-num {
      type uint8;
      description
        "Stack Port Number";
    }
    leaf port-state {
      type stack-ios-xe-oper:stacking-port-state;
      description
        "Stack Port State";
    }
    leaf switch-nbr-port {
      type uint8;
      description
        "Switch Number connected to Stack Port";
    }
    container sp-stats {
      description
        "Stack port statistics";
      uses stack-ios-xe-oper:stack-ports-stats;
    }
    leaf sp-stats-time {
      type yang:date-and-time;
      description
        "Stack port statistics are updated periodically.
         This leaf captures the timestamp of the last update.";
    }
  }

  grouping stack-node-info {
    description
      "Stack Node Data";
    leaf chassis-number {
      type uint8;
      description
        "Chassis Number";
    }
    leaf priority {
      type uint8;
      description
        "Chassis Priority";
    }
    leaf serial-number {
      type string;
      description
        "Serial Number";
    }
    leaf latency {
      type uint32;
      units "nanoseconds";
      description
        "Latency in nanoseconds";
    }
    container keepalive-counters {
      description
        "Keepalive counters";
      uses stack-ios-xe-oper:stack-node-keepalive;
    }
    leaf interface-mtu {
      type uint32;
      units "bytes";
      description
        "Interface MTU";
    }
    leaf role {
      type stack-ios-xe-oper:stack-node-role-id;
      description
        "Chassis Role";
    }
    leaf node-state {
      type stack-ios-xe-oper:stack-node-state;
      description
        "Chassis State";
    }
    leaf stack-mode {
      type stack-ios-xe-oper:stacking-mode;
      description
        "Stack mode";
    }
    leaf sso-ready-flag {
      type boolean;
      description
        "Standby SSO Ready flag";
    }
    leaf mac-address {
      type yang:mac-address;
      description
        "MAC Address of the switch";
    }
    list stack-ports {
      description
        "Switch Stack Port link Status";
      uses stack-ios-xe-oper:stack-port-info;
    }
    leaf reload-reason {
      type string;
      description
        "Reload reason for all stack members";
    }
    leaf ha-interface {
      when "(../stack-mode='mode-active-standby')";
      type string;
      description
        "HA interface";
    }
    leaf local-ip {
      when "(../stack-mode='mode-active-standby')";
      type inet:ip-address;
      description
        "Local IP address";
    }
    leaf local-ip-mask {
      when "(../stack-mode='mode-active-standby')";
      type inet:ip-address;
      description
        "Local IP address mask";
    }
    leaf remote-ip {
      when "(../stack-mode='mode-active-standby')";
      type inet:ip-address;
      description
        "Remote IP address";
    }
    leaf remote-mac-address {
      when "(../stack-mode='mode-active-standby')";
      type yang:mac-address;
      description
        "Remote mac address";
    }
    leaf peer-timeout {
      when "(../stack-mode='mode-active-standby')";
      type uint16;
      units "milliseconds";
      description
        "Peer timeout";
    }
    leaf retry-count {
      when "(../stack-mode='mode-active-standby')";
      type uint16;
      description
        "Retry count";
    }
    leaf hw-version {
      when "(../stack-mode='mode-active-standby')";
      type string;
      description
        "Hardware version";
    }
    leaf mode {
      when "(../stack-mode='mode-active-standby')";
      type stack-ios-xe-oper:stack-type;
      description
        "Value of configured mode";
    }
    leaf configured-mode {
      when "(../stack-mode='mode-active-standby')";
      type stack-ios-xe-oper:stack-mode-config;
      description
        "Configured mode";
    }
    leaf mac-persistency-wait-time {
      when "(../stack-mode='mode-active-standby')";
      type uint32;
      units "minutes";
      description
        "MAC persistent wait time. When value is 0 then indefinite wait time.";
    }
  }

  grouping stack-info {
    description
      "Stack Data";
    leaf size {
      type uint8;
      description
        "Stack size";
    }
    leaf ring-speed {
      type uint64;
      description
        "Stack Ring speed";
    }
    leaf ring-status {
      type stack-ios-xe-oper:stack-ring-status;
      description
        "Stack Ring status";
    }
    leaf stack-mac-address {
      type yang:mac-address;
      description
        "Stack MAC address";
    }
    leaf stack-boottime {
      type yang:date-and-time;
      description
        "Stack boot time";
    }
  }

  container stack-oper-data {
    config false;
    description
      "stack operational data";
    list stack-node {
      key "chassis-number";
      description
        "Stack Node Data";
      uses stack-ios-xe-oper:stack-node-info;
    }
    container stack-info {
      presence "stack-info";
      description
        "High level Stack Data";
      uses stack-ios-xe-oper:stack-info;
    }
  }
}
