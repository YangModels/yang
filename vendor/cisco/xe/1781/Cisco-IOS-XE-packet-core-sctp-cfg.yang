module Cisco-IOS-XE-packet-core-sctp-cfg {
  yang-version 1;
  namespace "http://cisco.com/ns/yang/Cisco-IOS-XE-packet-core-sctp-cfg";
  prefix packet-core-sctp-cfg;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Packet-Core SCTP Profile configurations.
     Copyright (c) 2021 by Cisco Systems, Inc.
     All rights reserved.";

  revision 2021-11-01 {
    description
      "Initial revision";
    reference
      "1.0.0";
    cisco-semver:module-version "1.0.0";
  }

  grouping sctp-profile {
    description
      "SCTP Profile config";
    leaf profile-name {
      type string {
        length "1..32" {
          error-message "Invalid length for SCTP Profile name: Valid length is 1 to 32 ASCII characters";
          error-app-tag "must-violation";
        }
        pattern '[!-~]([ -~]*[!-~])?' {
          error-message "Please use ASCII 32-126 characters and avoid leading/trailing spaces";
          error-app-tag "must-violation";
        }
      }
      description
        "SCTP Profile Name";
    }
    leaf status {
      type boolean;
      default "false";
      description
        "Administrative status of SCTP Profile";
    }
    leaf if-name {
      type string;
      default "";
      description
        "Interface Name (eg. (Ten)GigabitEthernet1/Loopback1/Port-channel1)";
    }
    leaf hb-intrvl {
      type uint16 {
        range "2 .. 30";
      }
      units "seconds";
      default "3";
      description
        "SCTP Heartbeat interval (secs)";
    }
    leaf max-retrans {
      type uint16 {
        range "0 .. 255";
      }
      default "5";
      description
        "SCTP max retransmissions";
    }
    leaf max-in-streams {
      type uint16 {
        range "1 .. 16";
      }
      default "16";
      description
        "Max supported inbound streams";
    }
    leaf max-out-streams {
      type uint16 {
        range "1 .. 16";
      }
      default "16";
      description
        "Max supported outbound streams";
    }
    leaf stale-conn-timeout {
      type uint16 {
        range "2 .. 10";
      }
      units "seconds";
      default "5";
      description
        "Stale/Idle connection timeout (secs)";
    }
  }

  container packet-core-sctp-cfg-data {
    description
      "Packet-Core SCTP Profile configuration data";
    container sctp-profiles {
      description
        "SCTP Profiles configuration";
      list sctp-profile {
        key "profile-name";
        description
          "SCTP profile config for Packet-Core";
        uses packet-core-sctp-cfg:sctp-profile;
      }
    }
  }
}
