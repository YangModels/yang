module Cisco-IOS-XE-packet-core-plmn-cfg {
  yang-version 1;
  namespace "http://cisco.com/ns/yang/Cisco-IOS-XE-packet-core-plmn-cfg";
  prefix packet-core-plmn-cfg;

  import Cisco-IOS-XE-packet-core-types {
    prefix packet-core-types;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Packet-Core served PLMN ID configurations.
     Copyright (c) 2021 by Cisco Systems, Inc.
     All rights reserved.";

  revision 2021-11-01 {
    description
      "Initial revision";
    reference
      "1.0.0";
    cisco-semver:module-version "1.0.0";
  }

  grouping snpn {
    description
      "Config for a Stand-alone Non-Public Network (SNPN)";
    leaf status {
      type boolean;
      must "(../status = 'true')" {
        error-message "SNPN cannot be administratively disabled";
        error-app-tag "must-violation";
      }
      default "true";
      description
        "Administrative state of SNPN";
    }
  }

  grouping plmn {
    description
      "PLMN configuration";
    leaf name {
      type string {
        length "1..32" {
          error-message "Invalid length for PLMN name: Valid length is 1 to 32 ASCII characters";
          error-app-tag "must-violation";
        }
        pattern '[!-~]([ -~]*[!-~])?' {
          error-message "Please use ASCII 32-126 characters and avoid leading/trailing spaces";
          error-app-tag "must-violation";
        }
      }
      description
        "PLMN Name";
    }
    leaf status {
      type boolean;
      default "false";
      description
        "Administrative state of PLMN";
    }
    container snpns {
      description
        "A list of Non-Public Networks (NPN), or more specifically,
         Stand-alone NPN (SNPNs) served under the configured PLMN";
      list snpn {
        key "assign-mode value";
        description
          "Standalone Non-Public Networks (NPN)";
        uses packet-core-plmn-cfg:snpn;
        uses packet-core-types:snpn-nid;
      }
    }
  }

  container packet-core-plmn-cfg-data {
    description
      "Packet-Core PLMN configuration data";
    container plmns {
      description
        "PLMNs configuration";
      list plmn {
        key "name";
        description
          "PLMN configuration for Packet-Core";
        uses packet-core-plmn-cfg:plmn;
        uses packet-core-types:plmn-id;
      }
    }
  }
}
