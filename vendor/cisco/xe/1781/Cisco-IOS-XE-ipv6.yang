submodule Cisco-IOS-XE-ipv6 {
  belongs-to Cisco-IOS-XE-native {
    prefix ios;
  }

  import cisco-semver {
    prefix cisco-semver;
  }
  import ietf-inet-types {
    prefix inet;
  }
  import Cisco-IOS-XE-types {
    prefix ios-types;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native IPv6 Yang Model.
     Copyright (c) 2016-2021 by Cisco Systems, Inc.
     All rights reserved.";

  revision 2022-03-01 {
    description
      "- Added error-interval for icmp
       - Changed 'ipv6 cef' model parameters";
    cisco-semver:module-version "5.1.0";
  }
  revision 2021-11-01 {
    description
      "- Initial revision for 17.7.1
       - Obsolete hop by hop option
       - Made start and last node obsolete
       - Added start-address and prefix-length node";
    cisco-semver:module-version "5.0.0";
  }
  revision 2021-07-01 {
    description
      "- Initial revision for 17.6.1
       - Added new node hop by hop processing
       - Deprecated 'address' node in 'source-guard' and replaced it with
         a new node 'address-config'";
    cisco-semver:module-version "4.3.0";
  }
  revision 2021-03-01 {
    description
      "- Add support for ipv6 icmp od-length enable
       - Add support for bridge all data traffic
       - Add support for ipv6 local pool";
    cisco-semver:module-version "4.2.0";
  }
  revision 2020-11-01 {
    description
      "- Added the missing commands to fill the gap between CLI and Yang for SISF
       - Added support for 'ipv6 icmp od-length enable' CLI";
    cisco-semver:module-version "4.1.0";
  }
  revision 2020-07-01 {
    description
      " - Moved ipv6 prefix list nodes to deprecate from obsolete
        - Added ipv6 local policy model";
    cisco-semver:module-version "4.0.0";
  }
  revision 2020-03-01 {
    description
      "- Added prefix-lists cli-remove-before-change for replace
       - Added range and default value for leaf distance
       - Added ipv6 deny-echo-reply";
    cisco-semver:module-version "3.0.0";
  }
  revision 2019-11-01 {
    description
      "- Added prefix-lists config";
    cisco-semver:module-version "2.0.0";
  }
  revision 2019-07-01 {
    description
      "- Establish semantic version baseline
       - Deprecate ipv6 router eigrp
       - Added ipv6 ospf
       - Added ipv6 address-validate";
    cisco-semver:module-version "1.0.0";
  }
  revision 2019-02-04 {
    description
      "Fixed a bug in ip prefix-list";
  }
  revision 2018-08-31 {
    description
      "Added model for ipv6 route static *";
  }
  revision 2018-07-23 {
    description
      "Removed tag option under ipv6 route * multicast";
  }
  revision 2018-06-28 {
    description
      "Added must constraints for deleting vrf";
  }
  revision 2017-07-05 {
    description
      "Adding model for ipv6 router ospf *";
  }
  revision 2017-05-17 {
    description
      "This revision fixes the problem in ipv6 route";
  }
  revision 2017-02-23 {
    description
      "Changes to support openconfig-network-instance mapping";
  }
  revision 2017-02-07 {
    description
      "Initial revision";
  }

  grouping ipv6-route-options-grouping {
    leaf distance {
      type uint8 {
        range "1..255";
      }
      default "1";
    }
    choice type-choice {
      leaf multicast {
        description
          "Route only usable by multicast";
        type empty;
      }
      leaf unicast {
        description
          "Route only usable by unicast";
        type empty;
      }
    }
    leaf tag {
      description
        "Tag value";
      type uint32;
      when 'not(../multicast)';
    }
    leaf track {
      description
        "Tracked";
      type uint32;
    }
    leaf name {
      description
        "Specify name of the next hop";
      type string;
    }
  }

  grouping ipv6-route-grouping {
    list ipv6-route-list {
      key "prefix";
      leaf prefix {
        type ios-types:ipv6-prefix;
      }
      list ipv6-fwd-list {
        key "fwd";
        leaf fwd {
          type union {
            type enumeration {
              enum Null0;
            }
            type inet:ipv6-address;
            type string;
          }
        }
        list interface-next-hop {
          description
            "IPv6 address of next-hop";
          key "ipv6-address";
          leaf ipv6-address {
            type inet:ipv6-address;
          }
          uses ipv6-route-options-grouping;
        }
        uses ipv6-route-options-grouping;
      }
    }
  }

  grouping ipv6-route-grouping-min-elements {
    list ipv6-route-list {
      key "prefix";
      min-elements 1;
      leaf prefix {
        type ios-types:ipv6-prefix;
      }
      list ipv6-fwd-list {
        key "fwd";
        leaf fwd {
          type union {
            type enumeration {
              enum Null0;
            }
            type inet:ipv6-address;
            type string;
          }
        }
        list interface-next-hop {
          description
            "IPv6 address of next-hop";
          key "ipv6-address";
          leaf ipv6-address {
            type inet:ipv6-address;
          }
          uses ipv6-route-options-grouping;
        }
        uses ipv6-route-options-grouping;
      }
    }
  }

  grouping ipv6-bfd-unassociate-grouping {
    leaf interface {
      type union {
        type enumeration {
          enum Null0;
        }
        type string;
      }
    }
    leaf ipv6 {
      description
        "IPv6 address of BFD neighbor";
      type inet:ipv6-address;
    }
    leaf unassociate {
      description
        "Unassociated Neighbor";
      when '../ipv6';
      type empty;
    }
  }

  grouping config-ipv6-grouping {
    container ipv6 {
      description
        "Global IPv6 configuration commands";
      container source-guard {
        description
          "Configure IPv6 sourceguard";
        list policy {
          description
            "Configure a policy for feature sourceguard";
          key "source-guard-policy-name";
          leaf source-guard-policy-name {
            type string;
          }
          container validate {
            description
              "Validate the src of the received data traffic";
            leaf address-config {
              description
                "Validate against addresses learned in NDP/DHCP traffic (default)";
              type boolean;
              default "true";
            }
            leaf address {
              status deprecated;
              description
                "DEPRECATED: deprecated and replaced by address-config";
              type empty;
            }
            leaf prefix {
              description
                "Validate against prefixes learned in RA or DHCP-PD traffic";
              type empty;
            }
          }
          container deny {
            description
              "Block data traffic";
            leaf global-autoconf {
              description
                "Drop data traffic from global autoconfigured addresses";
              type empty;
            }
          }
          container permit {
            description
              "Allow data traffic";
            leaf link-local {
              description
                "Allow data traffic from all Link-local addresses";
              type empty;
            }
          }
          leaf trusted {
            description
              "Bridge all data traffic";
            type empty;
          }
        }
      }
      container destination-guard {
        description
          "Configure Destination guard";
        list policy {
          description
            "Configure a policy for feature destguard";
          key "destination-guard-policy-name";
          leaf destination-guard-policy-name {
            type string;
          }
          container enforcement {
            description
              "Sets the enforcement level";
            leaf always {
              description
                "Enforced under all conditions (default)";
              type empty;
            }
            leaf stressed {
              description
                "Enforced when system is under stress";
              type empty;
            }
          }
        }
      }
      container dhcp {
        description
          "IPv6 DHCP";
      }
      container dhcp-relay {
        description
          "Configure IPv6 DHCP relay agent";
      }
      container access-list {
        description
          "Configure access lists";
      }
      leaf deny-echo-reply {
        description
          "Allow/Deny Echo-reply to anycast/multicast address";
        type empty;
      }
      leaf hbh-option {
        status obsolete;
        description
          "Hop by hop option processing enable";
        type empty;
      }
      leaf flowset {
        description
          "Set flow label random for originated packets";
        type empty;
      }
      leaf unicast-routing {
        description
          "Enable unicast routing";
        type empty;
      }
      leaf address-validate {
        description
          "Reserved Interface Identifiers validation";
        type boolean;
        default "true";
      }
      container icmp {
        description
          "Configure ICMP parameters";
        container od-length {
          description
            "Original Datagram Length";
          leaf enable {
            description
              "Enable Feature";
            default "true";
            type boolean;
          }
        }
        container error-interval {
          description
            "Interval between ICMP error messages";
          leaf interval {
            description
              "Interval between tokens in milliseconds";
            type uint32 {
              range "0..2147483647";
            }
            default "100";
          }
          leaf bucket {
            description
              "Bucket size";
            when '../interval';
            type uint8 {
              range "1..200";
            }
            default "10";
          }
        }
      }
      container local {
        description
          "Specify local options";
        container policy {
          description
            "Enable policy routing";
          leaf route-map {
            description
              "Policy route map";
            type string {
              length "1..222";
            }
          }
        }
        list pool {
          description
            "IPv6 Local address pool lists";
          key "id";
          leaf id {
            type union {
              type string;
              type enumeration {
                enum default;
              }
            }
          }
          leaf start {
            description
              "Obsolete - start";
            status obsolete;
            type inet:ipv6-address;
          }
          leaf start-address {
            description
              "X:X:X:X::X/<0-128>  IPv6 pool prefix x:x::y/<z>";
            type ios-types:ipv6-prefix;
          }
          leaf last {
            description
              "Obsolete - last";
            status obsolete;
            type inet:ipv6-address;
          }
          leaf prefix-length {
            description
              "Prefix length to assign from pool";
            type uint16 {
              range "1..128";
            }
          }
          leaf group {
            description
              "Create ip local pool group";
            type string {
              length "1..80";
            }
          }
        }
      }
      container multicast {
        description
          "Configure multicast related commands";
      }
      container cef {
        description
          "Cisco Express Forwarding";
        presence "true";
      }
      container nd {
        description
          "Configure IPv6 ND";
      }
      container ospf {
        description
          "Configure IPv6 OSPF";
        leaf name-lookup {
          description
            "Display OSPF router ids as DNS names";
          type empty;
        }
      }
      container pim {
        description
          "Configure Protocol Independent Multicast";
      }
      container route {
        description
          "Configure static routes";
        uses ipv6-route-grouping;
        list vrf {
          description
            "Configure static route for a VPN Routing/Forwarding instance";
          key "name";
          leaf name {
            must '/ios:native/ios:vrf/ios:definition[ios:name=current()] or /ios:native/ios:ip/ios:vrf[ios:name=current()]' {
              error-message "VRF must be created 1st, deleted last";
            }
            type string;
          }
          uses ipv6-route-grouping-min-elements;
        }
        container static {
          description
            "Configure static route attributes";
          container bfd {
            description
              "Configure a Static Route BFD neighbor";
            list iface_name {
              key "interface ipv6";
              uses ipv6-bfd-unassociate-grouping;
            }
            list vrf {
              description
                "IPv6 Routing table";
              key "name interface ipv6";
              leaf name {
                must "(/ios:native/ios:vrf/ios:definition[ios:name=current()] and
                       /ios:native/ios:vrf/ios:definition[ios:name=current()]/ios:address-family/ios:ipv6) or
                       /ios:native/ios:ip/ios:vrf[ios:name=current()]" {
                  error-message "IPv6 routing table vrf does not exist";
                }
                type string;
              }
              uses ipv6-bfd-unassociate-grouping;
            }
          }
          container resolve {
            description
              "Configure static route resolution";
            leaf default {
              description
                "Static route resolution via default";
              type empty;
            }
          }
        }
      }
      container router {
        description
          "Enable an IPV6 routing process";
        list eigrp {
          status obsolete;
          description
            "Enhanced Interior Gateway Routing Protocol (EIGRP)";
          key "id";
          leaf id {
            status obsolete;
            description
              "Autonomous System ID";
            type uint16 {
              range "1..65535";
            }
          }
        }
        list ospf {
          description
            "Open Shortest Path First (OSPFv3)";
          key "id";
          leaf id {
            description
              "Process ID";
            type uint16 {
              range "1..65535";
            }
          }
        }
      }
      leaf source-route {
        description
          "Process packets with source routing header options";
        type boolean;
      }
      container spd {
        description
          "spd";
        leaf mode {
          type enumeration {
            enum aggressive;
          }
        }
        container queue {
          description
            "queue";
          leaf max-threshold {
            description
              "Max threshold";
            type uint16 {
              range "0..65535";
            }
          }
          leaf min-threshold {
            description
              "Min threshold";
            must '. < ../max-threshold' {
              error-message "min-threshold must be less than max-threshold";
            }
            type uint16 {
              range "0..65535";
            }
          }
        }
      }
      container prefix-lists {
        description
          "Build a prefix list";
        list prefixes {
          key "name no";
          leaf name {
            type string {
              pattern '([^s].*)|(s[^e].*)|(se[^q].*)|(seq[^u].*)|(sequ[^e].*)|(seque[^n].*)|(sequen[^c].*)|(sequenc[^e].*)|(sequence[^\-].*)|(sequence\-[^n].*)|(sequence\-n[^u].*)|(sequence\-nu[^m].*)|(sequence\-num[^b].*)|(sequence\-numb[^e].*)|(sequence\-numbe[^r].*)|(sequence\-number..*)';
            }
          }
          leaf no {
            type uint32 {
              range "1..4294967294";
            }
          }
          leaf action {
            type enumeration {
              enum permit;
              enum deny;
            }
          }
          leaf ip {
            type inet:ipv6-prefix;
          }
          leaf ge {
            description
              "Minimum prefix length to be matched";
            type uint8 {
              range "1..128";
            }
          }
          leaf le {
            description
              "Maximum prefix length to be matched";
            type uint8 {
              range "1..128";
            }
          }
        }
        list prefix-list-description {
          key "name";
          leaf name {
            type string {
              pattern '([^s].*)|(s[^e].*)|(se[^q].*)|(seq[^u].*)|(sequ[^e].*)|(seque[^n].*)|(sequen[^c].*)|(sequenc[^e].*)|(sequence[^\-].*)|(sequence\-[^n].*)|(sequence\-n[^u].*)|(sequence\-nu[^m].*)|(sequence\-num[^b].*)|(sequence\-numb[^e].*)|(sequence\-numbe[^r].*)|(sequence\-number..*)';
            }
          }
          leaf description {
            description
              "Prefix-list specific description";
            type string {
              length "1..80";
            }
          }
        }
        leaf sequence-number {
          description
            "Include/exclude sequence numbers in NVGEN";
          type empty;
        }
      }
      container prefix-list {
        status deprecated;
        description
          "Build a prefix list";
        list prefixes {
          status deprecated;
          key "name";
          leaf name {
            status deprecated;
            type string {
              pattern '([^s].*)|(s[^e].*)|(se[^q].*)(seq[^u].*)|(sequ[^e].*)|(seque[^n].*)|(sequen[^c].*)|(sequenc[^e].*)|(sequence[^\-].*)|(sequence\-[^n].*)|(sequence\-n[^u].*)|(sequence\-nu[^m].*)|(sequence\-num[^b].*)|(sequence\-numb[^e].*)|(sequence\-numbe[^r].*)|(sequence\-number..*)';
            }
          }
          leaf description {
            status deprecated;
            description
              "Prefix-list specific description";
            type string {
              length "1..80";
            }
          }
          container permit {
            status deprecated;
            description
              "Specify packets to forward";
            leaf address {
              status deprecated;
              type ios-types:ipv6-prefix;
            }
            leaf ge {
              status deprecated;
              description
                "Minimum prefix length to be matched";
              type uint8 {
                range "0..128";
              }
            }
            leaf le {
              status deprecated;
              description
                "Maximum prefix length to be matched";
              type uint8 {
                range "0..128";
              }
            }
          }
          container deny {
            status deprecated;
            description
              "Specify packets to reject";
            leaf address {
              status deprecated;
              type ios-types:ipv6-prefix;
            }
            leaf ge {
              status deprecated;
              description
                "Minimum prefix length to be matched";
              type uint8 {
                range "0..128";
              }
            }
            leaf le {
              status deprecated;
              description
                "Maximum prefix length to be matched";
              type uint8 {
                range "0..128";
              }
            }
          }
          list seq {
            status deprecated;
            description
              "sequence number of an entry";
            key "no";
            leaf no {
              status deprecated;
              type uint32 {
                range "1..4294967294";
              }
            }
            container deny {
              status deprecated;
              description
                "Specify packets to reject";
              leaf ip {
                status deprecated;
                type ios-types:ipv6-prefix;
              }
              leaf ge {
                status deprecated;
                description
                  "Minimum prefix length to be matched";
                type uint16 {
                  range "1..128";
                }
              }
              leaf le {
                status deprecated;
                description
                  "Maximum prefix length to be matched";
                type uint16 {
                  range "1..128";
                }
              }
            }
            container permit {
              status deprecated;
              description
                "Specify packets to forward";
              leaf ip {
                status deprecated;
                type ios-types:ipv6-prefix;
              }
              leaf ge {
                status deprecated;
                description
                  "Minimum prefix length to be matched";
                type uint16 {
                  range "1..128";
                }
              }
              leaf le {
                status deprecated;
                description
                  "Maximum prefix length to be matched";
                type uint16 {
                  range "1..128";
                }
              }
            }
          }
        }
        leaf sequence-number {
          status deprecated;
          description
            "Include/exclude sequence numbers in NVGEN";
          type empty;
        }
      }
      list neighbor {
        description
          "Neighbor";
        key "address interface";
        leaf address {
          description
            "X:X:X:X::X  IPv6 address";
          type inet:ipv6-address;
        }
        leaf interface {
          type string;
        }
        leaf hardware-address {
          description
            "H.H.H  48-bit hardware address";
          type string;
        }
      }
      container visibility {
        description
          "NetFlow Global Command";
      }
    }
  }
}
