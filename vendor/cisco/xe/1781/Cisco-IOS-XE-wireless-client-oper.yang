module Cisco-IOS-XE-wireless-client-oper {
  yang-version 1;
  namespace "http://cisco.com/ns/yang/Cisco-IOS-XE-wireless-client-oper";
  prefix wireless-client-oper;

  import Cisco-IOS-XE-wireless-client-types {
    prefix wireless-client-types;
  }
  import Cisco-IOS-XE-wireless-enum-types {
    prefix wireless-enum-types;
  }
  import Cisco-IOS-XE-wireless-mobility-types {
    prefix wireless-mobility-types;
  }
  import Cisco-IOS-XE-wireless-types {
    prefix wireless-types;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for wireless client operational data.
     Copyright (c) 2016-2021 by Cisco Systems, Inc.
     All rights reserved.";

  revision 2022-03-01 {
    description
      "- Added additional client dot11 oper data";
    reference
      "7.8.0";
    cisco-semver:module-version "7.8.0";
  }
  revision 2021-11-01 {
    description
      "- Added SAE Password Element support
       - Added client receive group counter
       - Added SAE and OWE authentication ID numbers";
    reference
      "7.7.0";
    cisco-semver:module-version "7.7.0";
  }
  revision 2021-07-01 {
    description
      "- Added description for link-local bridge VLAN and enablement
       - Updated description of AP slot ID with invalid slot ID information
       - Added 6Ghz capability for client
       - Added enum for 6 GHz radio type and protocol type";
    reference
      "7.6.0";
    cisco-semver:module-version "7.6.0";
  }
  revision 2021-03-01 {
    description
      "- Added Group Management Cipher and Group Cipher info
       - Updated description string from Identity PSK P2P tag to PSK P2P tag
       - Removed device OS and vendor source constraints";
    reference
      "7.5.0";
    cisco-semver:module-version "7.5.0";
  }
  revision 2020-11-01 {
    description
      "- Updated description of client statistics parameters to display from network device perspective
       - Added WIFI to cellular steering info for client";
    reference
      "7.4.0";
    cisco-semver:module-version "7.4.0";
  }
  revision 2020-07-01 {
    description
      "- Added cellular info for client
       - Added WiFi direct client support
       - Added terms and conditions, subscription remediation and WNM deauthentication reason URL for Hotspot 2.0 release 3
       - Added VLAN information for client
       - Updated description string from User Private Network to User Defined (Private) Network";
    reference
      "7.3.0";
    cisco-semver:module-version "7.3.0";
  }
  revision 2020-03-01 {
    description
      " - Added EoGRE central forwarding
        - Added central NAT status for client
        - Added 802.11k Radio Measurement Enabled Capabilities of Client
        - Added 802.11k Radio Measurement for Beacon Report Request (Client Scan Report) parameters
        - Added parameter to indicate whether or not client's MAC address is locally administered";
    reference
      "7.2.0";
    cisco-semver:module-version "7.2.0";
  }
  revision 2019-11-01 {
    description
      " - Added User Private Network status for client
        - Added L3 VLAN Override status for client
        - Added User Private identity for client
        - Added Device Classifier Client Operational Data
        - Added AP local client state
        - Added Identity PSK Tag for Client
        - Added Country Name to Device Classifier Client-
          Operational Data, an additional protocol for Device-
          Classification
        - Added Method in Client Operational Data";
    reference
      "7.1.0";
    cisco-semver:module-version "7.1.0";
  }
  revision 2019-07-26 {
    description
      "- Added Hotspot 2.0 client data
       - Added when constraint to wlan-id
       - Added MBO client non-oper/non-preferred channel info
       - Added additional information for wired clients
       - Added run latency and dot11 roam type in mobility history
       - Added additional information for supported channels,
         host name and operating system name of the clients
       - Added tx-retries and username
       - Added semantic version
       - Added Method in Client Operational Data";
    reference
      "7.0.0";
    cisco-semver:module-version "7.0.0";
  }
  revision 2019-01-01 {
    description
      " - EoGRE related information and join time for client
        - Add Guest Lan Client attribute
        - Removal of unused leaves
        - Cleaned up spelling errors in descriptions
        - Addition of mobility discovery throttles under CAC statistics
        - Added a counter that indicates move count of foreign client
        - Adding EoGRE related fields and containers
        - Removed unnecessary enums from exclusion auth method
        - Renamed mobility interface client stats container
        - Added client mobility history data
        - Removed mobility interface events stats
        - Changing description of the fields
        - Modified 802.11k neighbor list related information
        - Added association time field";
    reference
      "6.0.0";
    cisco-semver:module-version "6.0.0";
  }
  revision 2018-11-24 {
    description
      "- Remove leaf client-active
       - Add Units for mm-complete-timestamp
       - Remove binary encoded buffers
       - Add HE capable client flag
       - Add MMIF internal error statistics
       - Hiding SANET and some of client oper fields";
    reference
      "5.0.0";
    cisco-semver:module-version "5.0.0";
  }
  revision 2018-03-22 {
    description
      "Addition of location-info node. Enum value changes";
    reference
      "4.0.0";
    cisco-semver:module-version "4.0.0";
  }
  revision 2018-03-21 {
    description
      "Removal of location-info node";
    reference
      "3.0.0";
    cisco-semver:module-version "3.0.0";
  }
  revision 2018-01-24 {
    description
      "The first generally available version";
    reference
      "2.0.0";
    cisco-semver:module-version "2.0.0";
  }
  revision 2017-09-25 {
    description
      "Properly indicated leaf-list ordering";
    reference
      "1.1.0";
    cisco-semver:module-version "1.1.0";
  }
  revision 2017-05-05 {
    description
      "Initial revision";
    reference
      "1.0.0";
    cisco-semver:module-version "1.0.0";
  }

  typedef dot11i-auth-key-mgmt-type {
    type enumeration {
      enum akm-unknown {
        value 0;
        description
          "The client's AKM type is Unknown";
      }
      enum 8021x {
        value 1;
        description
          "The client's AKM type is IEEE 802.1X";
      }
      enum psk {
        value 2;
        description
          "The client's AKM type is PSK";
      }
      enum ft-8021x {
        value 3;
        description
          "The client's AKM type is Fast Transition (FT)-802.1x";
      }
      enum ft-psk {
        value 4;
        description
          "The client's AKM type is Fast Transition (FT)-PSK";
      }
      enum 8021x-sha256 {
        value 5;
        description
          "The client's AKM type is IEEE 802.1X with SHA256 key derivation";
      }
      enum psk-sha256 {
        value 6;
        description
          "The client's AKM type is PSK SHA256 key derivation";
      }
      enum sae {
        value 8;
        description
          "The client's AKM type is Simultaneous Authentication of Equals (SAE)";
      }
      enum ft-sae {
        value 9;
        description
          "The client's AKM type is Fast Transition (FT)-SAE";
      }
      enum suiteb-1x {
        value 11;
        description
          "The client's AKM type is SUITEB-1X";
      }
      enum suiteb192-1x {
        value 12;
        description
          "The client's AKM type is SUITEB192-1X";
      }
      enum owe {
        value 18;
        description
          "The client's AKM type is OWE";
      }
    }
    description
      "List of Authentication Key Management (AKM) type(s) for the client";
  }

  typedef encrypt-policy {
    type enumeration {
      enum encryp-policy-wep104 {
        value 0;
        description
          "The Encryption policy type for the client is WEP (104 bits)";
      }
      enum encryp-policy-none {
        value 1;
        description
          "There is no Encryption policy type for the client";
      }
      enum encryp-policy-wep40 {
        value 2;
        description
          "The Encryption policy type for the client is WEP (40 bits)";
      }
      enum encryp-policy-wep128 {
        value 3;
        description
          "The Encryption policy type for the client is WEP (128 bits)";
      }
      enum encryp-policy-aes-ccm128 {
        value 4;
        description
          "The Encryption policy type for the client is AES-CCMP (128 bits)";
      }
      enum encryp-policy-tkip-mic {
        value 5;
        description
          "The Encryption policy type for the client is TKIP-MIC";
      }
      enum encryp-policy-cisco-tkip-wep40 {
        value 6;
        description
          "The Encryption policy type for the client is CKIP-WEP (40 bits)";
      }
      enum encryp-policy-cisco-tkip-wep104 {
        value 7;
        description
          "The Encryption policy type for the client is CKIP-WEP (104 bits)";
      }
      enum encryp-policy-cisco-tkip-wep128 {
        value 8;
        description
          "The Encryption policy type for the client is CKIP-WEP (128 bits)";
      }
      enum encryp-policy-ckip-kp-40 {
        value 9;
        description
          "The Encryption policy type for the client is CKIP-KeyPermutation (40 bits)";
      }
      enum encryp-policy-ckip-kp-104 {
        value 10;
        description
          "The Encryption policy type for the client is CKIP-KeyPermutation (104 bits)";
      }
      enum encryp-policy-ckip-mmh-40 {
        value 11;
        description
          "The Encryption policy type for the client is CKIP-MMH (40 bits)";
      }
      enum encryp-policy-ckip-mmh-104 {
        value 12;
        description
          "The Encryption policy type for the client is CKIP-MMH (104 bits)";
      }
      enum encryp-policy-ckip-kp-mmh-40 {
        value 13;
        description
          "The Encryption policy type for the client is CKIP-KeyPermutation with MMH (40 bits)";
      }
      enum encryp-policy-ckip-kp-mmh-104 {
        value 14;
        description
          "The Encryption policy type for the client is CKIP-KeyPermutation with MMH (104 bits)";
      }
      enum encryp-policy-wapi-sms4 {
        value 15;
        description
          "The Encryption policy type for the client is WAPI";
      }
      enum encryp-policy-aes-gcmp128 {
        value 20;
        description
          "The Encryption policy type for the client is GCMP128";
      }
      enum encryp-policy-aes-gcmp256 {
        value 21;
        description
          "The Encryption policy type for the client is GCMP256";
      }
      enum encryp-policy-aes-ccmp256 {
        value 22;
        description
          "The Encryption policy type for the client is CCMP256";
      }
    }
    description
      "List of encryption policy types for the client send in add mobile.";
  }

  typedef cellular-network-type {
    type enumeration {
      enum cellular-unknown {
        value 0;
        description
          "Client's cellular network type is unknown";
      }
      enum cellular-2g {
        value 1;
        description
          "Client's cellular network type is GPRS, EDGE, or CDMA";
      }
      enum cellular-3g {
        value 2;
        description
          "Client's cellular network type is UMTS, EVDO, HSDPA, or HSUPA";
      }
      enum cellular-4g {
        value 3;
        description
          "Client's cellular network type is LTE";
      }
      enum cellular-5g {
        value 4;
        description
          "Client's cellular network type is 5G";
      }
    }
    description
      "This data type indicates the client's cellular network type";
  }

  typedef cellular-signal-scale {
    type enumeration {
      enum cellular-signal-none {
        value 0;
        description
          "Client's cellular signal strength is unknown";
      }
      enum cellular-signal-poor {
        value 1;
        description
          "Client's cellular signal strength is poor";
      }
      enum cellular-signal-moderate {
        value 2;
        description
          "Client's cellular signal strength is moderate";
      }
      enum cellular-signal-good {
        value 3;
        description
          "Client's cellular signal strength is good";
      }
      enum cellular-signal-great {
        value 4;
        description
          "Client's cellular signal strength is great";
      }
      enum cellular-signal-excellent {
        value 5;
        description
          "Client's cellular signal strength is excellent";
      }
    }
    description
      "This data type indicates the client's cellular signal strength";
  }

  typedef dot11-sae-pwe {
    type enumeration {
      enum sae-pwe-mode-none {
        value 0;
        description
          "SAE Password Element mode unknown";
      }
      enum sae-hunting-and-pecking {
        value 1;
        description
          "SAE Password Element Hunting and Pecking";
      }
      enum sae-hash-to-element {
        value 2;
        description
          "SAE Password Element Hash to Element";
      }
    }
    description
      "This data type indicates sae password element mode for client";
  }

  typedef client-authentication-type {
    type enumeration {
      enum client-authentication-type-local {
        value 0;
        description
          "The client is Locally authenticated";
      }
      enum client-authentication-type-central {
        value 1;
        description
          "The client is Centrally authenticated";
      }
      enum client-is-non-hreap {
        value 2;
        description
          "AP to which the client is connected is in local mode. Authentication type is supported only when the AP is Flex-Connect Mode";
      }
    }
    description
      "This data type indicates whether the client is centrally (on Controller) or locally (on AP) authenticated";
  }

  typedef client-switching-mode {
    type enumeration {
      enum client-switching-mode-unknown {
        value 0;
        description
          "The switching mode of the client traffic is unknown";
      }
      enum local {
        value 1;
        description
          "The client traffic is locally switched from the AP";
      }
      enum central {
        value 2;
        description
          "The client traffic is centrally switched from Wireless LAN Controller";
      }
    }
    description
      "This data type indicates whether the data from the client is centrally (on Controller) or locally (on AP) switched";
  }

  typedef authentication-method-id {
    type enumeration {
      enum no-method-id {
        value 0;
        description
          "No Authentication method";
      }
      enum dot1x-auth-id {
        value 1;
        description
          "IEEE 802.1X Authentication method";
      }
      enum mab-id {
        value 2;
        description
          "MAC Authentication method";
      }
      enum web-auth-id {
        value 3;
        description
          "Web Authentication method";
      }
      enum static-method-id {
        value 4;
        description
          "Static method";
      }
      enum eou {
        value 5;
        description
          "EAP Over UDP method";
      }
      enum dot1x-supp-id {
        value 6;
        description
          "IEEE 802.1X Supplicant method";
      }
      enum sae-id {
        value 7;
        description
          "WPA3 SAE Authentication method";
      }
      enum owe-id {
        value 8;
        description
          "WPA3 OWE Authentication method";
      }
    }
    description
      "Authentication method";
  }

  typedef dc-db-attr-type-e {
    type enumeration {
      enum proto-none {
        value 0;
        description
          "Protocol Not Assigned";
      }
      enum proto-oui {
        value 1;
        description
          "Protocol OUI";
      }
      enum proto-cdp {
        value 2;
        description
          "Protocol CDP";
      }
      enum proto-lldp {
        value 3;
        description
          "Protocol LLDP";
      }
      enum proto-dhcp {
        value 4;
        description
          "Protocol DHCP";
      }
      enum proto-mdns {
        value 5;
        description
          "Protocol MDNS";
      }
      enum proto-http {
        value 6;
        description
          "Protocol HTTP";
      }
      enum proto-sip {
        value 7;
        description
          "Protocol SIP";
      }
      enum proto-h323 {
        value 8;
        description
          "Protocol H323";
      }
      enum proto-snmp {
        value 9;
        description
          "Protocol SNMP";
      }
      enum proto-nmap {
        value 10;
        description
          "Protocol Network Mapper";
      }
      enum proto-dot11-device-analytics {
        value 11;
        description
          "802.11 Association Frames for Vendor Mobile Clients";
      }
    }
    description
      "Device Classifier Protocol Source";
  }

  typedef dc-power-type-e {
    type enumeration {
      enum power-none {
        value 0;
        description
          "Power Type Not Assigned";
      }
      enum ac-powered {
        value 1;
        description
          "Power Type AC";
      }
      enum dc-powered {
        value 2;
        description
          "Power Type DC";
      }
    }
    description
      "Device Classifier Power Type";
  }

  typedef upn-status {
    type bits {
      bit upn-enable {
        position 0;
        description
          "User Defined (Private) Network enable bit.";
      }
      bit upn-unicast-drop-enable {
        position 1;
        description
          "User Defined (Private) Network Drop Unicast bit.";
      }
    }
    description
      "User Defined (Private) Network enable status flags for the client.";
  }

  typedef protocol-map {
    type bits {
      bit protocol-map-oui {
        position 0;
        description
          "OUI Based Classification Bit";
      }
      bit protocol-map-cdp {
        position 1;
        description
          "CDP Based Classification Bit";
      }
      bit protocol-map-lldp {
        position 2;
        description
          "LLDP Based Classification Bit";
      }
      bit protocol-map-dhcp {
        position 3;
        description
          "DHCP Based Classification Bit";
      }
      bit protocol-map-mdns {
        position 4;
        description
          "MDNS Based Classification Bit";
      }
      bit protocol-map-http {
        position 5;
        description
          "HTTP Based Classification Bit";
      }
      bit protocol-map-sip {
        position 6;
        description
          "SIP Based Classification Bit";
      }
      bit protocol-map-h323 {
        position 7;
        description
          "H323 Based Classification Bit";
      }
      bit protocol-map-snmp {
        position 8;
        description
          "SNMP Based Classification Bit";
      }
      bit protocol-map-nmap {
        position 9;
        description
          "Network Mapper Based Classification Bit";
      }
      bit protocol-map-dot11-device-analytics {
        position 10;
        description
          "802.11 Association Frames Based Classification Bit for different Vendors";
      }
    }
    description
      "Flags for Protocols used for Client Classification";
  }

  grouping ms-wifi {
    description
      "WiFi security details of the client";
    leaf wpa-version {
      type wireless-client-types:dot11-eap-wpa-version;
      description
        "WPA version of the client";
    }
    leaf cipher-suite {
      type wireless-client-types:dot11i-cipher-suite;
      description
        "IEEE 802.11i Cipher Suite type";
    }
    leaf auth-key-mgmt {
      type wireless-client-oper:dot11i-auth-key-mgmt-type;
      description
        "IEEE 802.11i Authentication Key Management information";
    }
    leaf group-mgmt-cipher-suite {
      type wireless-client-types:dot11i-cipher-suite;
      description
        "IEEE 802.11i Group Management Cipher Suite";
    }
    leaf group-cipher-suite {
      type wireless-client-types:dot11i-cipher-suite;
      description
        "IEEE 802.11i Group Cipher Suite";
    }
    leaf pwe-mode {
      type wireless-client-oper:dot11-sae-pwe;
      description
        "SAE Password Element Mode";
    }
  }

  grouping ms-supported-channels {
    description
      "List of supported channels";
    leaf-list supported-channels-list {
      type uint8;
      max-elements 50;
      ordered-by user;
      description
        "List of supported channels";
    }
  }

  grouping dot11k-rm-beacon-meas-req-oper {
    description
      "802.11k Radio Measurement for Beacon Report Request (Client Scan Report)";
    leaf period {
      type uint32;
      units "seconds";
      description
        "Period/interval to request measurements in seconds.";
    }
    leaf repeat-num {
      when 'not(boolean(../repeat-forever))';
      type uint32;
      description
        "Number of times left to repeat requests.";
    }
    leaf repeat-forever {
      type empty;
      description
        "Present if continually repeating requests for measurements (until cleared).";
    }
    leaf all-cisco-operating-classes {
      type empty;
      description
        "Present if requesting beacon measurements for all Cisco network channels in set of six
         operating classes: {81, 82, 115, 118, 121, 124}. False if requesting a single
         operating-class.";
    }
    leaf operating-class {
      when 'not(boolean(../all-cisco-operating-classes))';
      type uint8;
      description
        "Specific operating class to request beacon measurements from. Only used if
         all-cisco-operating-classes is False. Validated operating classes are:
         81, 82, 115, 118, 121, 124.";
    }
    leaf channel-num {
      type uint8;
      description
        "Specific channel number to request beacon measurements for. A channel number
         of 0 indicates requesting for beacon measurements on all channels in the
         requested operating class.";
    }
    leaf meas-mode {
      type wireless-enum-types:dot11k-rm-beacon-measurement-scan-report-measurement-modes;
      description
        "Measurement mode to control how requested beacon measurements are measured.
           (0) Passive - Passively measure beacons without probing.
           (1) Active - Actively measure beacons with probing.
           (2) Table - Report stored beacon measurements already received.";
    }
    leaf current-bssid {
      type boolean;
      description
        "True if BSSID/AP to request beacon measurements for will always be the BSSID of
         the AP the client is associated to.";
    }
    leaf bssid {
      type yang:mac-address;
      description
        "BSSID/AP to request beacon measurements for. The wildcard BSSID is used to request
         beacon measurements for all neighboring BSSs/APs.";
    }
    leaf current-ssid {
      type boolean;
      description
        "True if SSID/WLAN to request beacon measurements for will always be the SSID of
         the WLAN the client is associated to.";
    }
    leaf ssid {
      type string;
      description
        "SSID name to request beacon measurements for. An empty (zero-length)
         SSID string is used to request beacon measurements for all WLAN/SSIDs,
         even from rogue networks/APs.";
    }
    leaf default-rand-interval {
      type boolean;
      description
        "True if the maximum start delay (randomization interval) for the client to start beacon
         measurements is set to the default of passive/active = 128 msec, table = 0 msec.";
    }
    leaf rand-interval {
      type uint32;
      units "milliseconds";
      description
        "Randomization Interval: Maximum measurement start delay for the client to randomly
         start the beacon measurement in msec.";
    }
    leaf default-meas-duration {
      type boolean;
      description
        "True if the measurement duration for the client to measure beacons is set to the default
         of passive = 112 msec, active = 112 msec, table = 0 msec.";
    }
    leaf meas-duration {
      type uint32;
      units "milliseconds";
      description
        "Measurement Duration: Maximum measurement duration for client to measure beacons in msec.";
    }
    leaf dialog-token {
      type uint8;
      description
        "Dialog token used in the last request, beginning from 1 and wrapping at 255.";
    }
    leaf last-req-trigger {
      type wireless-enum-types:dot11k-rm-beacon-measurement-scan-report-triggers;
      description
        "Action which triggered the last request to be sent.";
    }
    leaf last-req-time {
      type yang:date-and-time;
      description
        "Timestamp of when last request was sent.";
    }
    leaf next-req-time {
      type yang:date-and-time;
      description
        "Timestamp of when next request will be sent.";
    }
    leaf last-report-time {
      type yang:date-and-time;
      description
        "Timestamp of when the last beacon scan report was received.";
    }
  }

  grouping dot11-wfd-client-cap {
    description
      "WiFi direct client capabilities";
    leaf wifi-direct-capable {
      type boolean;
      description
        "Whether client is WiFi direct capable";
    }
    leaf is-wlan-infra-managed {
      when "../wifi-direct-capable = 'true'";
      type boolean;
      description
        "Whether client is capable of being managed by the WLAN ";
    }
    leaf is-concurrent-oper-capable {
      when "../wifi-direct-capable = 'true'";
      type boolean;
      description
        "Whether client supports concurrent operation with WLAN";
    }
    leaf is-providing-xconnect {
      when "../wifi-direct-capable = 'true'";
      type boolean;
      description
        "Whether client is hosting a P2P Group that provides cross connection";
    }
  }

  grouping ewlc-eogre-client {
    description
      "EoGRE Client information";
    leaf is-eogre {
      type boolean;
      description
        "Whether this is an EoGRE client";
    }
    leaf previous-match-reason {
      type wireless-enum-types:eogre-client-match-reason;
      description
        "Previous output of the match process of client to EoGRE client";
    }
    leaf match-reason {
      type wireless-enum-types:eogre-client-match-reason;
      description
        "Output of the match process of client to EoGRE client";
    }
    leaf is-aaa-data {
      type boolean;
      description
        "Is AAA override received for this client";
    }
    leaf realm {
      type string;
      description
        "Client's realm matching EoGRE rule";
    }
    leaf vlan {
      type uint16 {
        range "1 .. 4094";
      }
      description
        "Vlan tagging for EoGRE client traffic";
    }
    leaf domain {
      type string;
      description
        "EoGRE domain";
    }
    leaf primary-gw {
      type inet:ip-address;
      description
        "IP address of the primary gateway";
    }
    leaf secondary-gw {
      type inet:ip-address;
      description
        "IP address of the secondary gateway";
    }
    leaf plumbed-gw {
      type string;
      description
        "Tunnel Gateway Name programmed to carry client traffic";
    }
    leaf tunnel-ifid {
      type uint32;
      description
        "Tunnel Gateway datapath index";
    }
    leaf is-central-fwd {
      type boolean;
      description
        "Client is centrally forwarded";
    }
  }

  grouping client-dot11k-neighbor-list {
    description
      "802.11k neighbor list";
    leaf-list dot11k-neighbor {
      type yang:mac-address;
      max-elements 9;
      ordered-by user;
      description
        "Neighbor Radio Identifier";
    }
  }

  grouping hotspot20-data {
    description
      "Mobile station Hotspot 2.0 information";
    leaf is-hs20 {
      type boolean;
      description
        "is Hotspot 2.0 data received for this client";
    }
    leaf version {
      type wireless-enum-types:enm-hs20-supported-version;
      description
        "Supported Hotspot release version";
    }
    leaf consortium-oi {
      type string;
      description
        "Roaming consortium membership OI";
    }
    leaf pps-mo-id {
      type uint16;
      description
        "Per provider subscription";
    }
    leaf swt-timer {
      type uint16;
      description
        "Session Warning Timer value";
    }
    leaf swt-timestamp {
      type yang:date-and-time;
      description
        "SWT timestamp";
    }
    leaf terms-conditions-url {
      type string;
      description
        "Terms and conditions URL";
    }
    leaf subscription-remediation-url {
      type string;
      description
        "Subscription remediation URL";
    }
    leaf deauth-reason-url {
      type string;
      description
        "WNM deauthentication reason URL";
    }
  }

  grouping st-ap-local-client-state {
    description
      "State for locally authenticated/associated client";
    leaf-list acl-names {
      type string;
      max-elements 25;
      ordered-by user;
      description
        "Client's ACL list";
    }
    leaf-list client-state-servers {
      type yang:mac-address;
      max-elements 10;
      ordered-by user;
      description
        "List of client's state backup servers";
    }
  }

  grouping cellular-information {
    description
      "Client's cellular information";
    leaf capable {
      type boolean;
      description
        "Indicates whether client is cellular capable";
    }
    leaf network-type {
      type wireless-client-oper:cellular-network-type;
      description
        "Cellular network type";
    }
    leaf signal-scale {
      type wireless-client-oper:cellular-signal-scale;
      description
        "Cellular signal strength(none,poor,moderate,good,great,excellent)";
    }
    leaf cell-id {
      type uint16;
      description
        "Cellular cell identifier";
    }
  }

  grouping ewlc-client-dot11-oper-data {
    description
      "IEEE 802.11 operational data of the client";
    leaf ms-mac-address {
      type yang:mac-address;
      description
        "Mac Address of the Client";
    }
    leaf dot11-state {
      type wireless-client-types:dot11-state;
      description
        "DOT11 status for Client";
    }
    leaf ms-bssid {
      type yang:mac-address;
      description
        "Basic Service Set Identifier to which the Mobile station is connected. MAC addresses are used as a network address for most IEEE 802 network technologies, including Ethernet, Wi-Fi and Bluetooth.";
    }
    leaf ap-mac-address {
      type yang:mac-address;
      description
        "MAC Address of the Access Point to which the client has joined. MAC addresses are used as a network address for most IEEE 802 network technologies, including Ethernet, Wi-Fi and Bluetooth.";
    }
    leaf current-channel {
      type uint8;
      description
        "Current Channel on which the wireless client is communicating with Access Point in the wireless LAN.";
    }
    leaf ms-wlan-id {
      type uint32;
      description
        "Wireless LAN ID to which the client is connected in the wireless network.";
    }
    leaf vap-ssid {
      when "(../ewlc-ms-phy-type!='client-802-3')";
      type string;
      description
        "Service Set Identifier (SSID) of the Wireless LAN to which the client is connected.";
    }
    leaf policy-profile {
      type string;
      description
        "Policy profile applied on the Wireless LAN to which the wireless client is connected";
    }
    leaf ms-ap-slot-id {
      type uint8;
      description
        "Slot ID of the access point radio on which the wireless client is connected, slot 255 represents invalid slot ID.";
    }
    leaf radio-type {
      type wireless-client-types:ms-radio-type;
      description
        "Type of the Radio of the AP to which the client is associated";
    }
    leaf ms-association-id {
      type uint16;
      description
        "Association ID of the mobile station";
    }
    leaf ms-reason-code {
      type wireless-client-types:reason-code;
      description
        "Updated when the mobile station sends an unsolicited deauthentication or disassociation frame";
    }
    leaf ms-assoc-time {
      type yang:date-and-time;
      description
        "The time at which the association request is received from the mobile station to wireless LAN.";
    }
    leaf is-11g-client {
      type boolean;
      description
        "Flag indicating whether the client is connected through IEEE 802.11g protocol";
    }
    container ms-wifi {
      description
        "WiFi security of Mobile Station used during the association.";
      uses wireless-client-oper:ms-wifi;
    }
    leaf ms-wme-enabled {
      type boolean;
      description
        "Indicator whether Wireless Multimedia Extensions is enabled, or not";
    }
    leaf dot11w-enabled {
      type boolean;
      description
        "Flag indicator for IEEE 802.11w feature is enabled";
    }
    container dot11k-neighbor-list {
      description
        "802.11k neighbor list";
      uses wireless-client-oper:client-dot11k-neighbor-list;
    }
    leaf ewlc-ms-phy-type {
      type wireless-client-types:ms-phy-radio-type;
      description
        "Radio PHY type to which the wireless mobile station is connected";
    }
    leaf encryption-type {
      type wireless-client-oper:encrypt-policy;
      description
        "Encryption policy used by the client while communicating with Access Point.";
    }
    leaf client-wep-policy-type {
      type wireless-client-types:client-wep-policy-type;
      description
        "Client Wired Equivalent Privacy (WEP) policy type";
    }
    leaf bss-trans-capable {
      type boolean;
      description
        "Indicator whether the client is IEEE 802.11v capable";
    }
    leaf ms-apple-capable {
      type boolean;
      description
        "Indicator whether client has Fastlane Support";
    }
    leaf wlan-profile {
      type string;
      description
        "Profile applied on the Wireless/Remote/Guest LAN to which the client is connected";
    }
    leaf dms-capable {
      type boolean;
      description
        "Indicator if client is Directed Multicast Service (DMS) Capable";
    }
    container eogre-client {
      description
        "EoGRE Client information";
      uses wireless-client-oper:ewlc-eogre-client;
    }
    container ms-hs20-data {
      description
        "Hotspot client info";
      uses wireless-client-oper:hotspot20-data;
    }
    leaf qosmap-capable {
      type boolean;
      description
        "QoS Map Capability";
    }
    leaf-list non-oper-chan {
      type uint8;
      max-elements 64;
      ordered-by user;
      description
        "List of client's non-operable channels";
    }
    leaf-list non-prefer-chan {
      type uint8;
      max-elements 64;
      ordered-by user;
      description
        "List of client's non-prefer channels";
    }
    container ms-supported-channels-list {
      description
        "List of supported channels";
      uses wireless-client-oper:ms-supported-channels;
    }
    container ap-local-client-state {
      description
        "AP local client state";
      uses wireless-client-oper:st-ap-local-client-state;
    }
    leaf rm-capabilities {
      type wireless-types:flag-dot11k-rm-capabilities;
      description
        "802.11k Radio Measurement Enabled Capabilities";
    }
    container dot11k-rm-beacon-meas-req-parameters {
      description
        "802.11k Radio Measurement for Beacon Report Request (Client Scan Report)";
      uses wireless-client-oper:dot11k-rm-beacon-meas-req-oper;
    }
    container cellular-info {
      description
        "Contains client's cellular information";
      uses wireless-client-oper:cellular-information;
    }
    container wifi-direct-client-capabilities {
      description
        "WiFi direct (P2P) client capabilities";
      uses wireless-client-oper:dot11-wfd-client-cap;
    }
    leaf wtc-support {
      type boolean;
      description
        "Client's WIFI to cellular steering support";
    }
    leaf abr-support {
      type boolean;
      description
        "Client's aggregate beacon request support";
    }
    leaf wtc-resp {
      type boolean;
      description
        "Indicates whether client send WIFI to cellular response in BSS transition response";
    }
    leaf wtc-resp-code {
      type uint8;
      description
        "Client's WIFI to cellular response code";
    }
    leaf dot11-6ghz-cap {
      type boolean;
      description
        "Indicates whether this client is 6Ghz capable";
    }
    leaf link-local-enable {
      type boolean;
      description
        "Indicates whether the link-local bridging feature is enabled for this client";
    }
    leaf link-local-vlan-id {
      when "../link-local-enable = 'true' and /client-oper-data/mobility-oper-data[ms-mac-addr = current()/../ms-mac-address]/mm-client-role != 'mm-client-role-anchor'";
      type uint16;
      description
        "The link-local bridge VLAN for this client";
    }
  }

  grouping mmif-client-mobility-history-entry {
    description
      "Client association and mobility history data";
    leaf instance-id {
      type uint32;
      description
        "Wireless management process instance to which client has associated";
    }
    leaf ms-ap-slot-id {
      type uint32;
      description
        "Wireless access point slot ID to which client has connected, slot 255 represents invalid slot ID.";
    }
    leaf ms-assoc-time {
      type yang:date-and-time;
      description
        "Client association timestamp";
    }
    leaf role {
      type wireless-mobility-types:mm-client-role;
      description
        "Client mobility role";
    }
    leaf bssid {
      type yang:mac-address;
      description
        "BSSID to which client has associated";
    }
    leaf ap-name {
      type string;
      description
        "Name of wireless access point to which client has associated";
    }
    leaf run-latency {
      type uint32;
      units "milli-seconds";
      description
        "Time taken by client to reach 'RUN' state";
    }
    leaf dot11-roam-type {
      type wireless-mobility-types:dot11-client-roam-type;
      description
        "Dot11 roam type";
    }
  }

  grouping mmif-client-mobility-history {
    description
      "List of client's association and mobility history entries";
    list entry {
      description
        "Client association and mobility history entry";
      uses wireless-client-oper:mmif-client-mobility-history-entry;
    }
  }

  grouping mmif-client-history {
    description
      "Client association and mobility history";
    leaf client-mac {
      type yang:mac-address;
      description
        "Client MAC address";
    }
    container mobility-history {
      description
        "Client association and mobility history of client";
      uses wireless-client-oper:mmif-client-mobility-history;
    }
  }

  grouping mmif-client-stats {
    description
      "Mobility Interface client statistics";
    leaf client-mac {
      type yang:mac-address;
      description
        "MAC Address of the wireless client. MAC addresses are used as a network address for most IEEE 802 network technologies, including Ethernet, Wi-Fi and Bluetooth.";
    }
    container mblty-stats {
      description
        "Mobility Interface mobility event statistics";
      uses wireless-mobility-types:mmif-mobility-stats;
    }
    list ipc-stats {
      max-elements 255;
      description
        "Inter-process messaging statistics for mobility control CAPWAP messages";
      uses wireless-mobility-types:mm-msg-stats;
    }
  }

  grouping ewlc-mafsm-oper-data {
    description
      "Client mobility data";
    leaf ms-mac-addr {
      type yang:mac-address;
      description
        "MAC address of wireless mobile station";
    }
    leaf mm-client-role {
      type wireless-mobility-types:mm-client-role;
      description
        "Mobility role of wireless mobile stations on Wireless LAN Controller";
    }
    leaf mm-client-roam-type {
      type wireless-mobility-types:mm-client-roam-type;
      description
        "Roam type indicates Layer 2 or Layer 3 mobility roam by client";
    }
    leaf mm-instance {
      type uint32;
      description
        "Move count of client indicating number of inter-controller roams performed by client";
    }
    leaf mm-complete-timestamp {
      type yang:date-and-time;
      description
        "Timestamp at which mobility discovery was completed for client";
    }
    leaf mm-remote-tunnel-ip {
      type inet:ip-address;
      description
        "Primary IP address of mobility peer for an anchor or foreign client";
    }
    leaf mm-remote-tunnel-sec-ip {
      type inet:ip-address;
      description
        "Secondary IP address of mobility peer for an anchor or foreign client";
    }
    leaf mm-remote-platform-id {
      type uint8;
      description
        "Platform ID of mobility peer for an anchor or foreign client";
    }
    leaf mm-remote-tunnel-id {
      type uint32;
      description
        "Mobility peer tunnel identifier for an anchor or foreign client";
    }
    leaf mm-anchor-ip {
      type inet:ip-address;
      description
        "Anchor wireless LAN controller's address for a foreign client";
    }
  }

  grouping ewlc-client-wlan-policy {
    description
      "Client WLAN policy";
    leaf current-switching-mode {
      type wireless-client-oper:client-switching-mode;
      description
        "Client traffic can be switched locally from Access Point or Centrally from the Wireless LAN Controller. Current switching mode indicates the type of switched used for the client traffic";
    }
    leaf wlan-switching-mode {
      type wireless-client-oper:client-switching-mode;
      description
        "All clients joined the Wireless LAN will have the same traffic switching mode. Wlan switching mode, which is initialized based on the WLAN properties";
    }
    leaf central-authentication {
      type wireless-client-oper:client-authentication-type;
      description
        "Indicator of whether the client is centrally through Wireless LAN Controller or locally through Access Point authenticated. NA for clients connected to Local Mode Access Points";
    }
    leaf central-dhcp {
      type boolean;
      description
        "Indicator of whether the client is centrally through Wireless LAN Controller or locally through Access Point gets IP address using DHCP.";
    }
    leaf central-assoc-enable {
      type boolean;
      description
        "Indicator of whether the client is centrally through Wireless LAN Controller or locally through Access Point gets Associated to the Wireless LAN.";
    }
    leaf vlan-central-switching {
      type boolean;
      description
        "Client traffic can be switched locally from Access Point or Centrally from the Wireless LAN Controller. Vlan based switching mode indicates the client traffic is switched based on the vlan using central switching mode.";
    }
    leaf is-fabric-client {
      type boolean;
      description
        "Indicator of whether the client is associated to Wireless WLAN broadcasted by Access Point in the Fabric Network.";
    }
    leaf is-guest-fabric-client {
      type boolean;
      description
        "Indicator of whether the client is associated to Guest Wireless WLAN broadcasted by Access Point in the Fabric Network.";
    }
    leaf upn-bit-flag {
      type wireless-client-oper:upn-status;
      description
        "Indicator of User Defined (Private) Network enabled status for the client.";
    }
  }

  grouping guest-lan-data {
    description
      "Client Information specific to Wired Guest clients";
    leaf wired-vlan {
      type uint16;
      description
        "In wired guest scenario on Foreign controller: the VLAN the client joins and is learned";
    }
    leaf phy-ifid {
      type uint32;
      description
        "In wired guest scenario on Foreign controller: the physical interface ID the clients joins";
    }
    leaf idle-time-seconds {
      type uint32;
      units "seconds";
      description
        "For guest-lan clients on foreign controller, the idle time of the client, measured in seconds";
    }
  }

  grouping ipsk-p2p-tag {
    description
      "PSK P2P tag";
    leaf-list ipsk-tag-value {
      type uint8;
      max-elements 8;
      ordered-by user;
      description
        "PSK P2P tag value which is computed based on the wlan profile name and PSK passphrase";
    }
  }

  grouping ewlc-client-common-oper-data {
    description
      "Client Common Operational Data";
    leaf client-mac {
      type yang:mac-address;
      description
        "MAC Address of the wireless mobile station. MAC addresses are used as a network address for most IEEE 802 network technologies, including Ethernet, Wi-Fi and Bluetooth.";
    }
    leaf ap-name {
      type string;
      description
        "The Access Point name to which the client is connected in the Wireless Network";
    }
    leaf ms-ap-slot-id {
      type uint8;
      description
        "The radio slot on the access point to which the client is connected in the wireless network, slot 255 represents invalid slot ID.";
    }
    leaf ms-radio-type {
      type wireless-client-types:ms-phy-radio-type;
      description
        "The Wireless Radio type of the client using which it has connected to the Access Point in the Wireless Network";
    }
    leaf wlan-id {
      when "(../client-type!='client-802-3-guest-lan') and (../client-type!='dot11-client-rlan')";
      type uint32;
      description
        "Wireless LAN Id indicates the unique Wireless LAN to which the client is connected";
    }
    leaf client-type {
      type wireless-client-types:ms-client-type;
      description
        "Client traffic can be switched locally from Access Point in HREAP mode or Centrally from the Wireless LAN Controller in the Local mode. Client Type indicates the wireless network type to which the client is connected based on the traffic switching type.";
    }
    leaf co-state {
      type wireless-client-types:client-co-state;
      description
        "The state of the client indicates the last phase of the association the client has been able to complete successfully.";
    }
    leaf aaa-override-passphrase {
      type boolean;
      description
        "AAA override passphrase enabled";
    }
    leaf is-tvi-enabled {
      type boolean;
      description
        "The Encrypted Traffic Analytics can be enabled on Wireless LANs. This flag indicates the enablement of the Encrypted Traffic Analytics for the client.";
    }
    container wlan-policy {
      description
        "Wireless LAN policy inherited by the wireless client after joining to the Wireless LAN.";
      uses wireless-client-oper:ewlc-client-wlan-policy;
    }
    leaf username {
      type string;
      description
        "Username of the client";
    }
    container guest-lan-client-info {
      description
        "Guest LAN Client information";
      uses wireless-client-oper:guest-lan-data;
    }
    leaf method-id {
      type wireless-client-oper:authentication-method-id;
      description
        "Method Identifier";
    }
    leaf l3-vlan-override-received {
      type boolean;
      description
        "Client received a VLAN Override after L3 authentication";
    }
    container ipsk-tag {
      description
        "PSK tag of the Client";
      uses wireless-client-oper:ipsk-p2p-tag;
    }
    leaf upn-id {
      type uint32;
      description
        "User Defined (Private) Network Identity";
    }
    leaf is-central-nat {
      type empty;
      description
        "Is central NAT enabled for this Client";
    }
    leaf is-locally-administered-mac {
      type boolean;
      description
        "Is client's MAC address locally administered";
    }
    leaf idle-timeout {
      type uint32;
      units "seconds";
      description
        "Client idle state timeout: Amount of time before idle clients get deleted";
    }
    leaf idle-timestamp {
      type yang:date-and-time;
      description
        "Timestamp of when client moved to idle state";
    }
  }

  grouping ewlc-client-stats-oper-data {
    description
      "Client Statistical Operational data";
    leaf ms-mac-address {
      type yang:mac-address;
      description
        "MAC Address of the wireless mobile station. MAC addresses are used as a network address for most IEEE 802 network technologies, including Ethernet, Wi-Fi and Bluetooth.";
    }
    leaf bytes-rx {
      type uint64;
      description
        "The number of bytes of wireless data traffic received from the Mobile station on a particular Wireless LAN.";
    }
    leaf bytes-tx {
      type uint64;
      description
        "The number of bytes of wireless data traffic transmitted to the Mobile station on a particular Wireless LAN.";
    }
    leaf policy-errs {
      type uint64;
      description
        "Mobile station policy errors";
    }
    leaf pkts-rx {
      type uint64;
      description
        "The number of packets of wireless data traffic received from the Mobile station on a particular Wireless LAN.";
    }
    leaf pkts-tx {
      type uint64;
      description
        "The number of packets of wireless data traffic transmitted to the Mobile station on a particular Wireless LAN.";
    }
    leaf data-retries {
      type uint64;
      description
        "The number of retries a wireless mobile station has executed for the wireless data traffic on a particular Wireless LAN.";
    }
    leaf mic-mismatch {
      type uint64;
      description
        "The number of packets from wireless mobile station for which Message Integrity Check (MIC) mismatch occured on a particular Wireless LAN.";
    }
    leaf mic-missing {
      type uint64;
      description
        "The number of packets from wireless mobile station for which Message Integrity Check (MIC) missing occured on a particular Wireless LAN.";
    }
    leaf most-recent-rssi {
      type int8;
      description
        "RSSI is the relative received signal strength in a wireless environment, is an indication of the power level being received by the receive radio after the antenna and possible cable loss. Last updated Radio Signal Strength indicator is recorded.";
    }
    leaf most-recent-snr {
      type uint8;
      description
        "Signal-to-noise ratio (abbreviated SNR or S/N) is a measure used in science and engineering that compares the level of a desired signal to the level of background noise. Last updated Signal To Noise Ratio is recorded.";
    }
    leaf tx-excessive-retries {
      type uint64;
      description
        "Mobile station excessive retries";
    }
    leaf tx-retries {
      type uint64;
      description
        "Number of frames transmitted with the Retry bit set";
    }
    leaf speed {
      type uint32;
      description
        "Latest speed of the connected client.";
    }
    leaf spatial-stream {
      type uint32;
      description
        "Number of Spatial Streams supported by the client.";
    }
    leaf glan-stats-update-timestamp {
      type yang:date-and-time;
      description
        "For guest-lan clients, time when statistics were last updated";
    }
    leaf glan-idle-update-timestamp {
      type yang:date-and-time;
      description
        "For guest-lan clients, time when idle time was last updated";
    }
    leaf rx-group-counter {
      type uint64;
      description
        "The total count of broadcast and multicast frames sent by the client";
    }
  }

  grouping client-wsa-info {
    description
      "Client wireless service assurance information";
    leaf client-mac {
      type yang:mac-address;
      description
        "Client MAC address";
    }
    leaf device-hostname {
      type string;
      description
        "Device hostname";
    }
    leaf device-os {
      type string;
      description
        "Device operating system";
    }
  }

  grouping dc-client-info {
    description
      "Device Classification info of client";
    leaf client-mac {
      type yang:mac-address;
      description
        "Client MAC address";
    }
    leaf device-type {
      type string;
      description
        "Client Device Classification";
    }
    leaf protocol-map {
      type wireless-client-oper:protocol-map;
      description
        "A Map of Protocols used for Device Classification";
    }
    leaf confidence-level {
      type uint32;
      description
        "Confidence Level of classification";
    }
    leaf classified-time {
      type yang:date-and-time;
      description
        "Time of Classification";
    }
    leaf day-zero-dc {
      type string;
      description
        "MAC based Device Classification";
    }
    leaf sw-version {
      when "(../sw-version-src != 'proto-none') and (../sw-version-src != 'proto-dot11-device-analytics')";
      type string;
      description
        "Software Version of the Client";
    }
    leaf sw-version-src {
      type wireless-client-oper:dc-db-attr-type-e;
      description
        "Network Protocol used as a source of device's software version info";
    }
    leaf device-os {
      when "(../device-os-src != 'proto-none')";
      type string;
      description
        "Device Operating System";
    }
    leaf device-sub-version {
      when "(../device-os-src != 'proto-none')";
      type string;
      description
        "Device Sub-Version";
    }
    leaf device-os-src {
      type wireless-client-oper:dc-db-attr-type-e;
      description
        "Network Protocol used as a source of device's operating system info";
    }
    leaf device-name {
      type string;
      description
        "Name of the Device";
    }
    leaf device-vendor {
      when "(../device-vendor-src != 'proto-none')";
      type string;
      description
        "Device Vendor";
    }
    leaf device-vendor-src {
      type wireless-client-oper:dc-db-attr-type-e;
      description
        "Network Protocol used as a source of device's vendor info";
    }
    leaf sales-code {
      when "(../sales-code-src != 'proto-none') and (../sales-code-src != 'proto-dot11-device-analytics')";
      type string;
      description
        "Sales Code for Devices";
    }
    leaf sales-code-src {
      type wireless-client-oper:dc-db-attr-type-e;
      description
        "Network Protocol used as a source of device's sales code info";
    }
    leaf device {
      when "(../device-src != 'proto-none') and (../device-src != 'proto-dot11-device-analytics')";
      type string;
      description
        "Form of the Device";
    }
    leaf device-src {
      type wireless-client-oper:dc-db-attr-type-e;
      description
        "Network Protocol used as a source of device's form info";
    }
    leaf country-name {
      when "(../country-name-src != 'proto-none') and (../country-name-src != 'proto-dot11-device-analytics')";
      type string;
      description
        "Country of the Device";
    }
    leaf country-name-src {
      type wireless-client-oper:dc-db-attr-type-e;
      description
        "Network Protocol used as a source of device's country name info";
    }
    leaf model-name {
      when "(../model-name-src != 'proto-none')";
      type string;
      description
        "Model name of the device";
    }
    leaf model-name-src {
      type wireless-client-oper:dc-db-attr-type-e;
      description
        "Network protocol used as a source of device model name info";
    }
    leaf power-type {
      when "(../power-type-src != 'proto-none')";
      type wireless-client-oper:dc-power-type-e;
      description
        "Power type of the device";
    }
    leaf power-type-src {
      type wireless-client-oper:dc-db-attr-type-e;
      description
        "Network protocol used as a source of device power type info";
    }
    leaf hw-model {
      when "(../hw-model-src != 'proto-none')";
      type string;
      description
        "Hardware model of the device";
    }
    leaf hw-model-src {
      type wireless-client-oper:dc-db-attr-type-e;
      description
        "Network protocol used as a source of device hardware model info";
    }
  }

  grouping epm-svc-block {
    description
      "Policy Service block";
    leaf mac {
      type yang:mac-address;
      description
        "MAC address of the client";
    }
    leaf res-vlan-id {
      type uint32;
      description
        "VLAN ID associated with client";
    }
    leaf res-vlan-name {
      type string;
      description
        "VLAN name associated with client";
    }
  }

  grouping sisf-db-ip-key {
    description
      "IP address information of client.";
    leaf zone-id {
      type uint32;
      description
        "Zone identifier";
    }
    leaf ip-addr {
      type inet:ip-address;
      description
        "IP address of client";
    }
  }

  grouping sisf-db-mac-ip-binding {
    description
      "MAC address to IP binding";
    container ip-key {
      description
        "IP address";
      uses wireless-client-oper:sisf-db-ip-key;
    }
  }

  grouping sisf-db-mac-entry {
    description
      "MAC address to IP binding";
    leaf mac-addr {
      type yang:mac-address;
      description
        "MAC address";
    }
    container ipv4-binding {
      description
        "IPv4 binding";
      uses wireless-client-oper:sisf-db-mac-ip-binding;
    }
    list ipv6-binding {
      max-elements 8;
      description
        "IPv6 binding";
      uses wireless-client-oper:sisf-db-mac-ip-binding;
    }
  }

  container client-oper-data {
    config false;
    description
      "Root container of wireless client operational parameters";
    list common-oper-data {
      key "client-mac";
      description
        "List containing common operational data of the client";
      uses wireless-client-oper:ewlc-client-common-oper-data;
    }
    list dot11-oper-data {
      key "ms-mac-address";
      description
        "Container for capturing the 802.11 operational data of the client";
      uses wireless-client-oper:ewlc-client-dot11-oper-data;
    }
    list mobility-oper-data {
      key "ms-mac-addr";
      description
        "Container for capturing mobility operational data of client";
      uses wireless-client-oper:ewlc-mafsm-oper-data;
    }
    list mm-if-client-stats {
      key "client-mac";
      description
        "Container for capturing client Mobility Interface stats";
      uses wireless-client-oper:mmif-client-stats;
    }
    list mm-if-client-history {
      key "client-mac";
      description
        "Container for capturing client mobility history";
      uses wireless-client-oper:mmif-client-history;
    }
    list traffic-stats {
      key "ms-mac-address";
      description
        "Container for capturing the client traffic statistics info";
      uses wireless-client-oper:ewlc-client-stats-oper-data;
    }
    list policy-data {
      key "mac";
      description
        "Container for capturing the Client VLAN info";
      uses wireless-client-oper:epm-svc-block;
    }
    list client-wsa-info {
      key "client-mac";
      description
        "Wireless service assurance info for client";
      uses wireless-client-oper:client-wsa-info;
    }
    list sisf-db-mac {
      key "mac-addr";
      description
        "List containing IPv4 binding and multiple IPv6 bindings info";
      uses wireless-client-oper:sisf-db-mac-entry;
    }
    list dc-info {
      key "client-mac";
      description
        "Device Classifier Client Operational Data";
      uses wireless-client-oper:dc-client-info;
    }
  }
}
