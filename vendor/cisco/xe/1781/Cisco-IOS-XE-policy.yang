module Cisco-IOS-XE-policy {
  namespace "http://cisco.com/ns/yang/Cisco-IOS-XE-policy";
  prefix ios-policy;

  import cisco-semver {
    prefix cisco-semver;
  }
  import ietf-inet-types {
    prefix inet;
  }
  import ietf-yang-types {
    prefix yang;
  }
  import Cisco-IOS-XE-types {
    prefix ios-types;
  }
  import Cisco-IOS-XE-native {
    prefix ios;
  }
  import Cisco-IOS-XE-atm {
    prefix ios-atm;
  }
  import Cisco-IOS-XE-interface-common {
    prefix ios-ifc;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Policy Map Yang Model.
     Copyright (c) 2016-2021 by Cisco Systems, Inc.
     All rights reserved.";

  revision 2022-03-01 {
    description
      "- Added classification(match filter) and marking (set action) support for traffic-class
       - Added support for Queueing type policy
       - Deprecated set discard-class leaf and created container for the same
       - Added default for timeout in sleeping-client";
    cisco-semver:module-version "6.3.0";
  }
  revision 2021-11-01 {
    description
      "- Added leaf to enable optimization for policy";
    cisco-semver:module-version "6.2.0";
  }
  revision 2021-07-01 {
    description
      "- Updates for missing content required for evpn-service-model
       - Change leaf-list device-type-list to device-type-new to support
       - both regular expressions and normal strings in device-type
       - Added port channel-subinterface argument for service-policy
       - added pppoe service yang model under policy-map
       - Added match packet-tag for class-map";
    cisco-semver:module-version "6.1.0";
  }
  revision 2021-03-01 {
    description
      "- Deprecate table-map ";
    cisco-semver:module-version "6.0.0";
  }
  revision 2020-11-01 {
    description
      "- Add verify-availability option for set-next-hop
       - Change input/output of service-policy epbr to leafref
       - Add set interface for epbr
       - Add ZBFW rule-based unified logging
       - Add conflict for set vrf verify-availability and next-hop
       - Police model changes are done to remove ambiguity for Turbo-ConfD Parser
       - Remove 'when' condition for site-manage to improve vManage performance";
    cisco-semver:module-version "5.0.0";
  }
  revision 2020-07-01 {
    description
      "- Added peer model as deprecated node
       - Added match traffic-category for class-map
       - Replacing leaf with container for set-next-hop";
    cisco-semver:module-version "4.0.0";
  }
  revision 2020-03-01 {
    description
      "-Support for MPLS EXP WRED option under random-detect
       - Added match application criteria for class-map
       - Added set-domain in policy-map";
    cisco-semver:module-version "3.0.0";
  }
  revision 2019-11-01 {
    description
      "- Corrected upper-bound value for target bit-rate
       - Changes made to include CLIs in class-map
       - Added missing commands for policy-map
       - Corrected shaper range
       - Fixed gaps in parameter-map type subscriber attribute-to-service
       - Fix hardening issues in policy-map
       - Changes made to include CLIs in class-map
       - Must constraint and range modification in parameter-map type webauth
       - Adding remove-before-change annotation for child service-policy action
       - Adding choice cir-bc, for police-policy-map-case case
       - Deprecated the redundant random-detect standalone leaf
       - Replacing container with leaf for exceed-set-dscp-transmit
       - Allow no bandwidth ... and bandwidth in the same commit";
    cisco-semver:module-version "2.0.0";
  }
  revision 2019-07-01 {
    description
      "- Establish semantic version baseline
       - Added leaf account-on-resolution for policy-map type performance-monitor
       - Corrected exceed-action and violate-action commands
       - Corrected marking and drop command under police restrictions
       - Added interface-template, config-macro, service-template in parameter-map
       - Fixed issues with parameter-map type webauth global
       - Add source interface,vrf, ipv6 for High Speed Logger
       - Add support for BD-VIF interface
       - Added parameter-map type subscriber attribute-to-service
       - Fix control-plane service-policy input/output commands
       - Fix hardening issues found in service-policy input and bandwidth
         remaining percent commands";
    cisco-semver:module-version "1.0.0";
  }
  revision 2019-01-30 {
    description
      "Added restrict leaf for policy-map */event */<class#> class/<action#>";
  }
  revision 2019-01-22 {
    description
      "Added leaf for App-hosting Gigabit Ethernet interface";
  }
  revision 2018-12-14 {
    description
      "Corrected shape adaptive data model";
  }
  revision 2018-12-06 {
    description
      "Change non-strict-leafref's to leafref's for threat-defense features";
  }
  revision 2018-11-29 {
    description
      "Add 'site-manager' type to class-map type";
  }
  revision 2018-11-21 {
    description
      "Cleanup spelling errors in description statements";
  }
  revision 2018-11-15 {
    description
      "Add 'remove-before-change' annotation to policy-map service-policy";
  }
  revision 2018-11-12 {
    description
      "Adding type epbr for policy-map";
  }
  revision 2018-11-06 {
    description
      "Remove instances of max string length of 128/256/512";
  }
  revision 2018-10-29 {
    description
      "Adding type umbrella for policy-map";
  }
  revision 2018-10-21 {
    description
      "fix issue in 'performance-monitor' of 'config-interface-service-policy-grouping'";
  }
  revision 2018-10-18 {
    description
      "Change nested match class-map type to leafref from string";
  }
  revision 2018-10-11 {
    description
      "Add description to shape average";
  }
  revision 2018-09-18 {
    description
      "Disallow class-default as class-map name";
  }
  revision 2018-09-12 {
    description
      "Set max elements for parameter-map type regex";
  }
  revision 2018-08-28 {
    description
      "Add class-map protocol matches before deletes to appease AppFW";
  }
  revision 2018-08-01 {
    description
      "Added application-family for match protocol attribute";
  }
  revision 2018-07-03 {
    description
      "Added 'access-control' & 'packet-service' in 'config-interface-service-policy-grouping'";
  }
  revision 2018-06-28 {
    description
      "Added must constraints for deleting vrf";
  }
  revision 2018-05-14 {
    description
      "Limit string lengths for threat-defense features";
  }
  revision 2018-05-10 {
    description
      "changed leaf service-policy type to leafref under class of policy-map";
  }
  revision 2018-04-30 {
    description
      "Add service policy for ATM interface and PVC";
  }
  revision 2018-04-27 {
    description
      "Add interface Ethernet for policy";
  }
  revision 2018-04-26 {
    description
      "Refactor 'vpn zone security [allow-dia]'";
  }
  revision 2018-04-24 {
    description
      "Add interface Serial for policy";
  }
  revision 2018-04-20 {
    description
      "Remove 'when' annotation from policy-map and class-map protocol models";
  }
  revision 2018-04-12 {
    description
      "Add AppFW models";
  }
  revision 2018-03-22 {
    description
      "add tailf:cli-remove-before-change for interface service-policy input/output";
  }
  revision 2018-03-13 {
    description
      "fix the empty key-entry issue under class";
  }
  revision 2018-03-08 {
    description
      "Add interface Cellular for policy";
  }
  revision 2018-03-05 {
    description
      "Allow to add random-detect and shape or bandwidth as the same commit";
  }
  revision 2018-02-09 {
    description
      "Add ZBFW VPN config";
  }
  revision 2018-02-06 {
    description
      "Refactor parameter-map";
  }
  revision 2017-12-05 {
    description
      "Added Change for parameter-map and class-map match";
  }
  revision 2017-11-27 {
    description
      "Added Change 25GE name";
  }
  revision 2017-11-14 {
    description
      "This revision has changes for new 100GE interface addition";
  }
  revision 2017-09-15 {
    description
      "This revision has changes for new 2gig interface addition";
  }
  revision 2017-09-01 {
    description
      "Add dependency for random-detect cos";
  }
  revision 2017-08-26 {
    description
      "Add parameter-map regex";
  }
  revision 2017-08-24 {
    description
      "Add sequence optional for random-detect precedence";
  }
  revision 2017-08-16 {
    description
      "This revision has changes for new 5gig and 25gig interfaces addition";
  }
  revision 2017-07-31 {
    description
      "Changes to match protocol and attribute";
  }
  revision 2017-07-21 {
    description
      "add class-map match service";
  }
  revision 2017-07-16 {
    description
      "add random-detect cos options";
  }
  revision 2017-07-13 {
    description
      "Changed protocol-name as a string to support dynamically updated protocol-pack";
  }
  revision 2017-06-07 {
    description
      "add dependency match group-object security source";
  }
  revision 2017-05-08 {
    description
      "add more protocol support in match protocol";
  }
  revision 2017-03-31 {
    description
      "fix conform-action issue under policy-map";
  }
  revision 2017-03-20 {
    description
      "Add class-map match group-object";
  }
  revision 2017-02-09 {
    description
      "policy-map shape average option - account";
  }
  revision 2017-02-07 {
    description
      "Initial revision";
  }

  typedef application_source {
    type enumeration {
      enum cli;
      enum cube;
      enum msp;
      enum nbar;
      enum rfmd;
      enum rsvp;
      enum cac;
    }
  }

  typedef application_vendors {
    type enumeration {
      enum Axis;
      enum Cisco;
      enum Panasonic;
      enum Robert-Bosch;
      enum ViaVideo;
    }
  }

  typedef precedence-type2 {
    type union {
      type uint8 {
        range "0..7";
      }
      type enumeration {
        enum rsvp;
      }
    }
  }

  typedef policy-action-type {
    type enumeration {
      enum bandwidth;
      enum compression;
      enum drop;
      enum estimate;
      enum fair-queue;
      enum forward;
      enum netflow-sampler;
      enum police;
      enum priority;
      enum queue-limit;
      enum random-detect;
      enum service-policy;
      enum set;
      enum shape;
      enum trust;
      enum dbl;
      enum queue-buffers;
    }
  }

  typedef class-name-type {
    type union {
      type string {
        length "1..205";
      }
      type enumeration {
        enum class-default;
      }
    }
  }

  typedef police-packets-bytes-type {
    type enumeration {
      enum packets;
      enum bytes;
    }
  }

  typedef bytes-ms-us-type {
    type enumeration {
      enum bytes;
      enum ms;
      enum us;
    }
  }

  typedef police-pps-bps-type {
    type enumeration {
      enum pps;
      enum bps;
    }
  }

  typedef police-bps-type {
    type uint64 {
      range "8000..64000000000";
    }
  }

  typedef police-burst-type {
    type uint32 {
      range "1000..512000000";
    }
  }

  typedef policy-percent-type {
    type uint8 {
      range "1..100";
    }
  }

  typedef police-bit-rate-type {
    type uint64 {
      range "8000..100000000000";
    }
  }

  grouping match-application-source-grouping {
    container source {
      leaf cac {
        description
          "Application source Call Admission Control";
        type empty;
      }
      leaf cli {
        description
          "Application source Command line interface";
        type empty;
      }
      leaf cube {
        description
          "Application source Cisco Unified Border Element";
        type empty;
      }
      leaf msp {
        description
          "Application source msp";
        type empty;
      }
      leaf nbar {
        description
          "Application source Network Based Application Recognition";
        type empty;
      }
      leaf rfmd {
        description
          "Application source Reverse Flow metadata";
        type empty;
      }
      leaf rsvp {
        description
          "Application source Resource Reservation Protocol";
        type empty;
      }
    }
  }

  grouping match-application-version-grouping {
    container version-conf {
      description
        "Version configuration";
      container version {
        description
          "Applications version";
        list version-name-source-list {
          description
            "List for application version and source configuration";
          key "version-str-name source";
          leaf version-str-name {
            description
              "Version string";
            type string {
              length "1..40";
            }
          }
          leaf source {
            description
              "Applications source";
            type application_source;
          }
        }
        list version-name-list {
          description
            "List for application version configuration";
          key "version-name";
          leaf version-name {
            description
              "Version string";
            type string {
              length "1..52";
            }
          }
        }
      }
    }
  }

  grouping match-application-vendor-grouping {
    container vendor-conf {
      container vendor {
        description
          "Applications vendor";
        list vendor-name-source-list {
          description
            "List of application vendor source configuration";
          key "vendor-str-name source";
          leaf vendor-str-name {
            description
              "Applications version";
            type application_vendors;
          }
          leaf source {
            description
              "Applications source";
            type application_source;
          }
        }
        list vendor-name-version-source-list {
          description
            "List of Application vendor version
             source configuration";
          key "vendor-name version source";
          leaf vendor-name {
            description
              "Applications vendor";
            type application_vendors;
          }
          leaf version {
            description
              "Applications version";
            type string {
              length "1..28";
            }
          }
          leaf source {
            description
              "Applications source";
            type application_source;
          }
        }
        list vendor-name-version-list {
          description
            "List of vendor version configuration";
          key "vendor-str-name version";
          leaf vendor-str-name {
            description
              "Application vendor name";
            type application_vendors;
          }
          leaf version {
            description
              "Applications version";
            type string {
              length "1..28";
            }
          }
        }
      }
    }
  }

  grouping police-action-transmit-grouping {
    leaf transmit {
      description
        "transmit packet";
      type empty;
    }
  }

  grouping police-action-drop-grouping {
    leaf drop {
      description
        "drop packet";
      type empty;
    }
  }

  grouping police-conform-action-grouping {
    container conform-set-clp-transmit {
      container conform-action {
        description
          "action when rate is less than conform burst";
        leaf set-clp-transmit {
          description
            "set atm clp and send it";
          type empty;
          must 'not ((../../../conform-set-cos-transmit/conform-action/set-cos-transmit) or(../../../exceed-set-cos-transmit/exceed-action/set-cos-transmit) or(../../../violate-set-cos-transmit/violate-action/set-cos-transmit))' {
            error-message "Two layer 2 markings (cos and clp) are not allowed";
          }
        }
      }
    }
    container conform-set-cos-transmit-table {
      container conform-action {
        description
          "action when rate is less than conform burst";
        leaf set-cos-transmit {
          description
            "rewrite packet cos and send it";
          type ios-types:cos_value-type;
        }
        leaf table {
          description
            "Specify table-map";
          status deprecated;
          type leafref {
            path "/ios:native/ios:table-map/ios:name";
          }
        }
        container table-container {
          leaf table {
            description
              "Specify table-map";
            type leafref {
              path "/ios:native/ios:table-map/ios:name";
            }
          }
        }
      }
    }
    container conform-set-cos-transmit {
      container conform-action {
        description
          "action when rate is less than conform burst";
        leaf set-cos-transmit {
          description
            "rewrite packet cos and send it";
          type ios-types:cos_value-type;
          must 'not ((../../../conform-set-clp-transmit/conform-action/set-clp-transmit) or(../../../exceed-set-clp-transmit/exceed-action/set-clp-transmit) or(../../../violate-set-clp-transmit/violate-action/set-clp-transmit))' {
            error-message "Two layer 2 markings (cos and clp) are not allowed";
          }
        }
      }
    }
    container conform-set-discard-class-transmit {
      container conform-action {
        description
          "action when rate is less than conform burst";
        leaf set-discard-class-transmit {
          description
            "set discard-class and send it";
          type uint8 {
            range "0..7";
          }
        }
      }
    }
    container conform-set-dscp-transmit-table {
      container conform-action {
        description
          "action when rate is less than conform burst";
        leaf set-dscp-transmit {
          description
            "set dscp and send it";
          type ios-types:dscp-type;
        }
        leaf table {
          description
            "Specify table-map";
          status deprecated;
          type leafref {
            path "/ios:native/ios:table-map/ios:name";
          }
        }
        container table-container {
          leaf table {
            description
              "Specify table-map";
            type leafref {
              path "/ios:native/ios:table-map/ios:name";
            }
          }
        }
      }
    }
    container conform-set-dscp-transmit {
      container conform-action {
        description
          "action when rate is less than conform burst";
        leaf set-dscp-transmit {
          description
            "set dscp and send it";
          type ios-types:dscp-type;
          must 'not ((../../../conform-set-prec-transmit/conform-action/set-prec-transmit) or(../../../exceed-set-prec-transmit/exceed-action/set-prec-transmit) or (../../../violate-set-prec-transmit/violate-action/set-prec-transmit)) ' {
            error-message "Two layer 3 markings (dscp and precedence) are not allowed";
          }
        }
      }
    }
    container conform-set-frde-transmit {
      container conform-action {
        description
          "action when rate is less than conform burst";
        leaf set-frde-transmit {
          description
            "set FR DE and send it";
          type empty;
        }
      }
    }
    container conform-set-mpls-exp-imposition-transmit-table {
      container conform-action {
        description
          "action when rate is less than conform burst";
        leaf set-mpls-exp-imposition-transmit {
          description
            "set exp at tag imposition and send it";
          type ios-types:exp_value-type;
        }
        leaf table {
          description
            "Specify table-map";
          status deprecated;
          type leafref {
            path "/ios:native/ios:table-map/ios:name";
          }
        }
        container table-container {
          leaf table {
            description
              "Specify table-map";
            type leafref {
              path "/ios:native/ios:table-map/ios:name";
            }
          }
        }
      }
    }
    container conform-set-mpls-exp-imposition-transmit {
      container conform-action {
        description
          "action when rate is less than conform burst";
        leaf set-mpls-exp-imposition-transmit {
          description
            "set exp at tag imposition and send it";
          type ios-types:exp_value-type;
        }
      }
    }
    container conform-set-mpls-exp-topmost-transmit-table {
      container conform-action {
        description
          "action when rate is less than conform burst";
        leaf set-mpls-exp-topmost-transmit {
          description
            "set exp on topmost label and send it";
          type ios-types:exp_value-type;
        }
        leaf table {
          description
            "Specify table-map";
          status deprecated;
          type leafref {
            path "/ios:native/ios:table-map/ios:name";
          }
        }
        container table-container {
          leaf table {
            description
              "Specify table-map";
            type leafref {
              path "/ios:native/ios:table-map/ios:name";
            }
          }
        }
      }
    }
    container conform-set-mpls-exp-topmost-transmit {
      container conform-action {
        description
          "action when rate is less than conform burst";
        leaf set-mpls-exp-topmost-transmit {
          description
            "set exp on topmost label and send it";
          type ios-types:exp_value-type;
        }
      }
    }
    container conform-set-prec-transmit-table {
      container conform-action {
        description
          "action when rate is less than conform burst";
        leaf set-prec-transmit {
          description
            "rewrite packet precedence and send it";
          type ios-types:prec_value-type;
        }
        leaf table {
          description
            "Specify table-map";
          status deprecated;
          type leafref {
            path "/ios:native/ios:table-map/ios:name";
          }
        }
        container table-container {
          leaf table {
            description
              "Specify table-map";
            type leafref {
              path "/ios:native/ios:table-map/ios:name";
            }
          }
        }
      }
    }
    container conform-set-prec-transmit {
      container conform-action {
        description
          "action when rate is less than conform burst";
        leaf set-prec-transmit {
          description
            "rewrite packet precedence and send it";
          type ios-types:prec_value-type;
          must 'not ((../../../conform-set-dscp-transmit/conform-action/set-dscp-transmit) or(../../../exceed-set-dscp-transmit-table/exceed-action/set-dscp-transmit) or (../../../violate-set-dscp-transmit/violate-action/set-dscp-transmit)) ' {
            error-message "Two layer 3 markings (dscp and precedence) are not allowed";
          }
        }
      }
    }
    container conform-set-qos-transmit-table {
      container conform-action {
        description
          "action when rate is less than conform burst";
        leaf set-qos-transmit {
          description
            "set qos-group and send it";
          type ios-types:qos_value-type;
        }
        leaf table {
          description
            "Specify table-map";
          status deprecated;
          type leafref {
            path "/ios:native/ios:table-map/ios:name";
          }
        }
        container table-container {
          leaf table {
            description
              "Specify table-map";
            type leafref {
              path "/ios:native/ios:table-map/ios:name";
            }
          }
        }
      }
    }
    container conform-set-qos-transmit {
      container conform-action {
        description
          "action when rate is less than conform burst";
        leaf set-qos-transmit {
          description
            "set qos-group and send it";
          type ios-types:qos_value-type;
        }
      }
    }
    container conform-transmit {
      container conform-action {
        description
          "action when rate is less than conform burst";
        uses police-action-transmit-grouping {
          refine "transmit" {
            must 'not (../../../conform-drop/conform-action/drop)' {
              error-message "Conflicting Transmit and drop actions for conform-actiondrop";
            }
          }
        }
      }
    }
    container conform-drop {
      container conform-action {
        description
          "action when rate is less than conform burst";
        uses police-action-drop-grouping {
          refine "drop" {
            must 'not (../../../exceed-transmit/exceed-action/transmit)' {
              error-message "conform-action action can not be drop when exceed-action action is transmit";
            }
          }
        }
      }
    }
  }

  grouping police-exceed-action-grouping {
    container exceed-dscp {
      container exceed-action {
        description
          "action when rate is within conform and conform + exceed burst";
        leaf dscp {
          type ios-types:dscp-type;
          must 'not (../../../violate-transmit/violate-action/transmit)' {
            error-message "exceed-action should be transmit when violate-action is transmit";
          }
        }
      }
    }
    container exceed-set-clp-transmit {
      container exceed-action {
        description
          "action when rate is within conform and conform + exceed burst";
        leaf set-clp-transmit {
          description
            "set atm clp and send it";
          type empty;
          must 'not ((../../../conform-set-cos-transmit/conform-action/set-cos-transmit) or(../../../exceed-set-cos-transmit/exceed-action/set-cos-transmit) or(../../../violate-set-cos-transmit/violate-action/set-cos-transmit))' {
            error-message "Two layer 2 marking are not allowed together";
          }
          must 'not (../../../violate-transmit/violate-action/transmit)' {
            error-message "exceed-action should be transmit when violate-action is transmit";
          }
        }
      }
    }
    container exceed-set-cos-transmit {
      container exceed-action {
        description
          "action when rate is within conform and conform + exceed burst";
        leaf set-cos-transmit {
          description
            "rewrite packet cos and send it";
          type ios-types:cos_value-type;
          must 'not ((../../../conform-set-clp-transmit/conform-action/set-clp-transmit) or(../../../exceed-set-clp-transmit/exceed-action/set-clp-transmit) or(../../../violate-set-clp-transmit/violate-action/set-clp-transmit))' {
            error-message "Two layer 2 marking are not allowed together";
          }
          must 'not (../../../violate-transmit/violate-action/transmit)' {
            error-message "exceed-action should be transmit when violate-action is transmit";
          }
        }
        leaf table {
          description
            "Specify table-map";
          status deprecated;
          type leafref {
            path "/ios:native/ios:table-map/ios:name";
          }
        }
        container table-container {
          leaf table {
            description
              "Specify table-map";
            type leafref {
              path "/ios:native/ios:table-map/ios:name";
            }
          }
        }
      }
    }
    container exceed-set-cos-transmit-val {
      container exceed-action {
        description
          "action when rate is within conform and conform + exceed burst";
        leaf set-cos-transmit {
          description
            "rewrite packet cos and send it";
          type ios-types:cos_value-type;
          must 'not ((../../../conform-set-clp-transmit/conform-action/set-clp-transmit) or(../../../exceed-set-clp-transmit/exceed-action/set-clp-transmit) or(../../../violate-set-clp-transmit/violate-action/set-clp-transmit))' {
            error-message "Two layer 2 marking are not allowed together";
          }
          must 'not (../../../violate-transmit/violate-action/transmit)' {
            error-message "exceed-action should be transmit when violate-action is transmit";
          }
        }
      }
    }
    container exceed-set-discard-class-transmit {
      container exceed-action {
        description
          "action when rate is within conform and conform + exceed burst";
        leaf set-discard-class-transmit {
          description
            "set discard-class and send it";
          type uint8 {
            range "0..7";
          }
          must 'not (../../../violate-transmit/violate-action/transmit)' {
            error-message "exceed-action should be transmit when violate-action is transmit";
          }
        }
      }
    }
    container exceed-set-dscp-transmit-table {
      container exceed-action {
        description
          "action when rate is within conform and conform + exceed burst";
        leaf set-dscp-transmit {
          description
            "set dscp and send it";
          type ios-types:dscp-type;
          must 'not ((../../../conform-set-prec-transmit/conform-action/set-prec-transmit) or(../../../exceed-set-prec-transmit/exceed-action/set-prec-transmit) or (../../../violate-set-prec-transmit/violate-action/set-prec-transmit)) ' {
            error-message "Two layer 3 markings are not allowed together";
          }
          must 'not (../../../violate-transmit/violate-action/transmit)' {
            error-message "exceed-action should be transmit when violate-action is transmit";
          }
        }
        leaf table {
          description
            "Specify table-map";
          status deprecated;
          type leafref {
            path "/ios:native/ios:table-map/ios:name";
          }
        }
        container table-container {
          leaf table {
            description
              "Specify table-map";
            type leafref {
              path "/ios:native/ios:table-map/ios:name";
            }
          }
        }
      }
    }
    container exceed-set-dscp-transmit {
      container exceed-action {
        description
          "action when rate is within conform and conform + exceed burst";
        leaf set-dscp-transmit-config {
          description
            "set dscp and send it";
          type ios-types:dscp-type;
          must 'not ((../../../conform-set-prec-transmit/conform-action/set-prec-transmit) or(../../../exceed-set-prec-transmit/exceed-action/set-prec-transmit) or (../../../violate-set-prec-transmit/violate-action/set-prec-transmit)) ' {
            error-message "Two layer 3 markings (dscp and precedence) are not allowed";
          }
        }
        container set-dscp-transmit {
          description
            "Deprecated";
          status deprecated;
          container dscp {
            status deprecated;
            leaf table {
              status deprecated;
              type enumeration {
                enum policed-dscp;
              }
            }
          }
        }
      }
    }
    container exceed-set-frde-transmit {
      container exceed-action {
        description
          "action when rate is within conform and conform + exceed burst";
        leaf set-frde-transmit {
          description
            "set FR DE and send it";
          type empty;
          must 'not (../../../violate-transmit/violate-action/transmit)' {
            error-message "exceed-action should be transmit when violate-action is transmit";
          }
        }
      }
    }
    container exceed-set-mpls-exp-imposition-transmit {
      container exceed-action {
        description
          "action when rate is within conform and conform + exceed burst";
        leaf set-mpls-exp-imposition-transmit {
          description
            "set exp at tag imposition and send it";
          type ios-types:exp_value-type;
          must 'not (../../../violate-transmit/violate-action/transmit)' {
            error-message "exceed-action should be transmit when violate-action is transmit";
          }
        }
      }
    }
    container exceed-set-mpls-exp-topmost-transmit {
      container exceed-action {
        description
          "action when rate is within conform and conform + exceed burst";
        leaf set-mpls-exp-topmost-transmit {
          description
            "set exp on topmost label and send it";
          type ios-types:exp_value-type;
          must 'not (../../../violate-transmit/violate-action/transmit)' {
            error-message "exceed-action should be transmit when violate-action is transmit";
          }
        }
      }
    }
    container exceed-set-prec-transmit {
      container exceed-action {
        description
          "action when rate is within conform and conform + exceed burst";
        leaf set-prec-transmit {
          description
            "rewrite packet precedence and send it";
          type ios-types:prec_value-type;
          must 'not ((../../../conform-set-dscp-transmit/conform-action/set-dscp-transmit) or(../../../exceed-set-dscp-transmit-table/exceed-action/set-dscp-transmit) or (../../../violate-set-dscp-transmit/violate-action/set-dscp-transmit)) ' {
            error-message "Two layer 3 markings are not allowed together";
          }
          must 'not (../../../violate-transmit/violate-action/transmit)' {
            error-message "exceed-action should be transmit when violate-action is transmit";
          }
        }
        leaf table {
          description
            "Specify table-map";
          status deprecated;
          type leafref {
            path "/ios:native/ios:table-map/ios:name";
          }
        }
        container table-container {
          leaf table {
            description
              "Specify table-map";
            type leafref {
              path "/ios:native/ios:table-map/ios:name";
            }
          }
        }
      }
    }
    container exceed-set-prec-transmit-val {
      container exceed-action {
        description
          "action when rate is within conform and conform + exceed burst";
        leaf set-prec-transmit {
          description
            "rewrite packet precedence and send it";
          type ios-types:prec_value-type;
          must 'not ((../../../conform-set-dscp-transmit/conform-action/set-dscp-transmit) or(../../../exceed-set-dscp-transmit-table/exceed-action/set-dscp-transmit) or (../../../violate-set-dscp-transmit/violate-action/set-dscp-transmit)) ' {
            error-message "Two layer 3 markings are not allowed together";
          }
          must 'not (../../../violate-transmit/violate-action/transmit)' {
            error-message "exceed-action should be transmit when violate-action is transmit";
          }
        }
      }
    }
    container exceed-set-qos-transmit {
      container exceed-action {
        description
          "action when rate is within conform and conform + exceed burst";
        leaf set-qos-transmit {
          description
            "set qos-group and send it";
          type ios-types:qos_value-type;
          must 'not (../../../violate-transmit/violate-action/transmit)' {
            error-message "exceed-action should be transmit when violate-action is transmit";
          }
        }
      }
    }
    container exceed-transmit {
      container exceed-action {
        description
          "action when rate is within conform and conform + exceed burst";
        uses police-action-transmit-grouping {
          refine "transmit" {
            must 'not (../../../exceed-drop/exceed-action/drop)' {
              error-message "Conflicting Transmit and drop actions for exceed-actiondrop";
            }
          }
        }
      }
    }
    container exceed-drop {
      container exceed-action {
        description
          "action when rate is within conform and conform + exceed burst";
        uses police-action-drop-grouping {
          refine "drop" {
            must 'not (../../../violate-transmit/violate-action/transmit)' {
              error-message "exceed-action should be transmit when violate-action is transmit";
            }
          }
        }
      }
    }
  }

  grouping police-violate-action-grouping {
    container violate-set-clp-transmit {
      container violate-action {
        description
          "action when rate is greater than conform + exceed burst";
        leaf set-clp-transmit {
          description
            "set atm clp and send it";
          type empty;
          must 'not ((../../../conform-set-cos-transmit/conform-action/set-cos-transmit) or(../../../exceed-set-cos-transmit/exceed-action/set-cos-transmit) or(../../../violate-set-cos-transmit/violate-action/set-cos-transmit))' {
            error-message "Two layer 2 marking are not allowed together";
          }
        }
      }
    }
    container violate-set-cos-transmit {
      container violate-action {
        description
          "action when rate is greater than conform + exceed burst";
        leaf set-cos-transmit {
          description
            "rewrite packet cos and send it";
          type ios-types:cos_value-type;
          must 'not ((../../../conform-set-clp-transmit/conform-action/set-clp-transmit) or(../../../exceed-set-clp-transmit/exceed-action/set-clp-transmit) or(../../../violate-set-clp-transmit/violate-action/set-clp-transmit))' {
            error-message "Two layer 2 marking are not allowed together";
          }
        }
        leaf table {
          description
            "Specify table-map";
          type leafref {
            path "/ios:native/ios:table-map/ios:name";
          }
        }
      }
    }
    container violate-set-discard-class-transmit {
      container violate-action {
        description
          "action when rate is greater than conform + exceed burst";
        leaf set-discard-class-transmit {
          description
            "set discard-class and send it";
          type uint8 {
            range "0..7";
          }
        }
      }
    }
    container violate-set-dscp-transmit {
      container violate-action {
        description
          "action when rate is greater than conform + exceed burst";
        leaf set-dscp-transmit {
          description
            "set dscp and send it";
          type ios-types:dscp-type;
          must 'not ((../../../conform-set-prec-transmit/conform-action/set-prec-transmit) or(../../../exceed-set-prec-transmit/exceed-action/set-prec-transmit) or (../../../violate-set-prec-transmit/violate-action/set-prec-transmit)) ' {
            error-message "Two layer 3 markings are not allowed together";
          }
        }
        leaf table {
          description
            "Specify table-map";
          type leafref {
            path "/ios:native/ios:table-map/ios:name";
          }
        }
      }
    }
    container violate-set-frde-transmit {
      container violate-action {
        description
          "action when rate is greater than conform + exceed burst";
        leaf set-frde-transmit {
          description
            "set FR DE and send it";
          type empty;
        }
      }
    }
    container violate-set-mpls-exp-imposition-transmit {
      container violate-action {
        description
          "action when rate is greater than conform + exceed burst";
        leaf set-mpls-exp-imposition-transmit {
          description
            "set exp at tag imposition and send it";
          type ios-types:exp_value-type;
        }
      }
    }
    container violate-set-mpls-exp-topmost-transmit {
      container violate-action {
        description
          "action when rate is greater than conform + exceed burst";
        leaf set-mpls-exp-topmost-transmit {
          description
            "set exp on topmost label and send it";
          type ios-types:exp_value-type;
        }
      }
    }
    container violate-set-prec-transmit {
      container violate-action {
        description
          "action when rate is greater than conform + exceed burst";
        leaf set-prec-transmit {
          description
            "rewrite packet precedence and send it";
          type ios-types:prec_value-type;
          must 'not ((../../../conform-set-dscp-transmit/conform-action/set-dscp-transmit) or(../../../exceed-set-dscp-transmit-table/exceed-action/set-dscp-transmit) or (../../../violate-set-dscp-transmit/violate-action/set-dscp-transmit)) ' {
            error-message "Two layer 3 markings are not allowed together";
          }
        }
        leaf table {
          description
            "Specify table-map";
          type leafref {
            path "/ios:native/ios:table-map/ios:name";
          }
        }
      }
    }
    container violate-set-qos-transmit {
      container violate-action {
        description
          "action when rate is greater than conform + exceed burst";
        leaf set-qos-transmit {
          description
            "set qos-group and send it";
          type ios-types:qos_value-type;
        }
      }
    }
    container violate-transmit {
      container violate-action {
        description
          "action when rate is greater than conform + exceed burst";
        uses police-action-transmit-grouping {
          refine "transmit" {
            must 'not (../../../violate-drop/violate-action/drop)' {
              error-message "Conflicting Transmit and drop actions for violate-actiondrop";
            }
          }
        }
      }
    }
    container violate-drop {
      container violate-action {
        description
          "action when rate is greater than conform + exceed burst";
        uses police-action-drop-grouping;
      }
    }
  }

  grouping police-action-grouping {
    container actions {
      uses police-conform-action-grouping;
      uses police-exceed-action-grouping;
      uses police-violate-action-grouping;
    }
  }

  grouping random-detect-grouping {
    leaf min-threshold {
      description
        "minimum threshold (in packet by default)";
      type uint32 {
        range "1..512000000";
      }
    }
    leaf min-threshold-unit {
      description
        "bytes supported on ASR platform only, ms on ASR100x only, us on ASR9xx only";
      type bytes-ms-us-type;
    }
    leaf max-threshold {
      description
        "maximum threshold (in packet by default)";
      type uint32 {
        range "1..512000000";
      }
    }
    leaf max-threshold-unit {
      description
        "bytes supported on ASR platform only, ms on ASR100x only, us on ASR9xx only";
      type bytes-ms-us-type;
    }
    leaf denominator {
      description
        "mark probability denominator";
      type uint16 {
        range "1..65535";
      }
    }
  }

  grouping random-detect-percent-grouping {
    leaf percent {
      description
        "% of minimum threshold";
      type empty;
    }
    leaf min-threshold-percent {
      description
        "Minimum threshold percentage";
      type uint32 {
        range "1..100";
      }
    }
    leaf max-threshold-percent {
      description
        "Maximum threshold percentage";
      type uint32 {
        range "1..100";
      }
    }
  }

  grouping config-shape-adaptive-range-grouping {
    choice upper-choice {
      case range-bps {
        container upper-lower-bound-bps {
          description
            "Maximum/Minimum rate in bps shape can adapt to";
          leaf upper-bound {
            description
              "Upper Bound Target Rate (bps) (8000-10000000000)
               (postfix k, m, g optional, decimal point allowed)";
            type ios-types:storm-control-threshold-type;
          }
          leaf lower-bound {
            description
              "Lower Bound Target Rate (bps) (8000-100000000000)
               (postfix k, m, g optional, decimal point allowed)";
            type ios-types:storm-control-threshold-type;
          }
        }
      }
      case range-percent {
        container upper-lower-bound-percent {
          description
            "Maximum/Minimum rate in percent shape can adapt to";
          container upper-bound {
            description
              "Maximum/Minimum rate shape can adapt to";
            leaf percent {
              description
                "% of parent bandwidth for upper bound rate";
              type uint8 {
                range "1..100";
              }
            }
          }
          container lower-bound {
            description
              "% of parent bandwidth for lower bound rate";
            leaf percent {
              description
                "percentage";
              must '. < ../../upper-bound/percent' {
                error-message
                  "lower percent must be lesser
                   than upper percent";
              }
              type uint8 {
                range "1..100";
              }
            }
          }
        }
      }
    }
  }

  grouping config-epbr-set-vrf-nexthop-v4-action-grouping {
    choice epbr-set-nexthop-v4 {
      case normal-case {
        leaf address {
          description
            "IPv4 next-hop address";
          type inet:ipv4-address;
        }
      }
      case list-case {
        leaf-list addresses {
          description
            "Tracking reachable nexthop";
          ordered-by user;
          type inet:ipv4-address;
        }
      }
    }
  }

  grouping config-epbr-set-nexthop-v4-action-grouping {
    choice epbr-set-nexthop-v4 {
      case normal-case {
        leaf address {
          description
            "IPv4 next-hop address";
          type inet:ipv4-address;
        }
      }
      case list-case {
        leaf-list addresses {
          description
            "Tracking reachable nexthop";
          ordered-by user;
          type inet:ipv4-address;
        }
      }
      case verify-availability-case {
        list verify-availability {
          description
            "Verify if nexthop is reachable";
          key "ipv4";
          leaf ipv4 {
            description
              "IP address of next hop";
            type inet:ipv4-address;
          }
          leaf sequence {
            type uint16 {
              range "1..65535";
            }
          }
          leaf track {
            description
              "Set the next hop depending on the state
               of a tracked object";
            type uint16 {
              range "1..1000";
            }
          }
        }
      }
    }
  }

  grouping config-epbr-set-vrf-nexthop-v6-action-grouping {
    choice epbr-set-nexthop-v6 {
      case normal-case {
        leaf address {
          description
            "IPv6 next-hop address";
          type inet:ipv6-address;
        }
      }
      case list-case {
        leaf-list addresses {
          description
            "Tracking reachable nexthop";
          ordered-by user;
          type inet:ipv6-address;
        }
      }
    }
  }

  grouping config-epbr-set-nexthop-v6-action-grouping {
    choice epbr-set-nexthop-v6 {
      case normal-case {
        leaf address {
          description
            "IPv6 next-hop address";
          type inet:ipv6-address;
        }
      }
      case list-case {
        leaf-list addresses {
          description
            "Tracking reachable nexthop";
          ordered-by user;
          type inet:ipv6-address;
        }
      }
      case verify-availability-case {
        list verify-availability {
          description
            "Verify if nexthop is reachable";
          key "ipv6";
          leaf ipv6 {
            description
              "IP address of next hop";
            type inet:ipv6-address;
          }
          leaf sequence {
            type uint16 {
              range "1..65535";
            }
          }
          leaf track {
            description
              "Set the next hop depending on the state
               of a tracked object";
            type uint16 {
              range "1..1000";
            }
          }
        }
      }
    }
  }

  grouping random-detect-grouping-deprecated {
    leaf min-threshold {
      status deprecated;
      description
        "minimum threshold (in packet by default)";
      type uint32 {
        range "1..512000000";
      }
    }
    leaf min-threshold-unit {
      status deprecated;
      description
        "bytes supported on ASR platform only, ms on ASR100x only, us on ASR9xx only";
      type bytes-ms-us-type;
    }
    leaf max-threshold {
      status deprecated;
      description
        "maximum threshold (in packet by default)";
      type uint32 {
        range "1..512000000";
      }
    }
    leaf max-threshold-unit {
      status deprecated;
      description
        "bytes supported on ASR platform only, ms on ASR100x only, us on ASR9xx only";
      type bytes-ms-us-type;
    }
    leaf denominator {
      status deprecated;
      description
        "mark probability denominator";
      type uint16 {
        range "1..65535";
      }
    }
  }

  grouping config-cos-table-map-grouping {
    container cos {
      leaf table {
        description
          "Set code point value based on tablemap.";
        type string;
      }
    }
  }

  grouping config-dscp-table-map-grouping {
    container dscp {
      leaf table {
        description
          "Set code point value based on tablemap.";
        type string;
      }
    }
  }

  grouping config-mpls-table-map-grouping {
    container mpls {
      container experimental {
        container imposition {
          leaf table {
            description
              "Set code point value based on tablemap.";
            type string;
          }
        }
      }
    }
  }

  grouping config-precedence-table-map-grouping {
    container precedence {
      leaf table {
        description
          "Set code point value based on tablemap.";
        type string;
      }
    }
  }

  grouping config-policy-map-grouping {
    list policy-map {
      description
        "Configure QoS Policy Map";
      key "name";
      leaf name {
        description
          "Name of the policy map";
        type string {
          length "1..203";
        }
      }
      leaf type {
        description
          "type of the policy-map";
        type enumeration {
          enum access-control;
          enum appnav;
          enum inspect;
          enum control;
          enum epbr;
          enum packet-service;
          enum performance-monitor;
          enum service;
          enum service-chain;
          enum umbrella;
          enum queueing;
        }
      }
      leaf subscriber {
        description
          "Domain name of the policy map";
        type empty;
      }
      leaf protocol {
        description
          "protocol of policy map";
        type enumeration {
          enum avc;
          enum http;
          enum im;
          enum imap;
          enum p2p;
          enum pop3;
          enum smtp;
          enum sunrpc;
        }
      }
      leaf optimized {
        description
          "Optimization enable for policy";
        must "(../type = 'inspect')";
        type empty;
      }
      list event {
        description
          "The event type this control class-map triggers upon";
        key "event-type";
        ordered-by user;
        leaf event-type {
          type enumeration {
            enum aaa-available;
            enum absolute-timeout;
            enum agent-found;
            enum authentication-failure;
            enum authentication-success;
            enum authorization-failure;
            enum authorization-success;
            enum identity-update;
            enum inactivity-timeout;
            enum remote-authentication-failure;
            enum remote-authentication-success;
            enum session-disconnected;
            enum session-started;
            enum tag-added;
            enum tag-removed;
            enum template-activated;
            enum template-activation-failed;
            enum template-deactivated;
            enum template-deactivation-failed;
            enum timer-expiry;
            enum violation;
            enum remote-update;
          }
        }
        leaf match-type {
          type enumeration {
            enum match-all;
            enum match-first;
          }
          default "match-all";
        }
        list class-number {
          description
            "class number, 1 for 1st class, 2 for 2nd...";
          key "number";
          leaf number {
            type uint8 {
              range "1..254";
            }
          }
          leaf class {
            description
              "The class type this control policy-map triggers upon";
            type union {
              type enumeration {
                enum always;
              }
              type string;
            }
            must "((/ios:native/ios:policy/class-map[ios-policy:name = current()]/ios-policy:type = 'control') or (current() = 'always'))" {
              error-message
                "class map does not exist
                 or currently active on a policy";
            }
          }
          leaf execution-type {
            type enumeration {
              enum do-all;
              enum do-until-failure;
              enum do-until-success;
            }
            default "do-until-failure";
          }
          list action-number {
            description
              "action number, 1 for 1st class, 2 for 2nd...";
            key "number";
            leaf number {
              type uint8 {
                range "1..254";
              }
            }
            leaf terminate-config {
              description
                "terminate auth method";
              type enumeration {
                enum dot1x;
                enum mab;
                enum webauth;
              }
            }
            container terminate {
              status deprecated;
              description
                "terminate auth method. DEPRECATED use terminate-config";
              leaf dot1x {
                status deprecated;
                description
                  "dot1x method";
                type empty;
              }
              leaf mab {
                status deprecated;
                description
                  "mab method";
                type empty;
              }
              leaf webauth {
                status deprecated;
                description
                  "webauth method";
                type empty;
              }
            }
            leaf replace {
              description
                "clear existing session and create session for violating host";
              type empty;
            }
            leaf restrict {
              description
                "drop violating packets and generate a syslog";
              type empty;
            }
            leaf clear-session {
              description
                "clears an active session";
              type empty;
            }
            leaf clear-authenticated-data-hosts-on-port {
              description
                "clears authenticated data hosts on the port";
              type empty;
            }
            leaf protect {
              description
                "silently drop violating packets";
              type empty;
            }
            leaf err-disable {
              description
                "temporarily disable port";
              type empty;
            }
            container resume {
              description
                "resume operation to be specified";
              leaf reauthentication {
                description
                  "resume reauthentication";
                type empty;
              }
            }
            leaf authentication-restart {
              description
                "restarts the auth sequence after the specified number of sec";
              type uint16 {
                range "1..65535";
              }
            }
            container pause {
              description
                "pause operation to be specified";
              leaf reauthentication {
                description
                  "pause reauthentication";
                type empty;
              }
            }
            leaf authorize {
              description
                "authorize session";
              type empty;
            }
            container activate {
              description
                "activate template or policy";
              container service-template-config {
                leaf service-template {
                  description
                    "activate service template";
                  type string {
                    length "1..48";
                  }
                }
                leaf aaa-list {
                  description
                    "Named Method List";
                  type string;
                }
                leaf precedence {
                  description
                    "Template precedence";
                  type uint8 {
                    range "1..254";
                  }
                }
                leaf replace-all {
                  description
                    "Replace all existing authorization data and services";
                  type empty;
                }
              }
              leaf service-template {
                status deprecated;
                description
                  "DEPRECATED. Use service-template-config instead. activate service template";
                type string;
              }
              leaf interface-template {
                description
                  "activate interface template";
                type string;
              }
              container policy {
                description
                  "activate policy";
                container type {
                  description
                    "policy type";
                  container control {
                    description
                      "policy type control";
                    leaf subscriber {
                      description
                        "policy type control subscriber";
                      type string;
                    }
                  }
                }
              }
            }
            container deactivate {
              description
                "deactivate template or policy";
              leaf service-template {
                description
                  "activate service template";
                type string;
              }
              leaf interface-template {
                description
                  "activate interface template";
                type string;
              }
              container policy {
                description
                  "activate policy";
                container type {
                  description
                    "policy type";
                  container control {
                    description
                      "policy type control";
                    leaf subscriber {
                      description
                        "policy type control subscriber";
                      type string;
                    }
                  }
                }
              }
            }
            container set-timer {
              description
                "set abs timer to pop N seconds from now";
              leaf name {
                description
                  "timer name";
                type string;
              }
              leaf value {
                description
                  "Enter a value between 1 and 65535";
                type uint16 {
                  range "0..65535";
                }
              }
            }
            leaf set-domain {
              description
                "set domain";
              type enumeration {
                enum data;
                enum voice;
                enum switch;
              }
            }
            leaf unauthorize {
              description
                "unauthorize session";
              type empty;
            }
            leaf notify {
              description
                "notifies the session attributes";
              type empty;
            }
            container authenticate {
              description
                "authenticate a session";
              container using {
                description
                  "authenticate a session";
                leaf method {
                  type enumeration {
                    enum dot1x;
                    enum mab;
                    enum webauth;
                  }
                }
                container aaa {
                  description
                    "configure aaa method list";
                  leaf authc-list {
                    description
                      "Specify authentication method list";
                    type string;
                  }
                  leaf authz-list {
                    description
                      "Specify authorization method list";
                    type string;
                  }
                }
                leaf both {
                  description
                    "Enabling Dot1x Authenticator & Supplicant";
                  type empty;
                }
                leaf retries {
                  description
                    "Number of times to retry failed authentications";
                  type uint8 {
                    range "1..5";
                  }
                }
                leaf retry-time {
                  description
                    "Time interval between retries";
                  type uint16 {
                    range "0..65535";
                  }
                }
                leaf priority {
                  description
                    "Method priority";
                  type uint8 {
                    range "1..254";
                  }
                }
                leaf parameter-map {
                  description
                    "Specify parameter map name";
                  type string;
                }
              }
            }
            container map {
              description
                "map identity-update attribute to a auto-conf templates";
              container attribute-to-service {
                description
                  "map identity-update attribute to a auto-conf templates";
                leaf table {
                  description
                    "map identity-update attribute to a auto-conf templates";
                  type string;
                }
              }
            }
          }
        }
      }
      container pppoe {
        description
          "Configure PPPoE related commands";
        list service {
          description
            "Service name to be advertised to PPPoE client";
          key "name";
          ordered-by user;
          leaf name {
            description
              "Name of service policy-map";
            type string {
              pattern '.*';
              length "1..49";
            }
          }
        }
      }
      list class {
        description
          "policy criteria";
        key "name";
        ordered-by user;
        leaf name {
          type class-name-type;
        }
        leaf type {
          description
            "type of the class-map";
          type enumeration {
            enum inspect;
          }
        }
        leaf direct-cloud-access {
          description
            "Umbrella Direct Cloud Access Action";
          type empty;
        }
        leaf insert-before {
          description
            "Insert the class before a specified class";
          when "../../type = 'appnav'";
          type string;
        }
        container appnav-policy {
          when "../../type = 'appnav'";
          list distribute {
            description
              "Distribute action";
            key "service-node-group";
            leaf service-node-group {
              description
                "Distribute to service-node-group";
              type string;
            }
            leaf insert-before {
              description
                "Insert before specific node";
              type string;
            }
          }
          leaf monitor-load {
            description
              "Monitor AO";
            when '../distribute';
            type enumeration {
              enum MS-port-mapper;
              enum cifs;
              enum http;
              enum ica;
              enum mapi;
              enum nfs;
              enum ssl;
              enum video;
            }
          }
          leaf pass-through {
            description
              "pass-through action";
            type empty;
          }
        }
        container avc {
          when "../../protocol = 'avc'";
          choice avc-allow-or-drop {
            leaf allow {
              description
                "Allow the packet";
              type empty;
            }
            leaf deny {
              description
                "Deny the packet";
              type empty;
            }
          }
        }
        container policy {
          when "../../type = 'inspect'";
          leaf action {
            type enumeration {
              enum cxsc;
              enum drop;
              enum inspect;
              enum pass;
            }
          }
          leaf log {
            description
              "Send logging message for drop or pass";
            when "../action = 'drop'or ../action = 'pass'";
            type empty;
          }
          leaf parameter-map {
            when "../action = 'inspect' or ../action = 'cxsc'";
            type leafref {
              path "/ios:native/ios:parameter-map/ios:type/ios-policy:inspect/ios-policy:name";
            }
          }
        }
        container service-policy {
          when "../../type = 'inspect'";
          description
            "Deep Packet Inspection Engine";
          leaf type {
            type enumeration {
              enum avc;
              enum gtpv0;
              enum gtpv1;
              enum imap;
              enum pop3;
              enum smtp;
              enum sunrpc;
            }
          }
          leaf policy-map {
            description
              "DPI policy-map name";
            type leafref {
              path "/ios:native/ios:policy/ios-policy:policy-map/ios-policy:name";
            }
          }
        }
        container pm-policy {
          when "../../type = 'performance-monitor'";
          container flow {
            description
              "Flow subcommands";
            leaf monitor {
              description
                "Apply a Flow Monitor";
              type string;
            }
          }
          container monitor {
            description
              "Monitor related parameters";
            container metric {
              description
                "Monitor metric";
              container rtp {
                description
                  "RTP metrics parameters";
                list clock-rate {
                  description
                    "RTP timestamp field's sampling frequency";
                  key "number";
                  leaf number {
                    type union {
                      type uint8 {
                        range "0..127";
                      }
                      type enumeration {
                        enum celb;
                        enum cn;
                        enum default;
                        enum dvi4;
                        enum dvi4-2;
                        enum dvi4-3;
                        enum dvi4-4;
                        enum g722;
                        enum g723;
                        enum g728;
                        enum g729;
                        enum gsm;
                        enum h261;
                        enum h263;
                        enum jpeg;
                        enum l16;
                        enum l16-2;
                        enum lpc;
                        enum mp2t;
                        enum mpa;
                        enum mpv;
                        enum nv;
                        enum pcma;
                        enum pcmu;
                        enum qcelp;
                      }
                    }
                  }
                  leaf frequency {
                    type uint32 {
                      range "1000..192000";
                    }
                  }
                }
              }
            }
          }
          list react {
            description
              "Configure threshold crossing actions";
            key "id";
            leaf id {
              type uint16;
            }
            leaf mode {
              type enumeration {
                enum media-stop;
                enum mrv;
                enum rtp-jitter-average;
                enum transport-packets-lost-rate;
              }
            }
            leaf description {
              description
                "Description for the instance";
              type string;
            }
            container action {
              description
                "Config react action";
              leaf snmp {
                description
                  "SNMP is notified of the event";
                type empty;
              }
              leaf syslog {
                description
                  "The threshold-crossing event is logged to syslog";
                type empty;
              }
            }
            container alarm {
              description
                "Config react alarm";
              leaf severity {
                description
                  "Alarm severity - default level none";
                type enumeration {
                  enum alert;
                  enum critical;
                  enum emergency;
                  enum error;
                  enum info;
                }
              }
              container type {
                description
                  "Alarm raised type - for each flow or a group";
                leaf discrete {
                  description
                    "Alert for each flow within the class";
                  type empty;
                }
                container grouped {
                  description
                    "Alert if more than one flow cross the threshold";
                  leaf count {
                    description
                      "Number of flows in the group cross the threshold";
                    type uint16;
                  }
                  leaf percent {
                    description
                      "Percent of flows in the group cross the threshold";
                    type uint8 {
                      range "1..100";
                    }
                  }
                }
              }
            }
            container threshold {
              description
                "Config react threshold";
              container value {
                description
                  "Range of percentage loss that would trigger the alarm";
                leaf ge {
                  description
                    "greater and equal to";
                  type string;
                }
                leaf gt {
                  description
                    "greater than";
                  type string;
                }
                leaf le {
                  description
                    "less and equal to";
                  type string;
                }
                leaf lt {
                  description
                    "less than";
                  type string;
                }
                container range {
                  description
                    "threshold within the range of";
                  leaf low {
                    type string;
                  }
                  leaf high {
                    type string;
                  }
                }
              }
            }
          }
        }
        container inspect-police {
          when "../policy/action = 'inspect'";
          container police {
            description
              "Police";
            leaf rate {
              description
                "Specify police rate";
              type uint32 {
                range "8000..2000000000";
              }
            }
            leaf burst {
              description
                "Specify 'burst' parameter";
              type uint32 {
                range "1000..512000000";
              }
            }
          }
        }
        leaf random-detect {
          status deprecated;
          type empty;
        }
        list action-list {
          key "action-type";
          leaf action-type {
            type policy-action-type;
          }
          choice action-param {
            case bandwidth-case {
              container bandwidth {
                when "../action-type = 'bandwidth'";
                leaf bits {
                  type uint32 {
                    range "1..100000000";
                  }
                  must 'not ((../percent) or (../remaining/percent) or(../remaining/ratio))' {
                    error-message "Mixed bandwidth types are not supported. Pls configure bandwidth command either in kbps, percent, remaining percent or remaining ratio but not mixed";
                  }
                }
                leaf percent {
                  description
                    "% of total Bandwidth";
                  type policy-percent-type;
                  must 'not ((../bits) or (../remaining/percent) or(../remaining/ratio))' {
                    error-message "Mixed bandwidth types are not supported. Pls configure bandwidth command either in kbps, percent, remaining percent or remaining ratio but not mixed";
                  }
                }
                container remaining {
                  description
                    "% of the remaining bandwidth";
                  leaf rem-option {
                    type enumeration {
                      enum percent;
                      enum ratio;
                    }
                  }
                  leaf percent {
                    description
                      "% of the remaining bandwidth";
                    when "../rem-option='percent'";
                    type policy-percent-type;
                    must 'not ((../ratio) or (../../percent) or (../../bits))' {
                      error-message "Mixed bandwidth types are not supported. Pls configure bandwidth command either in kbps, percent, remaining percent or remaining ratio but not mixed";
                    }
                  }
                  leaf ratio {
                    description
                      "ratio for sharing excess bandwidth";
                    when "../rem-option='ratio'";
                    type uint32 {
                      range "1..65536";
                    }
                    must 'not ((../percent) or (../../percent) or (../../bits))' {
                      error-message "Mixed bandwidth types are not supported. Pls configure bandwidth command either in kbps, percent, remaining percent or remaining ratio but not mixed";
                    }
                  }
                  container account {
                    description
                      "Overhead Accounting";
                    when "../rem-option = 'percent' or ../rem-option = 'ratio'";
                    leaf user-defined {
                      description
                        "Offset Size";
                      type int32 {
                        range "-1000000..1000000";
                      }
                    }
                  }
                }
              }
            }
            case compression-case {
              container compression {
                when "../action-type = 'compression'";
                container header {
                  description
                    "configure header compression";
                  presence "configure header compression";
                  leaf ip {
                    description
                      "configure ip header compression";
                    type enumeration {
                      enum rtp;
                      enum tcp;
                    }
                  }
                }
              }
            }
            case estimate-case {
              container estimate {
                when "../action-type = 'estimate'";
                container bandwidth {
                  presence "bandwidth required to service this class";
                  description
                    "bandwidth required to service this class";
                  container delay-one-in {
                    description
                      "specify QoS target delay";
                    leaf doi {
                      type uint32 {
                        range "50..1000000";
                      }
                    }
                    leaf milliseconds {
                      type uint32 {
                        range "8..1000";
                      }
                    }
                  }
                  leaf drop-one-in {
                    description
                      "specify QoS target loss rate";
                    type uint32;
                  }
                }
              }
            }
            case forward-case {
              container forward {
                when "../action-type = 'forward'";
                leaf service-path {
                  description
                    "Service Path Entries";
                  type uint32 {
                    range "0..16777215";
                  }
                }
                leaf service-index {
                  description
                    "Service Index";
                  type uint8 {
                    range "2..255";
                  }
                }
              }
            }
            case fair-queue-case {
              container fair-queue {
                when "../action-type = 'fair-queue'";
                leaf dynamic-queues {
                  type uint32 {
                    range "16|32|64|128|256|512|1024|2048|4096";
                  }
                }
                leaf queue-limit {
                  description
                    "per flow queue limit";
                  type uint16 {
                    range "1..32768";
                  }
                }
              }
            }
            case netflow-sampler-case {
              leaf netflow-sampler {
                when "../action-type = 'netflow-sampler'";
                type string;
              }
            }
            case police-case {
              choice police-choice {
                case police-aggregate-case {
                  container police-aggregate {
                    container police {
                      when "../../action-type = 'police'";
                      leaf aggregate {
                        description
                          "Choose aggregate policer for current class";
                        type string;
                      }
                    }
                  }
                }
                case police-policy-map-case {
                  container police-policy-map {
                    container police {
                      when "../../action-type = 'police'";
                      choice cir-bc-choice {
                        case cir-bc {
                          leaf cir {
                            description
                              "Committed information rate";
                            type police-bit-rate-type;
                          }
                          leaf bc {
                            description
                              "Conform burst";
                            type police-burst-type;
                          }
                        }
                      }
                      leaf be {
                        description
                          "Excess burst";
                        when '../bc';
                        type police-burst-type;
                      }
                      leaf pir {
                        description
                          "Peak Information Rate";
                        type police-bps-type;
                      }
                      container pir-be {
                        when '../pir';
                        leaf be {
                          description
                            "Excess burst";
                          type police-burst-type;
                        }
                      }
                      uses police-action-grouping;
                    }
                  }
                }
                case police-cir-percent-case {
                  container police-cir-percent {
                    container police {
                      when "../../action-type = 'police'";
                      container cir {
                        description
                          "Committed information rate";
                        container percent {
                          description
                            "% of interface bandwidth for Committed information rate";
                          leaf percentage {
                            type ios-types:percentage;
                          }
                          leaf bc {
                            description
                              "Conform burst";
                            type uint16;
                          }
                          container bc-ms {
                            when '../bc';
                            leaf ms {
                              description
                                "Milli seconds";
                              type empty;
                            }
                          }
                          leaf be {
                            when '../bc-ms/ms';
                            type uint16;
                          }
                          container be-ms {
                            when '../be';
                            leaf ms {
                              description
                                "Milli seconds";
                              type empty;
                            }
                          }
                          container pir {
                            description
                              "Peak Information Rate";
                            leaf percent {
                              description
                                "% of interface bandwidth for Peak Information Rate";
                              type ios-types:percentage;
                            }
                          }
                          container pir-be {
                            when '../pir';
                            leaf be {
                              description
                                "Excess burst";
                              type uint16;
                            }
                          }
                          container pir-be-ms {
                            when '../pir-be/be';
                            leaf ms {
                              description
                                "Milli seconds";
                              type empty;
                            }
                          }
                          uses police-action-grouping;
                        }
                      }
                    }
                  }
                }
                case police-rate-unit-case {
                  container police-rate-unit {
                    container police {
                      when "../../action-type = 'police'";
                      container rate {
                        description
                          "Specify police rate";
                        leaf units {
                          type uint64;
                        }
                        leaf xps {
                          type police-pps-bps-type;
                        }
                        container burst {
                          description
                            "Specify 'burst' parameter";
                          leaf burst-value {
                            type uint32;
                          }
                          leaf burst-type {
                            type police-packets-bytes-type;
                          }
                        }
                        container peak-rate {
                          description
                            "Specify peak rate";
                          leaf peak-rate-value {
                            type uint32 {
                              range "1..512000000";
                            }
                          }
                          leaf xps {
                            type police-pps-bps-type;
                          }
                        }
                        container peak-burst {
                          description
                            "Specify 'peak-burst' parameter for peak-rate";
                          leaf burst-value {
                            type uint32;
                          }
                          leaf burst-type {
                            type police-packets-bytes-type;
                          }
                        }
                        uses police-action-grouping;
                      }
                    }
                  }
                }
                case police-rate-percent-case {
                  container police-rate-percent {
                    container police {
                      when "../../action-type = 'police'";
                      container rate {
                        description
                          "Specify police rate";
                        container percent {
                          description
                            "% of interface bandwidth for rate";
                          leaf percentage {
                            type ios-types:percentage;
                          }
                          leaf burst {
                            description
                              "Specify 'burst' parameter";
                            type uint16 {
                              range "1..2000";
                            }
                          }
                          leaf ms {
                            description
                              "Treat 'burst' value in milliseconds";
                            when '../burst';
                            type empty;
                          }
                          container peak-rate {
                            description
                              "Specify peak rate";
                            leaf percent {
                              description
                                "% of interface bandwidth for peak-rate";
                              type ios-types:percentage;
                            }
                          }
                          leaf peak-burst {
                            description
                              "Specify 'peak-burst' parameter for 'peak-rate'";
                            type uint16;
                          }
                          container peak-burst-ms {
                            when '../peak-burst';
                            leaf ms {
                              description
                                "Milli seconds";
                              type empty;
                            }
                          }
                          uses police-action-grouping;
                        }
                      }
                    }
                  }
                }
                case police-rate-pdp-case {
                  container police-rate-pdp {
                    container police {
                      when "../../action-type = 'police'";
                      container rate {
                        description
                          "Specify police rate";
                        container pdp {
                          description
                            "% of interface bandwidth for rate";
                          leaf burst {
                            description
                              "Conform burst";
                            type police-burst-type;
                          }
                          leaf peak-rate {
                            description
                              "Specify peak rate";
                            type enumeration {
                              enum pdp;
                            }
                          }
                          leaf peak-burst {
                            description
                              "Specify 'peak-burst' parameter for 'peak-rate'";
                            when '../peak-rate';
                            type police-burst-type;
                          }
                          uses police-action-grouping;
                        }
                      }
                    }
                  }
                }
                case police-target-bitrate-case {
                  container police-target-bitrate {
                    container police {
                      when "../../action-type = 'police'";
                      leaf bit-rate {
                        description
                          "Target bit rate (bits per second) (postfix k, m, g optional),decimal point allowed";
                        type police-bit-rate-type;
                      }
                      leaf confirm_burst-byte {
                        description
                          "Burst Byte";
                        type uint64 {
                          range "100..512000000";
                        }
                      }
                      leaf excess_burst-byte {
                        description
                          "Burst Byte";
                        type uint64 {
                          range "100..512000000";
                        }
                      }
                      leaf conform-action {
                        status deprecated;
                        description
                          "action when rate is less than conform burst";
                        type empty;
                      }
                      leaf transmit {
                        status deprecated;
                        description
                          "transmit packet";
                        type empty;
                      }
                      leaf exceed-action {
                        status deprecated;
                        description
                          "action when rate is within conform and conform + exceed burst";
                        type empty;
                      }
                      leaf drop {
                        status deprecated;
                        description
                          "drop packet";
                        type empty;
                      }
                      leaf set-dscp-transmit {
                        status deprecated;
                        description
                          "set dscp and send it";
                        type empty;
                      }
                      leaf dscp {
                        status deprecated;
                        description
                          "Set packet dscp from dscp";
                        type empty;
                      }
                      leaf table {
                        status deprecated;
                        description
                          "Specify table-map";
                        type string;
                      }
                      container actions {
                        uses police-conform-action-grouping;
                        uses police-exceed-action-grouping;
                        uses police-violate-action-grouping;
                      }
                    }
                  }
                }
                case police-flow-case {
                  container police-flow {
                    container police {
                      when "../../action-type = 'police'";
                      container flow {
                        description
                          "police each flow";
                        leaf mask {
                          description
                            "flow mask to be used for policing";
                          type enumeration {
                            enum dest-only;
                            enum full-flow;
                            enum src-only;
                          }
                        }
                        leaf bps {
                          type police-bps-type;
                        }
                        leaf burst-normal {
                          type police-burst-type;
                          when '../bps';
                        }
                        uses police-action-grouping;
                      }
                    }
                  }
                }
                case police-catalyst-case {
                  container police-catalyst {
                    container police {
                      when "../../action-type = 'police'";
                      leaf bps-value {
                        type string;
                      }
                      leaf bps {
                        type empty;
                      }
                      leaf byte-value {
                        type string;
                      }
                      leaf byte {
                        type empty;
                      }
                      container actions {
                        uses police-conform-action-grouping;
                        uses police-exceed-action-grouping;
                        uses police-violate-action-grouping;
                      }
                    }
                  }
                }
                case police-switch-case {
                  container police-switch {
                    container police {
                      when "../../action-type = 'police'";
                      leaf cir {
                        type uint32 {
                          range "8000..1000000000";
                        }
                      }
                      leaf bc {
                        type uint32 {
                          range "8000..2000000";
                        }
                      }
                      leaf exceed-action {
                        description
                          "action when rate is exceeded";
                        type enumeration {
                          enum drop;
                          enum policed-dscp-transmit;
                        }
                      }
                    }
                  }
                }
              }
            }
            case priority-case {
              container priority {
                when "../action-type = 'priority'";
                leaf level {
                  description
                    "Multi-Level Priority Queue";
                  type uint8 {
                    range "1..2";
                  }
                }
                choice priority-type {
                  leaf kilo-bits {
                    type uint32 {
                      range "1..100000000";
                    }
                  }
                  leaf percent {
                    description
                      "% of total bandwidth";
                    type uint16 {
                      range "1..100";
                    }
                  }
                }
                leaf burst {
                  type uint32 {
                    range "32..2000000";
                  }
                }
              }
            }
            case queue-buffers-case {
              container queue-buffers {
                when "../action-type = 'queue-buffers'";
                leaf ratio {
                  description
                    "Relative buffer size for queue";
                  type uint8 {
                    range "0..100";
                  }
                }
              }
            }
            case queue-limit-case {
              container queue-limit {
                description
                  "<1-64000000> in bytes, <1-3400> in ms, <1-512000> in us, <1-8192000> in packets by default";
                when "../action-type = 'queue-limit'";
                must "(../../../class/name = 'class-default') or (../../action-list/shape or ../../action-list/bandwidth or ../../action-list/priority)" {
                  error-message "queue-limit not allowed without bandwidth shape or priority command";
                }
                leaf queue-limit-value {
                  type uint32 {
                    range "1..64000000";
                  }
                }
                leaf queue-limit-type {
                  type enumeration {
                    enum bytes;
                    enum ms;
                    enum packets;
                    enum us;
                  }
                }
              }
              container queue-limit-dscp {
                when "../action-type = 'queue-limit'";
                list dscp {
                  description
                    "parameters for each dscp value";
                  key "dscp-val";
                  leaf dscp-val {
                    type ios-types:dscp-type;
                  }
                  leaf values {
                    description
                      "dscp values";
                    type empty;
                  }
                  leaf dscp-val1 {
                    type ios-types:dscp-type;
                  }
                  leaf percent {
                    description
                      "% of threshold";
                    type uint8 {
                      range "0..100";
                    }
                  }
                }
              }
            }
            case random-detect {
              container random-detect {
                when "../action-type = 'random-detect'";
                container aggregate {
                  description
                    "aggregate subclasses";
                  presence "true";
                  leaf minimum-thresh {
                    description
                      "minimum threshold for red aggregate";
                    type uint32 {
                      range "0..1000000";
                    }
                  }
                  leaf maximum-thresh {
                    description
                      "maximum threshold for red aggregate";
                    type uint32 {
                      range "0..1000000";
                    }
                  }
                  leaf mark-probability {
                    description
                      "mark-probability for red aggregate";
                    type empty;
                  }
                  leaf denominator {
                    type uint32 {
                      range "0..65535";
                    }
                  }
                }
                leaf cos-based {
                  description
                    "Enable cos-class-based WRED as drop policy, supported on ASR9xx platform only";
                  type empty;
                }
                container cos {
                  description
                    "parameters for each cos value, supported on ASR9xx platform only";
                  leaf cos-val {
                    type uint16 {
                      range "0..7";
                    }
                  }
                  uses random-detect-grouping;
                }
                leaf discard-class-based {
                  description
                    "Enable discard-class-based WRED as drop policy";
                  type empty;
                }
                list discard-class-list {
                  description
                    "parameters for each discard-class value";
                  key "dclass";
                  leaf dclass {
                    type uint16 {
                      range "0..7";
                    }
                  }
                  uses random-detect-grouping;
                }
                container discard-class {
                  description
                    "parameters for each discard-class value";
                  status deprecated;
                  leaf dclass {
                    status deprecated;
                    type uint16 {
                      range "0..7";
                    }
                  }
                  uses random-detect-grouping-deprecated;
                }
                leaf dscp-based {
                  description
                    "Enable dscp-based WRED as drop policy";
                  type empty;
                }
                list dscp {
                  description
                    "parameters for each dscp value";
                  key "dscp-val";
                  leaf dscp-val {
                    type ios-types:dscp-type;
                  }
                  uses random-detect-grouping;
                }
                leaf ecn {
                  description
                    "explicit congestion notification";
                  type empty;
                }
                leaf exponential-weighting-constant {
                  description
                    "weight for mean queue depth calculation";
                  type uint16 {
                    range "1..16";
                  }
                }
                leaf precedence-based {
                  description
                    "Enable precedence-based WRED as drop policy";
                  type empty;
                }
                container precedence {
                  description
                    "parameters for each precedence value";
                  leaf prec {
                    type precedence-type2;
                  }
                  uses random-detect-grouping;
                }
                leaf mpls-exp-based {
                  description
                    "Enable mpls-based WRED as drop policy";
                  type empty;
                }
                list exp {
                  description
                    "parameters for each mpls exp value";
                  must '../mpls-exp-based' {
                    error-message
                      "random-detect mpls-exp-based
                       must be enabled first";
                  }
                  key "exp-val";
                  leaf exp-val {
                    description
                      "Subclass ID";
                    type uint16 {
                      range "0..7";
                    }
                  }
                  choice exp-choice {
                    case random-detect-grouping {
                      uses random-detect-grouping;
                    }
                    case percent-group {
                      uses random-detect-percent-grouping;
                    }
                  }
                }
              }
            }
            case service-policy-case {
              leaf service-policy {
                type leafref {
                  path "/ios:native/ios:policy/policy-map/name";
                }
              }
            }
            case set-case {
              container set {
                when "../action-type = 'set'";
                leaf atm-clp {
                  description
                    "Set ATM CLP bit to 1";
                  type empty;
                }
                container cos {
                  description
                    "Set IEEE 802.1Q/ISL class of service/user priority";
                  choice cos-type {
                    case a {
                      leaf val {
                        type uint16 {
                          range "0..7";
                        }
                      }
                    }
                    case b {
                      leaf pack {
                        type enumeration {
                          enum dscp;
                          enum precedence;
                          enum cos;
                          enum qos-group;
                          enum wlan;
                        }
                      }
                      leaf user-priority {
                        description
                          "Set value from WLAN user-priority";
                        when "../pack = 'wlan'";
                        type empty;
                      }
                      leaf table {
                        description
                          "Set code point value based on tablemap.";
                        type string;
                      }
                    }
                  }
                }
                container traffic-class {
                  description
                    "Set traffic class";
                  choice traffic-class-type {
                    case traffic-value {
                      leaf value {
                        description
                          "Traffic class value";
                        type uint8 {
                          range "0..7";
                        }
                      }
                    }
                    case traffic-cos {
                      uses config-cos-table-map-grouping;
                    }
                    case traffic-dscp {
                      uses config-dscp-table-map-grouping;
                    }
                    case traffic-mpls {
                      uses config-mpls-table-map-grouping;
                    }
                    case traffic-precedence {
                      uses config-precedence-table-map-grouping;
                    }
                  }
                }
                container discard-class-group {
                  description
                    "Set discard class action";
                  choice discard-class-type {
                    case discard-val {
                      leaf discard-class-val {
                        description
                          "Discard behavior identifier";
                        type uint8 {
                          range "0..7";
                        }
                      }
                    }
                    case discard-cos-type {
                      uses config-cos-table-map-grouping;
                    }
                    case discard-dscp-type {
                      uses config-dscp-table-map-grouping;
                    }
                    case discard-mpls-type {
                      uses config-mpls-table-map-grouping;
                    }
                    case discard-precedence-type {
                      uses config-precedence-table-map-grouping;
                    }
                  }
                }
                leaf discard-class {
                  description
                    "Discard behavior identifier";
                  status deprecated;
                  type uint16 {
                    range "0..7";
                  }
                }
                container dscp {
                  description
                    "Set DSCP in IP(v4) and IPv6 packets";
                  container dscp {
                    description
                      "Set packet dscp from dscp";
                    presence "true";
                    leaf table {
                      description
                        "Set packet dscp from dscp based on table map.";
                      type string;
                    }
                  }
                  leaf tunnel {
                    description
                      "set tunnel packet dscp";
                    type empty;
                  }
                  leaf dscp-val {
                    type ios-types:dscp-type;
                  }
                }
                leaf fr-de {
                  description
                    "Set FR DE bit to 1";
                  type empty;
                }
                container ip {
                  description
                    "Set IP specific values";
                  choice ip-choice {
                    container dscp {
                      description
                        "Set IP DSCP (DiffServ CodePoint)";
                      leaf tunnel {
                        description
                          "set tunnel packet dscp";
                        type empty;
                      }
                      leaf dscp-val {
                        type ios-types:dscp-type;
                      }
                    }
                    container precedence {
                      description
                        "Set IP precedence";
                      presence "Set IP precedence";
                      leaf precedence-val {
                        type ios-types:precedence-type;
                      }
                    }
                  }
                }
                container mpls {
                  description
                    "Set MPLS specific values";
                  container experimental {
                    description
                      "Set Experimental value";
                    container imposition {
                      description
                        "Set Experimental value at tag imposition";
                      leaf exp-value {
                        type uint8 {
                          range "0..7";
                        }
                      }
                    }
                    container topmost {
                      description
                        "Set Experimental value  on topmost label";
                      leaf exp-value {
                        type uint8 {
                          range "0..7";
                        }
                      }
                    }
                  }
                }
                container qos-group {
                  description
                    "Set QoS Group";
                  leaf qos-group-value {
                    type uint8 {
                      range "0..99";
                    }
                  }
                }
                container wlan {
                  description
                    "Set WLAN";
                  leaf user-priority {
                    description
                      "Set WLAN user-priority";
                    type uint8 {
                      range "0..7";
                    }
                  }
                }
                container ipv4 {
                  description
                    "IPv4 redirect action";
                  choice ipv4-choice {
                    case set-next-hop {
                      container next-hop-config {
                        description
                          "Redirect next-hop";
                        uses config-epbr-set-nexthop-v4-action-grouping;
                      }
                      leaf next-hop {
                        description
                          "Deprecated";
                        status deprecated;
                        type inet:ipv4-address;
                      }
                    }
                    case set-vrf {
                      container vrf {
                        description
                          "Redirect VRF";
                        list verify-availability-list {
                          must 'not (../vrf-name)' {
                            error-message "please remove other set vrf first";
                          }
                          key "vrf-name next-hop verify-availability";
                          leaf vrf-name {
                            type string;
                          }
                          leaf next-hop {
                            description
                              "Set next hop";
                            type enumeration {
                              enum next-hop;
                            }
                          }
                          leaf verify-availability {
                            description
                              "Configure verify availability for next hop";
                            type inet:ipv4-address;
                          }
                          leaf sequence {
                            description
                              "Set next-hop sequence";
                            type uint16 {
                              range "1..65535";
                            }
                          }
                          leaf track {
                            description
                              "Set the next hop depending on the state
                               of a tracked object";
                            type uint16 {
                              range "1..1000";
                            }
                          }
                        }
                        leaf vrf-name {
                          must 'not (../verify-availability-list)' {
                            error-message "please remove other verify-availability first";
                          }
                          type string;
                        }
                        container next-hop-config {
                          description
                            "Redirect next-hop";
                          uses config-epbr-set-vrf-nexthop-v4-action-grouping;
                        }
                        leaf next-hop {
                          description
                            "Deprecated";
                          status deprecated;
                          type inet:ipv4-address;
                        }
                      }
                    }
                    case set-global {
                      container global {
                        description
                          "Redirect to global routing table";
                        presence "set next-hop global routing table";
                        container next-hop-config {
                          description
                            "Redirect next-hop";
                          uses config-epbr-set-nexthop-v4-action-grouping;
                        }
                        leaf next-hop {
                          description
                            "Deprecated";
                          status deprecated;
                          type inet:ipv4-address;
                        }
                      }
                    }
                  }
                }
                container ipv6 {
                  description
                    "IPv6 redirect action";
                  choice ipv6-choice {
                    case set-next-hop {
                      container next-hop-config {
                        description
                          "Redirect next-hop";
                        uses config-epbr-set-nexthop-v6-action-grouping;
                      }
                      leaf next-hop {
                        description
                          "Deprecated";
                        status deprecated;
                        type inet:ipv6-address;
                      }
                    }
                    case set-vrf {
                      container vrf {
                        description
                          "Redirect VRF";
                        list verify-availability-list {
                          must 'not (../vrf-name)' {
                            error-message "please remove other set vrf first";
                          }
                          key "vrf-name next-hop verify-availability";
                          leaf vrf-name {
                            type string;
                          }
                          leaf next-hop {
                            description
                              "Set next hop";
                            type enumeration {
                              enum next-hop;
                            }
                          }
                          leaf verify-availability {
                            description
                              "Configure verify availability for next hop";
                            type inet:ipv6-address;
                          }
                          leaf sequence {
                            description
                              "Set next-hop sequence";
                            type uint16 {
                              range "1..65535";
                            }
                          }
                          leaf track {
                            description
                              "Set the next hop depending on the state
                               of a tracked object";
                            type uint16 {
                              range "1..1000";
                            }
                          }
                        }
                        leaf vrf-name {
                          must 'not (../verify-availability-list)' {
                            error-message "please remove other verify-availability first";
                          }
                          type string;
                        }
                        container next-hop-config {
                          description
                            "Redirect next-hop";
                          uses config-epbr-set-vrf-nexthop-v6-action-grouping;
                        }
                        leaf next-hop {
                          description
                            "Deprecated";
                          status deprecated;
                          type inet:ipv6-address;
                        }
                      }
                    }
                    case set-global {
                      container global {
                        description
                          "Redirect to global routing table";
                        presence "set next-hop global routing table";
                        container next-hop-config {
                          description
                            "Redirect next-hop";
                          uses config-epbr-set-nexthop-v6-action-grouping;
                        }
                        leaf next-hop {
                          description
                            "Deprecated";
                          status deprecated;
                          type inet:ipv6-address;
                        }
                      }
                    }
                  }
                }
                container forward-class {
                  description
                    "Set packets forward-class value";
                  when "../../../../type = 'epbr'";
                  leaf forward-class-value {
                    type uint8 {
                      range "0..7";
                    }
                  }
                }
                container interface {
                  description
                    "Set output interface";
                  uses ios-ifc:interface-grouping;
                }
              }
            }
            case shape-case {
              container shape {
                when "../action-type = 'shape'";
                container adaptive {
                  description
                    "Enable Traffic Shaping adaptation";
                  choice adaptive-choice {
                    case bps {
                      leaf bits-per-second {
                        description
                          "Lower Bound Target Bit Rate (bits per second)";
                        must '../../average' {
                          error-message
                            "shape <average|peak>' command
                             needs to be configured first";
                        }
                        type uint32 {
                          range "8000..1215752192";
                        }
                      }
                    }
                    case range {
                      uses config-shape-adaptive-range-grouping;
                    }
                  }
                }
                container average {
                  description
                    "configure token bucket: CIR (bps) [Bc (bits) [Be (bits)]], send out Bc only per interval";
                  choice average-choice {
                    case a {
                      leaf bit-rate {
                        description
                          "Target Bit Rate (bits/sec)";
                        type uint64 {
                          range "8000..100000000000";
                        }
                      }
                      leaf bits-per-interval-sustained {
                        description
                          "bits per interval, sustained. Recommend not to configure, algo finds the best value";
                        type uint32 {
                          range "256..154400000";
                        }
                      }
                      leaf bits-per-interval-excess {
                        description
                          "bits per interval, excess.";
                        when '../bits-per-interval-sustained';
                        type uint32 {
                          range "0..154400000";
                        }
                      }
                      container account {
                        description
                          "Overhead Accounting";
                        leaf user-defined {
                          description
                            "Offset Size";
                          type int32 {
                            range "-1000000..1000000";
                          }
                        }
                      }
                    }
                    case b {
                      leaf percent {
                        description
                          "% of interface bandwidth for Committed information rate";
                        type ios-types:percentage;
                      }
                      leaf burst-size-sustained {
                        description
                          "sustained burst in milliseconds. Recommend not to configure it, the algorithm will find out the best value";
                        type uint16 {
                          range "10..2000";
                        }
                      }
                      leaf ms {
                        description
                          "milliseconds";
                        type empty;
                      }
                      container bse {
                        leaf burst-size-excess {
                          description
                            "sustained burst in milliseconds. Recommend not to configure it, the algorithm will find out the best value";
                          type uint16 {
                            range "10..2000";
                          }
                        }
                        leaf ms {
                          description
                            "milliseconds";
                          type empty;
                        }
                      }
                    }
                  }
                }
                leaf fecn-adapt {
                  description
                    "Enable Traffic Shaping reflection of FECN as BECN";
                  type empty;
                }
                container fr-voice-adapt {
                  description
                    "Enable rate adjustment depending on voice presence";
                  presence "Enable rate adjustment depending on voice presence";
                  leaf deactivation {
                    type uint16 {
                      range "1..10000";
                    }
                  }
                }
                leaf max-buffers {
                  description
                    "Set Maximum Buffer Limit";
                  type uint16 {
                    range "1..4096";
                  }
                }
              }
            }
            case trust-case {
              leaf trust {
                when "../action-type = 'trust'";
                type enumeration {
                  enum cos;
                  enum dscp;
                  enum ip-precedence;
                }
              }
            }
          }
        }
      }
      leaf description {
        description
          "Policy-Map description";
        type string {
          length "1..200";
        }
      }
      leaf sequence-interval {
        description
          "Enable sequence number capability";
        when "../type = 'appnav'";
        type uint16;
      }
      container parameter {
        description
          "policy parameters";
        when "../type = 'epbr' or ../type = 'performance-monitor'";
        container default {
          description
            "default parameter map";
          leaf flow-stickness {
            description
              "flow-stickness parameter map";
            when "../../../type = 'epbr'";
            type empty;
          }
          leaf account-on-resolution {
            description
              "account-on-resolution parameter map";
            when "../../../type = 'performance-monitor'";
            type empty;
          }
        }
      }
    }
  }

  grouping class-map-match-result-type-grouping {
    leaf aaa-timeout {
      description
        "aaa timeout type";
      type empty;
    }
    leaf agent-not-found {
      description
        "agent not found type";
      type empty;
    }
    leaf authoritative {
      description
        "failure type";
      type empty;
    }
    leaf method-timeout {
      description
        "method_timeout type";
      type empty;
    }
    leaf none {
      description
        "no type";
      type empty;
    }
    leaf success {
      description
        "success type";
      type empty;
    }
  }

  grouping class-map-control-filter-grouping {
    list activated-service-template {
      description
        "match name of service template activated on session";
      key "service-name";
      leaf service-name {
        description
          "Enter service name";
        type string;
      }
    }
    leaf-list authorization-failure {
      description
        "match the type of authorization failure from an authorization failed event";
      type enumeration {
        enum domain-change-failed;
        enum linksec-failed;
        enum tunnel-return;
      }
    }
    leaf-list day {
      description
        "match day of week";
      type enumeration {
        enum Daily;
        enum Fri;
        enum Mon;
        enum Sat;
        enum Sun;
        enum Thurs;
        enum Tue;
        enum Wed;
        enum Weekdays;
        enum Weekends;
      }
    }
    list join-time-of-day {
      description
        "join time of day";
      key "start-time end-time";
      leaf start-time {
        type ios-types:hhmm-type;
      }
      leaf end-time {
        type ios-types:hhmm-type;
      }
    }
    leaf-list platform-type {
      description
        "name of the platform-type";
      type string;
    }
    leaf-list eap-type {
      description
        "match name of the eap-type";
      type enumeration {
        enum fast;
        enum gtc;
        enum leap;
        enum md5;
        enum mschapv2;
        enum peap;
        enum tls;
      }
    }
    container authorization-status {
      description
        "match the authorization status of the session";
      leaf authorized {
        description
          "authorized";
        type empty;
      }
      leaf unauthorized {
        description
          "unauthorized";
        type empty;
      }
    }
    container authorizing-method-priority {
      description
        "match the priority against the authorizing method's priority";
      leaf-list equal {
        description
          "list of equal to";
        type uint8 {
          range "1..254";
        }
      }
      leaf eq {
        status deprecated;
        description
          "equal to DEPRECATED";
        type uint8 {
          range "1..254";
        }
      }
      leaf-list greater-than {
        description
          "greater than";
        type uint8 {
          range "1..254";
        }
      }
      leaf gt {
        status deprecated;
        description
          "greater than, DEPRECATED";
        type uint8 {
          range "1..254";
        }
      }
      leaf-list less-than {
        description
          "less than";
        type uint8 {
          range "1..254";
        }
      }
      leaf lt {
        status deprecated;
        description
          "less than, DEPRECATED";
        type uint8 {
          range "1..254";
        }
      }
    }
    leaf-list client-type-list {
      description
        "match the type of device from an event";
      type enumeration {
        enum data;
        enum switch;
        enum video;
        enum voice;
      }
    }
    leaf client-type {
      status deprecated;
      description
        "match the type of device from an event, DEPRECATED";
      type enumeration {
        enum data;
        enum switch;
        enum video;
        enum voice;
      }
    }
    list device-type-new {
      description
        "List of device-type to match normal strings and/or strings with regular expressions";
      key "name";
      leaf name {
        description
          "match name of the device-type";
        type string;
      }
      leaf regex {
        description
          "match regular expression of the device-type";
        type empty;
      }
    }
    leaf-list device-type-list {
      status deprecated;
      description
        "match name of the device-type";
      type string;
    }
    leaf device-type {
      status deprecated;
      description
        "match name of the device-type, DEPRECATED";
      type string;
    }
    leaf-list interface-list {
      description
        "match the session interface";
      type string;
    }
    leaf interface {
      description
        "match the session interface, DEPRECATED";
      status deprecated;
      type string;
    }
    leaf-list ip-address-list {
      description
        "match the IP address from an event";
      type inet:ipv4-address;
    }
    leaf ip-address {
      description
        "match the IP address from an event DEPRECATED";
      status deprecated;
      type inet:ipv4-address;
    }
    leaf-list ipv6-address-list {
      description
        "match the IPv6 address from an event";
      type inet:ipv6-address;
    }
    leaf ipv6-address {
      description
        "match the IPv6 address from an event DEPRECATED";
      status deprecated;
      type inet:ipv6-address;
    }
    leaf-list mac-address-list {
      description
        "match the MAC address from an event";
      type ios-types:cisco-mac-address-type;
    }
    leaf mac-address {
      description
        "match the MAC address from an event, DEPRECATED";
      status deprecated;
      type ios-types:cisco-mac-address-type;
    }
    container method {
      description
        "match the type of authentication method from an event";
      leaf dot1x {
        description
          "dot1x";
        type empty;
      }
      leaf mab {
        description
          "mab";
        type empty;
      }
      leaf webauth {
        description
          "webauth";
        type empty;
      }
    }
    leaf-list oui-list {
      description
        "match the oui address from an event";
      type ios-types:cisco-mac-address-type;
    }
    leaf oui {
      description
        "match the oui address from an event, DEPRECATED";
      status deprecated;
      type ios-types:cisco-mac-address-type;
    }
    leaf-list port-type-list {
      description
        "match the type interface from an event";
      type enumeration {
        enum dot11-port;
        enum l2-port;
        enum l3-port;
      }
    }
    leaf port-type {
      description
        "match the type interface from an event, DEPRECATED";
      status deprecated;
      type enumeration {
        enum dot11-port;
        enum l2-port;
        enum l3-port;
      }
    }
    container result-type {
      description
        "match the result type, optionally for a specific method";
      container method {
        description
          "match the result of a particular method";
        container dot1x {
          description
            "dot1x result";
          uses class-map-match-result-type-grouping;
        }
        container mab {
          description
            "mab result";
          uses class-map-match-result-type-grouping;
        }
        container webauth {
          description
            "webauth result";
          uses class-map-match-result-type-grouping;
        }
      }
      uses class-map-match-result-type-grouping;
    }
    leaf-list service-template-name {
      description
        "match name of service template from an event";
      type string;
    }
    leaf service-template {
      description
        "match name of service template from an event, DEPRECATED";
      status deprecated;
      type string;
    }
    leaf-list session-type-name {
      description
        "match the session type";
      type enumeration {
        enum wired;
        enum wireless;
      }
    }
    leaf session-type {
      status deprecated;
      description
        "match the session type, DEPRECATED";
      type enumeration {
        enum wired;
        enum wireless;
      }
    }
    leaf-list sgt-name {
      description
        "match the sgt session";
      type uint16 {
        range "2..65519";
      }
    }
    leaf sgt {
      status deprecated;
      description
        "match the sgt session, DEPRECATED";
      type uint16 {
        range "2..65519";
      }
    }
    leaf-list ssid-list {
      description
        "match the ssid of the session";
      type string;
    }
    leaf ssid {
      status deprecated;
      description
        "match the ssid of the session, DEPRECATED";
      type string;
    }
    leaf-list tag-name {
      description
        "match tag from an event";
      type string;
    }
    leaf tag {
      status deprecated;
      description
        "match tag from an event, DEPRECATED";
      type string;
    }
    leaf-list timer-name {
      description
        "match the type of timer";
      type string;
    }
    leaf timer {
      status deprecated;
      description
        "match the type of timer, DEPRECATED";
      type string;
    }
    leaf-list user-role-name {
      description
        "match the user-role";
      type string;
    }
    leaf user-role {
      description
        "match the user-role, DEPRECATED";
      status deprecated;
      type string;
    }
    leaf-list username-list {
      description
        "match the username";
      type string;
    }
    leaf username {
      status deprecated;
      description
        "match the username, DEPRECATED";
      type string;
    }
  }

  grouping class-map-match-access-grouping {
    container access-group {
      description
        "Access group";
      leaf index {
        description
          "Numbered Access List";
        type ios-types:access-list-type;
      }
      leaf-list name {
        description
          "Named Access List";
        type string {
          length "1..64";
        }
      }
      container input {
        description
          "Input traffic class parameters";
        choice input-choice {
          case index {
            leaf index {
              description
                "Numbered Access List";
              type uint32 {
                range "1..2799";
              }
            }
          }
          case name {
            leaf name {
              description
                "Named Access List";
              type string {
                length "1..80";
              }
            }
          }
        }
      }
      container output {
        description
          "Output traffic class parameters";
        choice input-choice {
          case index {
            leaf index {
              description
                "Numbered Access List";
              type uint32 {
                range "1..2799";
              }
            }
          }
          case name {
            leaf name {
              description
                "Named Access List";
              type string {
                length "1..80";
              }
            }
          }
        }
      }
    }
    container protocol {
      description
        "Protocol";
      list protocols-list {
        description
          "List of protocols to match";
        key "protocols";
        leaf protocols {
          description
            "Name of the protocol to match";
          type string;
        }
      }
      container attribute {
        description
          "Attribute based protocol match";
        list application-group {
          description
            "Application-group attribute";
          key "name";
          leaf name {
            description
              "Application-group type class name to match";
            type string;
          }
        }
        list application-set {
          description
            "Application-set attribute";
          key "name";
          leaf name {
            description
              "Application-set type class name to match";
            type string;
          }
        }
        list application-family {
          description
            "Application-family attribute";
          key "name";
          leaf name {
            description
              "Application-family type class name to match";
            type string;
          }
        }
        list business-relevance {
          description
            "Application business-relevance";
          key "name";
          leaf name {
            description
              "Application business-relevance type class name to match";
            type string;
          }
        }
        list category {
          description
            "Category attribute";
          key "name";
          leaf name {
            description
              "Category type class name to match";
            type string;
          }
        }
        list encrypted {
          description
            "Encrypted applications";
          key "name";
          leaf name {
            description
              "Encrypted applications type class name to match";
            type string;
          }
        }
        list sub-category {
          description
            "Sub-category attribute";
          key "name";
          leaf name {
            description
              "Sub-category type class name to match";
            type string;
          }
        }
        list traffic-class {
          description
            "SRND class";
          key "name";
          leaf name {
            description
              "SRND class type class name to match";
            type string;
          }
        }
        list tunnel {
          description
            "Tunnelled applications";
          key "name";
          leaf name {
            description
              "Tunnelled applications type class name to match";
            type string;
          }
        }
      }
    }
    container traffic-category {
      description
        "Match on traffic-category";
      choice traffic-category-case {
        leaf allow {
          description
            "Match packets of 'allow' traffic category";
          type empty;
        }
        leaf optimize {
          description
            "Match packets of 'optimize' traffic category";
          type empty;
        }
      }
    }
  }

  grouping class-map-match-common-grouping {
    container current-method-priority {
      description
        "match the priority against the current method's priority";
      leaf-list equal {
        description
          "equal to";
        type uint8 {
          range "1..254";
        }
      }
      leaf eq {
        status deprecated;
        description
          "equal to, DEPRECATED";
        type uint8 {
          range "1..254";
        }
      }
      leaf-list greater-than {
        description
          "greater than";
        type uint8 {
          range "1..254";
        }
      }
      leaf gt {
        status deprecated;
        description
          "greater than, DEPRECATED";
        type uint8 {
          range "1..254";
        }
      }
      leaf-list less-than {
        description
          "less than";
        type uint8 {
          range "1..254";
        }
      }
      leaf lt {
        status deprecated;
        description
          "less than, DEPRECATED";
        type uint8 {
          range "1..254";
        }
      }
    }
    container application {
      description
        "Application to match";
      container application-group {
        description
          "Application Group to match";
        leaf telepresence-group {
          description
            "Telepresence Group";
          type empty;
        }
        leaf vmware-group {
          description
            "VMWARE Group";
          type empty;
        }
        leaf webex-group {
          description
            "WebEx Group";
          type empty;
        }
      }
      container attribute {
        description
          "Application attribute to match";
        leaf media-type {
          description
            "Media type attribute to match";
          type enumeration {
            enum audio;
            enum audio-video;
            enum control;
            enum data;
            enum video;
          }
        }
      }
      leaf cisco-phone {
        description
          "Cisco IP Phones and PC-based Unified Communicators";
        type empty;
      }
      container cisco-phone-conf {
        description
          "Cisco IP Phones and PC-based Unified Communicators configuration";
        container cisco-phone {
          description
            "Cisco IP Phones and PC-based Unified Communicators";
          container multiplex-type {
            description
              "Multiplex Type";
            leaf set {
              description
                "Multiplex Set";
              type empty;
            }
            leaf unset {
              description
                "Multiplex Unset";
              type empty;
            }
          }
          container signaling-type {
            description
              "Signaling Type";
            leaf bfcp {
              description
                "Binary floor control protocol signaling type";
              type empty;
            }
            leaf h323 {
              description
                "h323 signaling type";
              type empty;
            }
            leaf mgcp {
              description
                "Media gateway control protocol signaling type";
              type empty;
            }
            leaf sip {
              description
                "SIP signaling type";
              type empty;
            }
            leaf skinny {
              description
                "Skinny signaling type";
              type empty;
            }
          }
          container traffic-type {
            description
              "Traffic Type";
            leaf control {
              description
                "Control traffic type";
              type empty;
            }
          }
          container transport-type {
            description
              "Transport Type";
            leaf rtcp {
              description
                "Real time transport control
                 protocol transport type";
              type empty;
            }
            leaf rtp {
              description
                "Real time transport protocol transport type";
              type empty;
            }
          }
          uses match-application-source-grouping;
          uses match-application-version-grouping;
          uses match-application-vendor-grouping;
        }
      }
      leaf citrix {
        description
          "Citrix Application";
        type empty;
      }
      container citrix-conf {
        description
          "Citrix Application configurations";
        container citrix {
          description
            "Citrix Application";
          container traffic-type {
            description
              "Traffic Type";
            leaf background {
              description
                "Background traffic type";
              type empty;
            }
            leaf bulk {
              description
                "Bulk traffic type";
              type empty;
            }
            leaf desktop {
              description
                "Desktop traffic type";
              type empty;
            }
            leaf interactive {
              description
                "Interactive traffic type";
              type empty;
            }
            leaf realtime {
              description
                "Realtime traffic type";
              type empty;
            }
            leaf session {
              description
                "Session traffic type";
              type empty;
            }
            leaf streaming {
              description
                "Streaming traffic type";
              type empty;
            }
            leaf tunnel {
              description
                "Tunnel traffic type";
              type empty;
            }
          }
          container transport-type {
            description
              "Transport Type";
            leaf ica {
              description
                "Independent computing
                 architecture transport type";
              type empty;
            }
            leaf rdp {
              description
                "Remote desktop protocol
                 transport type";
              type empty;
            }
          }
          uses match-application-source-grouping;
          uses match-application-version-grouping;
          uses match-application-vendor-grouping;
        }
      }
      leaf h323 {
        description
          "h323 Protocol";
        type empty;
      }
      container h323-conf {
        description
          "h323 Protocol Configuration";
        container h323 {
          description
            "h323 Protocol";
          uses match-application-source-grouping;
          uses match-application-version-grouping;
          uses match-application-vendor-grouping;
        }
      }
      leaf ip-camera {
        description
          "Internet Protocol Video Surveillance Camera";
        type empty;
      }
      container ip-camera-conf {
        description
          "Internet Protocol Video Surveillance
           Camera configurations";
        container ip-camera {
          description
            "Internet Protocol Video Surveillance Camera";
          container multiplex-type {
            description
              "Multiplex Type";
            leaf set {
              description
                "Multiplex Set";
              type empty;
            }
            leaf unset {
              description
                "Multiplex Unset";
              type empty;
            }
          }
          container signaling-type {
            description
              "Signaling Type";
            leaf rtsp {
              description
                "Real Time Streaming
                 Protocol signalling type";
              type empty;
            }
          }
          container traffic-type {
            description
              "Traffic Type";
            leaf realtime {
              description
                "Realtime traffic type";
              type empty;
            }
          }
          container transport-type {
            description
              "Transport Type";
            leaf rtp {
              description
                "Real Time Protocol transport type";
              type empty;
            }
          }
          uses match-application-source-grouping;
          uses match-application-version-grouping;
          uses match-application-vendor-grouping;
        }
      }
      leaf jabber {
        description
          "Jabber Protocol";
        type empty;
      }
      container jabber-conf {
        description
          "Jabber Protocol configurations";
        container jabber {
          description
            "Jabber Protocol";
          uses match-application-source-grouping;
          uses match-application-version-grouping;
          uses match-application-vendor-grouping;
        }
      }
      leaf rtp {
        description
          "Real Time Protocol";
        type empty;
      }
      container rtp-conf {
        description
          "Real Time Protocol configurations";
        container rtp {
          description
            "Real Time Protocol";
          uses match-application-source-grouping;
          uses match-application-version-grouping;
          uses match-application-vendor-grouping;
        }
      }
      leaf rtsp {
        description
          "Real Time Streaming Protocol";
        type empty;
      }
      container rtsp-conf {
        description
          "Real Time Streaming Protocol configurations";
        container rtsp {
          description
            "Real Time Streaming Protocol";
          uses match-application-source-grouping;
          uses match-application-version-grouping;
          uses match-application-vendor-grouping;
        }
      }
      leaf sip {
        description
          "Session Initiation Protocol";
        type empty;
      }
      container sip-conf {
        description
          "Session Initiation Protocol configurations";
        container sip {
          description
            "Session Initiation Protocol";
          uses match-application-source-grouping;
          uses match-application-version-grouping;
          uses match-application-vendor-grouping;
        }
      }
      leaf surveillance-distribution {
        description
          "Surveillance Distribution";
        type empty;
      }
      container surveillance-distribution-conf {
        description
          "Surveillance Distribution configurations";
        container surveillance-distribution {
          description
            "Surveillance Distribution";
          container multiplex-type {
            description
              "Multiplex Type";
            leaf set {
              description
                "Multiplex Set";
              type empty;
            }
            leaf unset {
              description
                "Multiplex Unset";
              type empty;
            }
          }
          container signaling-type {
            description
              "Signaling Type";
            leaf rtsp {
              description
                "Real Time Streaming Protocol signalling type";
              type empty;
            }
          }
          container traffic-type {
            description
              "Traffic Type";
            leaf realtime {
              description
                "Realtime traffic type";
              type empty;
            }
            leaf streaming {
              description
                "Streaming traffic type";
              type empty;
            }
          }
          container transport-type {
            description
              "Transport Type";
            leaf rtp {
              description
                "Real Time Protocol transport type";
              type empty;
            }
          }
          uses match-application-source-grouping;
          uses match-application-version-grouping;
          uses match-application-vendor-grouping;
        }
      }
      leaf telepresence-control {
        description
          "Telepresence-control stream";
        type empty;
      }
      container telepresence-control-conf {
        description
          "Telepresence-control stream configurations";
        container telepresence-control {
          description
            "Telepresence-control stream";
          container signaling-type {
            description
              "Signaling Type";
            leaf bfcp {
              description
                "Binary floor control protocol signaling type";
              type empty;
            }
            leaf ccp {
              description
                "ccp signaling type";
              type empty;
            }
            leaf clue {
              description
                "Clue signaling type";
              type empty;
            }
            leaf h323 {
              description
                "h323 signaling type";
              type empty;
            }
            leaf mscp {
              description
                "Multicast Shortcut
                 Control Protocol signaling type";
              type empty;
            }
            leaf sip {
              description
                "SIP signaling type";
              type empty;
            }
            leaf xccp {
              description
                "Extended call control provider
                 signaling type";
              type empty;
            }
          }
          uses match-application-source-grouping;
          uses match-application-version-grouping;
          uses match-application-vendor-grouping;
        }
      }
      leaf telepresence-data {
        description
          "Telepresence-data stream";
        type empty;
      }
      container telepresence-data-conf {
        description
          "Telepresence-data stream configurations";
        container telepresence-data {
          description
            "Telepresence-data stream";
          uses match-application-source-grouping;
          uses match-application-version-grouping;
          uses match-application-vendor-grouping;
        }
      }
      leaf telepresence-media {
        description
          "Telepresence-media stream";
        type empty;
      }
      container telepresence-media-conf {
        description
          "Telepresence-media stream configurations";
        container telepresence-media {
          description
            "Telepresence-media stream";
          container multiplex-type {
            description
              "Multiplex Type";
            leaf set {
              description
                "Multiplex Set";
              type empty;
            }
            leaf unset {
              description
                "Multiplex Unset";
              type empty;
            }
          }
          container traffic-type {
            description
              "Traffic Type";
            leaf control {
              description
                "Control traffic type";
              type empty;
            }
          }
          container transport-type {
            description
              "Transport Type";
            leaf rtcp {
              description
                "Real Time transport Control
                 Protocol transport type";
              type empty;
            }
            leaf rtp {
              description
                "Real Time Protocol transport type";
              type empty;
            }
          }
          uses match-application-source-grouping;
          uses match-application-version-grouping;
          uses match-application-vendor-grouping;
        }
      }
      leaf vmware-view {
        description
          "vmware view";
        type empty;
      }
      container vmware-view-conf {
        description
          "vmware view configurations";
        container vmware-view {
          description
            "vmware view";
          container traffic-type {
            description
              "Traffic Type";
            leaf desktop {
              description
                "Desktop traffic type";
              type empty;
            }
            leaf desktop-feedback {
              description
                "Desktop-feedback traffic type";
              type empty;
            }
            leaf session {
              description
                "Session traffic type";
              type empty;
            }
            leaf streaming {
              description
                "Streaming traffic type";
              type empty;
            }
            leaf tunnel {
              description
                "Tunnel traffic type";
              type empty;
            }
            leaf usb-redirection {
              description
                "Usb-redirection traffic type";
              type empty;
            }
          }
          container transport-type {
            description
              "Transport Type";
            leaf pcoip {
              description
                " Pc over ip transport type";
              type empty;
            }
            leaf rdp {
              description
                "Remote Desktop
                 Protocol transport type";
              type empty;
            }
          }
          uses match-application-source-grouping;
          uses match-application-version-grouping;
          uses match-application-vendor-grouping;
        }
      }
      leaf webex-meeting {
        description
          "Webex-meeting stream";
        type empty;
      }
      container webex-meeting-conf {
        description
          "webex-meeting stream configurations";
        container webex-meeting {
          description
            "webex-meeting stream";
          container traffic-type {
            description
              "Traffic Type";
            leaf control {
              description
                "Control traffic type";
              type empty;
            }
            leaf sharing {
              description
                "Sharing traffic type";
              type empty;
            }
            leaf streaming {
              description
                "Streaming traffic type";
              type empty;
            }
          }
          container transport-type {
            description
              "Transport Type";
            leaf http {
              description
                "Hyper text transport
                 protocol transport type";
              type empty;
            }
          }
          uses match-application-source-grouping;
          uses match-application-version-grouping;
          uses match-application-vendor-grouping;
        }
      }
      leaf wyze-zero-client {
        description
          "Zero client";
        type empty;
      }
      container wyze-zero-client-conf {
        description
          "Zero client configurations";
        container wyze-zero-client {
          description
            "Zero client";
          container traffic-type {
            description
              "Traffic Type";
            leaf streaming {
              description
                "Streaming traffic type";
              type empty;
            }
          }
          uses match-application-source-grouping;
          uses match-application-version-grouping;
          uses match-application-vendor-grouping;
        }
      }
      leaf xmpp-client {
        description
          "Extensible Messaging and Presence Protocol";
        type empty;
      }
      container xmpp-client-conf {
        description
          "Extensible Messaging and Presence Protocol
           configurations";
        container xmpp-client {
          description
            "Extensible Messaging and Presence Protocol";
          uses match-application-source-grouping;
          uses match-application-version-grouping;
          uses match-application-vendor-grouping;
        }
      }
    }
    leaf any {
      description
        "Any packets";
      type empty;
    }
    leaf-list class-map {
      description
        "Class map";
      type leafref {
        path "/ios:native/ios:policy/ios-policy:class-map/ios-policy:name";
      }
    }
    leaf-list cos {
      description
        "IEEE 802.1Q/ISL class of service/user priority values";
      type uint8 {
        range "0..7";
      }
    }
    leaf-list traffic-class {
      description
        "Match traffic class";
      type uint8 {
        range "1..7";
      }
    }
    container destination-address {
      description
        "Destination address";
      leaf-list mac {
        description
          "MAC address";
        type yang:mac-address;
      }
    }
    leaf-list discard-class {
      description
        "Discard behavior identifier";
      type uint8 {
        range "0..7";
      }
    }
    leaf-list dscp {
      description
        "Match DSCP in IP(v4) and IPv6 packets";
      type ios-types:dscp-type;
    }
    leaf fr-de {
      description
        "Match on Frame-relay DE bit";
      type empty;
    }
    leaf-list fr-dlci {
      description
        "Match on fr-dlci";
      type uint16 {
        range "16..1007";
      }
    }
    container l2 {
      description
        "Match l2 src MAC";
      container src-mac {
        description
          "match src-mac";
        leaf miss {
          type empty;
          description
            "set to match on src-mac miss";
        }
      }
      container dst-mac {
        description
          "match ls dst MAC";
        leaf miss {
          type empty;
          description
            "set to match on dst-mac miss";
        }
      }
    }
    container group-object {
      description
        "Match object-group";
      container security {
        description
          "Match object-group security";
        leaf-list source {
          description
            "Match source object-group security";
          type string;
        }
        leaf-list destination {
          description
            "Match destination object-group security";
          type string;
        }
      }
    }
    leaf-list input-interface {
      description
        "Select an input interface to match";
      type string;
    }
    container ip {
      description
        "IP specific values";
      leaf-list dscp {
        description
          "Match IP DSCP (DiffServ CodePoints)";
        type ios-types:dscp-type;
      }
      leaf-list precedence {
        description
          "Match IP precedence";
        type ios-types:precedence-type;
      }
      list rtp {
        description
          "Match RTP port nos";
        key "port1 port2";
        leaf port1 {
          type uint16 {
            range "2000..65535";
          }
        }
        leaf port2 {
          type uint16 {
            range "0..16383";
          }
        }
      }
    }
    leaf non-client-nrt {
      type empty;
    }
    container mpls {
      description
        "Multi Protocol Label Switching specific values";
      container experimental {
        description
          "Match MPLS experimental";
        leaf-list topmost {
          description
            "Match MPLS experimental value on topmost label";
          type uint8 {
            range "0..7";
          }
        }
      }
    }
    container packet {
      description
        "Layer 3 Packet length";
      container length {
        description
          "Layer 3 Packet length";
        leaf max {
          description
            "Maximum length of packet";
          type uint16 {
            range "1..2000";
          }
        }
        leaf min {
          description
            "Minimum length of packet";
          type uint16 {
            range "1..2000";
          }
        }
      }
    }
    leaf-list precedence {
      description
        "Match Precedence in IP(v4) and IPv6 packets";
      type ios-types:precedence-type;
    }
    container nbar-protocol {
      description
        "nbar-protocol";
      leaf name {
        description
          "nbar policy-name";
        type string;
      }
    }
    leaf-list qos-group {
      description
        "Qos-group";
      type uint16 {
        range "0..99";
      }
    }
    container security-group {
      description
        "Security group";
      container destination {
        description
          "Destination security group";
        leaf tag {
          description
            "Security group tag";
          type uint16;
        }
      }
      container source {
        description
          "Source security group";
        leaf tag {
          description
            "Security group tag";
          type uint16;
        }
      }
    }
    list service {
      description
        "Service Instance to match";
      key "efp";
      leaf efp {
        description
          "Ethernet Flow Point(EFP) range to match";
        type uint16 {
          range "1..4000";
        }
      }
      leaf instance {
        description
          "Service Instance to match";
        type empty;
      }
      leaf ethernet {
        description
          "Service Instance to match";
        type empty;
      }
    }
    container source-address {
      description
        "Source address";
      leaf-list mac {
        description
          "MAC address";
        type yang:mac-address;
      }
    }
    container vlan {
      description
        "VLANs to match";
      leaf-list inner {
        description
          "Inner tag to match";
        type union {
          type uint16 {
            range "1..4094";
          }
          type string;
        }
      }
      leaf-list value {
        description
          "value of vlan to match";
        type union {
          type uint16 {
            range "1..4094";
          }
          type string;
        }
      }
    }
    container packet-tag {
      description
        "match packet-tag";
      list packet-tag {
        description
          "match packet-tag";
        key "pak-type pak-value pak-mask";
        leaf pak-type {
          description
            "packet-tag type";
          type uint8 {
            range "1..8";
          }
        }
        leaf pak-value {
          description
            "packet-tag value";
          type uint32 {
            range "0..65535";
          }
        }
        leaf pak-mask {
          description
            "packet-tag mask";
          type uint32 {
            range "0..65535";
          }
        }
      }
    }
  }

  grouping class-map-appnav-match-grouping {
    list peer-config {
      description
        "APPNAV Peer Filter";
      when "../../type = 'appnav'";
      ordered-by user;
      key "name";
      leaf name {
        type string;
      }
    }
    leaf peer {
      status deprecated;
      description
        "APPNAV Peer Filter";
      when "../../type = 'appnav'";
      type string;
    }
  }

  grouping class-map-appnav-not-match-grouping {
    list peer-config {
      description
        "APPNAV Peer Filter";
      when "../../../type = 'appnav'";
      ordered-by user;
      key "name";
      leaf name {
        type string;
      }
    }
    leaf peer {
      status deprecated;
      description
        "APPNAV Peer Filter";
      when "../../../type = 'appnav'";
      type string;
    }
  }

  grouping config-class-map-grouping {
    list class-map {
      description
        "configure qos class map";
      key "name";
      leaf name {
        description
          "name of the class map";
        type string {
          length "1..205";
        }
      }
      leaf type {
        description
          "type of the class-map";
        type enumeration {
          enum access-control;
          enum appnav;
          enum control;
          enum inspect;
          enum multicast-flows;
          enum stack;
          enum traffic;
          enum site-manager;
        }
      }
      leaf subscriber {
        description
          "Domain name of the class map";
        type empty;
      }
      leaf protocol {
        description
          "protocol of the class map";
        type enumeration {
          enum aol;
          enum edonkey;
          enum fasttrack;
          enum gnutella;
          enum http;
          enum imap;
          enum kazaa2;
          enum msnmsgr;
          enum pop3;
          enum smtp;
          enum sunrpc;
          enum ymsgr;
        }
      }
      leaf prematch {
        description
          "Logical-AND/Logical-OR of all matching statements under this class map";
        type enumeration {
          enum match-all;
          enum match-any;
          enum match-none;
        }
        mandatory true;
      }
      leaf description {
        description
          "Class-Map description";
        type string {
          length "1..200";
        }
      }
      container match {
        description
          "classification criteria";
        uses class-map-match-common-grouping;
        uses class-map-match-access-grouping;
        uses class-map-appnav-match-grouping;
        uses class-map-control-filter-grouping;
        container not {
          description
            "Negate this match result";
          uses class-map-match-common-grouping;
          uses class-map-match-access-grouping;
          uses class-map-appnav-not-match-grouping;
        }
      }
      container no-match {
        description
          "no-match filter";
        uses class-map-control-filter-grouping;
        container current-method-priority {
          description
            "match the priority against the current method's priority";
          leaf-list eq {
            description
              "equal to";
            type uint8 {
              range "1..254";
            }
          }
          leaf-list gt {
            description
              "greater than";
            type uint8 {
              range "1..254";
            }
          }
          leaf-list lt {
            description
              "less than";
            type uint8 {
              range "1..254";
            }
          }
        }
      }
    }
  }

  grouping config-parameter-map-type-cws-tunnel-global-grouping {
    container cws-tunnel {
      description
        "Cloud Web Security tunnel mode";
      container global {
        description
          "cws_tunnel global parameter-map";
        presence "true";
        leaf fail-open {
          description
            "Allow traffic to go in clear if CWS Towers are unreachable";
          type empty;
        }
        container license {
          description
            "License Key";
          container unencypted {
            description
              "Unencrypted License";
            leaf hex-string {
              description
                "32 char non encrypted hex key";
              type string;
            }
          }
          container encrypted {
            description
              "Encrypted License";
            leaf hex-string {
              description
                "66 char encrypted hex key";
              type string;
            }
          }
        }
        leaf logging {
          description
            "CWS syslogs";
          type empty;
        }
        container primary {
          description
            "Primary tower";
          presence "true";
          container tower {
            description
              "Tower configuration for CWS";
            leaf ipv4 {
              description
                "IPv4 address of the tower";
              type inet:ipv4-address;
            }
            leaf name {
              description
                "Fully Qualified Domain Name of tower";
              type string;
            }
          }
        }
        leaf redirect-list {
          description
            "Set access-list for reverse route from CWS Tower
             Standard IP access-list number <1-199>
             Standard IP access-list number (expanded range) <1300-2699>";
          type union {
            type uint16 {
              range "1..199";
            }
            type uint16 {
              range "1300..2699";
            }
          }
        }
        container secondary {
          description
            "Secondary tower";
          presence "true";
          container tower {
            description
              "Tower configuration for CWS";
            leaf ipv4 {
              description
                "IPv4 address of the tower";
              type inet:ipv4-address;
            }
            leaf name {
              description
                "Fully Qualified Domain Name of tower";
              type string;
            }
          }
        }
        container whitelist {
          description
            "Disable redirection to CWS
             Access list (standard) <1-199>
             Access list (extended) <1300-2699>
             Access list name";
          presence "true";
          container acl {
            description
              "Access list";
            leaf acl-number {
              type union {
                type uint16 {
                  range "1..199";
                }
                type uint16 {
                  range "1300..2699";
                }
              }
            }
            leaf name {
              description
                "Access list name";
              type string {
                length "1..64";
              }
            }
          }
          container domain-name {
            description
              "Domain name based Whitelist";
            leaf regex {
              description
                "Domain name regex parameter map";
              type leafref {
                path "/ios:native/ios:parameter-map/ios:type/ios-policy:regex/ios-policy:name";
              }
            }
          }
          container download {
            description
              "whitelist download command";
            presence "true";
            leaf interval {
              description
                "Download interval in minutes";
              type uint16 {
                range "5..10080";
              }
            }
          }
        }
      }
    }
  }

  grouping config-parameter-map-type-inspect-grouping {
    list inspect {
      description
        "inspect parameter-map";
      key "name";
      leaf name {
        type string;
      }
      container alert {
        description
          "Turn on/off alert";
        leaf on {
          description
            "Turn on alert";
          type empty;
        }
      }
      container application-inspect {
        description
          "Turn on application inspection";
        leaf dns {
          type boolean;
          default "true";
        }
        leaf exec {
          type boolean;
          default "true";
        }
        leaf ftp {
          type boolean;
          default "true";
        }
        leaf gtp {
          type boolean;
          default "true";
        }
        leaf h323 {
          type boolean;
          default "true";
        }
        leaf http {
          type boolean;
          default "true";
        }
        leaf imap {
          type boolean;
          default "true";
        }
        leaf login {
          type boolean;
          default "true";
        }
        leaf msrpc {
          type boolean;
          default "true";
        }
        leaf netbios {
          type boolean;
          default "true";
        }
        leaf pop3 {
          type boolean;
          default "true";
        }
        leaf rtsp {
          type boolean;
          default "true";
        }
        leaf shell {
          type boolean;
          default "true";
        }
        leaf sip {
          type boolean;
          default "true";
        }
        leaf skinny {
          type boolean;
          default "true";
        }
        leaf smtp {
          type boolean;
          default "true";
        }
        leaf sunrpc {
          type boolean;
          default "true";
        }
        leaf tftp {
          type boolean;
          default "true";
        }
      }
      container audit-trail {
        description
          "Turn on/off audit trail";
        leaf on {
          description
            "Turn on audit trail";
          type empty;
        }
      }
      leaf dns-timeout {
        description
          "Timeout in seconds";
        type uint32 {
          range "1..2147483";
        }
      }
      container icmp {
        description
          "Config timeout values for icmp";
        container idle-time {
          description
            "Specify idle timeout for icmp";
          leaf timeout {
            type uint32 {
              range "1..2147483";
            }
          }
          leaf ageout-time {
            description
              "Specify aggressive age-out time for icmp";
            type uint32 {
              range "1..2147483";
            }
          }
        }
      }
      leaf icmp-unreachable-allow {
        description
          "ICMP unreachable packets are allowed";
        type empty;
      }
      container log {
        description
          "Configure inspect logging parameters";
        leaf dropped-packets {
          description
            "Log dropped packets";
          type empty;
        }
        leaf flow {
          description
            "Log flow info";
          type empty;
        }
      }
      container max-incomplete {
        description
          "Specify maximum number of incomplete connections before clamping";
        leaf high {
          description
            "Specify high-watermark for clamping";
          type uint32 {
            range "1..2147483647";
          }
        }
        leaf low {
          description
            "Specify low-watermark for clamping";
          type uint32 {
            range "1..2147483647";
          }
        }
      }
      container one-minute {
        description
          "Specify one-minute-sample watermarks for clamping";
        leaf high {
          description
            "Specify high-watermark for clamping";
          type uint32 {
            range "1..2147483647";
          }
        }
        leaf low {
          description
            "Specify low-watermark for clamping";
          type uint32 {
            range "1..2147483647";
          }
        }
      }
      container sessions {
        description
          "Configure sessions related parameters";
        leaf maximum {
          description
            "Maximum sessions";
          type uint32 {
            range "1..2147483647";
          }
        }
        leaf packet {
          description
            "Simultaneous packets per session";
          type uint8 {
            range "25..100";
          }
        }
        container rate {
          description
            "Specify watermarks for clamping";
          container high {
            description
              "Specify high-watermark for clamping";
            leaf value {
              type uint32 {
                range "1..2147483647";
              }
            }
            leaf time {
              description
                "Specify the time for which session rate limit is applied";
              type uint32 {
                range "1..2147483647";
              }
            }
          }
          container low {
            description
              "Specify low-watermark for clamping";
            leaf value {
              type uint32 {
                range "1..2147483647";
              }
            }
            leaf time {
              description
                "Specify the time for which session rate limit is applied";
              type uint32 {
                range "1..2147483647";
              }
            }
          }
        }
      }
      container tcp {
        description
          "Config timeout values for tcp connections";
        container finwait-time {
          description
            "Specify timeout for TCP connections after a FIN";
          leaf timeout {
            type uint32 {
              range "1..2147483";
            }
          }
          leaf ageout-time {
            description
              "Specify aggressive age-out time for tcp";
            type uint32 {
              range "1..2147483";
            }
          }
        }
        container half-close {
          description
            "Specify tcp halfclose reset RST transmission on/off";
          container reset {
            description
              "Specify tcp halfclose reset RST transmission on/off";
            leaf off {
              description
                "Turn off tcp halfclose reset RST transmission";
              type empty;
            }
          }
        }
        container half-open {
          description
            "Specify tcp halfopen reset RST transmission on/off";
          container reset {
            description
              "Specify tcp halfopen reset RST transmission on/off";
            leaf off {
              description
                "Turn off tcp halfopen reset RST transmission";
              type empty;
            }
          }
        }
        container idle {
          description
            "Specify tcp idle reset RST transmission on/off";
          container reset {
            description
              "Specify tcp idle reset RST transmission on/off";
            leaf off {
              description
                "Turn off tcp idle reset RST transmission";
              type empty;
            }
          }
        }
        container idle-time {
          description
            "Specify idle timeout for tcp connections";
          leaf timeout {
            type uint32 {
              range "1..2147483";
            }
          }
          leaf ageout-time {
            description
              "Specify aggressive age-out time for tcp";
            type uint32 {
              range "1..2147483";
            }
          }
        }
        container max-incomplete {
          description
            "Specify max half-open connection per host";
          container host {
            description
              "Specify max half-open connection per host";
            leaf value {
              type uint32 {
                range "1..4294967295";
              }
            }
            leaf block-time {
              description
                "Specify the maximum time to block new connection attempts to host";
              type uint16 {
                range "0..35791";
              }
            }
          }
        }
        container synwait-time {
          description
            "Specify timeout for TCP connections after a SYN and no further data";
          leaf timeout {
            type uint32 {
              range "1..2147483";
            }
          }
          leaf ageout-time {
            description
              "Specify aggressive age-out time for syn wait-time";
            type uint32 {
              range "1..2147483";
            }
          }
        }
        container window-scale-enforcement {
          description
            "Specify tcp window scaling enforcement";
          leaf loose {
            description
              "Loose enforcement";
            type empty;
          }
        }
      }
      container udp {
        description
          "Config timeout values for udp flows";
        container half-open {
          description
            "Config timeout values for udp half open flows";
          container idle-time {
            description
              "Specify idle timeout for udp half open";
            leaf timeout {
              type uint32 {
                range "1..2147483";
              }
            }
            leaf ageout-time {
              description
                "Specify aggressive age-out time for udp half open";
              type uint32 {
                range "1..2147483";
              }
            }
          }
        }
        container idle-time {
          description
            "Specify idle timeout for udp";
          leaf timeout {
            type uint32 {
              range "1..2147483";
            }
          }
          leaf ageout-time {
            description
              "Specify aggressive age-out time for udp";
            type uint32 {
              range "1..2147483";
            }
          }
        }
      }
      container zone-mismatch {
        description
          "Config zone-mismatch option";
        leaf drop {
          type empty;
        }
      }
    }
  }

  grouping config-inspect-aggressive-aging-grouping {
    container aggressive-aging {
      description
        "Aggressive Aging parameters";
      choice absolute-percent {
        case absolute-case {
          leaf high {
            description
              "Specify the high watermark for aggressive-aging";
            type uint64 {
              range "1..4294967295";
            }
          }
          leaf low {
            description
              "Specify the low watermark for aggressive-aging";
            type uint64 {
              range "1..4294967295";
            }
          }
        }
        case percent-case {
          leaf high-percent {
            description
              "Specify the high watermark for aggressive-aging in percents";
            type uint8 {
              range "1..100";
            }
          }
          leaf low-percent {
            description
              "Specify the low watermark for aggressive-aging in percents";
            type uint8 {
              range "1..100";
            }
          }
        }
      }
    }
  }

  grouping config-parameter-map-type-inspect-global-deprecate-grouping {
    container inspect-global-deprecate {
      container inspect {
        description
          "inspect parameter-map";
        container global {
          description
            "inspect global parameter-map";
          presence "true";
          container alert {
            description
              "Turn on/off alert";
            leaf on {
              description
                "Turn on alert";
              type empty;
            }
          }
          container lisp {
            description
              "Turn on LISP options";
            leaf inner-packet-inspection {
              description
                "inner-packet-inspection";
              type empty;
            }
          }
          container log {
            description
              "Configure inspect logging parameters";
            leaf dropped-packets {
              description
                "Log dropped packets";
              type empty;
            }
            container flow-export {
              description
                "Configure inspect external logging parameters";
              container template {
                description
                  "Configure record template parameters";
                leaf timeout-rate {
                  description
                    "Rate to resend the template in seconds";
                  type uint32 {
                    range "0..65535";
                  }
                }
              }
              container v9 {
                description
                  "Netflow version 9";
                container udp {
                  description
                    "Use UDP to export records";
                  container destination {
                    description
                      "Specify the flow-export destination";
                    leaf dst-ip {
                      type inet:ipv4-address;
                    }
                    leaf dst-port {
                      type uint16;
                    }
                  }
                }
              }
            }
          }
          container max-incomplete {
            description
              "Specify max half-open connection";
            container half-open-sessions {
              leaf number {
                type uint32 {
                  range "1..4294967295";
                }
              }
              container aggressive-aging {
                description
                  "Aggressive Aging parameters";
                choice absolute-percent {
                  case absolute-case {
                    leaf high {
                      description
                        "Specify the high watermark for aggressive-aging";
                      type uint64 {
                        range "1..4294967295";
                      }
                    }
                    leaf low {
                      description
                        "Specify the low watermark for aggressive-aging";
                      type uint64 {
                        range "1..4294967295";
                      }
                    }
                  }
                  case percent-case {
                    leaf high-percent {
                      description
                        "Specify the high watermark for aggressive-aging in percents";
                      type uint8 {
                        range "1..100";
                      }
                    }
                    leaf low-percent {
                      description
                        "Specify the low watermark for aggressive-aging in percents";
                      type uint8 {
                        range "1..100";
                      }
                    }
                  }
                }
              }
            }
            leaf icmp {
              description
                "Specify max half-open ICMP connections";
              type uint32 {
                range "1..4294967295";
              }
            }
            leaf tcp {
              description
                "Specify max half-open TCP connections";
              type uint32 {
                range "1..4294967295";
              }
            }
            leaf udp {
              description
                "Specify max half-open UDP connections";
              type uint32 {
                range "1..4294967295";
              }
            }
          }
          leaf multi-tenancy {
            description
              "Enable multi-tenancy";
            type empty;
          }
          container per-box {
            description
              "Configure per-box attributes";
            uses config-inspect-aggressive-aging-grouping;
            container max-incomplete {
              description
                "Specify max half-open connection";
              container half-open-sessions {
                leaf number {
                  type uint32 {
                    range "1..4294967295";
                  }
                }
                container aggressive-aging {
                  description
                    "Aggressive Aging parameters";
                  choice absolute-percent {
                    case absolute-case {
                      leaf high {
                        description
                          "Specify the high watermark for aggressive-aging";
                        type uint64 {
                          range "1..4294967295";
                        }
                      }
                      leaf low {
                        description
                          "Specify the low watermark for aggressive-aging";
                        type uint64 {
                          range "1..4294967295";
                        }
                      }
                    }
                    case percent-case {
                      leaf high-percent {
                        description
                          "Specify the high watermark for aggressive-aging in percents";
                        type uint8 {
                          range "1..100";
                        }
                      }
                      leaf low-percent {
                        description
                          "Specify the low watermark for aggressive-aging in percents";
                        type uint8 {
                          range "1..100";
                        }
                      }
                    }
                  }
                }
              }
              leaf icmp {
                description
                  "Specify max half-open ICMP connections";
                type uint32 {
                  range "1..4294967295";
                }
              }
              leaf tcp {
                description
                  "Specify max half-open TCP connections";
                type uint32 {
                  range "1..4294967295";
                }
              }
              leaf udp {
                description
                  "Specify max half-open UDP connections";
                type uint32 {
                  range "1..4294967295";
                }
              }
            }
            container tcp {
              description
                "Configure tcp syn-flood limit";
              container syn-flood {
                description
                  "syn-flood limit";
                leaf limit {
                  description
                    "syn-flood limit";
                  type uint32 {
                    range "1..4294967295";
                  }
                }
              }
            }
          }
          container session {
            description
              "Configure session total parameter";
            leaf packet {
              description
                "Simultaneous packets per session";
              type uint8 {
                range "25..100";
              }
            }
            leaf total {
              description
                "session total";
              type uint32 {
                range "1..4294967295";
              }
            }
          }
          container tcp {
            description
              "Configure tcp syn-flood limit";
            container syn-flood {
              description
                "syn-flood limit";
              leaf limit {
                description
                  "syn-flood limit";
                type uint32 {
                  range "1..4294967295";
                }
              }
            }
          }
          list vrf {
            description
              "vrf binding with parameter map";
            key "id";
            leaf id {
              must '/ios:native/ios:vrf/ios:definition[ios:name=current()] or /ios:native/ios:ip/ios:vrf[ios:name=current()]' {
                error-message "VRF must be created 1st, deleted last";
              }
              type string {
                length "1..32";
              }
            }
            leaf inspect {
              description
                "vrf binding with parameter map";
              type leafref {
                path "/ios:native/ios:parameter-map/ios:type/ios-policy:inspect-vrf/ios-policy:name";
              }
            }
          }
        }
      }
    }
  }

  grouping config-parameter-map-type-inspect-global-grouping {
    container inspect-global {
      description
        "inspect global parameter-map";
      presence "true";
      uses config-inspect-aggressive-aging-grouping;
      container alert {
        description
          "Turn on/off alert";
        leaf on {
          description
            "Turn on alert";
          type empty;
        }
      }
      leaf icmp-unreachable-allow {
        description
          "ICMP unreachable packets are allowed";
        type empty;
      }
      container inspect {
        description
          "vrf binding with parameter map";
        leaf name {
          type leafref {
            path "/ios:native/ios:parameter-map/ios:type/ios-policy:inspect-vrf/ios-policy:name";
          }
        }
        list vrf {
          description
            "vrf binding with parameter map";
          key "id";
          leaf id {
            must '/ios:native/ios:vrf/ios:definition[ios:name=current()] or /ios:native/ios:ip/ios:vrf[ios:name=current()]' {
              error-message "VRF must be created 1st, deleted last";
            }
            type string {
              length "1..32";
            }
          }
          leaf name {
            type leafref {
              path "/ios:native/ios:parameter-map/ios:type/ios-policy:inspect-vrf/ios-policy:name";
            }
          }
        }
      }
      container lisp {
        description
          "Turn on LISP options";
        leaf inner-packet-inspection {
          description
            "inner-packet-inspection";
          type empty;
        }
      }
      container log {
        description
          "Configure inspect logging parameters";
        leaf dropped-packets {
          description
            "Log dropped packets";
          type empty;
        }
        leaf flow {
          description
            "Enable connection events on all security policies";
          type empty;
        }
        container flow-export {
          description
            "Configure inspect external logging parameters";
          container template {
            description
              "Configure record template parameters";
            leaf timeout-rate {
              description
                "Rate to resend the template in seconds";
              type uint32 {
                range "0..65535";
              }
            }
          }
          container v9 {
            description
              "Netflow version 9";
            container udp {
              description
                "Use UDP to export records";
              container destination {
                description
                  "Specify the flow-export destination";
                leaf dst-ip {
                  description
                    "destination IP address";
                  type inet:ipv4-address;
                }
                leaf dst-port {
                  description
                    "Destination port number";
                  type uint16;
                }
                leaf vrf {
                  description
                    "Optional VRF label";
                  type string;
                }
                leaf source {
                  description
                    "Specify interface for source address";
                  type string;
                }
              }
              container ipv6-destination {
                description
                  "Specify the flow-export IPv6 destination";
                leaf dst-ip {
                  description
                    "destination IP address";
                  type inet:ipv6-address;
                }
                leaf dst-port {
                  description
                    "Destination port number";
                  type uint16;
                }
                leaf vrf {
                  description
                    "Optional VRF label";
                  type string;
                }
                leaf source {
                  description
                    "Specify interface for source address";
                  type string;
                }
              }
            }
          }
          leaf fnf {
            description
              "Enable log record exports using Flexible NetFlow infrastructure";
            type empty;
          }
        }
      }
      container max-incomplete {
        description
          "Specify max half-open connection";
        container half-open-sessions {
          leaf number {
            type uint32 {
              range "1..4294967295";
            }
          }
          container aggressive-aging {
            description
              "Aggressive Aging parameters";
            choice absolute-percent {
              case absolute-case {
                leaf high {
                  description
                    "Specify the high watermark for aggressive-aging";
                  type uint64 {
                    range "1..4294967295";
                  }
                }
                leaf low {
                  description
                    "Specify the low watermark for aggressive-aging";
                  type uint64 {
                    range "1..4294967295";
                  }
                }
              }
              case percent-case {
                leaf high-percent {
                  description
                    "Specify the high watermark for aggressive-aging in percents";
                  type uint8 {
                    range "1..100";
                  }
                }
                leaf low-percent {
                  description
                    "Specify the low watermark for aggressive-aging in percents";
                  type uint8 {
                    range "1..100";
                  }
                }
              }
            }
          }
        }
        leaf icmp {
          description
            "Specify max half-open ICMP connections";
          type uint32 {
            range "1..4294967295";
          }
        }
        leaf tcp {
          description
            "Specify max half-open TCP connections";
          type uint32 {
            range "1..4294967295";
          }
        }
        leaf udp {
          description
            "Specify max half-open UDP connections";
          type uint32 {
            range "1..4294967295";
          }
        }
      }
      leaf multi-tenancy {
        description
          "Enable multi-tenancy";
        type empty;
      }
      container tcp {
        description
          "Configure tcp syn-flood limit";
        container syn-flood {
          description
            "syn-flood limit";
          leaf limit {
            description
              "syn-flood limit";
            type uint32 {
              range "1..4294967295";
            }
          }
        }
        container window-scale-enforcement {
          description
            "Specify tcp window scaling enforcement";
          leaf loose {
            description
              "Loose enforcement";
            type empty;
          }
        }
      }
      container vpn {
        description
          "vpn zone security vpn enabled";
        container zone {
          description
            "vpn zone security to be enabled";
          leaf security {
            description
              "vpn zone security to be enabled";
            type empty;
          }
          leaf allow-dia {
            description
              "allow-dia";
            type empty;
          }
        }
      }
      container zone-mismatch {
        description
          "Config zone-mismatch option";
        leaf drop {
          type empty;
        }
      }
      leaf session-reclassify-allow {
        type empty;
      }
    }
  }

  grouping config-parameter-map-type-inspect-vrf-grouping {
    list inspect-vrf {
      description
        "inspect vrf parameter-map";
      key "name";
      leaf name {
        type string;
      }
      container alert {
        description
          "Turn on/off alert";
        leaf on {
          description
            "Turn on alert";
          type empty;
        }
      }
      container max-incomplete {
        description
          "Specify max half-open connection per VRF";
        container half-open-sessions {
          leaf number {
            type uint32 {
              range "1..4294967295";
            }
          }
        }
        leaf icmp {
          description
            "Specify max half-open ICMP connections per VRF";
          type uint32 {
            range "1..4294967295";
          }
        }
        leaf tcp {
          description
            "Specify max half-open TCP connections per VRF";
          type uint32 {
            range "1..4294967295";
          }
        }
        leaf udp {
          description
            "Specify max half-open UDP connections per VRF";
          type uint32 {
            range "1..4294967295";
          }
        }
      }
      container session {
        description
          "Configure session total";
        leaf total {
          description
            "total";
          type uint32 {
            range "1..4294967295";
          }
        }
      }
      container tcp {
        description
          "Configure tcp syn-flood limit";
        container syn-flood {
          description
            "syn-flood limit";
          leaf limit {
            description
              "syn-flood limit";
            type uint32 {
              range "1..4294967295";
            }
          }
        }
      }
    }
  }

  grouping config-td-rate-grouping {
    leaf average-time-frame {
      description
        "Configure Threat Detection average time frame";
      type uint16 {
        range "600..3600";
      }
    }
    leaf average-threshold {
      description
        "Configure Threat Detection average threshold";
      type uint32 {
        range "1..4294967295";
      }
    }
    leaf burst-threshold {
      description
        "Configure Threat Detection burst threshold";
      type uint32 {
        range "1..1000000000";
      }
    }
  }

  grouping config-parameter-map-type-inspect-zone-grouping {
    list inspect-zone {
      description
        "inspect zone parameter-map";
      key "name";
      leaf name {
        type string;
      }
      container alert {
        description
          "Turn on/off alert";
        leaf on {
          description
            "Turn on alert";
          type empty;
        }
      }
      leaf max-destination {
        description
          "config maximum destination";
        type uint32 {
          range "1..4294967295";
        }
      }
      container tcp {
        description
          "Configure tcp syn-flood per-destination rate";
        container syn-flood {
          description
            "maximum syn packet";
          container rate {
            description
              "maximum syn packet rate";
            leaf per-destination {
              description
                "per destination";
              type uint32 {
                range "1..1000000000";
              }
            }
          }
        }
      }
      container threat-detection {
        description
          "Configure Threat Detection";
        leaf basic-threat {
          description
            "Enable Threat Detection";
          type empty;
        }
        container rate {
          description
            "Configure Threat Detection rate";
          container fw-drop {
            description
              "Configure Threat Detection rate for firewall drop events";
            uses config-td-rate-grouping;
          }
          container inspect-drop {
            description
              "Configure Threat Detection rate for firewall inspection based drop events";
            uses config-td-rate-grouping;
          }
          container syn-attack {
            description
              "Configure Threat Detection rate for syn attack events";
            uses config-td-rate-grouping;
          }
        }
      }
    }
  }

  grouping config-parameter-map-type-regex-grouping {
    list regex {
      description
        "regex parameter-map";
      key "name";
      leaf name {
        type string;
      }
      list pattern {
        description
          "Configure pattern to match";
        key "regexp";
        max-elements 64;
        leaf regexp {
          type string {
            length "1..240";
          }
        }
      }
    }
  }

  grouping config-parameter-map-type-webauth-grouping {
    list webauth {
      description
        "WEBAUTH parameters";
      key "name";
      leaf name {
        must "not(.='global')" {
          error-message "Please use webauth-global to configure global parameter-map";
        }
        type string {
          length "1..256";
        }
      }
      leaf captive-bypass-portal {
        description
          "Turn on captive bypass";
        type empty;
      }
      container consent {
        description
          "consent parameters";
        leaf email {
          description
            "Turn-on Consent with Email";
          must "../../type = 'consent'" {
            error-message "% First configure 'type consent'";
          }
          type empty;
        }
      }
      container custom-page {
        description
          "custom-page - login, expired, success or failure page";
        container login {
          description
            "auth-proxy login parameters";
          leaf device {
            description
              "Specify name of the HTML file";
            type string {
              pattern '(((bootflash:)|(harddisk:)|(flash:)).*)';
            }
          }
          container expired {
            description
              "Expired authentication proxy";
            leaf device {
              description
                "Specify name of the HTML file";
              type string {
                pattern '(((bootflash:)|(harddisk:)|(flash:)).*)';
              }
            }
          }
        }
        container failure {
          description
            "Failed authentication proxy";
          leaf device {
            description
              "Specify name of the HTML file";
            type string {
              pattern '(((bootflash:)|(harddisk:)|(flash:)).*)';
            }
          }
        }
        container success {
          description
            "Successful authentication proxy";
          leaf device {
            description
              "Specify name of the HTML file";
            type string {
              pattern '(((bootflash:)|(harddisk:)|(flash:)).*)';
            }
          }
        }
      }
      container login-auth-bypass {
        description
          "Login Auth Bypass for FQDN";
        container ip-access-list {
          description
            "fqdn acl name";
          leaf name {
            type string;
          }
          leaf domain-name-list {
            description
              "Domain list name";
            type string;
          }
        }
      }
      leaf logout-window-disabled {
        description
          "Webauth logout window disable";
        type empty;
      }
      leaf max-http-conns {
        description
          "Webauth max HTTP connections per client";
        type uint8 {
          range "1..200";
        }
      }
      container redirect {
        description
          "redirect url";
        container append {
          description
            "Append tag name to redirect URL";
          container ap-mac {
            description
              "AP MAC Address";
            leaf tag {
              type string;
            }
          }
          container client-mac {
            description
              "client MAC name";
            leaf tag {
              type string;
            }
          }
          container wlan-ssid {
            description
              "WLAN SSID name";
            leaf tag {
              type string;
            }
          }
        }
        container portal {
          description
            "External Portal";
          leaf ipv4 {
            type inet:ipv4-address;
          }
          leaf ipv6 {
            type inet:ipv6-address;
          }
        }
        leaf for-login {
          description
            "Specify URL string (maximum allowed length is 230 chars)";
          type string {
            length "1..230";
          }
        }
        leaf on-failure {
          description
            "Specify URL string (maximum allowed length is 230 chars)";
          type string {
            length "1..230";
          }
        }
        leaf on-success {
          description
            "Specify URL string (maximum allowed length is 230 chars)";
          type string {
            length "1..230";
          }
        }
      }
      container sleeping-client {
        description
          "enable sleeping client for webauth";
        presence "true";
        leaf timeout {
          description
            "Sleep timeout in Minute";
          type uint16 {
            range "10..43200";
          }
          default "720";
        }
      }
      leaf success-window-disable {
        description
          "Disable Success Window";
        type empty;
      }
      container timeout {
        description
          "timeout for the webauth session";
        container init-state {
          description
            "init-state timeout";
          leaf sec {
            description
              "WEBAUTH Timeout in Seconds";
            type uint32 {
              range "60..3932100";
            }
          }
        }
        container fin-wait {
          description
            "fin-wait timeout";
          leaf msec {
            description
              "WEBAUTH Timeout in milliseconds";
            type uint32 {
              range "1..2147483647";
            }
          }
        }
      }
      leaf type {
        description
          "type - web-auth, consent or both";
        must "((../consent/email and . = 'consent') or (not(../consent/email)))" {
          error-message "% First unconfigure 'consent email'";
        }
        type enumeration {
          enum authbypass;
          enum consent;
          enum webauth;
          enum webconsent;
        }
      }
    }
  }

  grouping config-parameter-map-type-subscriber-grouping {
    container subscriber {
      description
        "some text for subscriber";
      list attribute-to-service {
        description
          "some text for attribute-to-service";
        key "name";
        leaf name {
          type string {
            length "1..99";
          }
        }
        list map-number {
          description
            "map number, 1 for 1st map, 2 for 2nd...";
          key "number";
          leaf number {
            type uint8 {
              range "1..254";
            }
          }
          container map {
            description
              "map statement";
            container device-type {
              description
                "specify device-type";
              leaf filter-type {
                type enumeration {
                  enum eq;
                  enum not-eq;
                  enum regex;
                }
              }
              leaf device-name {
                type string;
              }
            }
            container mac-address {
              description
                "specify mac-address";
              leaf filter-type {
                description
                  "filter-type-name";
                type enumeration {
                  enum eq;
                  enum not-eq;
                }
              }
              leaf mac {
                description
                  "mac-address";
                type ios-types:cisco-mac-address-type;
              }
            }
            container oui {
              description
                "specify oui";
              leaf filter-type {
                description
                  "filter-type-name";
                type enumeration {
                  enum eq;
                  enum not-eq;
                }
              }
              leaf oui-address {
                description
                  "Enter oui address";
                type string;
              }
            }
            container user-role {
              description
                "specify user-role";
              leaf filter-type {
                description
                  "filter-type-name";
                type enumeration {
                  enum regex;
                  enum eq;
                  enum not-eq;
                }
              }
              leaf user-role {
                description
                  "Enter user-role";
                type string;
              }
            }
            container username {
              description
                "specify username";
              leaf filter-type {
                description
                  "filter-type-name";
                type enumeration {
                  enum regex;
                  enum eq;
                  enum not-eq;
                }
              }
              leaf username {
                description
                  "Enter username";
                type string;
              }
            }
          }
          list apply-template {
            description
              "action number, 1 for 1st number, 2 for 2nd...";
            key "num";
            leaf num {
              type uint8 {
                range "1..254";
              }
            }
            leaf config-macro {
              description
                "specify a config-macro";
              type string;
            }
            leaf interface-template {
              description
                "specify interface-template";
              type string;
            }
            leaf service-template {
              description
                "specify service-template";
              type string;
            }
          }
        }
      }
    }
  }

  grouping config-parameter-map-type-webauth-global-grouping {
    container webauth-global {
      container webauth {
        description
          "WEBAUTH parameters";
        container global {
          description
            "Global parameter-map";
          presence "true";
          container banner-conf {
            leaf banner {
              description
                "Banner file or text";
              type empty;
            }
            leaf file {
              description
                "Specify name of the banner-file";
              type string;
            }
            leaf text {
              description
                "c banner-text c, where 'c' is a delimiting character
                 (maximum 200 characters)";
              type string {
                length "1..200";
              }
            }
            leaf title {
              description
                "c banner-title-text c, where 'c' is a delimiting character
                 (maximum 127 characters)";
              type string {
                length "1..127";
              }
            }
          }
          leaf captive-bypass-portal {
            description
              "Turn on captive bypass";
            type empty;
          }
          leaf cisco-logo-disable {
            description
              "Disable Cisco logo on internal html pages";
            type empty;
          }
          container consent {
            description
              "consent parameters";
            leaf email {
              description
                "Turn-on Consent with Email";
              must "../../type = 'consent'" {
                error-message "% First configure 'type consent'";
              }
              type empty;
            }
          }
          container custom-page {
            description
              "custom-page - login, expired, success or failure page";
            container login {
              description
                "auth-proxy login parameters";
              leaf device {
                type string;
              }
              container expired {
                description
                  "Expired authentication proxy";
                leaf device {
                  type string;
                }
              }
            }
            container failure {
              description
                "Failed authentication proxy";
              leaf device {
                type string;
              }
            }
            container success {
              description
                "Successful authentication proxy";
              leaf device {
                type string;
              }
            }
          }
          container http {
            description
              "Configure Webauth HTTP Server";
            leaf port {
              description
                "Port Range Number";
              type uint16 {
                range "81..65535";
              }
            }
          }
          leaf intercept-https-enable {
            description
              "Enable intercept of https traffic";
            type empty;
          }
          container login-auth-bypass {
            description
              "Login Auth Bypass for FQDN";
            container ip-access-list {
              description
                "fqdn acl name";
              leaf name {
                type string;
              }
              leaf domain-name-list {
                description
                  "Domain list name";
                type string;
              }
            }
          }
          leaf logout-window-disabled {
            description
              "Webauth logout window disable";
            type empty;
          }
          leaf max-http-conns {
            description
              "Webauth max HTTP connections per client";
            type uint8 {
              range "1..200";
            }
          }
          container redirect {
            description
              "redirect url";
            container append {
              description
                "Append tag name to redirect URL";
              container ap-mac {
                description
                  "AP MAC Address";
                leaf tag {
                  type string;
                }
              }
              container client-mac {
                description
                  "client MAC name";
                leaf tag {
                  type string;
                }
              }
              container wlan-ssid {
                description
                  "WLAN SSID name";
                leaf tag {
                  type string;
                }
              }
            }
            container portal {
              description
                "External portal";
              leaf ipv4 {
                type inet:ipv4-address;
              }
              leaf ipv6 {
                type inet:ipv6-address;
              }
            }
            leaf for-login {
              description
                "Specify URL string (maximum allowed length is 230 chars)";
              type string {
                length "1..230";
              }
            }
            leaf on-failure {
              description
                "Specify URL string (maximum allowed length is 230 chars)";
              type string {
                length "1..230";
              }
            }
            leaf on-success {
              description
                "Specify URL string (maximum allowed length is 230 chars)";
              type string {
                length "1..230";
              }
            }
          }
          leaf secure-webauth-disable {
            description
              "Disable HTTP secure server for Webauth";
            type empty;
          }
          container sleeping-client {
            description
              "enable sleeping client for webauth";
            leaf timeout {
              description
                "Sleep timeout in Minute";
              type uint32 {
                range "10..43200";
              }
            }
          }
          leaf success-window-disable {
            description
              "Disable Success Window";
            type empty;
          }
          container timeout {
            description
              "timeout for the webauth session";
            container init-state {
              description
                "init-state timeout";
              leaf sec {
                description
                  "WEBAUTH Timeout in Seconds";
                type uint32 {
                  range "60..3932100";
                }
              }
            }
            container fin-wait {
              description
                "fin-wait timeout";
              leaf msec {
                description
                  "WEBAUTH Timeout in milliseconds";
                type uint32 {
                  range "1..2147483647";
                }
              }
            }
          }
          leaf type {
            description
              "type - web-auth, consent or both";
            must "((../consent/email and . = 'consent') or (not(../consent/email)))" {
              error-message "% First unconfigure 'consent email'";
            }
            type enumeration {
              enum authbypass;
              enum consent;
              enum webauth;
              enum webconsent;
            }
          }
          leaf trustpoint {
            description
              "Specify the trustpoint name";
            type string;
          }
          container virtual-ip {
            description
              "Virtual Ip Address";
            container ipv4 {
              description
                "Ipv4 Address";
              leaf address {
                description
                  "Recovery IP address";
                type inet:ipv4-address;
              }
              leaf virtual-host {
                description
                  "Virtual host name";
                type string;
              }
            }
            container ipv6 {
              description
                "Ipv6 Address";
              leaf address {
                description
                  "Recovery IP address";
                type inet:ipv6-address;
              }
              leaf virtual-host {
                description
                  "Virtual host name";
                type string;
              }
            }
          }
          container watch-list {
            description
              "Watch List of webauth clients";
            leaf enabled {
              description
                "Enable Watch list";
              type empty;
            }
            leaf dynamic-expiry-timeout {
              description
                "dynamic_expiry_timeout";
              type uint32 {
                range "0..2147483";
              }
            }
            container add-item {
              description
                "Add item to Watch-list";
              leaf ipv4 {
                description
                  "IPv4 Watch List Entry";
                type inet:ipv4-address;
              }
              leaf ipv6 {
                description
                  "IPv6 Watch List Entry";
                type inet:ipv6-address;
              }
            }
          }
          leaf webauth-http-enable {
            description
              "Configure HTTP Server for webauth";
            type empty;
          }
          leaf webauth-bypass-intercept {
            description
              "Specify the webauth bypass ACL name";
            type string;
          }
        }
      }
    }
  }

  grouping config-service-policy-direction-grouping {
    leaf input {
      description
        "Assign policy-map to the input of an interface";
      type leafref {
        path "/ios:native/ios:policy/policy-map/name";
      }
      must "not (/ios:native/ios:policy/ios-policy:policy-map[ios-policy:name = current()]/ios-policy:class/ios-policy:action-list/ios-policy:action-type = 'bandwidth')" {
        error-message "bandwidth command is not supported in input direction for this interface";
      }
      must "not (/ios:native/ios:policy/ios-policy:policy-map[ios-policy:name = current()]/ios-policy:class/ios-policy:action-list/ios-policy:action-type = 'priority')" {
        error-message "priority command is not supported in input direction for this interface";
      }
      must "not (/ios:native/ios:policy/ios-policy:policy-map[ios-policy:name = current()]/ios-policy:class/ios-policy:action-list/ios-policy:action-type = 'queue-limit')" {
        error-message "queue-limit command is not supported in input direction for this interface";
      }
      must "not (/ios:native/ios:policy/ios-policy:policy-map[ios-policy:name = current()]/ios-policy:class/ios-policy:action-list/ios-policy:action-type = 'shape')" {
        error-message "shape command is not supported in input direction for this interface";
      }
      must "not (/ios:native/ios:policy/ios-policy:policy-map[ios-policy:name = current()]/ios-policy:class/ios-policy:action-list/ios-policy:action-type = 'random-detect')" {
        error-message "random-detect command in policy-map is not supported ininput direction for this interface";
      }
      must "not (/ios:native/ios:policy/ios-policy:policy-map[ios-policy:name = current()]/ios-policy:class/ios-policy:action-list/ios-policy:police-rate-unit/ios-policy:police/ios-policy:rate/ios-policy:xps = 'pps')" {
        error-message "police parameters in packets per second only allowed forcontrol-plane service-policy";
      }
    }
    leaf output {
      description
        "Assign policy-map to the output of an interface";
      type leafref {
        path "/ios:native/ios:policy/policy-map/name";
      }
    }
  }

  grouping config-control-plane-service-policy-direction-grouping {
    leaf input {
      description
        "Assign policy-map to the input of an interface";
      type leafref {
        path "/ios:native/ios:policy/policy-map/name";
      }
      must 'not (/ios:native/ios:policy/policy-map[ios-policy:name = current()]/ios-policy:type)' {
        error-message "policy map should be of same type";
      }
      must "not (/ios:native/ios:policy/ios-policy:policy-map[ios-policy:name = current()]/ios-policy:class/ios-policy:action-list/ios-policy:action-type = 'bandwidth')" {
        error-message "bandwidth not supported on control-plane";
      }
      must "not (/ios:native/ios:policy/ios-policy:policy-map[ios-policy:name = current()]/ios-policy:class/ios-policy:action-list/ios-policy:action-type = 'priority')" {
        error-message "priority not supported on control-plane";
      }
      must "not (/ios:native/ios:policy/ios-policy:policy-map[ios-policy:name = current()]/ios-policy:class/ios-policy:action-list/ios-policy:action-type = 'queue-limit')" {
        error-message "queue-limit not supported on control-plane";
      }
      must "not (/ios:native/ios:policy/ios-policy:policy-map[ios-policy:name = current()]/ios-policy:class/ios-policy:action-list/ios-policy:action-type = 'shape')" {
        error-message "shape not supported on control-plane";
      }
      must "not (/ios:native/ios:policy/ios-policy:policy-map[ios-policy:name = current()]/ios-policy:class/ios-policy:action-list/ios-policy:action-type = 'random-detect')" {
        error-message "random-detect not supported on control-plane";
      }
    }
    leaf output {
      description
        "Assign policy-map to the output of an interface";
      type leafref {
        path "/ios:native/ios:policy/policy-map/name";
      }
      must 'not (/ios:native/ios:policy/policy-map[ios-policy:name = current()]/ios-policy:type)' {
        error-message "policy map should be of same type";
      }
      must "not (/ios:native/ios:policy/ios-policy:policy-map[ios-policy:name = current()]/ios-policy:class/ios-policy:action-list/ios-policy:action-type = 'bandwidth')" {
        error-message "bandwidth not supported on control-plane";
      }
      must "not (/ios:native/ios:policy/ios-policy:policy-map[ios-policy:name = current()]/ios-policy:class/ios-policy:action-list/ios-policy:action-type = 'priority')" {
        error-message "priority not supported on control-plane";
      }
      must "not (/ios:native/ios:policy/ios-policy:policy-map[ios-policy:name = current()]/ios-policy:class/ios-policy:action-list/ios-policy:action-type = 'queue-limit')" {
        error-message "queue-limit not supported on control-plane";
      }
      must "not (/ios:native/ios:policy/ios-policy:policy-map[ios-policy:name = current()]/ios-policy:class/ios-policy:action-list/ios-policy:action-type = 'shape')" {
        error-message "shape not supported on control-plane";
      }
      must "not (/ios:native/ios:policy/ios-policy:policy-map[ios-policy:name = current()]/ios-policy:class/ios-policy:action-list/ios-policy:action-type = 'random-detect')" {
        error-message "random-detect not supported on control-plane";
      }
    }
  }

  grouping config-service-policy-grouping {
    container service-policy {
      uses config-control-plane-service-policy-direction-grouping;
    }
  }

  grouping config-interface-service-policy-grouping-common {
    leaf history {
      description
        "Keep history of QoS metrics";
      type empty;
    }
    uses config-service-policy-direction-grouping {
      refine "input" {
        must 'not (/ios:native/ios:policy/policy-map[ios-policy:name = current()]/ios-policy:type)' {
          error-message "policy map should be of same type";
        }
      }
      refine "output" {
        must 'not (/ios:native/ios:policy/policy-map[ios-policy:name = current()]/ios-policy:type)' {
          error-message "policy map should be of same type";
        }
      }
    }
    container type {
      description
        "Configure CPL Service Policy";
      container access-control {
        description
          "access-control specific policy-map";
        uses config-service-policy-direction-grouping {
          refine "input" {
            must "(/ios:native/ios:policy/policy-map[ios-policy:name = current()]/ios-policy:type = 'access-control')" {
              error-message "policy map should be of same type";
            }
          }
          refine "output" {
            must "(/ios:native/ios:policy/policy-map[ios-policy:name = current()]/ios-policy:type = 'access-control')" {
              error-message "policy map should be of same type";
            }
          }
        }
      }
      container control {
        leaf subscriber {
          must "(/ios:native/ios:policy/policy-map[ios-policy:name = current()]/ios-policy:type = 'control' or .='BUILTIN_AUTOCONF_POLICY')" {
            error-message
              "policy map does not exist
               or currently active on an interface";
          }
          type string;
        }
      }
      container packet-service {
        description
          "Configure Packet-Service Service Policy";
        uses config-service-policy-direction-grouping {
          refine "input" {
            must "(/ios:native/ios:policy/policy-map[ios-policy:name = current()]/ios-policy:type = 'packet-service')" {
              error-message "policy map should be of same type";
            }
          }
          refine "output" {
            must "(/ios:native/ios:policy/policy-map[ios-policy:name = current()]/ios-policy:type = 'packet-service')" {
              error-message "policy map should be of same type";
            }
          }
        }
      }
      container performance-monitor {
        description
          "Configure media monitor service-policy type";
        uses config-service-policy-direction-grouping {
          refine "input" {
            must "(/ios:native/ios:policy/policy-map[ios-policy:name = current()]/ios-policy:type = 'performance-monitor')" {
              error-message "policy map should be of same type";
            }
          }
          refine "output" {
            must "(/ios:native/ios:policy/policy-map[ios-policy:name = current()]/ios-policy:type = 'performance-monitor')" {
              error-message "policy map should be of same type";
            }
          }
        }
      }
      container service-chain {
        description
          "Configure Service-chain Service Policy";
        container input {
          description
            "Assign policy-map to the input of an interface";
          leaf name {
            type string;
          }
        }
        container output {
          description
            "Assign policy-map to the output of an interface";
          leaf name {
            type string;
          }
        }
      }
      container epbr {
        description
          "Configure ePBR Service Policy";
        leaf input2 {
          description
            "Assign policy-map to the input of an interface";
          must "(/ios:native/ios:policy/policy-map[ios-policy:name = current()]/ios-policy:type = 'epbr')" {
            error-message "policy map should be of same type";
          }
          type leafref {
            path "/ios:native/ios:policy/policy-map/name";
          }
        }
        leaf output2 {
          description
            "Assign policy-map to the output of an interface";
          must "(/ios:native/ios:policy/policy-map[ios-policy:name = current()]/ios-policy:type = 'epbr')" {
            error-message "policy map should be of same type";
          }
          type leafref {
            path "/ios:native/ios:policy/policy-map/name";
          }
        }
        leaf input {
          description
            "Deprecated";
          status deprecated;
          type string;
        }
        leaf output {
          description
            "Deprecated";
          status deprecated;
          type string;
        }
      }
      container queueing {
        description
          "Queueing type policy-map";
        uses config-service-policy-direction-grouping {
          refine "input" {
            must "not (/ios:native/ios:policy/ios-policy:policy-map[ios-policy:name = current()]/ios-policy:type = 'queueing')" {
              error-message "Queueing policy is not supported in input direction";
            }
          }
          refine "output" {
            must "(/ios:native/ios:policy/policy-map[ios-policy:name = current()]/ios-policy:type = 'queueing')" {
              error-message "policy map should be of same type";
            }
          }
        }
      }
    }
  }

  grouping config-interface-service-policy-grouping {
    container service-policy {
      description
        "Apply service-policy to non-atm pvc interfaces";
      uses config-interface-service-policy-grouping-common;
    }
  }

  grouping config-interface-service-policy-grouping-atm {
    container service-policy {
      description
        "Apply service-policy to atm pvc interfaces";
      uses config-interface-service-policy-grouping-common;
    }
  }

  augment "/ios:native/ios:policy" {
    uses config-class-map-grouping;
    uses config-policy-map-grouping;
  }

  augment "/ios:native/ios:parameter-map/ios:type" {
    uses config-parameter-map-type-cws-tunnel-global-grouping;
  }

  augment "/ios:native/ios:parameter-map/ios:type" {
    uses config-parameter-map-type-subscriber-grouping;
  }

  augment "/ios:native/ios:parameter-map/ios:type" {
    uses config-parameter-map-type-inspect-grouping;
  }

  augment "/ios:native/ios:parameter-map/ios:type" {
    uses config-parameter-map-type-inspect-global-deprecate-grouping;
  }

  augment "/ios:native/ios:parameter-map/ios:type" {
    uses config-parameter-map-type-inspect-global-grouping;
  }

  augment "/ios:native/ios:parameter-map/ios:type" {
    uses config-parameter-map-type-inspect-vrf-grouping;
  }

  augment "/ios:native/ios:parameter-map/ios:type" {
    uses config-parameter-map-type-inspect-zone-grouping;
  }

  augment "/ios:native/ios:parameter-map/ios:type" {
    uses config-parameter-map-type-regex-grouping;
  }

  augment "/ios:native/ios:parameter-map/ios:type" {
    uses config-parameter-map-type-webauth-grouping;
  }

  augment "/ios:native/ios:parameter-map/ios:type" {
    uses config-parameter-map-type-webauth-global-grouping;
  }

  augment "/ios:native/ios:control-plane" {
    uses config-service-policy-grouping;
  }

  augment "/ios:native/ios:interface/ios:Ethernet" {
    uses config-interface-service-policy-grouping;
  }

  augment "/ios:native/ios:interface/ios:FastEthernet" {
    uses config-interface-service-policy-grouping;
  }

  augment "/ios:native/ios:interface/ios:ATM" {
    uses config-interface-service-policy-grouping;
  }

  augment "/ios:native/ios:interface/ios:ATM-subinterface/ios:ATM" {
    uses config-interface-service-policy-grouping;
  }

  augment "/ios:native/ios:interface/ios:ATM/ios-atm:pvc" {
    uses config-interface-service-policy-grouping-atm;
  }

  augment "/ios:native/ios:interface/ios:ATM-subinterface/ios:ATM/ios-atm:pvc" {
    uses config-interface-service-policy-grouping-atm;
  }

  augment "/ios:native/ios:interface/ios:GigabitEthernet" {
    uses config-interface-service-policy-grouping;
  }

  augment "/ios:native/ios:interface/ios:TenGigabitEthernet" {
    uses config-interface-service-policy-grouping;
  }

  augment "/ios:native/ios:interface/ios:FiveGigabitEthernet" {
    uses config-interface-service-policy-grouping;
  }

  augment "/ios:native/ios:interface/ios:AppGigabitEthernet" {
    uses config-interface-service-policy-grouping;
  }

  augment "/ios:native/ios:interface/ios:TwentyFiveGigE" {
    uses config-interface-service-policy-grouping;
  }

  augment "/ios:native/ios:interface/ios:FortyGigabitEthernet" {
    uses config-interface-service-policy-grouping;
  }

  augment "/ios:native/ios:interface/ios:TwoGigabitEthernet" {
    uses config-interface-service-policy-grouping;
  }

  augment "/ios:native/ios:interface/ios:HundredGigE" {
    uses config-interface-service-policy-grouping;
  }

  augment "/ios:native/ios:interface/ios:Multilink" {
    uses config-interface-service-policy-grouping;
  }

  augment "/ios:native/ios:interface/ios:Port-channel" {
    uses config-interface-service-policy-grouping;
  }

  augment "/ios:native/ios:interface/ios:Port-channel-subinterface/ios:Port-channel" {
    uses config-interface-service-policy-grouping;
  }

  augment "/ios:native/ios:interface/ios:Loopback" {
    uses config-interface-service-policy-grouping;
  }

  augment "/ios:native/ios:interface/ios:Tunnel" {
    uses config-interface-service-policy-grouping;
  }

  augment "/ios:native/ios:interface/ios:LISP" {
    uses config-interface-service-policy-grouping;
  }

  augment "/ios:native/ios:interface/ios:VirtualPortGroup" {
    uses config-interface-service-policy-grouping;
  }

  augment "/ios:native/ios:interface/ios:Virtual-Template" {
    uses config-interface-service-policy-grouping;
  }

  augment "/ios:native/ios:interface/ios:vasileft" {
    uses config-interface-service-policy-grouping;
  }

  augment "/ios:native/ios:interface/ios:vasiright" {
    uses config-interface-service-policy-grouping;
  }

  augment "/ios:native/ios:interface/ios:Vlan" {
    uses config-interface-service-policy-grouping;
  }

  augment "/ios:native/ios:interface/ios:BDI" {
    uses config-interface-service-policy-grouping;
  }

  augment "/ios:native/ios:interface/ios:Cellular" {
    uses config-interface-service-policy-grouping;
  }

  augment "/ios:native/ios:interface/ios:Dialer" {
    uses config-interface-service-policy-grouping;
  }

  augment "/ios:native/ios:interface/ios:Serial" {
    uses config-interface-service-policy-grouping;
  }

  augment "/ios:native/ios:interface/ios:BD-VIF" {
    uses config-interface-service-policy-grouping;
  }

  augment "/ios:native/ios:interface/ios:nve" {
    uses config-interface-service-policy-grouping;
  }
}
