module Cisco-IOS-XE-chassis-rpc {
  yang-version 1;
  namespace "http://cisco.com/ns/yang/Cisco-IOS-XE-chassis-rpc";
  prefix chassis-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Added facility to set chassis number and priority.
     Copyright (c) 2021 by Cisco Systems, Inc.
     All rights reserved.";

  revision 2022-03-01 {
    description
      "Initial revision";
    reference
      "1.0.0";
    cisco-semver:module-version "1.0.0";
  }

  grouping chassis-priority {
    description
      "Set priority of the specified chassis";
    leaf number {
      type uint8 {
        range "1..2";
      }
      mandatory true;
      description
        "Chassis number";
    }
    leaf priority {
      type uint8 {
        range "1..2";
      }
      mandatory true;
      description
        "Chassis priority";
    }
  }

  grouping chassis-number {
    description
      "Set number of the specified chassis";
    leaf number {
      type uint8 {
        range "1..2";
      }
      mandatory true;
      description
        "Current chassis number";
    }
    leaf renumber {
      type uint8 {
        range "1..2";
      }
      mandatory true;
      description
        "New chassis number";
    }
  }

  rpc set-chassis-priority {
    description
      "Set chassis priority RPC.
       Chassis with higher priority will become active module
       on next reboot of active and standby modules.";
    input {
      uses chassis-rpc:chassis-priority;
    }
  }

  rpc set-chassis-number {
    description
      "Set chassis number RPC.
       Changing the chassis number may result in a configuration change.
       The interface configuration associated with the old chassis number
       will remain as a provisioned configuration.
       New chassis number will be effective after next reboot.";
    input {
      uses chassis-rpc:chassis-number;
    }
  }
}
