module Cisco-IOS-XE-line-deviation {
  namespace "http://cisco.com/ns/yang/Cisco-IOS-XE-line-deviation";
  prefix ios-line-d;

  import Cisco-IOS-XE-native {
    prefix ios;
  }
  import cisco-semver {
    prefix cisco-semver;
  }

  organization
    "Cisco Systems, Inc.";
  description
    "Cisco XE Native Line, Deviation Yang Model.
     Copyright (c) 2020 by Cisco Systems, Inc.
     All rights reserved.";

  revision 2020-11-01 {
    description
      "Added line vty deviation";
    cisco-semver:module-version "1.0.1";
  }

  deviation "/ios:native/ios:line/ios:vty/ios:first" {
    deviate replace {
      type uint16 {
        range "0..530";
      }
    }
  }

  deviation "/ios:native/ios:line/ios:vty/ios:last" {
    deviate replace {
      type uint16 {
        range "1..530";
      }
    }
  }
}
