module Cisco-IOS-XE-nd-deviation {
  namespace "http://cisco.com/ns/yang/Cisco-IOS-XE-nd-deviation.yang";
  prefix ios-nd-deviation;

  import Cisco-IOS-XE-native {
    prefix ios;
  }
  import Cisco-IOS-XE-nd {
    prefix ios-nd;
  }
  import cisco-semver {
    prefix cisco-semver;
  }

  organization
    "Cisco Systems";
  description
    "Cisco XE Native Deviation YANG module for IOS
     Copyright (c) 2020 by Cisco Systems, Inc.
     All rights reserved.";

  revision 2020-06-09 {
    description
      "Added prefix deviation";
    cisco-semver:module-version "1.0.0";
  }

  deviation "/ios:native/ios:interface/ios:Virtual-Template/ios:ipv6/ios:nd/ios-nd:prefix" {
    deviate not-supported;
  }
}
