module Cisco-IOS-XE-cfm-oper {
  yang-version 1;
  namespace "http://cisco.com/ns/yang/Cisco-IOS-XE-cfm-oper";
  prefix cfm-stats-ios-xe-oper;

  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions for
     monitoring the Connectivity Fault Management protocol operation in a Network Element.
     Copyright (c) 2016-2017, 2019 by Cisco Systems, Inc.
     All rights reserved.";

  revision 2019-05-01 {
    description
      "Added semantic version";
    reference "2.2.0";
    cisco-semver:module-version "2.2.0";
  }
  revision 2018-10-29 {
    description
      "Cleaned up spelling errors in descriptions.";
    reference "2.1.0";
    cisco-semver:module-version "2.1.0";
  }
  revision 2017-06-06 {
    description
      "Last cleared time attribute type change";
    reference "2.0.0";
    cisco-semver:module-version "2.0.0";
  }
  revision 2017-02-07 {
    description
      "Initial revision";
    reference "1.0.0";
    cisco-semver:module-version "1.0.0";
  }

  typedef cfm-last-cleared-type {
    type enumeration {
      enum "never-cleared" {
        value 0;
        description
          "CFM stats have never been cleared";
      }
      enum "cleared-before" {
        value 1;
        description
          "CFM stats have been cleared once before";
      }
    }
    description
      "Describes whether CFM stats have been cleared";
  }

  grouping mep-key {
    description
      "This type describes a key in a list of MEPS";
    leaf domain-name {
      type string;
      description
        "The name of the Domain corresponding the the MEP";
    }
    leaf ma-name {
      type string;
      description
        "The name of the MA corresponding the the MEP";
    }
    leaf mpid {
      type uint32;
      description
        "ID of the MEP";
    }
  }

  grouping cfm-cleared-type {
    description
      "Type describes the last time when the counters were cleared";
    choice cleared-choice {
      description
        "The last time when the counters were cleared";
      case never-cleared {
        leaf never {
          type empty;
          description
            "Never been cleared";
        }
      }
      case cleared-before {
        leaf time {
          type yang:date-and-time;
          description
            "Date and time of the last time stats were cleared";
        }
      }
    }
  }

  grouping mep-params {
    description
      "MEP parameters";
    container last-cleared {
      description
        "Info on when the stats were last cleared";
      uses cfm-stats-ios-xe-oper:cfm-cleared-type;
    }
    leaf ccm-transmitted {
      type yang:counter64;
      description
        "The number of CCMs transmitted from the local MEP";
    }
    leaf ccm-seq-errors {
      type yang:counter64;
      description
        "The number of CCM sequence number errors detected";
    }
    leaf ltr-unexpected {
      type yang:counter64;
      description
        "The number of unexpected linktrace reply packets
         received at this MEP";
    }
    leaf lbr-transmitted {
      type yang:counter64;
      description
        "The number of loopback reply packets transmitted
         from the local MEP";
    }
    leaf lbr-seq-errors {
      type yang:counter64;
      description
        "The number of loopback reply packets received 
         with sequence number errors";
    }
    leaf lbr-received-ok {
      type yang:counter64;
      description
        "The number of valid loopback reply packets received";
    }
    leaf lbr-received-bad {
      type yang:counter64;
      description
        "The number of loopback reply packets received 
         with corrupted data pattern";
    }
  }

  container cfm-statistics {
    config false;
    description
      "Data nodes for CFM Statistics";
    container cfm-meps {
      description
        "CFM statistics";
      list cfm-mep {
        key "domain-name ma-name mpid";
        description
          "The list of MEP entries in the system";
        uses cfm-stats-ios-xe-oper:mep-key;
        uses cfm-stats-ios-xe-oper:mep-params;
      }
    }
  }
}
