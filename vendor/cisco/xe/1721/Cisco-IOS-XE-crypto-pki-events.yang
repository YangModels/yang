module Cisco-IOS-XE-crypto-pki-events {
  yang-version 1;
  namespace "http://cisco.com/ns/yang/Cisco-IOS-XE-crypto-pki-events";
  prefix crypto-pki-ios-xe-events;

  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for crypto PKI events data.
     Copyright (c) 2019 by Cisco Systems, Inc.
     All rights reserved.";

  revision 2019-11-01 {
    description
      "Initial revision";
    reference "1.0.0";
    cisco-semver:module-version "1.0.0";
  }

  grouping pki-certificate-expiry-update {
    description
      "Certificate expiry update";
    leaf trust-point {
      type string;
      description
        "Trustpoint name";
    }
    leaf expires-at {
      type yang:date-and-time;
      description
        "Absolute time of expiry";
    }
    leaf is-ca-cert {
      type boolean;
      description
        "Set to true if expiring certificate is a CA certificate";
    }
    leaf subject-name {
      type string;
      description
        "Subject name of expiring certificate";
    }
    leaf issuer-name {
      type string;
      description
        "Issuer name of expiring certificate";
    }
    leaf serial-number {
      type string;
      description
        "Serial number of the expiring certificate";
    }
  }

  notification pki-certificate-expiry {
    description
      "Certificate expiry update";
    uses crypto-pki-ios-xe-events:pki-certificate-expiry-update;
  }
  container crypto-pki-events {
    config false;
    description
      "crypto PKI events";
  }
}
