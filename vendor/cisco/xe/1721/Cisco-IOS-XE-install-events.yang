module Cisco-IOS-XE-install-events {
  yang-version 1;
  namespace "http://cisco.com/ns/yang/Cisco-IOS-XE-install-events";
  prefix install-ios-xe-events;

  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for install status notification for image install events.
     Copyright (c) 2019 by Cisco Systems, Inc.
     All rights reserved.";

  revision 2020-03-01 {
    description
      "Initial revision";
    reference "1.0.0";
    cisco-semver:module-version "1.0.0";
  }

  typedef installation-status {
    type enumeration {
      enum "download-start" {
        value 0;
        description
          "Download Start";
      }
      enum "download-complete" {
        value 1;
        description
          "Download Complete";
      }
      enum "verification-complete" {
        value 2;
        description
          "Verification Complete";
      }
      enum "upgrade-apply-complete" {
        value 3;
        description
          "Upgrade Apply Complete";
      }
      enum "sync-partition-start" {
        value 4;
        description
          "Sync Partition Start";
      }
      enum "sync-partition-complete" {
        value 5;
        description
          "Sync Partition Start";
      }
      enum "install-complete" {
        value 6;
        description
          "Install Complete";
      }
      enum "install-fail" {
        value 7;
        description
          "Install Fail";
      }
      enum "reboot" {
        value 8;
        description
          "Reboot";
      }
      enum "install-start" {
        value 9;
        description
          "Install Start";
      }
      enum "uninstall-complete" {
        value 10;
        description
          "Uninstall Complete";
      }
      enum "uninstall-fail" {
        value 11;
        description
          "Uninstall Fail";
      }
      enum "reset-complete" {
        value 12;
        description
          "Reset Complete";
      }
      enum "reset-fail" {
        value 13;
        description
          "Reset Fail";
      }
      enum "config-commit-confirm-complete" {
        value 14;
        description
          "Confirmation for configuration commit complete";
      }
      enum "config-commit-confirm-fail" {
        value 15;
        description
          "Confirmation for configuration commit fail";
      }
      enum "rollback-complete" {
        value 16;
        description
          "Rollback Complete";
      }
      enum "rollback-fail" {
        value 17;
        description
          "Rollback Fail";
      }
      enum "download-fail" {
        value 18;
        description
          "Download Fail";
      }
      enum "download-success" {
        value 19;
        description
          "Download Success";
      }
    }
    description
      "Installation Status";
  }

  typedef install-sub-state {
    type enumeration {
      enum "none" {
        value 0;
        description
          "None or not applicable";
      }
      enum "install-adding-pkg" {
        value 1;
        description
          "Install add package in progress";
      }
      enum "install-expanding-pkg" {
        value 2;
        description
          "Install expand package in progress";
      }
      enum "install-expand-pkg-done" {
        value 3;
        description
          "Install completes successful expand package";
      }
      enum "install-activating-pkg" {
        value 4;
        description
          "Activating package in progress";
      }
      enum "install-activate-dev-boot" {
        value 5;
        description
          "Activate or deactivate complete and starting device boot";
      }
      enum "install-error-msg" {
        value 6;
        description
          "Action failed error";
      }
      enum "install-oper-invoked" {
        value 7;
        description
          "Operation is invoked in install infra for the action";
      }
      enum "install-inprogress" {
        value 8;
        description
          "Operation is in progress";
      }
    }
    description
      "Install sub state provides the intermediate sub state status during
       install and activate operations. This helps to see the progress during 
       long waiting install action operation.";
  }

  typedef install-action {
    type enumeration {
      enum "install" {
        value 0;
        description
          "Install action type";
      }
      enum "activate" {
        value 1;
        description
          "Activate action type";
      }
      enum "install-commit" {
        value 2;
        description
          "Commit action type";
      }
      enum "rollback" {
        value 3;
        description
          "Rollback action type";
      }
      enum "deactivate" {
        value 4;
        description
          "Deactivate action type";
      }
      enum "remove" {
        value 5;
        description
          "Remove action type";
      }
      enum "auto-abort-timer" {
        value 6;
        description
          "Auto abort timer action type";
      }
      enum "abort" {
        value 7;
        description
          "Abort action type";
      }
    }
    description
      "Install action type";
  }

  grouping common-notification-header {
    description
      "Install notification header";
    leaf host-name {
      type string;
      description
        "Host name";
    }
  }

  grouping install-notification-fields {
    description
      "Install operation state";
    leaf status {
      type install-ios-xe-events:installation-status;
      description
        "Installation status";
    }
    leaf action-type {
      type install-ios-xe-events:install-action;
      description
        "Action type";
    }
    leaf sub-state {
      type install-ios-xe-events:install-sub-state;
      description
        "Intermediate sub state of install status";
    }
    leaf uuid {
      type string;
      description
        "Universally unique identifier 128-bit number UUID is received from action rpc";
    }
  }

  notification install-status {
    description
      "install status notification";
    uses install-ios-xe-events:common-notification-header;
    uses install-ios-xe-events:install-notification-fields;
  }
  container install-events {
    config false;
    description
      "install events";
  }
}
