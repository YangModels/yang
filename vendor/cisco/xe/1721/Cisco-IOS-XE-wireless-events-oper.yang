module Cisco-IOS-XE-wireless-events-oper {
  yang-version 1;
  namespace "http://cisco.com/ns/yang/Cisco-IOS-XE-wireless-events-oper";
  prefix wireless-event-oper;

  import Cisco-IOS-XE-wireless-mobility-types {
    prefix wireless-mobility-types;
  }
  import Cisco-IOS-XE-wsa-types {
    prefix wsa-types;
  }
  import ietf-inet-types {
    prefix inet;
  }
  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for wireless operations events generated from the Cisco Wireless
     controller. These models may produce high volume of data.
     Copyright (c) 2018-2019 by Cisco Systems, Inc.
     All rights reserved";

  revision 2020-03-01 {
    description
      "- Added beacon DS information in impersonation event.
       - Added new rogue WSA event.
       - Added client mac in rogue WSA event.";
    reference "1.4.0";
    cisco-semver:module-version "1.4.0";
  }
  revision 2019-05-01 {
    description
      "- Added rogue WSA events.
       - Added semantic version";
    reference "1.3.0";
    cisco-semver:module-version "1.3.0";
  }
  revision 2018-10-29 {
    description
      "Cleaned up spelling errors in descriptions.";
    reference "1.2.0";
    cisco-semver:module-version "1.2.0";
  }
  revision 2018-10-05 {
    description
      "Addition of fabric parameters to wsa client event.";
    reference "1.1.0";
    cisco-semver:module-version "1.1.0";
  }
  revision 2018-06-11 {
    description
      "Initial revision";
    reference "1.0.0";
    cisco-semver:module-version "1.0.0";
  }

  typedef rogue-event-type {
    type enumeration {
      enum "rogue-potential-honeypot-detected" {
        value 0;
        description
          "Potential honeypot detected event";
      }
      enum "rogue-potential-honeypot-cleared" {
        value 1;
        description
          "Potential honeypot cleared event";
      }
      enum "rogue-ap-impersonation-detected" {
        value 2;
        description
          "AP impersonation detected event";
      }
      enum "rogue-mfp-containment-detected" {
        value 3;
        description
          "PMF containment attempt detected event";
      }
    }
    description
      "Rogue event type";
  }

  grouping rogue-potential-honeypot {
    description
      "Potential honeypot event";
    leaf ssid {
      type string;
      description
        "SSID name";
    }
    leaf channel {
      type uint32;
      description
        "Channel number";
    }
  }

  grouping rogue-ap-impersonation {
    description
      "AP impersonation event";
    leaf impersonating-src-mac {
      type yang:mac-address;
      description
        "Impersonating source MAC address";
    }
    leaf is-beacon-ds {
      type boolean;
      description
        "Impersonation attack is also a beacon DS attack";
    }
    leaf channel {
      type uint8;
      description
        "Channel where beacon DS attack is performed";
    }
  }

  grouping rogue-pmf-info {
    description
      "Info about rogue with PMF enabled";
    leaf is-client {
      type boolean;
      description
        "Indicates whether rogue is client or AP.";
    }
    leaf pmf-client-mac {
      when "(../is-client = 'true')";
      type yang:mac-address;
      description
        "MAC address of PMF client";
    }
  }

  grouping ap-lrad {
    description
      "AP LRAD information";
    leaf name {
      type string;
      description
        "AP name";
    }
    leaf mac-address {
      type yang:mac-address;
      description
        "AP MAC address";
    }
    leaf slot-id {
      type uint32;
      description
        "Slot ID";
    }
  }

  grouping rogue-event {
    description
      "Rogue WSA event";
    container reporting-ap {
      description
        "AP reporting the event";
      uses wireless-event-oper:ap-lrad;
    }
    leaf rogue-mac-address {
      type yang:mac-address;
      description
        "MAC of the rogue AP";
    }
    choice event-type-choice {
      description
        "Type of event";
      case rogue-potential-honeypot-detected {
        container potential-honeypot-detected {
          description
            "Potential honeypot detected event";
          uses wireless-event-oper:rogue-potential-honeypot;
        }
      }
      case rogue-potential-honeypot-cleared {
        container potential-honeypot-cleared {
          description
            "Potential honeypot cleared event";
          uses wireless-event-oper:rogue-potential-honeypot;
        }
      }
      case rogue-ap-impersonation-detected {
        container ap-impersonation-detected {
          description
            "AP impersonation detected event";
          uses wireless-event-oper:rogue-ap-impersonation;
        }
      }
      case rogue-mfp-containment-detected {
        container pmf-info-detected {
          description
            "PMF containment info (MAC address of Rogue client with PMF enabled)";
          uses wireless-event-oper:rogue-pmf-info;
        }
      }
    }
  }

  grouping st-dhcp-ip-addr {
    description
      "List of DHCP server IP addresses";
    leaf server-ip {
      type inet:ip-address;
      description
        "Server IP address";
    }
  }

  grouping wsa-client-eventq-db-elem {
    description
      "Wireless client lifecycle events data model";
    leaf client-mac {
      type yang:mac-address;
      description
        "Wireless Client's MAC Address";
    }
    leaf wtp-mac {
      type yang:mac-address;
      description
        "AP mac client is associated to";
    }
    leaf state-transition-timestamp {
      type yang:date-and-time;
      description
        "Timestamp indicating when a client transitioned into the present lifecycle event. Time elapsed since 00:00:00 UTC, Thursday, 1 January 1970";
    }
    leaf audit-session-id {
      type string;
      description
        "Audit session id of the session";
    }
    leaf ssid {
      type string;
      description
        "SSID client is associated to";
    }
    leaf client-event {
      type wsa-types:wsa-client-events;
      description
        "Wireless client event type, indicating the phase a client is in its lifecycle";
    }
    leaf client-event-result {
      type wsa-types:wsa-client-event-result;
      description
        "Wireless client event status, indicating a failure or success in client lifecycle";
    }
    leaf vlan-id {
      type uint32;
      description
        "Wireless Client layer 2 vlan id";
    }
    leaf client-vnid {
      type uint32;
      description
        "Fabric client's Virtual Network ID. This information is valid only if client is a fabric client";
    }
    leaf client-sgt {
      type uint16;
      description
        "Fabric client's group tag. This information is valid only if client is a fabric client";
    }
    leaf rssi {
      type int8;
      description
        "Last updated Radio Signal Strength indicator, of a Wireless Client";
    }
    leaf snr {
      type uint8;
      description
        "Last updated Signal strength to noise ratio, of a Wireless Client";
    }
    leaf ms-ap-slot-id {
      type uint8;
      description
        "AP slot client is associated to";
    }
    leaf mm-client-role {
      type wireless-mobility-types:mm-client-role;
      description
        "Wireless Client's mobility role";
    }
    leaf ipv4-address {
      type inet:ipv4-address;
      description
        "Wireless Client's IPv4 address";
    }
    leaf-list ipv6 {
      type inet:ipv6-address;
      max-elements "8";
      ordered-by user;
      description
        "Wireless Client's IPv6 list of addresses";
    }
    list dhcp-server-ip-addr {
      description
        "DHCP server IP the Wireless client has communicated with";
      uses wireless-event-oper:st-dhcp-ip-addr;
    }
    leaf aaa-server {
      type inet:ip-address;
      description
        "AAA server IP the Wireless client has communicated with";
    }
    leaf is-fabric-client {
      type boolean;
      description
        "Indicates whether the client is a fabric client or not";
    }
  }

  grouping wsa-client-eventq-db-elem-3p {
    description
      "Wireless client lifecycle third-party events data model enumeration";
    leaf client-event-reason {
      type wsa-types:wsa-client-event-reason-3p;
      description
        "Wireless client event reason third-party, indicating what is happening with a client in its current lifecycle event";
    }
    leaf client-event-reason-addon {
      type wsa-types:wsa-client-event-reason-addon-3p;
      description
        "Wireless client event reason addon third-party, provides more information about the client_event_reason";
    }
  }

  notification wsa-client-event {
    description
      "Wireless client operational events. Provides an event for each significant activity in the Wireless clients life cycle. It may generate high volume of data, depending on scale";
    uses wireless-event-oper:wsa-client-eventq-db-elem;
    uses wireless-event-oper:wsa-client-eventq-db-elem-3p;
  }
  notification rogue-events {
    description
      "Rogue WSA events. Provides an event for each significant activity of
       rogue. It may generate high volume of data, depending on scale";
    uses wireless-event-oper:rogue-event;
  }
  container wireless-events {
    config false;
    description
      "root container of wireless client operational events";
  }
}
