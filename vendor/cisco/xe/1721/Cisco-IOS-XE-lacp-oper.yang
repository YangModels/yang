module Cisco-IOS-XE-lacp-oper {
  yang-version 1;
  namespace "http://cisco.com/ns/yang/Cisco-IOS-XE-lacp-oper";
  prefix lacp-ios-xe-oper;

  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of yang definitions
     for LACP operational data.
     Copyright (c) 2019 by Cisco Systems, Inc.
     All rights reserved.";

  revision 2020-03-01 {
    description
      "Initial revision";
    reference "1.0.0";
    cisco-semver:module-version "1.0.0";
  }
  revision 2020-03-01 {
    description
      " - Added the count of suspended links";
    reference "0.0.0";
    cisco-semver:module-version "0.0.0";
  }

  typedef etherchannel-layer {
    type enumeration {
      enum "l2-etherchannel" {
        value 0;
        description
          "Layer 2 Etherchannel";
      }
      enum "l3-etherchannel" {
        value 1;
        description
          "Layer 3 Etherchannel";
      }
    }
    description
      "Layer 2 or Layer 3 Etherchannel";
  }

  grouping lag-oper-data {
    description
      "LAG oper data";
    leaf channel-group {
      type uint32;
      description
        "Channel-group or port-channel number";
    }
    leaf total-no-of-links {
      type uint32;
      description
        "Total number of links configured as part of the channel-group";
    }
    leaf total-no-of-links-bundled {
      type uint32;
      description
        "Total number of links bundled";
    }
    leaf total-no-of-links-standby {
      type uint32;
      description
        "Total number of links in standby";
    }
    leaf total-no-of-links-down {
      type uint32;
      description
        "Total number of links down";
    }
    leaf port-channel-up {
      type boolean;
      description
        "Port channel status is UP";
    }
    leaf layer-type {
      type lacp-ios-xe-oper:etherchannel-layer;
      description
        "Layer 2 or Layer 3 Etherchannel";
    }
    leaf total-no-of-links-suspended {
      type uint32;
      description
        "Total number of suspended links";
    }
  }

  container lag-oper-data {
    config false;
    description
      "LACP operational data";
    list lag-info {
      key "channel-group";
      description
        "LAG operational information details";
      uses lacp-ios-xe-oper:lag-oper-data;
    }
  }
}
