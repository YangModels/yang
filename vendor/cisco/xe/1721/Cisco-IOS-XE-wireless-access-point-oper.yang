module Cisco-IOS-XE-wireless-access-point-oper {
  yang-version 1;
  namespace "http://cisco.com/ns/yang/Cisco-IOS-XE-wireless-access-point-oper";
  prefix wireless-access-point-oper;

  import Cisco-IOS-XE-wireless-ap-types {
    prefix ap-types;
  }
  import Cisco-IOS-XE-wireless-enum-types {
    prefix wireless-enum-types;
  }
  import Cisco-IOS-XE-wireless-types {
    prefix wireless-types;
  }
  import ietf-inet-types {
    prefix inet;
  }
  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for access point operational data.
     Copyright (c) 2016-2020 by Cisco Systems, Inc.
     All rights reserved.";

  revision 2020-03-01 {
    description
      "- Added download image size percentage and ETA
       - Added window size for CAPWAP multiwindow
       - Added image name for CAPWAP WTP data
       - Added support for RADIUS counters
       - Added support for persistent SSID broadcast
       - Added support for AP proxy
       - Added IPv6 static address details for APs
       - Added two new flags for AP capability ap-min-two-antennas-to-be-enabled and ap-antennas-5-6-7-not-configurable";
    reference "6.4.0";
    cisco-semver:module-version "6.4.0";
  }
  revision 2019-11-01 {
    description
      "- Added AP AWIPS Capability
       - Added AP power type
       - Added UDP-Lite operational information
       - Added multi-lan-port-capable flag under AP capability
       - Added AP LAN operational information
       - Added support for IOX application hosting on APs
       - Added support for Auxiliary Client Interface on APs
       - Added radio enable time for AP
       - Added 802.11ax BSS color configuration and capability
       - Added strict-wired-uplink-capable flag under AP capability
       - Added dual radio mode and FRA capable parameters
       - Added AP LED flash state and duration timer
       - Added highest throughput supported by radio";
    reference "6.3.0";
    cisco-semver:module-version "6.3.0";
  }
  revision 2019-08-26 {
    description
      "- Added radio enable time for AP
       - Added flag definition for MCS rates
       - Added antenna-band-mode-capable flag under AP capability
       - Added SIA parameters for AP radio";
    reference "6.2.0";
    cisco-semver:module-version "6.2.0";
  }
  revision 2019-06-18 {
    description
      "- Added NTP server information to be used by AP
       - Added Various statistics counter for SSID
       - Added ap-mac-ssid-info to keep the list of clients MAC address for each SSID
       - Updated description for leaf node ht-enable
       - Added rrm-channel-change-reason
       - Added monitor mode optimization information
       - Added semantic version
       - Added slot-antenna-type
       - Added AP filter name";
    reference "6.1.0";
    cisco-semver:module-version "6.1.0";
  }
  revision 2019-02-24 {
    description
      "- Renamed QoS enum type
       - Removal of unused leaves from QoS enum
       - Added new enum for cac state type
       - Removal of unused leaves from qos client data
       - Added description of AP capabilities 
       - Added new leaf AP stationing type to identify AP type 
         indoor or outdoor
       - Added secondary 80 channel of 80+80 channel width
       - Added me-internal-ap
       - Removal of unused leaves
       - Added fallback wait status in AP upgrade status
       - Added fallback type in AP upgrade report
       - Added new enum for AP upgrade fallback type
       - Added current-band-id for radio-oper-stats
       - Cleaned up spelling errors in descriptions
       - Removed CAC counters from Radio statistics information
       - Added rrm-channel-change-reason
       - Removal of unused leaves
       - Added upgrade failure type in AP upgrade report
       - Added new enum for AP upgrade failure reason
       - Added lists for AP software related information
       - Updated description for leaf nodes leg-tx-bf-enabled, current-band-id and he-stbc-mode
       - Added leaf node current-active-band
       - Removed redundant leaves under capwap-data
       - Categorized attributes into AP static and dynamic information,
         clubbed the various version of the AP together and changed few
         of the leaf descriptions to make them more appropriate/precise
       - Added wtp-serial-num for capwap-data
       - Added additional AirTime Fairness Statistics
       - Added sensor-mode-capable and only-local-mode-capable flags under AP capability
       - Removal of less important leaf nodes from AP and Radio operational data
       - Removed radio-uptime from radio-oper-stats";
    reference "6.0.0";
    cisco-semver:module-version "6.0.0";
  }
  revision 2018-06-28 {
    description
      "- Add AP name for which bandwidth is allocated, number of active TSPEC and SIP calls
       - Remove voice client from qos client data
       - Add SIP active and rejected call counters
       - Add SIP call-control metrics";
    reference "5.0.0";
    cisco-semver:module-version "5.0.0";
  }
  revision 2018-04-02 {
    description
      "Replaced an existing attribute lookup_neigh_mac with 
       neighbor_ap_name";
    reference "4.0.0";
    cisco-semver:module-version "4.0.0";
  }
  revision 2018-03-22 {
    description
      "Enum value change";
    reference "3.0.0";
    cisco-semver:module-version "3.0.0";
  }
  revision 2018-01-24 {
    description
      "The first generally available version";
    reference "2.0.0";
    cisco-semver:module-version "2.0.0";
  }
  revision 2017-05-05 {
    description
      "Initial revision";
    reference "1.0.0";
    cisco-semver:module-version "1.0.0";
  }

  typedef enum-ap-state {
    type enumeration {
      enum "ap-down" {
        value 1;
        description
          "AP state is Down";
      }
      enum "ap-up" {
        value 2;
        description
          "AP state is Up";
      }
      enum "unregistered" {
        value 3;
        description
          "AP state is un-registered";
      }
      enum "registered" {
        value 4;
        description
          "AP state is Registered";
      }
      enum "downloading" {
        value 5;
        description
          "AP state is Image Download";
      }
    }
    description
      "Operational state of AP";
  }

  typedef enum-ap-stationing-type {
    type enumeration {
      enum "indoor-ap" {
        value 0;
        description
          "AP stationing type INDOOR";
      }
      enum "outdoor-ap" {
        value 1;
        description
          "AP stationing type OUTDOOR";
      }
    }
    description
      "AP stationing type, indoor or outdoor";
  }

  typedef enm-cert-type {
    type enumeration {
      enum "wireless-cert-mic" {
        value 1;
        description
          "Cert type: Manufacturer Installed Certificate";
      }
      enum "wireless-cert-ssc" {
        value 2;
        description
          "Cert type: Self Signed Certificate";
      }
      enum "wireless-cert-lsc" {
        value 3;
        description
          "Cert type: Locally Significant Certificate";
      }
    }
    description
      "enumeration to define certificate types with which
       AP can join";
  }

  typedef enum-radio-admin-state {
    type enumeration {
      enum "enabled" {
        value 1;
        description
          "Radio Admin State is Enabled";
      }
      enum "disabled" {
        value 2;
        description
          "Radio Admin State is Disabled";
      }
    }
    description
      "Radio Admin state";
  }

  typedef enum-radio-oper-state {
    type enumeration {
      enum "radio-up" {
        value 0;
        description
          "Radio Operational State Enabled";
      }
      enum "radio-down" {
        value 1;
        description
          "Radio Operational State Disabled";
      }
    }
    description
      "Radio Operational state";
  }

  typedef ewlc-rlan-poe-state {
    type enumeration {
      enum "poe-disabled" {
        value 0;
        description
          "PoE is disabled";
      }
      enum "poe-enabled" {
        value 1;
        description
          "PoE is enabled";
      }
      enum "poe-not-applicable" {
        value 2;
        description
          "PoE is not applicable on AP LAN port";
      }
    }
    description
      "PoE state of AP LAN port";
  }

  typedef enm-apphost-state {
    type enumeration {
      enum "apphost-disabled" {
        value 0;
        description
          "Application hosting is disabled";
      }
      enum "apphost-enabled" {
        value 1;
        description
          "Application hosting is enabled";
      }
      enum "apphost-libvrt-failure" {
        value 2;
        description
          "Application hosting failure because of Virtualization Library";
      }
      enum "apphost-caf-failure" {
        value 3;
        description
          "Application hosting failure because of Cisco Application hosting Framework";
      }
    }
    description
      "enumeration to define the possible states of the application hosting of the AP";
  }

  typedef flag-ap-capability {
    type bits {
      bit bridge-mode-capable {
        position 0;
        description
          "Ap capability for bridge mode";
      }
      bit mesh-daisy-chaining-capable {
        position 1;
        description
          "AP capability for daisy chaining mode";
      }
      bit cap-three-spatial-streams-capable {
        position 2;
        description
          "AP capability for spatial streams mode";
      }
      bit antenna-selection-restricted-capable {
        position 3;
        description
          "AP capability for antenna selection mode";
      }
      bit avc-cnf-capable {
        position 4;
        description
          "AP capability for avc fnf mode";
      }
      bit rxsop-threshold-capable {
        position 5;
        description
          "AP capability for rxsop threshold mode";
      }
      bit fabric-capability {
        position 6;
        description
          "AP capability for fabric mode";
      }
      bit rogue-rldp-capable {
        position 7;
        description
          "AP capability for rogue rldp mode";
      }
      bit barbados-external-antenna-sku-capable {
        position 8;
        description
          "Barbados AP capability for external antenna mode";
      }
      bit barbados-internal-antenna-sku-capable {
        position 9;
        description
          "Barbados AP capability for internal antenna mode";
      }
      bit barbados-location-antenna-sku-capable {
        position 10;
        description
          "Barbados AP capability for location antenna mode";
      }
      bit remote-lan-capable {
        position 11;
        description
          "AP capability for remote lan mode";
      }
      bit dot11ac-160mhz-channel-width-capable {
        position 12;
        description
          "AP capability for dot11 channel width mode";
      }
      bit location-optimized-monitor-mode-capable {
        position 13;
        description
          "AP capability for optimized monitor  mode";
      }
      bit avc-fnf-fabric-capable {
        position 14;
        description
          "AP capability for avc fabric mode";
      }
      bit telent-capable {
        position 15;
        description
          "AP capability for telnet mode";
      }
      bit ap-packet-capture-capable {
        position 16;
        description
          "AP capability for packet capture mode";
      }
      bit ap-cts-capable {
        position 17;
        description
          "AP capability for cts mode";
      }
      bit ap-qca-spectrum-intelligence-capable {
        position 18;
        description
          "AP capability for spectrum intelligence mode";
      }
      bit fips-capable {
        position 19;
        description
          "AP capability for fips mode";
      }
      bit is-dot1x-port-auth-capable {
        position 20;
        description
          "AP capability for dot1x port authentication mode";
      }
      bit ap-tracing-capable {
        position 21;
        description
          "AP capability for tracing enable from Controller";
      }
      bit ap-wpa3-capable {
        position 22;
        description
          "AP capability for WPA3 authentication";
      }
      bit is-lag-capable {
        position 23;
        description
          "AP capability for lag mode";
      }
      bit ap-eta-capable {
        position 24;
        description
          "AP capability for Encrypted Traffic Analytics";
      }
      bit is-li-capable {
        position 25;
        description
          "AP capability for LI";
      }
      bit office-extend-capable {
        position 26;
        description
          "AP capability for office extend mode";
      }
      bit eth2-rlan-capable {
        position 27;
        description
          "AP capability for Ethernet2 as RLAN port, when LAG is disabled";
      }
      bit nbn-capable {
        position 28;
        description
          "AP capability for NBN features";
      }
      bit ap-mewlc-capable {
        position 29;
        description
          "AP capability for AP MEWLC features";
      }
      bit sniffer-mode-capable {
        position 30;
        description
          "AP capability for sniffer mode";
      }
      bit icap-full-packet-trace-capable {
        position 31;
        description
          "AP capability for icap full packet trace";
      }
      bit icap-partial-capable {
        position 32;
        description
          "AP capability for icap partial packet trace";
      }
      bit icap-anomaly-detection-capable {
        position 33;
        description
          "AP capability for icap anomaly detection";
      }
      bit icp-statistics-capable {
        position 34;
        description
          "AP capability for icap statistics";
      }
      bit icap-rf-spectrum-capable {
        position 35;
        description
          "AP capability for icap RF spectrum";
      }
      bit icap-feature-capable {
        position 36;
        description
          "AP capability for icap features";
      }
      bit sensor-mode-capable {
        position 37;
        description
          "AP capability for sensor mode";
      }
      bit only-local-mode-capable {
        position 38;
        description
          "AP capability for only local mode";
      }
      bit antenna-band-mode-capable {
        position 39;
        description
          "AP capability for antenna band mode";
      }
      bit sia-capable {
        position 40;
        description
          "AP capability for Self Identifying Antenna";
      }
      bit ap-awips-capable {
        position 41;
        description
          "AP capability for AWIPS";
      }
      bit multi-lan-port-poe-capable {
        position 42;
        description
          "AP capability for multiple PoE ports support";
      }
      bit iox-hardware-capable {
        position 43;
        description
          "AP hardware capability for IOX feature";
      }
      bit auxiliary-client-interface-capable {
        position 44;
        description
          "AP Auxiliary Client Interface capability";
      }
      bit strict-wired-uplink-capable {
        position 45;
        description
          "AP capability for strict wired uplink";
      }
      bit ap-min-two-antennas-to-be-enabled {
        position 46;
        description
          "AP capability for minimum of two Antennas to be enabled";
      }
      bit ap-antennas-5-6-7-not-configurable {
        position 47;
        description
          "AP capability for Antenna ID 5, 6, 7 not configurable";
      }
      bit ap-indoor-mode-capable {
        position 48;
        description
          "AP capability for Indoor Mode";
      }
    }
    description
      "AP Capabilities";
  }

  typedef flag-dot11n-mcs-rates {
    type bits {
      bit dot11n-mcs-rate-zero {
        position 0;
        description
          "802.11n MCS Rate Index 0";
      }
      bit dot11n-mcs-rate-one {
        position 1;
        description
          "802.11n MCS Rate Index 1";
      }
      bit dot11n-mcs-rate-two {
        position 2;
        description
          "802.11n MCS Rate Index 2";
      }
      bit dot11n-mcs-rate-three {
        position 3;
        description
          "802.11n MCS Rate Index 3";
      }
      bit dot11n-mcs-rate-four {
        position 4;
        description
          "802.11n MCS Rate Index 4";
      }
      bit dot11n-mcs-rate-five {
        position 5;
        description
          "802.11n MCS Rate Index 5";
      }
      bit dot11n-mcs-rate-six {
        position 6;
        description
          "802.11n MCS Rate Index 6";
      }
      bit dot11n-mcs-rate-seven {
        position 7;
        description
          "802.11n MCS Rate Index 7";
      }
      bit dot11n-mcs-rate-eight {
        position 8;
        description
          "802.11n MCS Rate Index 8";
      }
      bit dot11n-mcs-rate-nine {
        position 9;
        description
          "802.11n MCS Rate Index 9";
      }
      bit dot11n-mcs-rate-ten {
        position 10;
        description
          "802.11n MCS Rate Index 10";
      }
      bit dot11n-mcs-rate-eleven {
        position 11;
        description
          "802.11n MCS Rate Index 11";
      }
      bit dot11n-mcs-rate-twelve {
        position 12;
        description
          "802.11n MCS Rate Index 12";
      }
      bit dot11n-mcs-rate-thirteen {
        position 13;
        description
          "802.11n MCS Rate Index 13";
      }
      bit dot11n-mcs-rate-fourteen {
        position 14;
        description
          "802.11n MCS Rate Index 14";
      }
      bit dot11n-mcs-rate-fifteen {
        position 15;
        description
          "802.11n MCS Rate Index 15";
      }
      bit dot11n-mcs-rate-sixteen {
        position 16;
        description
          "802.11n MCS Rate Index 16";
      }
      bit dot11n-mcs-rate-seventeen {
        position 17;
        description
          "802.11n MCS Rate Index 17";
      }
      bit dot11n-mcs-rate-eighteen {
        position 18;
        description
          "802.11n MCS Rate Index 18";
      }
      bit dot11n-mcs-rate-nineteen {
        position 19;
        description
          "802.11n MCS Rate Index 19";
      }
      bit dot11n-mcs-rate-twenty {
        position 20;
        description
          "802.11n MCS Rate Index 20";
      }
      bit dot11n-mcs-rate-twenty-one {
        position 21;
        description
          "802.11n MCS Rate Index 21";
      }
      bit dot11n-mcs-rate-twenty-two {
        position 22;
        description
          "802.11n MCS Rate Index 22";
      }
      bit dot11n-mcs-rate-twenty-three {
        position 23;
        description
          "802.11n MCS Rate Index 23";
      }
      bit dot11n-mcs-rate-twenty-four {
        position 24;
        description
          "802.11n MCS Rate Index 24";
      }
      bit dot11n-mcs-rate-twenty-five {
        position 25;
        description
          "802.11n MCS Rate Index 25";
      }
      bit dot11n-mcs-rate-twenty-six {
        position 26;
        description
          "802.11n MCS Rate Index 26";
      }
      bit dot11n-mcs-rate-twenty-seven {
        position 27;
        description
          "802.11n MCS Rate Index 27";
      }
      bit dot11n-mcs-rate-twenty-eight {
        position 28;
        description
          "802.11n MCS Rate Index 28";
      }
      bit dot11n-mcs-rate-twenty-nine {
        position 29;
        description
          "802.11n MCS Rate Index 29";
      }
      bit dot11n-mcs-rate-thirty {
        position 30;
        description
          "802.11n MCS Rate Index 30";
      }
      bit dot11n-mcs-rate-thirty-one {
        position 31;
        description
          "802.11n MCS Rate Index 31";
      }
    }
    description
      "802.11n MCS Rates";
  }

  grouping reboot-statistics {
    description
      "AP reboot Statistics";
    leaf reboot-reason {
      type wireless-types:spam-ap-reboot-reason;
      description
        "Reason for AP last reboot";
    }
  }

  grouping wtp-board-data {
    description
      "AP Board details";
    leaf wtp-serial-num {
      type string;
      description
        "AP serial number";
    }
    leaf wtp-enet-mac {
      type yang:mac-address;
      description
        "AP Ethernet MAC address";
    }
  }

  grouping st-ap-ip-data {
    description
      "IP address of AP";
    leaf ap-prefix {
      type uint32;
      description
        "Prefix length of the IPv6 Address of the AP.";
    }
    leaf mtu {
      type uint32;
      description
        "Maximum transmission unit size for the client";
    }
    leaf is-static-ap-ipaddr {
      type boolean;
      description
        "Value of True implies 
         AP is using static IP Address, value of False
         implies AP is using DHCP IP";
    }
    leaf domain-name {
      type string;
      description
        "AP domain name";
    }
    leaf ap-ip-addr {
      type inet:ipv4-address;
      description
        "Static IPv4 Address configuration for the AP.";
    }
    leaf ap-ipv6-addr {
      type inet:ipv6-address;
      description
        "Static IPv6 Address configuration for the AP.";
    }
    leaf ap-ip-netmask {
      type inet:ipv4-address;
      description
        "Netmask of the IPv4 address of the AP.";
    }
    leaf ap-ip-gateway {
      type inet:ipv4-address;
      description
        "Gateway for the IPv4 Address of the AP.";
    }
    leaf ap-ipv6-gateway {
      type inet:ipv6-address;
      description
        "Gateway for the IPv6 Address of the AP.";
    }
    leaf ap-name-server {
      type inet:ip-address;
      description
        "AP name server IP address";
    }
    leaf ap-name-server-type {
      type wireless-types:enm-ip-address-type;
      description
        "Type of the IP address of the name server";
    }
    leaf ap-ipv6-method {
      type wireless-types:enum-ap-ipv6-addr-method;
      description
        "Method used by AP to join over IPv6.";
    }
    leaf is-v6-static-addr {
      type empty;
      description
        "Static IPv6 address configured on the AP";
    }
  }

  grouping ap-link-audit-data {
    description
      "Link audit data";
    leaf linkaudit-delay-time {
      type uint32;
      description
        "Link latency recorded for this AP";
    }
    leaf linkaudit-max-time {
      type uint32;
      description
        "Maximum link latency recorded for the AP";
    }
    leaf linkaudit-min-time {
      type uint32;
      description
        "Minimum link latency recorded for the AP";
    }
  }

  grouping ap-tcp-mss-data {
    description
      "Configured TCP MSS value for client";
    leaf tcp-adjust-mss-size {
      type uint16;
      description
        "TCP Maximum Segment Size for the AP.
         Permissible value are between 536 and 1363.
         This will also enable the TCP MSS flag for this AP
         Value of 0 will disable the TCP MSS flag for this AP";
    }
  }

  grouping ap-universal-provision-data {
    description
      "Universal AP Data";
    leaf is-universal {
      type boolean;
      description
        "Value of True implies AP is Universal AP.
         A value of False implies AP is not universal AP";
    }
    leaf universal-prime-status {
      type string;
      description
        "Priming method of the Universal AP";
    }
  }

  grouping ap-pow-data {
    description
      "AP power related information";
    leaf power-injector-sel {
      type wireless-enum-types:power-injector-selection;
      description
        "Specify power level";
    }
    leaf power-injector-macaddr {
      type yang:mac-address;
      description
        "Mac address of the switch port
         that has a power injector and is valid only when
         'power_injector_sel' is in 'installed' mode.
         If set to 00:00:00:00:00:00, AP will detect the MAC address
         of the current switch port that has a power injector";
    }
    leaf pre-std-switch-enabled {
      type boolean;
      description
        "Pre-standard state of the AP, enabled or disabled.
         Value of 'true' denotes Pre-Standard state is Enabled,
         Value of 'false' denotes Pre-Standard state is Disabled";
    }
    leaf power-injector-enabled {
      type boolean;
      description
        "Power injector state, Enabled or Disabled.
         Value of 'true' denotes power injector state is Enabled,
         Value of 'false' denotes power injector state is Disabled";
    }
    leaf power-type {
      type wireless-enum-types:power-type;
      description
        "AP power type";
    }
    leaf power-mode {
      type wireless-enum-types:power-mode-type;
      description
        "This notification is generated whenever an AP detects low
         power from ethernet";
    }
  }

  grouping ap-sys-stats-data {
    description
      "AP system stats for CPU and memory usage";
    leaf cpu-usage {
      type uint8;
      description
        "AP CPU usage";
    }
    leaf memory-usage {
      type uint8;
      description
        "AP memory usage";
    }
  }

  grouping ap-prime-data {
    description
      "AP priming related information";
    leaf primary-controller-name {
      type string;
      description
        "Name of the primary controller configured for the AP";
    }
    leaf secondary-controller-name {
      type string;
      description
        "Name of the secondary controller configured for the AP";
    }
    leaf primary-controller-ip-addr {
      type inet:ip-address;
      description
        "IP address of the primary controller configured
         for the AP";
    }
    leaf secondary-controller-ip-addr {
      type inet:ip-address;
      description
        "IP address of the secondary controller configured
         for AP";
    }
    leaf tertiary-controller-name {
      type string;
      description
        "Name of the tertiary controller configured for the
         AP";
    }
    leaf tertiary-controller-ip-addr {
      type inet:ip-address;
      description
        "IP address of the tertiary controller configured
         for AP";
    }
    leaf ap-fallback-ip {
      type inet:ip-address;
      description
        "The fallback address: AP will join over this address when it can't join over static-ip.";
    }
    leaf fallback-enabled {
      type boolean;
      description
        "Value of true implies AP fallback is enabled";
    }
  }

  grouping ap-mgmt-data {
    description
      "AP management information";
    leaf is-telnet-enabled {
      type boolean;
      description
        "Value of 'true' indicates telnet session
         can be established to the AP";
    }
    leaf is-ssh-enabled {
      type boolean;
      description
        "Value of 'true' indicates SSH session
         can be established to the AP";
    }
  }

  grouping ap-aux-client-interface-data {
    description
      "Auxiliary Client Interface data";
    leaf is-enabled {
      type boolean;
      description
        "This indicates whether Auxiliary Client Interface is
         enabled on the Access Point";
    }
    leaf vlan-id {
      when "(../is-enabled = 'true')";
      type uint16;
      description
        "VLAN ID of the Auxiliary Client Interface.";
    }
    leaf ip-addr {
      when "(../is-enabled = 'true')";
      type inet:ip-address;
      description
        "IP address of the Auxiliary Client Interface.";
    }
    leaf ip-netmask {
      when "(../is-enabled = 'true')";
      type inet:ipv4-address;
      description
        "Netmask of the Auxiliary Client Interface.";
    }
  }

  grouping ap-ntp-server-info-cfg-data {
    description
      "NTP server information on Access Point configuration";
    leaf ntp-server-address {
      type inet:ip-address;
      description
        "Specifies the NTP server address to be used by the Access Point";
    }
  }

  grouping ap-persistent-ssid-data {
    description
      "Persistent SSID broadcast operation information";
    leaf is-persistent-ssid-enabled {
      type boolean;
      description
        "True if persistent SSID broadcast is enabled on AP";
    }
  }

  grouping ap-retransmit-data {
    description
      "AP retransmission related parameters";
    leaf count {
      type uint8;
      description
        "Total number of times config data is retransmitted";
    }
  }

  grouping st-ap-security-oper-data {
    description
      "LSC provisioning details";
    leaf cert-type {
      type wireless-access-point-oper:enm-cert-type;
      description
        "Enum values denoting AP Certificate Type.
         1 : manufactureinstalled : Manufacture Installed Certificate type (MIC).
         2 : selfsigned : Self Signed Certificate type (SSC).
         3 : localsignificance : Local Significance";
    }
  }

  grouping st-ap-oper-data {
    description
      "AP operational data";
    leaf wtp-mac {
      type yang:mac-address;
      description
        "MAC Address of the AP Radio";
    }
    leaf ap-antenna-band-mode {
      type wireless-enum-types:ant-band-mode;
      description
        "Antenna band mode. For 
         AP, in which this variable is not relevant,
         value of 'Not Applicable' will be returned.
         In the dual band mode, only two dual band antennas are used, 
         connected to ports 1 and 2. In this case, both bands share these antennas.";
    }
    leaf link-encryption-enabled {
      type boolean;
      description
        "True if  encryption between
         controller and AP is enabled. Encryption
         can only be enabled if ESM card in controller is plugged in. 
         Otherwise false.";
    }
    container ap-ip-data {
      description
        "AP IP address configuration";
      uses wireless-access-point-oper:st-ap-ip-data;
    }
    container ap-prime-info {
      description
        "Controller configuration for the AP";
      uses wireless-access-point-oper:ap-prime-data;
    }
    container ap-mgmt {
      description
        "AP management data";
      uses wireless-access-point-oper:ap-mgmt-data;
    }
    container ap-pow {
      description
        "AP power related data";
      uses wireless-access-point-oper:ap-pow-data;
    }
    container ap-sys-stats {
      description
        "AP system statistics";
      uses wireless-access-point-oper:ap-sys-stats-data;
    }
    container ipv4-tcp-mss {
      description
        "Configured IPv4 TCP MSS value for client";
      uses wireless-access-point-oper:ap-tcp-mss-data;
    }
    container ipv6-tcp-mss {
      description
        "Configured IPv6 TCP MSS value for client";
      uses wireless-access-point-oper:ap-tcp-mss-data;
    }
    container link-audit {
      description
        "Link audit data";
      uses wireless-access-point-oper:ap-link-audit-data;
    }
    container retransmit {
      description
        "AP retransmission parameters";
      uses wireless-access-point-oper:ap-retransmit-data;
    }
    container persistent-ssid {
      description
        "Persistent SSID broadcast operation information";
      uses wireless-access-point-oper:ap-persistent-ssid-data;
    }
    container ap-ntp-server-info-cfg {
      description
        "NTP server information to be used by AP";
      uses wireless-access-point-oper:ap-ntp-server-info-cfg-data;
    }
    leaf ap-udplite-info {
      type wireless-enum-types:ipv6-capwap-checksum-type;
      description
        "UDP-Lite operational information. enum values denoting
          0 UDP-Lite checksum not yet configured
          1 UDP-Lite checksum for IPv6 CAPWAP data packets
          2 checksum for IPv6 CAPWAP data packets";
    }
    container accounting {
      description
        "Accounting info to be sent to radius server";
      uses ap-types:st-accounting;
    }
    container aux-client-interface-data {
      description
        "Auxiliary Client Interface data";
      uses wireless-access-point-oper:ap-aux-client-interface-data;
    }
  }

  grouping wtp-descriptor-data {
    description
      "Structure stores the details about the WTP";
    leaf encryption-capabilities {
      type boolean;
      description
        "Encryption capabilities of the AP";
    }
  }

  grouping board-data-opt {
    description
      "AP Board details";
    leaf join-priority {
      type uint8;
      description
        "AP join priority";
    }
  }

  grouping wtp-policy-tag-info {
    description
      "AP tag relation information";
    leaf policy-tag-name {
      type string;
      description
        "policy tag associated with AP";
    }
  }

  grouping wtp-site-tag-info {
    description
      "Site tag associated with the AP";
    leaf site-tag-name {
      type string;
      description
        "AP site tag name";
    }
  }

  grouping wtp-rf-tag-info {
    description
      "RF tag information for the AP";
    leaf rf-tag-name {
      type string;
      description
        "RF tag name associated with the AP";
    }
  }

  grouping ap-filter-info {
    description
      "AP filter information";
    leaf filter-name {
      type string;
      description
        "AP filter name";
    }
  }

  grouping wtp-tags-data {
    description
      "WTP tag associations";
    container policy-tag-info {
      description
        "Policy tag information for the AP";
      uses wireless-access-point-oper:wtp-policy-tag-info;
    }
    container site-tag {
      description
        "Site tag information for the AP";
      uses wireless-access-point-oper:wtp-site-tag-info;
    }
    container rf-tag {
      description
        "RF tag information for the AP";
      uses wireless-access-point-oper:wtp-rf-tag-info;
    }
    container filter-info {
      description
        "AP filter information";
      uses wireless-access-point-oper:ap-filter-info;
    }
  }

  grouping wtp-xm-info {
    description
      "WTP extension module information";
    leaf is-module-present {
      type boolean;
      description
        "True if an external module is present or not";
    }
  }

  grouping st-sliding-window {
    description
      "CAPWAP multiwindow configuration";
    leaf multi-window-support {
      type boolean;
      description
        "True if CAPWAP multiwindow is enabled on AP";
    }
    leaf window-size {
      type uint16;
      description
        "Window size for CAPWAP multiwindow transport";
    }
  }

  grouping st-external-module-data {
    description
      "External module info used by AP";
    container xm-data {
      description
        "External module data";
      uses wireless-access-point-oper:wtp-xm-info;
    }
  }

  grouping st-ap-location {
    description
      "AP location information";
    leaf floor {
      type uint32;
      description
        "Floor of the AP";
    }
    leaf location {
      type string;
      description
        "User assigned location of the AP";
    }
  }

  grouping st-ap-services {
    description
      "Services used by AP";
    leaf monitor-mode-opt-type {
      type wireless-enum-types:lomm-mode-type;
      description
        "Monitor mode optimization type on the AP
         all      - All optimization is enabled
         tracking - Tracking is optimized
         wips     - WIPS optimization is enabled
         none     - No optimization is enabled";
    }
  }

  grouping st-wtp-version {
    description
      "AP software version information";
    container sw-ver {
      description
        "Software version of the AP";
      uses wireless-types:version-info;
    }
  }

  grouping st-ap-models {
    description
      "AP device model information";
    leaf model {
      type string;
      description
        "Stores the model string of the AP";
    }
  }

  grouping st-static-info {
    description
      "AP device static information";
    container board-data {
      description
        "AP Board Data";
      uses wireless-access-point-oper:wtp-board-data;
    }
    container board-data-opt {
      description
        "AP Additional Board data option";
      uses wireless-access-point-oper:board-data-opt;
    }
    container descriptor-data {
      description
        "AP FW,HW information";
      uses wireless-access-point-oper:wtp-descriptor-data;
    }
    container ap-prov {
      description
        "AP universal provision";
      uses wireless-access-point-oper:ap-universal-provision-data;
    }
    container ap-models {
      description
        "AP device model";
      uses wireless-access-point-oper:st-ap-models;
    }
    leaf num-ports {
      type uint8;
      description
        "Number of ports on AP";
    }
    leaf num-slots {
      type uint8;
      description
        "Number of slots present in the access point";
    }
    leaf wtp-model-type {
      type uint8;
      description
        "AP model type";
    }
    leaf ap-capability {
      type wireless-access-point-oper:flag-ap-capability;
      description
        "AP capabilities";
    }
    leaf is-mm-opt {
      type boolean;
      description
        "AP monitor mode optimization support";
    }
    leaf ap-image-name {
      type string;
      description
        "AP Software image name";
    }
  }

  grouping st-dynamic-info {
    description
      "AP device dynamic information";
    leaf led-state-enabled {
      type boolean;
      description
        "True if LED state of AP is enabled.";
    }
    leaf reset-button-state {
      type boolean;
      description
        "True if AP Reset button state is enabled";
    }
    leaf led-flash-enabled {
      type boolean;
      description
        "True if LED Flash state of AP is enabled.";
    }
    leaf flash-sec {
      type uint16;
      units "seconds";
      description
        "LED Flash timer duration for AP.";
    }
  }

  grouping st-ap-device-info {
    description
      "AP device specific information";
    container static-info {
      description
        "AP device static information";
      uses wireless-access-point-oper:st-static-info;
    }
    container dynamic-info {
      description
        "AP device dynamic information";
      uses wireless-access-point-oper:st-dynamic-info;
    }
    container wtp-version {
      description
        "AP software version";
      uses wireless-access-point-oper:st-wtp-version;
    }
  }

  grouping st-ap-state {
    description
      "The AP state";
    leaf ap-admin-state {
      type wireless-enum-types:admin-state;
      description
        "The AP admin state";
    }
    leaf ap-operation-state {
      type wireless-access-point-oper:enum-ap-state;
      description
        "The AP operation state";
    }
  }

  grouping st-ap-fabric-data {
    description
      "AP fabric related attributes";
    leaf is-fabric-ap {
      type boolean;
      description
        "True if AP is fabric AP";
    }
  }

  grouping st-ap-mode-data {
    description
      "AP modes related information";
    leaf ap-sub-mode {
      type ap-types:ap-sub-mode-type;
      description
        "value of 'true' indicates this AP is a WIPS AP.
         value of 'false' indicates this AP is not a WIPS AP.
         This applies only when the AP is either in Local or in Monitor mode";
    }
    leaf wtp-mode {
      type wireless-types:enm-ewlc-spam-ap-modes;
      description
        "Mode of the AP to which the Mobile Station is associated.";
    }
    container ap-fabric-data {
      description
        "AP fabric related attributes";
      uses wireless-access-point-oper:st-ap-fabric-data;
    }
  }

  grouping st-ap-times {
    description
      "AP time related information";
    leaf boot-time {
      type yang:date-and-time;
      description
        "Last AP reboot Date and Time";
    }
    leaf join-time {
      type yang:date-and-time;
      description
        "Date and Time at which AP joined";
    }
  }

  grouping st-proxy-info {
    description
      "HTTP proxy configuration provisioned to this AP";
    leaf hostname {
      type string;
      description
        "HTTP proxy hostname";
    }
    leaf port {
      type uint16;
      description
        "HTTP proxy port";
    }
    leaf no-proxy-list {
      type string;
      description
        "List of URLs to be excluded from proxying";
    }
  }

  grouping capwap-wtp-data {
    description
      "Base AP operational data";
    leaf wtp-mac {
      type yang:mac-address;
      description
        "MAC address of AP radio interface";
    }
    leaf ip-addr {
      type string;
      description
        "IP of the AP";
    }
    leaf name {
      type string;
      description
        "AP Name";
    }
    container device-detail {
      description
        "AP device related information";
      uses wireless-access-point-oper:st-ap-device-info;
    }
    leaf ap-lag-enabled {
      type boolean;
      description
        "AP lag status, TRUE indicates the LAG support is enabled, FALSE indicates the LAG support is disabled.";
    }
    container ap-location {
      description
        "AP Location info";
      uses wireless-access-point-oper:st-ap-location;
    }
    container ap-services {
      description
        "AP services info";
      uses wireless-access-point-oper:st-ap-services;
    }
    container tag-info {
      description
        "AP tag info";
      uses wireless-access-point-oper:wtp-tags-data;
    }
    container tunnel {
      description
        "Captures the rogue parameters";
      uses ap-types:st-tunnel;
    }
    container external-module-data {
      description
        "AP external module data info";
      uses wireless-access-point-oper:st-external-module-data;
    }
    leaf ipv6-joined {
      type uint8;
      description
        "True if the AP has joined in IPv6 mode";
    }
    container ap-state {
      description
        "AP state";
      uses wireless-access-point-oper:st-ap-state;
    }
    container ap-mode-data {
      description
        "AP mode related data";
      uses wireless-access-point-oper:st-ap-mode-data;
    }
    container ap-time-info {
      description
        "AP time related information";
      uses wireless-access-point-oper:st-ap-times;
    }
    leaf country-code {
      type string;
      description
        "Country Code configured for the AP";
    }
    container ap-security-data {
      description
        "AP LSC data";
      uses wireless-access-point-oper:st-ap-security-oper-data;
    }
    leaf num-radio-slots {
      type uint8;
      description
        "Number of radio slots used for the AP";
    }
    leaf dart-is-connected {
      type boolean;
      description
        "Xor Dart connector status.";
    }
    leaf is-master {
      type boolean;
      description
        "True if the AP is configured as MASTER AP during efficient image download";
    }
    container sliding-window {
      description
        "CAPWAP multiwindow transport info";
      uses wireless-access-point-oper:st-sliding-window;
    }
    leaf cdp-enable {
      type boolean;
      description
        "True if CDP is enabled or not on the AP";
    }
    leaf ap-stationing-type {
      type wireless-access-point-oper:enum-ap-stationing-type;
      description
        "Indoor or Outdoor AP";
    }
    container reboot-stats {
      description
        "AP reboot statistics";
      uses wireless-access-point-oper:reboot-statistics;
    }
    container proxy-info {
      description
        "Proxy configuration provisioned to AP";
      uses wireless-access-point-oper:st-proxy-info;
    }
    leaf image-size-eta {
      type yang:timeticks;
      description
        "The estimated amount of time left for the current image download to complete.";
    }
    leaf image-size-start-time {
      type yang:date-and-time;
      description
        "The time the current download started.";
    }
    leaf image-size-percentage {
      type uint32;
      description
        "The percentage of the current image download completed.";
    }
  }

  grouping ap-ethernet-intf-id {
    description
      "AP Ethernet interface info";
    leaf wtp-mac {
      type yang:mac-address;
      description
        "AP Ethernet interface MAC Address";
    }
    leaf if-index {
      type uint16;
      description
        "AP Ethernet interface index";
    }
  }

  grouping ap-ethernet-intf-info {
    description
      "AP Ethernet interface statistics";
    leaf if-name {
      type string;
      description
        "Ethernet interface Name";
    }
    leaf rx-pkts {
      type uint32;
      description
        "Number of packets received from Mobile Station";
    }
    leaf tx-pkts {
      type uint32;
      description
        "Number of packets sent to Mobile Station";
    }
  }

  grouping ap-name-mac-map {
    description
      "Mapping between AP name and base radio MAC";
    leaf wtp-name {
      type string;
      description
        "AP Name";
    }
    leaf wtp-mac {
      type yang:mac-address;
      description
        "AP radio MAC address";
    }
    leaf eth-mac {
      type yang:mac-address;
      description
        "AP ethernet MAC address";
    }
  }

  grouping ethernet-mac-wtp-mac-map {
    description
      "Mapping between AP ethernet name and base radio MAC";
    leaf ethernet-mac {
      type yang:mac-address;
      description
        "The Ethernet MAC of AP";
    }
    leaf wtp-mac {
      type yang:mac-address;
      description
        "The Radio MAC of AP";
    }
  }

  grouping st-radius-counters {
    description
      "A collection of RADIUS related state objects";
    leaf retried-access-requests {
      type uint64;
      description
        "The count of access request messages that were retried";
    }
    leaf access-accepts {
      type uint64;
      description
        "The count of access accept messages sent by the RADIUS server";
    }
    leaf access-rejects {
      type uint64;
      description
        "The count of access reject messages sent by the RADIUS server";
    }
    leaf timeout-access-requests {
      type uint64;
      description
        "The number of times an access request message timed out without any response from the RADIUS server";
    }
  }

  grouping ewlc-cdp-cache-data-key {
    description
      "Compound key of the table with device id as one of the attributes";
    leaf mac-addr {
      type yang:mac-address;
      description
        "Radio MAC address of the AP";
    }
    leaf cdp-cache-device-id {
      type string;
      description
        "The Device-ID string as reported in the CDP message";
    }
  }

  grouping cdp-cache-data-index-key {
    description
      "Compound key of the table with device index as one of the attributes";
    leaf wtp-mac-addr {
      type yang:mac-address;
      description
        "Radio MAC address of the AP";
    }
    leaf device-index {
      type uint32;
      description
        "A unique value for each device from which CDP messages are being received";
    }
  }

  grouping cdp-cache-neighbour-ip-addr {
    description
      "List of IP address.";
    leaf-list ip-address-value {
      type inet:ip-address;
      max-elements "9";
      ordered-by user;
      description
        "IP address value";
    }
  }

  grouping cdp-cache-data-op {
    description
      "An entry of the CDP cache data table";
    leaf ap-name {
      type string;
      description
        "AP Name";
    }
    leaf version {
      type uint8;
      description
        "Cisco Discovery Protocol version";
    }
    leaf cdp-cache-ap-address {
      type inet:ip-address;
      description
        "An indication of the type of address contained 
         in the corresponding instance of 
         clcCdpApCacheAddress for the AP";
    }
    container ip-address {
      description
        "All network-layer addresses(IPv4 and IPv6) of the device's
         SNMP-agent as reported in the most recent CDP message.";
      uses wireless-access-point-oper:cdp-cache-neighbour-ip-addr;
    }
  }

  grouping st-ap-mac-ssid-info {
    description
      "AP MAC and SSID informations";
    list ssid-clients-list-data {
      key "client-mac-address";
      description
        "List of Client MAC address which use this SSID";
      uses wireless-access-point-oper:st-ssid-clients-list-data;
    }
  }

  grouping st-ssid-clients-list-data {
    description
      "Clients MAC address";
    leaf client-mac-address {
      type yang:mac-address;
      description
        "Client MAC address";
    }
  }

  grouping wmm-cac-stats {
    description
      "WMM TSPEC call statistics";
    leaf calls-in-progress {
      type uint16;
      description
        "Total number of voice calls in progress";
    }
    leaf roam-calls-in-progress {
      type uint16;
      description
        "Total number of roaming voice calls in progress";
    }
    leaf calls-accepted {
      type uint16;
      description
        "Total number of calls accepted since AP joined";
    }
    leaf roam-calls-accepted {
      type uint16;
      description
        "Total number of roam calls accepted since AP joined";
    }
    leaf calls-rejected {
      type uint16;
      description
        "Total number of calls rejected since AP joined";
    }
    leaf roam-calls-rejected {
      type uint16;
      description
        "Total number of roam calls rejected since AP joined";
    }
    leaf calls-rejected-insuff-bw {
      type uint16;
      description
        "Total number of calls rejected due to insufficient bandwidth";
    }
    leaf calls-rejected-qos {
      type uint16;
      description
        "Total number of calls rejected due to wlan QoS settings";
    }
    leaf calls-rejected-phy-rate {
      type uint16;
      description
        "Total number of calls rejected due to un-acceptable PHY rate";
    }
    leaf calls-rejected-invalid-tspec {
      type uint16;
      description
        "Total number of calls rejected due to invalid TSPEC parameters";
    }
    leaf exp-bw-reqs-received {
      type uint16;
      description
        "Total number of exp bw requests received since AP join";
    }
    leaf exp-bw-reqs-accepted {
      type uint16;
      description
        "Total number of exp bw request calls admitted as
         expbwreqs since AP joined";
    }
  }

  grouping sip-cac-stats {
    description
      "SIP CAC statistics";
    leaf sip-calls-in-progress {
      type uint16;
      description
        "Total number of calls in progress";
    }
    leaf sip-roam-calls-in-progress {
      type uint16;
      description
        "Total number of roam calls in progress";
    }
    leaf sip-calls-accepted {
      type uint16;
      description
        "Total number of calls accepted since AP join";
    }
    leaf sip-roam-calls-accepted {
      type uint16;
      description
        "Total number of roam calls accepted since AP join";
    }
    leaf sip-preferred-calls-received {
      type uint16;
      description
        "Total number of Preferred calls received";
    }
    leaf sip-preferred-calls-accepted {
      type uint16;
      description
        "Total number of Preferred calls accepted";
    }
    leaf sip-preferred-calls-ongoing {
      type uint16;
      description
        "Total number of ongoing preferred calls";
    }
    leaf sip-calls-rejected-insuf-bw {
      type uint16;
      description
        "Total number of calls rejected insufficient bandwidth";
    }
    leaf sip-roam-calls-rejected-insuf-bw {
      type uint16;
      description
        "Total number of roam calls rejected insufficient bandwidth";
    }
  }

  grouping qos-ap-radio-key {
    description
      "Composite key structure for AP Radio record in DB";
    leaf radio-slot-id {
      type uint8;
      description
        "Slot id for radio";
    }
    leaf ap-mac {
      type yang:mac-address;
      description
        "AP mac address";
    }
  }

  grouping qos-ap-radio-data {
    description
      "QoS AP Radio data in DB";
    leaf wmm-voice-bw-allocated {
      type uint32;
      units "percentage";
      description
        "Voice Bandwidth allocated for Calls";
    }
    leaf wmm-max-voice-bandwidth {
      type uint32;
      units "percentage";
      description
        "Max RF bandwidth for Calls";
    }
    leaf wmm-bw-in-use {
      type uint32;
      units "percentage";
      description
        "Bandwidth is used in Voice Call (% of config bandwidth)";
    }
    container wmm-cac-stats {
      description
        "CAC stats data for this Radio on AP";
      uses wireless-access-point-oper:wmm-cac-stats;
    }
    leaf lbcac-measure {
      type boolean;
      description
        "load-based CAC setting measure";
    }
    leaf wmm-voice-roam-bw-in-use {
      type uint32;
      units "percentage";
      description
        "Bandwidth is used in Voice roam Call (% of config bandwidth)";
    }
    leaf sip-preferred-calls-mtu-used {
      type uint32;
      units "percentage";
      description
        "Total bandwidth is used for SIP preferred Call (% of config bandwidth)";
    }
    leaf cumulative-call-count {
      type uint32;
      description
        "completed sip call count";
    }
    leaf cumulative-seconds-used {
      type uint32;
      units "seconds";
      description
        "call duration for completed sip calls";
    }
    container sip-cac-stats {
      description
        "SIP CAC statistics";
      uses wireless-access-point-oper:sip-cac-stats;
    }
    leaf total-active-calls {
      type uint16;
      description
        "Total active calls include both TSpec and SIP calls";
    }
    leaf total-rejected-calls {
      type uint16;
      description
        "Total Rejected calls include both TSpec and SIP calls";
    }
  }

  grouping qos-client-voice-statistics {
    description
      "QoS Client Voice Statistics";
    leaf total-num-of-tspec-rcvd {
      type uint32;
      description
        "Total Number of TSPEC requests received";
    }
    leaf new-tspec-from-assoc-req {
      type uint32;
      description
        "Number of New TSPEC received from Assoc Request";
    }
    leaf tspec-renewal-from-assoc-req {
      type uint32;
      description
        "Number of TSPEC renewal received from Assoc Request";
    }
    leaf new-tspec-as-add-ts {
      type uint32;
      description
        "Number of new Add TS requests received";
    }
    leaf tspec-renewal-from-add-ts {
      type uint32;
      description
        "Number of Add TS renewal requests received";
    }
    leaf tspec-process-failed-get-rec {
      type uint32;
      description
        "Number of DB failures while processing TSPEC";
    }
    leaf total-sip-invite-on-caller {
      type uint32;
      description
        "Total number of SIP Invite received on Caller";
    }
    leaf total-sip-invite-on-callee {
      type uint32;
      description
        "Total number of SIP Invite received on Callee";
    }
    leaf total-num-of-call-report {
      type uint32;
      description
        "Total number of call-report received";
    }
    leaf total-sip-failure-trap-send {
      type uint32;
      description
        "Total number of SIP failure trap send";
    }
    leaf num-of-calls-accepted {
      type uint32;
      description
        "Total Number of calls accepted";
    }
    leaf num-of-calls-rejected-insuf-bw {
      type uint32;
      description
        "Number of calls rejected due to Insufficient BW";
    }
    leaf num-of-calls-rejected-qos {
      type uint32;
      description
        "Number of calls rejected due to QoS policy";
    }
    leaf num-of-calls-rejected-phy-rate {
      type uint32;
      description
        "Number of calls rejected due to PHY rate";
    }
    leaf num-of-calls-rej-invalid-tspec {
      type uint32;
      description
        "Number of calls rejected due to Invalid TSPEC";
    }
    leaf num-of-roam-calls-accepted {
      type uint32;
      description
        "Total Number of roam calls accepted";
    }
    leaf num-of-roam-calls-rejected {
      type uint32;
      description
        "Total Number of roam calls rejected";
    }
    leaf num-of-active-sip-calls {
      type uint32;
      description
        "Total Number of active SIP calls";
    }
    leaf num-of-active-tspec-calls {
      type uint32;
      description
        "Total Number of active TSPEC calls";
    }
  }

  grouping qos-global-statistics {
    description
      "QoS Global Statistics";
    container qos-client-voice-stats {
      description
        "QoS Client Voice related Statistics";
      uses wireless-access-point-oper:qos-client-voice-statistics;
    }
  }

  grouping ewlc-dual-radio-mode-config-data {
    description
      "Dual radio configuration and capability for AP radio";
    leaf dual-radio-mode {
      type wireless-enum-types:enum-dual-radio-mode;
      description
        "Dual radio mode for AP radio";
    }
    leaf dual-radio-capable {
      type wireless-enum-types:enum-dual-radio-capable;
      description
        "AP radio is dual radio capable";
    }
    leaf dual-radio-mode-op {
      type wireless-enum-types:enum-radio-mode-op;
      description
        "Dual radio mode operation for AP radio";
    }
  }

  grouping ewlc-phy-tx-power-cfg-data {
    description
      "Configured tx-power for AP radio";
    leaf phy-tx-power-config-type {
      type wireless-types:w-config-type;
      description
        "Type of Tx power configuration, Auto or Static";
    }
    leaf current-tx-power-level {
      type uint16;
      description
        "Tx Power level in the range from 1 to 8, 1 being the highest";
    }
  }

  grouping ewlc-phy-tx-power-level-cfg-data {
    description
      "Configured Tx power in dBm";
    leaf curr-tx-power-in-dbm {
      type int16;
      units "dBm";
      description
        "Transmit Power for the AP radio in dBm";
    }
  }

  grouping ewlc-phy-ht-cfg-data {
    description
      "802.11n configuration";
    leaf ht-enable {
      type uint8;
      description
        "802.11n configuration for the AP radio. It has a value representing the bit flag of MCS rates enabled on the AP radio";
    }
    leaf phy-ht-cfg-config-type {
      type wireless-types:w-config-type;
      description
        "Type of Channel configuration, Auto or Static";
    }
    leaf curr-freq {
      type uint16;
      description
        "Current operating frequency(Channel) on the AP radio";
    }
    leaf chan-width {
      type uint8;
      description
        "Channel width of the AP radio";
    }
    leaf ext-chan {
      type uint8;
      description
        "Current extended channel. Valid if the channel width is more than 20 Mhz";
    }
    leaf vht-enable {
      type boolean;
      description
        "802.11ac configuration for the AP radio.
         True  - 802.11ac is enabled. 
         False - 802.11ac is disabled.";
    }
    leaf rrm-channel-change-reason {
      type wireless-enum-types:rrm-channel-change-reason;
      description
        "Reason for Channel change by RRM";
    }
  }

  grouping ewlc-phy-ht-cap-data {
    description
      "802.11n capabilities";
    leaf vht-capable {
      type boolean;
      description
        "True if AP radio is 802.11ac capable";
    }
    leaf ht-capable {
      type boolean;
      description
        "True if AP radio is 802.11n capable";
    }
  }

  grouping ewlc-phy-he-cap-data {
    description
      "802.11ax Capability data for AP radio";
    leaf he-enabled {
      type boolean;
      description
        "AP radio is 802.11ax enabled";
    }
    leaf he-capable {
      type boolean;
      description
        "AP radio is 802.11ax capable";
    }
  }

  grouping ewlc-antenna-cfg-data {
    description
      "Information related to Antenna configuration";
    leaf diversity-selection {
      type wireless-enum-types:enm-antenna-selection;
      description
        "Diversity selection type, values connectorA, connectorB or enabled.
         Not applicable to 802.11a radio band";
    }
    leaf antenna-mode {
      type wireless-enum-types:enm-antenna-mode;
      description
        "Antenna Mode. For 802.11a this attribute will always be omni.
         Not applicable to 802.11b radio band";
    }
    leaf num-of-antennas {
      type uint8;
      description
        "Number of Antennas present on this AP radio";
    }
  }

  grouping ewlc-chan-pwr-info-data {
    description
      "Antenna parameters for AP radio";
    leaf antenna-gain {
      type uint8;
      units "dBi";
      description
        "Antenna gain for the AP radio, in units of two";
    }
    leaf int-antenna-gain {
      type uint8;
      units "dBi";
      description
        "Internal Antenna gain for the AP radio, in units of two";
    }
    leaf ext-antenna-gain {
      type uint8;
      units "dBi";
      description
        "External Antenna gain for the AP radio, in units of two";
    }
  }

  grouping cfg-entity-phy-tx-power-cfg {
    description
      "Tx-power configured on the radio";
    container cfg-data {
      description
        "Phy Tx Power Configuration";
      uses wireless-access-point-oper:ewlc-phy-tx-power-cfg-data;
    }
  }

  grouping cfg-entity-phy-tx-power-level-cfg {
    description
      "Configured tx power level on the AP radio";
    container cfg-data {
      description
        "Tx power level Configuration";
      uses wireless-access-point-oper:ewlc-phy-tx-power-level-cfg-data;
    }
  }

  grouping cfg-entity-phy-ht-cfg {
    description
      "802.11n configuration of the AP radio";
    container cfg-data {
      description
        "802.11n Configuration";
      uses wireless-access-point-oper:ewlc-phy-ht-cfg-data;
    }
  }

  grouping cfg-entity-phy-he-cap {
    description
      "802.11ax Capability information";
    container data {
      description
        "802.11ax Capability information";
      uses wireless-access-point-oper:ewlc-phy-he-cap-data;
    }
  }

  grouping cfg-entity-phy-ht-cap {
    description
      "802.11n capabilities of the AP radio";
    container data {
      description
        "802.11n Capabilities";
      uses wireless-access-point-oper:ewlc-phy-ht-cap-data;
    }
  }

  grouping cfg-entity-antenna-cfg {
    description
      "Configuration related to Antenna";
    container cfg-data {
      description
        "Antenna Configuration";
      uses wireless-access-point-oper:ewlc-antenna-cfg-data;
    }
  }

  grouping entity-channel-power-info {
    description
      "Antenna gain information for AP radio";
    container data {
      description
        "Antenna gain values for AP radio";
      uses wireless-access-point-oper:ewlc-chan-pwr-info-data;
    }
  }

  grouping st-sia-params {
    description
      "Self Identifying Antenna Parameters for the AP radio band";
    leaf is-rptnc-present {
      type boolean;
      description
        "SIA RP-TNC is present for the AP radio.
         True  -  SIA RP-TNC is present. 
         False -  SIA RP-TNC is not present.";
    }
    leaf is-dart-present {
      type boolean;
      description
        "SIA DART is present for the AP radio.
         True  -  SIA DART is present. 
         False -  SIA DART is not present.";
    }
  }

  grouping ewlc-radio-band-info {
    description
      "Information of the AP radio band";
    leaf band-id {
      type uint8;
      description
        "Band identifier of the radio interface";
    }
    leaf regulatory-domain {
      type string;
      description
        "Regulatory Domain code for Radio band";
    }
    container phy-tx-pwr-cfg {
      description
        "Configured radio Tx-power in dBm";
      uses wireless-access-point-oper:cfg-entity-phy-tx-power-cfg;
    }
    container phy-tx-pwr-lvl-cfg {
      description
        "Tx-power level configured on the radio";
      uses wireless-access-point-oper:cfg-entity-phy-tx-power-level-cfg;
    }
    container antenna-cfg {
      description
        "Antenna configuration";
      uses wireless-access-point-oper:cfg-entity-antenna-cfg;
    }
    container sia-params {
      description
        "Self Identifying Antenna parameters of the AP radio band";
      uses wireless-access-point-oper:st-sia-params;
    }
  }

  grouping st-bss-color-config {
    description
      "802.11ax BSS Color configuration and capability data for AP radio";
    leaf bss-color-capable {
      type boolean;
      description
        "AP radio is 802.11ax BSS Color capable";
    }
    leaf bss-color {
      type uint8 {
        range "0 .. 63";
      }
      description
        "Configured 802.11ax BSS Color, 0 meaning disabled";
    }
    leaf bss-color-config-type {
      type wireless-types:w-config-type;
      description
        "Type of 802.11ax BSS Color configuration";
    }
  }

  grouping ewlc-radio-operation-config {
    description
      "Radio operational configuration";
    leaf slot-id {
      type uint8;
      description
        "Radio slot identifier";
    }
    leaf radio-type {
      type wireless-enum-types:enm-radio-type;
      description
        "Type of the radio. Possible values are:
         radio-80211bg    - 802.11bg radio 
         radio-80211a     - 802.11a radio
         radio-80211abgn  - Dual band radio
         radio-remote-lan -  Remote LAN";
    }
    leaf admin-state {
      type wireless-access-point-oper:enum-radio-admin-state;
      description
        "Admin state of the radio interface";
    }
    leaf oper-state {
      type wireless-access-point-oper:enum-radio-oper-state;
      description
        "Operational state of the radio interface. Even though the admin state is enabled there are various reasons for which the operational state of the radio can be down";
    }
    leaf radio-mode {
      type wireless-types:enm-ewlc-ap-radio-modes;
      description
        "Current radio mode. Possible values are:
         radio-mode-invalid            - Invalid mode
         radio-mode-local              - Local mode
         radio-mode-monitor            - Monitor mode
         radio-mode-flex-connect       - Remote mode
         radio-mode-rogue-detector     - Rogue detector
         radio-mode-sniffer            - Sniffer mode
         radio-mode-bridge             - Bridge mode
         radio-mode-se-connect         - Spectrum mode
         radio-mode-hybrid-flexconnect - Hybrid mode
         radio-mode-remote-bridge      - Remote Bridge
         radio-mode-sensor             - Sensor mode";
    }
    leaf radio-sub-mode {
      type wireless-types:radio-sub-mode;
      description
        "Radio mode selection process, possible values are:
         radio-sub-mode-none   - None
         radio-sub-mode-auto   - radio mode is selected automatically
         radio-sub-mode-manual - Manual, radio mode is selected manually";
    }
    leaf radio-subtype {
      type wireless-types:ap-radio-subtype;
      description
        "Radio sub type indicating the radios capabilities, possible values are:
         ap-radio-subtype-main     - Main
         ap-radio-subtype-rx-only  - Rx-only, radio can only receive
         ap-radio-subtype-slave-ac - Slave AC
         ap-radio-subtype-rem-lan  - Remote lan
         ap-radio-subtype-tx-rx    - Radio can both receive and transmit";
    }
    leaf radio-subband {
      type wireless-enum-types:slot-radio-sub-band;
      description
        "Radio sub band, Valid only if the radio is in 5 GHz band";
    }
    leaf current-band-id {
      type uint8;
      description
        "Represents radio's current operating band identifier. 
         Possible values are:
         0 - current operational band is 2.4GHz
         1 - current operational band is 5GHz";
    }
    leaf current-active-band {
      type wireless-types:enm-ewlc-dot11-radio-band;
      description
        "Radio's current operating band, Possible values are:
         dot11-2-dot-4-ghz-band - Current operational band is 2.4GHz
         dot11-5-ghz-band       - Current operational band is 5GHz";
    }
    leaf xor-radio-mode {
      type wireless-types:enum-xor-radio-mode;
      description
        "Dual band(XOR) radio mode possible values are:
         xor-radio-mode-local   - Client serving
         xor-radio-mode-monitor - Monitor mode
         xor-radio-mode-sensor  - sensor mode";
    }
    container phy-ht-cfg {
      description
        "802.11n Configuration";
      uses wireless-access-point-oper:cfg-entity-phy-ht-cfg;
    }
    container phy-ht-cap {
      description
        "802.11n Capabilities";
      uses wireless-access-point-oper:cfg-entity-phy-ht-cap;
    }
    container xor-phy-ht-cap {
      description
        "802.11n capabilities for a dual-band radio";
      uses wireless-access-point-oper:cfg-entity-phy-ht-cap;
    }
    container phy-he-cap {
      description
        "802.11ax Capabilities for radio";
      uses wireless-access-point-oper:cfg-entity-phy-he-cap;
    }
    container chan-pwr-info {
      description
        "Mapping between all channels and allowed power levels on that channel";
      uses wireless-access-point-oper:entity-channel-power-info;
    }
    leaf antenna-pid {
      type string;
      description
        "Radio Antenna PID";
    }
    list radio-band-info {
      key "band-id";
      description
        "Radio Band Information";
      uses wireless-access-point-oper:ewlc-radio-band-info;
    }
    leaf reg-domain-check-status {
      type wireless-enum-types:reg-domain-status;
      description
        "regulatory-domain-check-status-not-set - Regulatory Domain check has failed.
         regulatory-domain-check-status-set     - Regulatory Domain check has passed.";
    }
    leaf slot-antenna-type {
      type wireless-types:radio-slot-antenna-type;
      description
        "Radio slot Antenna type";
    }
    leaf radio-enable-time {
      when "(../oper-state = 'radio-up')";
      type yang:date-and-time;
      description
        "Radio slot up time for AP";
    }
    leaf dot11n-mcs-rates {
      type wireless-access-point-oper:flag-dot11n-mcs-rates;
      description
        "802.11n MCS Rates";
    }
    container dual-radio-mode-cfg {
      description
        "Dual radio mode operation and capability";
      uses wireless-access-point-oper:ewlc-dual-radio-mode-config-data;
    }
    leaf radio-fra-capable {
      type wireless-enum-types:enum-radio-fra-capable;
      description
        "FRA capability";
    }
    container bss-color-cfg {
      description
        "802.11ax BSS Color radio configuration and capability";
      uses wireless-access-point-oper:st-bss-color-config;
    }
    leaf highest-throughput-proto {
      type wireless-enum-types:enm-radio-dot11-proto-supported;
      description
        "Highest throughput supported by radio as per 802.11 protocols";
    }
  }

  grouping st-mac-slot-id-comp-key {
    description
      "MAC address and slot id key";
    leaf ap-mac {
      type yang:mac-address;
      description
        "Mac address of AP";
    }
    leaf slot-id {
      type uint8;
      description
        "Radio slot identifier";
    }
  }

  grouping radio-statistics {
    description
      "Radio statistics information";
    leaf aid-user-list {
      type uint16;
      description
        "Number of Users associated with this radio";
    }
    leaf tx-fragment-count {
      type uint32;
      description
        "This counter shall be incremented for an acknowledged MPDU
         with an individual address in the address 1 field or an MPDU
         with a multicast address in the address 1 field of type Data
         or Management.";
    }
    leaf failed-count {
      type uint32;
      description
        "This counter shall increment when an MSDU is not transmitted
         successfully due to the number of transmit attempts exceeding
         either the  bsnAPIfDot11ShortRetryLimit or dot11LongRetryLimit.";
    }
    leaf rx-fragment-count {
      type uint32;
      description
        "This counter shall be incremented for each successfully
         received MPDU of type Data or Management.";
    }
    leaf tx-frame-count {
      type uint32;
      description
        "This counter shall increment for each successfully
         transmitted MSDU.";
    }
  }

  grouping st-ap-radio-neighbor-data {
    description
      "The MAC address, or BSSID, of a neighbor, and their corresponding RSSI.";
    leaf ssid {
      type string;
      description
        "Neighboring BSSID.";
    }
    leaf rssi {
      type int8;
      units "dBm";
      description
        "The RSSI of this neighboring BSSID.";
    }
    leaf channel {
      type uint16;
      description
        "The channel of this neighboring BSSID. This is to utilize 802.11ac nomenclature. For example, 40MHz channel 36-40 represented as channel 38. primary-channel used to identify the primary 20MHz channel of the neighbor.";
    }
    leaf primary-channel {
      type uint16;
      description
        "The primary 20MHz channel, if the neighbor is operating on bonded channel.";
    }
    leaf last-update-rcvd {
      type yang:date-and-time;
      description
        "Time when last update received for the bssid.";
    }
  }

  grouping st-data-distribution {
    description
      "AMPDU data distribution";
    leaf bytes-0-64 {
      type uint64;
      description
        "Number of AMPDU with size between 0 to 64 bytes";
    }
    leaf bytes-65-128 {
      type uint64;
      description
        "Number of AMPDU with size between 65 to 128 bytes";
    }
    leaf bytes-129-256 {
      type uint64;
      description
        "Number of AMPDU with size between 129 to 256 bytes";
    }
    leaf bytes-257-512 {
      type uint64;
      description
        "Number of AMPDU with size between 257 to 512 bytes";
    }
    leaf bytes-513-1024 {
      type uint64;
      description
        "Number of AMPDU with size between 513 to 1024 bytes";
    }
    leaf bytes-1025-2048 {
      type uint64;
      description
        "Number of AMPDU with size between 1025 to 2048 bytes";
    }
    leaf bytes-2049-4096 {
      type uint64;
      description
        "Number of AMPDU with size between 2049 to 4096 bytes";
    }
    leaf bytes-4097-8192 {
      type uint64;
      description
        "Number of AMPDU with size between 4097 to 8192 bytes";
    }
    leaf bytes-8193-16384 {
      type uint64;
      description
        "Number of AMPDU with size between 8193 to 16384 bytes";
    }
    leaf bytes-16385-32768 {
      type uint64;
      description
        "Number of AMPDU with size between 16385 to 32768 bytes";
    }
    leaf bytes-32769-65536 {
      type uint64;
      description
        "Number of AMPDU with size between 32769 to 65536 bytes";
    }
    leaf bytes-65537-131072 {
      type uint64;
      description
        "Number of AMPDU with size between 65537 to 131072 bytes";
    }
    leaf bytes-131073-262144 {
      type uint64;
      description
        "Number of AMPDU with size between 131073 to 262144 bytes";
    }
    leaf bytes-262145-524288 {
      type uint64;
      description
        "Number of AMPDU with size between 262145 to 524288 bytes";
    }
    leaf bytes-524289-1048576 {
      type uint64;
      description
        "Number of AMPDU with size between 524289 to 1048576 bytes";
    }
  }

  grouping st-mcs-traffic-stats {
    description
      "MCS index list";
    leaf mcs0 {
      type uint64;
      description
        "MCS index 0";
    }
    leaf mcs1 {
      type uint64;
      description
        "MCS index 1";
    }
    leaf mcs2 {
      type uint64;
      description
        "MCS index 2";
    }
    leaf mcs3 {
      type uint64;
      description
        "MCS index 3";
    }
    leaf mcs4 {
      type uint64;
      description
        "MCS index 4";
    }
    leaf mcs5 {
      type uint64;
      description
        "MCS index 5";
    }
    leaf mcs6 {
      type uint64;
      description
        "MCS index 6";
    }
    leaf mcs7 {
      type uint64;
      description
        "MCS index 7";
    }
    leaf mcs8 {
      type uint64;
      description
        "MCS index 8";
    }
    leaf mcs9 {
      type uint64;
      description
        "MCS index 9";
    }
  }

  grouping st-data-wmm {
    description
      "QoS Data frames, per WMM AC";
    leaf video {
      type uint64;
      description
        "Data frames marked as Access Category Video";
    }
    leaf voice {
      type uint64;
      description
        "Data frames marked as Access Category Voice";
    }
    leaf background {
      type uint64;
      description
        "Data frames marked as Access Category background";
    }
    leaf best-effort {
      type uint64;
      description
        "Data frames marked as Access Category best effort";
    }
  }

  grouping st-ssid-counter {
    description
      "List of ssid counters";
    leaf bssid-mac {
      type yang:mac-address;
      description
        "Mac address of the bssid";
    }
    leaf vap-id {
      type uint16;
      description
        "VAP id of the WLAN for the access point";
    }
    leaf tx-mgmt {
      type uint64;
      description
        "Number of 802.11 Management frames transmitted";
    }
    leaf rx-mgmt {
      type uint64;
      description
        "Number of 802.11 Management frames received";
    }
    leaf tx-bytes-data {
      type uint64;
      units "bytes";
      description
        "Total number of bytes of data frames transmitted";
    }
    container tx-data-dist {
      description
        "The distribution of Data frame sizes in bytes of successfully received AMPDU";
      uses wireless-access-point-oper:st-data-distribution;
    }
    container tx-data-wmm {
      description
        "Transmitted QoS Data frames, per WMM AC.";
      uses wireless-access-point-oper:st-data-wmm;
    }
    leaf tx-retries {
      type uint64;
      description
        "Number of frames transmitted with Retry bit set.";
    }
    leaf tx-retries-data {
      type uint64;
      description
        "Number of data frames transmitted with Retry bit set";
    }
    leaf tx-retries-subframes {
      type uint64;
      description
        "Aggregated MPDUs which had individual sub-frames that fail and require retransmission";
    }
    container tx-mcs {
      description
        "Transmitted Data frames, per MCS Index";
      uses wireless-access-point-oper:st-mcs-traffic-stats;
    }
    leaf rx-bytes-data {
      type uint64;
      units "bytes";
      description
        "Total number of bytes of data frames transmitted";
    }
    container rx-data-dist {
      description
        "The distribution of Data frame sizes in bytes of successfully received AMPDU";
      uses wireless-access-point-oper:st-data-distribution;
    }
    container rx-data-wmm {
      description
        "Received 802.11 Data frames, per WMM Access Category.";
      uses wireless-access-point-oper:st-data-wmm;
    }
    container rx-mcs {
      description
        "Received Data frames, per MCS Index";
      uses wireless-access-point-oper:st-mcs-traffic-stats;
    }
    leaf num-assoc-clients {
      type uint16;
      description
        "Number of clients associated to this BSS";
    }
    leaf noise-floor {
      type uint8;
      description
        "Noise floor information of the radio.";
    }
  }

  grouping ewlc-rlan-key {
    description
      "MAC address and port id key";
    leaf wtp-mac {
      type yang:mac-address;
      description
        "MAC Address of the AP Radio";
    }
    leaf rlan-port-id {
      type uint8;
      description
        "LAN port id of the AP";
    }
  }

  grouping ewlc-rlan-oper-config-entry {
    description
      "AP LAN port operational data";
    leaf rlan-oper-state {
      type boolean;
      description
        "Status of the LAN port";
    }
    leaf rlan-port-status {
      type boolean;
      description
        "Remote LAN status of the LAN port";
    }
    leaf rlan-vlan-id {
      type uint32;
      description
        "VLAN id of the LAN port";
    }
    leaf rlan-poe-state {
      type wireless-access-point-oper:ewlc-rlan-poe-state;
      description
        "PoE state of the LAN port";
    }
    leaf power-level-id {
      type uint8;
      description
        "Power level of the LAN port";
    }
  }

  grouping st-iot-device-comp-key {
    description
      "IoT device identifier";
    leaf ap-mac {
      type yang:mac-address;
      description
        "AP radio MAC address";
    }
    leaf device-mac {
      type yang:phys-address;
      description
        "IoT device MAC address";
    }
  }

  grouping st-iot-device {
    description
      "IoT device operational data";
    leaf name {
      type string;
      description
        "IoT device name";
    }
    leaf type {
      type string;
      description
        "IoT device type. For example: light bulb.";
    }
    leaf protocol {
      type string;
      description
        "IoT device protocol. For example: ZigBee.";
    }
    leaf connection-state {
      type string;
      description
        "State of the connection between the AP and the IoT device";
    }
    leaf battery-level {
      type int8 {
        range "-1 .. 100";
      }
      description
        "IoT device battery level";
    }
  }

  grouping st-iox-ap {
    description
      "AP IOx application hosting operational data";
    leaf ap-mac {
      type yang:mac-address;
      description
        "AP radio MAC address";
    }
    leaf apphost-state {
      type wireless-access-point-oper:enm-apphost-state;
      description
        "State of the application hosting reported by the AP";
    }
    leaf caf-token {
      type string;
      description
        "Cisco Application hosting Framework token";
    }
    leaf caf-port {
      type uint16;
      description
        "Cisco Application hosting Framework port number";
    }
  }

  container access-point-oper-data {
    config false;
    description
      "Root container of access point oper";
    list ap-mac-ssid-info {
      key "ap-mac wlan-id";
      description
        "AP MAC and SSID informations";
      uses wireless-access-point-oper:st-ap-mac-ssid-info;
      uses wireless-types:ap-mac-ssid;
    }
    list ssid-counters {
      key "wtp-mac slot-id wlan-id";
      description
        "Rx/Tx and data-rates information of SSID's broadcasting in AP";
      uses wireless-access-point-oper:st-ssid-counter;
      uses wireless-types:radio-wlanid-key;
    }
    list radius-counters {
      key "wtp-mac server-group-name server-ip";
      description
        "RADIUS related state information";
      uses wireless-access-point-oper:st-radius-counters;
      uses wireless-types:ap-radius-server-key;
    }
    list ap-radio-neighbor {
      key "ap-mac slot-id bssid";
      description
        "AP radio neighbor information.";
      uses wireless-types:radio-slot-bssid-key;
      uses wireless-access-point-oper:st-ap-radio-neighbor-data;
    }
    list radio-oper-data {
      key "wtp-mac radio-slot-id";
      description
        "Radio operational data corresponding
         to a radio of the 802.11 LWAPP AP";
      uses wireless-types:radio-slot-key;
      uses wireless-access-point-oper:ewlc-radio-operation-config;
    }
    list capwap-data {
      key "wtp-mac";
      description
        "Captures the information about the 802.11 LWAPP AP that has joined the controller";
      uses wireless-access-point-oper:capwap-wtp-data;
    }
    list ap-name-mac-map {
      key "wtp-name";
      description
        "Mapping between AP name and radio MAC of AP";
      uses wireless-access-point-oper:ap-name-mac-map;
    }
    list ethernet-mac-wtp-mac-map {
      key "ethernet-mac";
      description
        "Mapping between AP ethernet MAC and base radio MAC";
      uses wireless-access-point-oper:ethernet-mac-wtp-mac-map;
    }
    list radio-oper-stats {
      key "ap-mac slot-id";
      description
        "Operational statistics for a particular radio";
      uses wireless-access-point-oper:st-mac-slot-id-comp-key;
      uses wireless-access-point-oper:radio-statistics;
    }
    list ethernet-if-stats {
      key "wtp-mac if-index";
      description
        "Ethernet interface statistics";
      uses wireless-access-point-oper:ap-ethernet-intf-info;
      uses wireless-access-point-oper:ap-ethernet-intf-id;
    }
    list iot-devices {
      key "ap-mac device-mac";
      description
        "IoT device operational data";
      uses wireless-access-point-oper:st-iot-device;
      uses wireless-access-point-oper:st-iot-device-comp-key;
    }
    list ap-iox-oper-data {
      key "ap-mac";
      description
        "IOx application hosting operational data reported by the AP";
      uses wireless-access-point-oper:st-iox-ap;
    }
    list qos-radio-data {
      key "radio-slot-id ap-mac";
      description
        "This object specify a table for QoS AP Radio data records in DB";
      uses wireless-access-point-oper:qos-ap-radio-data;
      uses wireless-access-point-oper:qos-ap-radio-key;
    }
    container qos-global-stats {
      presence "qos-global-stats";
      description
        "This object specify a table for QoS Global statistics data in DB";
      uses wireless-access-point-oper:qos-global-statistics;
    }
    list oper-data {
      key "wtp-mac";
      description
        "Operational data corresponding to an
         802.11 LWAPP AP";
      uses wireless-access-point-oper:st-ap-oper-data;
    }
    list rlan-oper {
      key "wtp-mac rlan-port-id";
      description
        "LAN information of the AP";
      uses wireless-access-point-oper:ewlc-rlan-oper-config-entry;
      uses wireless-access-point-oper:ewlc-rlan-key;
    }
    list cdp-cache-data {
      key "mac-addr cdp-cache-device-id";
      description
        "contains the cached neighbor information obtained via receiving CDP messages on APs. Entries are added when a CDP advertisement is received from a neighboring device. Entries get deleted when CDP is disabled on the interface or globally";
      uses wireless-access-point-oper:cdp-cache-data-op;
      uses wireless-access-point-oper:ewlc-cdp-cache-data-key;
      uses wireless-access-point-oper:cdp-cache-data-index-key;
    }
  }
}
