module Cisco-IOS-XE-wireless-access-point-cfg-rpc {
  yang-version 1;
  namespace "http://cisco.com/ns/yang/Cisco-IOS-XE-wireless-access-point-cfg-rpc";
  prefix wireless-access-point-cfg-rpc;

  import Cisco-IOS-XE-wireless-enum-types {
    prefix wireless-enum-types;
  }
  import Cisco-IOS-XE-wireless-types {
    prefix wireless-types;
  }
  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Copyright (c) 2019-2020 by Cisco Systems, Inc.
     All rights reserved.";

  revision 2020-03-01 {
    description
      "Initial revision";
    reference "1.0.0";
    cisco-semver:module-version "1.0.0";
  }

  typedef ap-identifier {
    type enumeration {
      enum "ap-identifier-name" {
        value 0;
        description
          "Alternative AP name";
      }
      enum "ap-identifier-mac-address" {
        value 1;
        description
          "Alternative MAC address";
      }
    }
    description
      "Access point identifier";
  }

  grouping set-ap-vlan-tag {
    description
      "Configures VLAN tagging for non-bridge AP";
    leaf vlan-id {
      type uint32;
      mandatory true;
      description
        "Configure VLAN-ID";
    }
    choice alternative-choice {
      mandatory true;
      description
        "AP name or AP MAC address";
      case ap-identifier-name {
        leaf ap-name {
          type string;
          mandatory true;
          description
            "AP name for VLAN tagging";
        }
      }
      case ap-identifier-mac-address {
        leaf mac-addr {
          type yang:mac-address;
          mandatory true;
          description
            "MAC address of AP for VLAN tagging";
        }
      }
    }
  }

  grouping set-ap-monitor-mode-chnl-optimize {
    description
      "Channel scanning optimization for AP";
    leaf mode {
      type wireless-enum-types:lomm-mode-type;
      mandatory true;
      description
        "Select AP mode (none, tracking mode, WIPS mode, all)";
    }
    choice alternative-choice {
      mandatory true;
      description
        "AP name or AP MAC address";
      case ap-identifier-name {
        leaf ap-name {
          type string;
          mandatory true;
          description
            "AP name for channel scanning optimization";
        }
      }
      case ap-identifier-mac-address {
        leaf mac-addr {
          type yang:mac-address;
          mandatory true;
          description
            "MAC address of AP for channel scanning optimization";
        }
      }
    }
  }

  grouping set-lrad-led-state {
    description
      "Configure LED state for Cisco AP";
    leaf ledstate {
      type boolean;
      mandatory true;
      description
        "Led state of AP can be enabled (true) or disabled (false)";
    }
    choice alternative-choice {
      mandatory true;
      description
        "AP name or AP MAC address";
      case ap-identifier-name {
        leaf ap-name {
          type string;
          mandatory true;
          description
            "Name of AP to configure LED state";
        }
      }
      case ap-identifier-mac-address {
        leaf mac-addr {
          type yang:mac-address;
          mandatory true;
          description
            "MAC address of AP to configure LED state";
        }
      }
    }
  }

  grouping set-ap-location {
    description
      "Configure AP location";
    leaf location {
      type string;
      mandatory true;
      description
        "AP location (example sector A or room A)";
    }
    choice alternative-choice {
      mandatory true;
      description
        "AP name or AP MAC address";
      case ap-identifier-name {
        leaf ap-name {
          type string;
          mandatory true;
          description
            "AP name for location change";
        }
      }
      case ap-identifier-mac-address {
        leaf mac-addr {
          type yang:mac-address;
          mandatory true;
          description
            "MAC address of AP for location change";
        }
      }
    }
  }

  grouping set-ap-name {
    description
      "Configure a new AP name";
    leaf name {
      type string {
        length "1..32";
        pattern "[a-zA-Z0-9_\\-]*";
      }
      mandatory true;
      description
        "New AP name";
    }
    choice alternative-choice {
      mandatory true;
      description
        "AP name or AP MAC address";
      case ap-identifier-name {
        leaf ap-name {
          type string;
          mandatory true;
          description
            "Existing name of AP to be renamed";
        }
      }
      case ap-identifier-mac-address {
        leaf mac-addr {
          type yang:mac-address;
          mandatory true;
          description
            "MAC address of AP to be renamed";
        }
      }
    }
  }

  grouping set-ap-antenna-band-mode {
    description
      "Configure antenna band mode";
    leaf band-val {
      type wireless-enum-types:ant-band-mode;
      mandatory true;
      description
        "Band value can be unknown, single or dual";
    }
    choice alternative-choice {
      mandatory true;
      description
        "AP name or AP MAC address";
      case ap-identifier-name {
        leaf ap-name {
          type string;
          mandatory true;
          description
            "Name of AP to configure the antenna band mode";
        }
      }
      case ap-identifier-mac-address {
        leaf mac-addr {
          type yang:mac-address;
          mandatory true;
          description
            "MAC address of AP to configure the antenna band mode";
        }
      }
    }
  }

  grouping set-ap-country {
    description
      "Configure the country of operation";
    leaf country-string {
      type string;
      mandatory true;
      description
        "Country code for country of operation (i.e. US for United States)";
    }
    choice alternative-choice {
      mandatory true;
      description
        "Alternative AP name and MAC address";
      case ap-identifier-name {
        leaf ap-name {
          type string;
          mandatory true;
          description
            "AP name for configuring country of operation";
        }
      }
      case ap-identifier-mac-address {
        leaf mac-addr {
          type yang:mac-address;
          mandatory true;
          description
            "MAC address of AP for configuring country of operation";
        }
      }
    }
  }

  grouping set-ap-slot-ext-antenna-gain {
    description
      "Configures the external antenna gain of AP";
    leaf external-antenna-gain {
      type uint8;
      units "dBm";
      mandatory true;
      description
        "External antenna gain value in multiple of .5 decibel isotropic units (i.e. An integer value 4 means 4 x 0.5 = 2 decibel isotropic units of gain)";
    }
    leaf slot-id {
      type uint8;
      mandatory true;
      description
        "Slot ID of AP to configure the external antenna gain";
    }
    choice alternative-choice {
      mandatory true;
      description
        "AP name or AP MAC address";
      case ap-identifier-name {
        leaf ap-name {
          type string;
          mandatory true;
          description
            "Name of AP to configure the external antenna gain";
        }
      }
      case ap-identifier-mac-address {
        leaf mac-addr {
          type yang:mac-address;
          mandatory true;
          description
            "MAC address of AP to configure the external antenna gain";
        }
      }
    }
  }

  grouping dual-band-radio-band {
    description
      "Configures the 802.11 dual-band radio's current band i.e 2.4GHz/5GHz";
    leaf slot-id {
      type uint8;
      mandatory true;
      description
        "Slot ID of AP to configure the 802.11 dual-band radio's current band";
    }
    leaf band {
      type uint32;
      mandatory true;
      description
        "Current band of AP";
    }
    leaf toband {
      type uint32;
      mandatory true;
      description
        "New band to switch AP to from current band";
    }
    choice alternative-choice {
      mandatory true;
      description
        "AP name or AP MAC address";
      case ap-identifier-name {
        leaf ap-name {
          type string;
          mandatory true;
          description
            "Name of AP to configure the 802.11 dual-band radio's current band";
        }
      }
      case ap-identifier-mac-address {
        leaf mac-addr {
          type yang:mac-address;
          mandatory true;
          description
            "MAC address of AP to configure the 802.11 dual-band radio's current band";
        }
      }
    }
  }

  grouping set-ap-led-brightness-level {
    description
      "Configure the LED brightness level";
    leaf led-brightness-level {
      type uint8;
      mandatory true;
      description
        "LED brightness level (1..8)";
    }
    choice alternative-choice {
      mandatory true;
      description
        "AP name or AP MAC address";
      case ap-identifier-name {
        leaf ap-name {
          type string;
          mandatory true;
          description
            "Name of AP to configure the led brightness level";
        }
      }
      case ap-identifier-mac-address {
        leaf mac-addr {
          type yang:mac-address;
          mandatory true;
          description
            "MAC address of AP to configure the led brightness level";
        }
      }
    }
  }

  grouping set-ap-slot-tx-power-level {
    description
      "Modify transmit power level of an AP slot (band)";
    leaf tx-power-level {
      type uint8 {
        range "1 .. 8";
      }
      units "dBm";
      mandatory true;
      description
        "Transmit power level (1..8)";
    }
    leaf slot-id {
      type uint8;
      mandatory true;
      description
        "Slot ID of AP to configure transmit power level";
    }
    leaf band {
      type uint32;
      mandatory true;
      description
        "Band of AP to configure transmit power level";
    }
    choice alternative-choice {
      mandatory true;
      description
        "Alternative choice AP name and MAC address";
      case ap-identifier-name {
        leaf ap-name {
          type string;
          mandatory true;
          description
            "AP name for configuring transmit power level";
        }
      }
      case ap-identifier-mac-address {
        leaf mac-addr {
          type yang:mac-address;
          mandatory true;
          description
            "MAC address of AP for configuring transmit power level";
        }
      }
    }
  }

  grouping set-ap-slot-antenna-mode {
    description
      "Configures the antenna mode of the AP";
    leaf antenna-mode {
      type wireless-enum-types:enm-antenna-mode;
      mandatory true;
      description
        "Supported antenna mode";
    }
    leaf slot-id {
      type uint8;
      mandatory true;
      description
        "Slot ID of AP to configure the antenna mode";
    }
    choice alternative-choice {
      mandatory true;
      description
        "AP name or AP MAC address";
      case ap-identifier-name {
        leaf ap-name {
          type string;
          mandatory true;
          description
            "Name of AP to configure the antenna mode";
        }
      }
      case ap-identifier-mac-address {
        leaf mac-addr {
          type yang:mac-address;
          mandatory true;
          description
            "MAC address of AP to configure the antenna mode";
        }
      }
    }
  }

  grouping set-ap-admin-state {
    description
      "Disable/Enable AP admin state";
    leaf mode {
      type wireless-enum-types:enm-admin-status;
      mandatory true;
      description
        "Mode for AP admin state";
    }
    choice alternative-choice {
      mandatory true;
      description
        "AP name or AP MAC address";
      case ap-identifier-name {
        leaf ap-name {
          type string;
          mandatory true;
          description
            "AP name for changing AP admin state";
        }
      }
      case ap-identifier-mac-address {
        leaf mac-addr {
          type yang:mac-address;
          mandatory true;
          description
            "MAC address of AP for changing AP admin state";
        }
      }
    }
  }

  grouping set-ap-slot-admin-state {
    description
      "Configure admin state of AP slot";
    leaf mode {
      type wireless-enum-types:enm-admin-status;
      mandatory true;
      description
        "Mode of AP to configure admin state";
    }
    leaf slot-id {
      type uint8;
      mandatory true;
      description
        "Slot ID of AP to configure admin state";
    }
    leaf band {
      type uint32;
      mandatory true;
      description
        "Band of AP to configure admin state";
    }
    choice alternative-choice {
      mandatory true;
      description
        "AP name or AP MAC address";
      case ap-identifier-name {
        leaf ap-name {
          type string;
          mandatory true;
          description
            "Name of AP to configure admin state";
        }
      }
      case ap-identifier-mac-address {
        leaf mac-addr {
          type yang:mac-address;
          mandatory true;
          description
            "MAC address of AP to configure admin state";
        }
      }
    }
  }

  grouping set-ap-slot-tx-power-customize {
    description
      "Enables auto RF on a slot";
    leaf mode {
      type wireless-types:w-config-type;
      mandatory true;
      description
        "Select mode as CONFIG AUTO to configure transmit power of AP";
    }
    leaf slot-id {
      type uint8;
      mandatory true;
      description
        "Slot ID to configure transmit power of AP";
    }
    leaf band {
      type uint32;
      mandatory true;
      description
        "Band to configure transmit power of AP";
    }
    choice alternative-choice {
      mandatory true;
      description
        "AP name or AP MAC address";
      case ap-identifier-name {
        leaf ap-name {
          type string;
          mandatory true;
          description
            "Name of AP to configure transmit power of AP";
        }
      }
      case ap-identifier-mac-address {
        leaf mac-addr {
          type yang:mac-address;
          mandatory true;
          description
            "MAC address of AP to configure transmit power of AP";
        }
      }
    }
  }

  rpc set-ap-vlan-tag {
    description
      "Configure VLAN tagging for non-bridge AP";
    input {
      uses wireless-access-point-cfg-rpc:set-ap-vlan-tag;
    }
  }
  rpc set-ap-monitor-mode-chnl-optimize {
    description
      "Configure channel scanning optimization for AP";
    input {
      uses wireless-access-point-cfg-rpc:set-ap-monitor-mode-chnl-optimize;
    }
  }
  rpc set-lrad-led-state {
    description
      "Set LED-state for Cisco AP";
    input {
      uses wireless-access-point-cfg-rpc:set-lrad-led-state;
    }
  }
  rpc set-ap-location {
    description
      "Configure AP location";
    input {
      uses wireless-access-point-cfg-rpc:set-ap-location;
    }
  }
  rpc set-ap-name {
    description
      "Configure AP name";
    input {
      uses wireless-access-point-cfg-rpc:set-ap-name;
    }
  }
  rpc set-ap-antenna-band-mode {
    description
      "Configure antenna band mode";
    input {
      uses wireless-access-point-cfg-rpc:set-ap-antenna-band-mode;
    }
  }
  rpc set-ap-country {
    description
      "Configure the country of operation";
    input {
      uses wireless-access-point-cfg-rpc:set-ap-country;
    }
  }
  rpc set-ap-slot-ext-antenna-gain {
    description
      "Configures the external antenna gain of AP";
    input {
      uses wireless-access-point-cfg-rpc:set-ap-slot-ext-antenna-gain;
    }
  }
  rpc dual-band-radio-band {
    description
      "Configures the 802.11 dual-band radio's current band i.e 2.4GHz/5GHz";
    input {
      uses wireless-access-point-cfg-rpc:dual-band-radio-band;
    }
  }
  rpc set-ap-led-brightness-level {
    description
      "Configure the led brightness level";
    input {
      uses wireless-access-point-cfg-rpc:set-ap-led-brightness-level;
    }
  }
  rpc set-ap-slot-tx-power-level {
    description
      "Modify slot transmit power level";
    input {
      uses wireless-access-point-cfg-rpc:set-ap-slot-tx-power-level;
    }
  }
  rpc set-ap-slot-antenna-mode {
    description
      "Configures the 802.11a antenna mode";
    input {
      uses wireless-access-point-cfg-rpc:set-ap-slot-antenna-mode;
    }
  }
  rpc set-ap-admin-state {
    description
      "Enable/Disable AP admin state";
    input {
      uses wireless-access-point-cfg-rpc:set-ap-admin-state;
    }
  }
  rpc set-ap-slot-admin-state {
    description
      "Configure slot admin state";
    input {
      uses wireless-access-point-cfg-rpc:set-ap-slot-admin-state;
    }
  }
  rpc set-ap-slot-tx-power-customize {
    description
      "Enable auto RF on a slot";
    input {
      uses wireless-access-point-cfg-rpc:set-ap-slot-tx-power-customize;
    }
  }
}
