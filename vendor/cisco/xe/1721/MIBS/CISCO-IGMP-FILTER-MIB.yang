/*
 * Generated by confdc --mib2yang-std
 * Source: mgmt/dmi/model/mib/src/patched/CISCO-IGMP-FILTER-MIB.mib
 */
/*
 * This YANG module has been generated by smidump 0.5.0:
 *
 *      smidump -f yang CISCO-IGMP-FILTER-MIB
 *
 * Do not edit. Edit the source file instead!
 */

module CISCO-IGMP-FILTER-MIB {

  namespace "urn:ietf:params:xml:ns:yang:smiv2:CISCO-IGMP-FILTER-MIB";
  prefix CISCO-IGMP-FILTER-MIB;

  import IF-MIB {
    prefix "if-mib";
  }

  import INET-ADDRESS-MIB {
    prefix "inet-address";
  }

  import SNMPv2-TC {
    prefix "snmpv2-tc";
  }

  import ietf-yang-smiv2 {
    prefix "smiv2";
  }

  organization
   "Cisco Systems, Inc";

  contact
   "Cisco Systems
    Customer Service
    
    Postal: 170 W Tasman Drive
    San Jose, CA 95134
    USA
    
    Tel: +1 800 553-NETS
    
    Email: cs-ipmulticast@cisco.com";

  description
   "IGMP Filter configuration MIB. This MIB provides a
    mechanism for users to configure the system to intercept 
    IGMP joins for IP Multicast groups identified in this 
    MIB and only allow certain ports to join certain 
    multicast groups.";

  revision 2005-11-29 {
    description
     "Deprecated ciscoIgmpFilterGolbalMIBCompliance
      and added ciscoIgmpFilterGlobalMIBComplianceRev1
      to include ciscoIgmpFilterGlobalGroup under
      MANDATORY-GROUPS; Updated the imports such that
      Unsigned32 is imported from SNMPv2-SMI instead
      of CISCO-TC, and other clean up.";
  }

  revision 2002-05-09 {
    description
     "Corrected typos existing in the MIB.";
  }

  revision 2001-11-08 {
    description
     "Initial version of this MIB module";
  }


  container CISCO-IGMP-FILTER-MIB {
    config false;

    container cIgmpFilterGeneral {
      smiv2:oid "1.3.6.1.4.1.9.9.238.1.1";

      leaf cIgmpFilterEnable {
        type boolean;
        description
         "This object controls whether the IGMP filtering
          is enabled on the device. A false(2) value will 
          prevent the IGMP filtering action on the device.";
        smiv2:defval "false";
        smiv2:max-access "read-write";
        smiv2:oid "1.3.6.1.4.1.9.9.238.1.1.1";
      }

      leaf cIgmpFilterMaxProfiles {
        type uint32;
        units "profiles";
        description
         "Indicates the maximum number of profiles supported by
          this device.  A value of zero indicates no limitation on
          the number of profiles.";
        smiv2:max-access "read-only";
        smiv2:oid "1.3.6.1.4.1.9.9.238.1.1.2";
      }
    }

    container cIgmpFilterEditor {
      smiv2:oid "1.3.6.1.4.1.9.9.238.1.3";

      leaf cIgmpFilterEditSpinLock {
        type snmpv2-tc:TestAndIncr;
        description
         "This object is used to facilitate modification of
          IGMP Filter Editor Group in the CISCO-IGMP-FILTER-MIB 
          module by multiple managers.  In particular, it is 
          useful when modifying the value of the cIgmpFilterEditor 
          object. 
          
          The procedure for modifying the cIgmpFilterEditor 
          object is as follows: 
          
              1.  Retrieve the value of cIgmpFilterEditSpinLock and 
                  of object within cIgmpFilterEditor group. 
          
              2.  Generate new values for 'writeable' objects
                  in the cIgmpFilterEditor group except for 
                  cIgmpFilterEditSpinLock object.
          
              3.  Set the value of cIgmpFilterEditSpinLock to the 
                  retrieved value, and the value of objects in 
                  cIgmpFilterEditor to the new value. If the set
                  fails for the cIgmpFilterEditSpinLock object,
                  go back to step 1. 
          
          The cIgmpFilterApplyStatus and cIgmpFilterEditSpinLock 
          should be read together by NMS to make sure that the 
          result is associated with its configuration request.
          
          To add/delete or modify a profile ( through cIgmpFilterEditor
          objects ) following procedure may be followed as an example.:
          
              1.  GET(cIgmpFilterEditSpinLock.0) and save in sValue.
              2.  SET(cIgmpFilterEditSpinLock.0 = sValue,
                      cIgmpFilterEditProfileIndex.0 = validProfileNumber,
                      cIgmpFilterEditStartAddress.0 = validStartAddress,
                      cIgmpFilterEditEndAddress.0 = validEndAddress,
                      cIgmpFilterEditOperation.0 =  validOperation)
              3.  If the SET in step 2 is not successful go back
                  to step 1.
              4.  If the SET in step 2 is successful, user should 
                  GET(cIgmpFilterEditSpinLock.0) and 
                  GET(cIgmpFilterApplyStatus.0) simultaneously.
          
              5.  The cIgmpFilterApplyStatus.0 reflects the outcome of
                  step 2 only if
                  cIgmpFilterEditSpinLock.0 = sValue + 1 or
                  cIgmpFilterEditSpinLock.0 = 0 if sValue reaches
                  value at which cIgmpFilterEditSpinLock wraps 
                  around.";
        smiv2:max-access "read-write";
        smiv2:oid "1.3.6.1.4.1.9.9.238.1.3.1";
      }

      leaf cIgmpFilterEditProfileIndex {
        type uint32;
        description
         "Buffer object to edit corresponding object
          cIgmpFilterProfileIndex in cIgmpFilterTable.
          
          Maximum value this object can be set to is 
          determined by cIgmpFilterMaxProfiles object.";
        smiv2:max-access "read-write";
        smiv2:oid "1.3.6.1.4.1.9.9.238.1.3.2";
      }

      leaf cIgmpFilterEditStartAddressType {
        type inet-address:InetAddressType;
        description
         "Buffer object to edit corresponding object
          cIgmpFilterStartAddressType in cIgmpFilterTable.
          
          This object describes the type of Internet  
          address used to determine the start address 
          of IP multicast group for a profile.";
        smiv2:max-access "read-write";
        smiv2:oid "1.3.6.1.4.1.9.9.238.1.3.3";
      }

      leaf cIgmpFilterEditStartAddress {
        type inet-address:InetAddress {
          length "1..64";
        }
        description
         "Buffer object to edit corresponding object
          cIgmpFilterStartAddress in cIgmpFilterTable
            to establish start address of filtering
          range for a profile.";
        smiv2:max-access "read-write";
        smiv2:oid "1.3.6.1.4.1.9.9.238.1.3.4";
      }

      leaf cIgmpFilterEditEndAddressType {
        type inet-address:InetAddressType;
        description
         "Buffer object to edit corresponding object
          cIgmpFilterEndAddressType in cIgmpFilterTable.
          
          This object describes the type of Internet     
          address used to determine the start address 
          of IP multicast group for a profile.";
        smiv2:max-access "read-write";
        smiv2:oid "1.3.6.1.4.1.9.9.238.1.3.5";
      }

      leaf cIgmpFilterEditEndAddress {
        type inet-address:InetAddress;
        description
         "Buffer object to edit corresponding object
          cIgmpFilterEndAddress in cIgmpFilterTable 
          to establish end address of filtering 
          range for a profile.";
        smiv2:max-access "read-write";
        smiv2:oid "1.3.6.1.4.1.9.9.238.1.3.6";
      }

      leaf cIgmpFilterEditProfileAction {
        type enumeration {
          enum "unSpecified" {
            value "0";
          }
          enum "permit" {
            value "1";
          }
          enum "deny" {
            value "2";
          }
        }
        description
         "Buffer object to edit corresponding object in
          cIgmpFilterTable to determine filtering action
          of each profile.";
        smiv2:defval "deny";
        smiv2:max-access "read-write";
        smiv2:oid "1.3.6.1.4.1.9.9.238.1.3.7";
      }

      leaf cIgmpFilterEditOperation {
        type enumeration {
          enum "none" {
            value "1";
          }
          enum "add" {
            value "2";
          }
          enum "delete" {
            value "3";
          }
          enum "modify" {
            value "4";
          }
        }
        description
         "The function of this object is to allow user to
          apply the changes in cIgmpFilterEditor objects to 
          cIgmpFilterTable. 
          
          This object always has the value 'none' when read.
          When written each value causes the appropriate action:
          
          'add' - tries to insert the information contained 
          in cIgmpFilterEditor objects into  cIgmpFilterTable.
          If the entry already exists in the table the 'add' 
          fails.        
          
          'delete' - tries to delete corresponding entry from
          cIgmpFilterTable. If a user completely deletes a profile
          that has corresponding entries in the
          cIgmpFilterInterfaceTable, then all the interfaces mapped
          to corresponding profile will be cleared and set to zero.
          
          'modify' - Mode of operation used to edit an entry in
           cIgmpFilterTable. If the corresponding entry does not 
           exist, modify operation fails. This mode allows user to
           extend/truncate a contiguous filtered range, type of
           Internet addressing and filtering action for a profile. 
          
          'none' - no operation is performed.";
        smiv2:max-access "read-write";
        smiv2:oid "1.3.6.1.4.1.9.9.238.1.3.8";
      }

      leaf cIgmpFilterApplyStatus {
        type enumeration {
          enum "someOtherError" {
            value "1";
          }
          enum "succeeded" {
            value "2";
          }
          enum "inconsistentEdit" {
            value "3";
          }
          enum "entryPresentError" {
            value "4";
          }
          enum "entryNotPresentError" {
            value "5";
          }
        }
        description
         "The current status of an 'add', 'delete' or 'modify'
          operation. If no apply is currently active, the status 
          represented is that of the most recently completed 'add', 
          'delete' or 'modify' operation.
          
          The value of this objects indicates succeeded(2) state 
          initially when no 'add', 'delete', 'modify' operation
          has been carried out.
          
          The possible values are:
             someOtherError - the 'add', 'delete' or 'modify' failed 
             due to undefined error(s) in apply operation.
             (e.g., insufficient memory). 
          
             succeeded - the 'add', 'delete' or 'modify' operation
             was successful. (This value is also used when no
             apply has been invoked since the last time the local 
             system restarted.)
          
             inconsistentEdit - the 'add', 'delete' or 'modify' failed
             due to inconsistency of the data.
          
             entryPresentError - the 'add' operation failed  as the 
             corresponding entry already exists in cIgmpFilterTable.
          
             entryNotPresentError - the 'modify' operation failed 
             as no corresponding entry exists in cIgmpFilterTable.";
        smiv2:max-access "read-only";
        smiv2:oid "1.3.6.1.4.1.9.9.238.1.3.9";
      }
    }

    container cIgmpFilterTable {
      description
       "This table contains entries that identify lists of
        IP Multicast groups for each profile configured on
        the device. 
        
        Each entry contains a range of contiguous IP
        Multicast groups associated to a profile index.
        Multiple cIgmpFilterEntry may be associated
        with the same cIgmpFilterProfileIndex.
        
        All the cIgmpFilterEntry with  the same profile index 
        are subjected to the same IGMP filtering action as 
        defined in cIgmpFilterProfileAction.
        
        Each profile index may be associated with zero or more 
        interfaces through cIgmpFilterInterfaceIfIndex
        object in cIgmpFilterInterfaceTable.
        The maximum number of entries is determined by
        cIgmpFilterMaxProfiles.";
      smiv2:oid "1.3.6.1.4.1.9.9.238.1.2.1";

      list cIgmpFilterEntry {
        key "cIgmpFilterProfileIndex cIgmpFilterStartAddressType cIgmpFilterStartAddress";
        description
         "An entry (conceptual row) in the cIgmpFilterTable.
          
          The creation, deletion or modification of an entry
          is controlled through the MIB objects defined under
          cIgmpFilterEditor group.";
        smiv2:oid "1.3.6.1.4.1.9.9.238.1.2.1.1";

        leaf cIgmpFilterProfileIndex {
          type uint32;
          description
           "Index identifying this entry.";
          smiv2:max-access "not-accessible";
          smiv2:oid "1.3.6.1.4.1.9.9.238.1.2.1.1.1";
        }

        leaf cIgmpFilterStartAddressType {
          type inet-address:InetAddressType;
          description
           "This object describes the type of Internet
            address used to determine the start address 
            of IP multicast group for a profile.";
          smiv2:max-access "not-accessible";
          smiv2:oid "1.3.6.1.4.1.9.9.238.1.2.1.1.2";
        }

        leaf cIgmpFilterStartAddress {
          type inet-address:InetAddress {
            length "1..64";
          }
          description
           "This object describes the start of the IP multicast
            group address of a contiguous range which will be
            subjected to filtering operation.";
          smiv2:max-access "not-accessible";
          smiv2:oid "1.3.6.1.4.1.9.9.238.1.2.1.1.3";
        }

        leaf cIgmpFilterEndAddressType {
          type inet-address:InetAddressType;
          description
           "This object indicates the type of Internet
            address used to determine the end address 
            of IP multicast group for a profile.";
          smiv2:max-access "read-only";
          smiv2:oid "1.3.6.1.4.1.9.9.238.1.2.1.1.4";
        }

        leaf cIgmpFilterEndAddress {
          type inet-address:InetAddress;
          description
           "This object indicates the end of the IP multicast
            group address of a contiguous range which will be 
            subjected to filtering operation.";
          smiv2:max-access "read-only";
          smiv2:oid "1.3.6.1.4.1.9.9.238.1.2.1.1.5";
        }

        leaf cIgmpFilterProfileAction {
          type enumeration {
            enum "permit" {
              value "1";
            }
            enum "deny" {
              value "2";
            }
          }
          description
           "This object defines the action for
            filtering IGMP reports for this profile.
            
            If the object is set to deny(2):
            then all IGMP reports associated to IP multicast
            groups included in the profile identified by
            cIgmpFilterInterfaceProfileIndex will be dropped.
            
            If the object is set to permit(1):
            then all IGMP reports associated to IP multicast
            groups not included in the profile identified by
            cIgmpFilterInterfaceProfileIndex will be dropped.";
          smiv2:max-access "read-only";
          smiv2:oid "1.3.6.1.4.1.9.9.238.1.2.1.1.6";
        }
      }
    }

    container cIgmpFilterInterfaceTable {
      description
       "This table contains the list of interfaces that can
        support IGMP filter feature.";
      smiv2:oid "1.3.6.1.4.1.9.9.238.1.2.2";

      list cIgmpFilterInterfaceEntry {
        key "ifIndex";
        description
         "Each entry contains the configuration for associating
          the IGMP filter profile index with the interface.
          
          An entry is created for each of the IGMP filter capable 
          interface on the system.
          
          The entry is removed on removal of corresponding 
          interface from system.";
        smiv2:oid "1.3.6.1.4.1.9.9.238.1.2.2.1";

        leaf ifIndex {
          type leafref {
            path "/if-mib:IF-MIB/if-mib:ifTable/if-mib:ifEntry/if-mib:ifIndex";
          }
        }

        leaf cIgmpFilterInterfaceProfileIndex {
          type uint32;
          description
           "Specifies which IGMP filter profile applies to this
            interface. If the value of this MIB object matches the 
            value of cIgmpFilterProfileIndex in cIgmpFilterTable, 
            the corresponding profile configuration will apply to
            this interface. 
            
            Agent returns inconsistentValue if this profile 
            does not exist in cIgmpFilterTable. 
            A value of zero indicates no profile is associated
            with corresponding interface.
            
            The filtering action on each interface is also
            defined by the associated profile.";
          smiv2:defval "0";
          smiv2:max-access "read-write";
          smiv2:oid "1.3.6.1.4.1.9.9.238.1.2.2.1.1";
        }
      }
    }
  }

  smiv2:alias "ciscoIGMPFilterMIB" {
    smiv2:oid "1.3.6.1.4.1.9.9.238";
  }

  smiv2:alias "ciscoIgmpFilterMIBObjects" {
    smiv2:oid "1.3.6.1.4.1.9.9.238.1";
  }

  smiv2:alias "cIgmpFilterGeneral" {
    smiv2:oid "1.3.6.1.4.1.9.9.238.1.1";
  }

  smiv2:alias "cIgmpFilterInfo" {
    smiv2:oid "1.3.6.1.4.1.9.9.238.1.2";
  }

  smiv2:alias "cIgmpFilterEditor" {
    smiv2:oid "1.3.6.1.4.1.9.9.238.1.3";
  }

  smiv2:alias "ciscoIgmpFilterMIBConformance" {
    smiv2:oid "1.3.6.1.4.1.9.9.238.2";
  }

  smiv2:alias "ciscoIgmpFilterMIBCompliances" {
    smiv2:oid "1.3.6.1.4.1.9.9.238.2.1";
  }

  smiv2:alias "ciscoIgmpFilterMIBGroups" {
    smiv2:oid "1.3.6.1.4.1.9.9.238.2.2";
  }

}
