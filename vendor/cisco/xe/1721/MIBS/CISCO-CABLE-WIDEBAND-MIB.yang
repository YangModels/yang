/*
 * Generated by confdc --mib2yang-std
 * Source: mgmt/dmi/model/mib/src/patched/CISCO-CABLE-WIDEBAND-MIB.mib
 */
/*
 * This YANG module has been generated by smidump 0.5.0:
 *
 *      smidump -f yang CISCO-CABLE-WIDEBAND-MIB
 *
 * Do not edit. Edit the source file instead!
 */

module CISCO-CABLE-WIDEBAND-MIB {

  namespace "urn:ietf:params:xml:ns:yang:smiv2:CISCO-CABLE-WIDEBAND-MIB";
  prefix CISCO-CABLE-WIDEBAND-MIB;

  import DOCS-IF-MIB {
    prefix "docs-if";
  }

  import ENTITY-MIB {
    prefix "entity-mib";
  }

  import IF-MIB {
    prefix "if-mib";
  }

  import INET-ADDRESS-MIB {
    prefix "inet-address";
  }

  import SNMP-FRAMEWORK-MIB {
    prefix "snmp-framework";
  }

  import SNMPv2-TC {
    prefix "snmpv2-tc";
  }

  import ietf-inet-types {
    prefix "inet";
  }

  import ietf-yang-smiv2 {
    prefix "smiv2";
  }

  import ietf-yang-types {
    prefix "yang";
  }

  organization
   "Cisco Systems, Inc.";

  contact
   "Cisco Systems
    Customer Service
    
    Postal: Cisco Systems
    170 West Tasman Drive
    San Jose, CA 95134
    U.S.A.
    Phone:  +1 800 553-NETS
    E-mail: cs-ubr@cisco.com";

  description
   "This is the MIB module for the support of Channel Bonding
    Protocol for the Cable Modem Termination System (CMTS).
    
    Wideband DOCSIS is a method of increasing downstream
    bandwidth by simultaneously transmitting DOCSIS data
    over multiple RF channels. This DOCSIS data is
    organized as a sequence of 188-byte MPEG-TS data packets.
    
    A Wideband CMTS (WCMTS) is a CMTS that also transmits
    Wideband MPEG-TS packets.
    
    An Edge QAM (Quadrature Amplitude Modulation) device is one
    which provides the QAM and used to couple the Wideband MPEG-TS
    packet onto the HFC plant.
    
    A Wideband Cable Modem (WCM) is a CableModem (CM) that
    is able to receive Wideband MPEG-TS packets.
    
    A wideband channel or Bonded Group (BG) is a logical
    grouping of one or more physical RF channels over which
    MPEG-TS packets are carried. Wideband channel carries DOCSIS
    bonded packets encapsulated in MPEG-TS packets from a
    WCMTS to one or more WCMs.
    
    Packets outgoing from WCMTS to the WCM are formatted with
    the DOCSIS Header. The DOCSIS packets are then formatted into
    MPEG-TS data packets. These are 188 byte MPEG packets
    containing the DOCSIS information.
    Within DOCSIS Header of the WB Channel there is an extended
    header called, DOCSIS Bonding Extended Header, the format of
    which is shown below:
    
     --------------------------------------------------------
    |  ----------------------------------------------------  |
    | |  TYPE | LEN |       BSID           |      SEQ        |
    |  ----------------------------------------------------  |
    | |    byte 0   |     byte 1-2         |    byte 3-4     |
    |--------------------------------------------------------|
                  DOCSIS Bonding Extended Header
    
    BSID is the Bonding Service IDentifier, it defines a sequence
    number for a Wideband channel. It is used by the WCM to
    re-sequence packets received over downstream channels to
    maintain packet order. SEQ is per service flow sequence number.
    Whereas TYPE is the type of the Bonding Extended Header and LEN
    specifies its length.
    
    A Narrowband Channel is a standard DOCSIS downstream channel
    which contains exactly one RF channel.
    The wideband protocol utilizes the existing narrowband
    downstream channel for carrying the MAC management and
    signaling messages and the associated narrowband upstream
    for return data traffic and signaling.
    
    The channel bonding protocol supports multiple wideband
    bonded groups. This will allow the WCM to listen to multiple
    bonded groups at the same time. This would support (for example)
    multicast video being sent to a CPE device on the LAN side of
    the WCM in addition to standard DOCSIS data.
    
    Channel Bonding allows two types of Bonding Group (BG) interfaces.
    These are Secondary BG interface and non-Secondary BG
    interface. The Secondary BG interfaces will carry the multicast
    traffic, whereas, the non-Secondary BG interface will carry the
    non-multicast traffic.
    This MIB also allows for configuration of the RF channels
    on the WCMTS, as well as the association between the RF and
    narrowband downstream channels with the BG channel.
    
    Fiber Node is an optical node which terminates the fiber based
    downstream signal as an electrical signal onto a coaxial RF cable.
    
    DEPI:  Downstream external physical interface. 
    TSID:  MPEG2 Transport Stream ID.
    SFP:   Small Form-Factor Pluggable.";

  revision 2011-01-05 {
    description
     "Added ccwbWidebandObjGroupSup2 and ccwbWidebandNotifGroup.";
  }

  revision 2010-07-15 {
    description
     "Added ccwbWidebandObjGroupRev1.
      Deprecated ccwbWidebandObjGroup.";
  }

  revision 2008-12-03 {
    description
     "Added ccwbRFChannelUtilization and ccwbRFChanUtilInterval.";
  }

  revision 2006-06-06 {
    description
     "Initial version of this MIB module.";
  }


  container CISCO-CABLE-WIDEBAND-MIB {
    config false;

    container ciscoCableWidebandMIBObjects {
      smiv2:oid "1.3.6.1.4.1.9.9.479.1";

      leaf ccwbRFChanUtilInterval {
        type uint32 {
          range "0..86400";
        }
        units "seconds";
        description
         "The time interval in seconds over which the RF channels
          utilization index is calculated. All RF channels use the
          same interval.
          
          Setting a value of zero disables utilization reporting.
          
          This value should be persisted accross CMTS
          reinitializations.";
        smiv2:defval "0";
        smiv2:max-access "read-write";
        smiv2:oid "1.3.6.1.4.1.9.9.479.1.10";
      }

      leaf ccwbSFPLinkTrapEnable {
        type int32 {
          range "0..1";
        }
        description
         "This object specifies whether ccwbSFPLinkDownNotification and
          ccwbSFPLinkUpNotification are generated.";
        smiv2:max-access "read-write";
        smiv2:oid "1.3.6.1.4.1.9.9.479.1.11";
      }
    }

    container ccwbRFChannelTable {
      description
       "This table contains attributes of the physical
        RF channels. MPEG-TS packets are sent across RF
        channels within a wideband channel.
        
        These physical RF channels might be present on a
        different system but the WCMTS entity requires
        the knowledge of that system for its operation.";
      smiv2:oid "1.3.6.1.4.1.9.9.479.1.1";

      list ccwbRFChannelEntry {
        key "entPhysicalIndex ccwbRFChannelNum";
        description
         "An entry provides a list of attributes for a single
          downstream RF channel per WCMTS entity.
          
          An entry in this table exists for each configured
          RF channel on the WCMTS entity that provides the
          wideband DOCSIS functionality. The index, entPhysicalIndex,
          used here is the physical index of the wideband controller
          card. Since RF channels are considered part of the Wideband
          controller card, hence entPhysicalIndex is used for
          associating RF channels.";
        smiv2:oid "1.3.6.1.4.1.9.9.479.1.1.1";

        leaf entPhysicalIndex {
          type leafref {
            path "/entity-mib:ENTITY-MIB/entity-mib:entPhysicalTable/entity-mib:entPhysicalEntry/entity-mib:entPhysicalIndex";
          }
        }

        leaf ccwbRFChannelNum {
          type uint32 {
            range "0..255";
          }
          description
           "The WCMTS identification of the RF channel.
            The range of this object is limited to 0-18 in the
            case of annex A/256qam, and 0-23 for Annex B and C.";
          smiv2:max-access "not-accessible";
          smiv2:oid "1.3.6.1.4.1.9.9.479.1.1.1.1";
        }

        leaf ccwbRFChannelFrequency {
          type uint32 {
            range "0..1000000000";
          }
          units "hertz";
          status deprecated;
          description
           "The center of the downstream frequency associated with
            this RF channel. The final downstream RF frequency
            may be provided by an edge QAM device or the CMTS itself.
            See the associated compliance object for a description of
            valid frequencies that may be written to this object.
            
            If the downstream frequency associated with this
            RF channel is greater than the maximum value reportable
            by this object then this object should report its
            maximum value (1,000,000,000) and ccwbRFChannelFrequencyRev1
            must be used to report the downstream frequency.
            
            This object is deprecated and replaced by
            ccwbRFChannelFrequencyRev1.";
          reference
           "DOCSIS-RFI-SPEC: SP-RFIv1.1-I05-000714, Tables 4-1, 6-14.";
          smiv2:max-access "read-write";
          smiv2:oid "1.3.6.1.4.1.9.9.479.1.1.1.2";
        }

        leaf ccwbRFChannelWidth {
          type uint32 {
            range "0..16000000";
          }
          units "hertz";
          description
           "The bandwidth of this downstream RF channel. Most
            implementations are expected to support a channel width
            of 6 MHz (North America) and/or 8 MHz (Europe).
            See the associated compliance object for a description of
            the valid channel widths for this object.";
          reference
           "DOCSIS-RFI-SPEC: SP-RFIv1.1-I05-000714, Table 6-14.";
          smiv2:max-access "read-write";
          smiv2:oid "1.3.6.1.4.1.9.9.479.1.1.1.3";
        }

        leaf ccwbRFChannelModulation {
          type enumeration {
            enum "unknownQam" {
              value "0";
            }
            enum "qam64" {
              value "1";
            }
            enum "qam256" {
              value "2";
            }
            enum "qam1024" {
              value "3";
            }
          }
          description
           "The modulation type associated with this downstream RF
            channel. See the associated conformance object for write
            conditions an limitations. See the DOCSIS specification
            for specifics on the modulation profiles implied by qam64
            qam256 and qam1024.
            qam64, qam256 and qam1024 are various modulation schemes
            often used in digital cable and cable modem applications.
            The numbers 64/256/1024 in qam represent constellation
            points, which is the measurement of qam transmission
            capability, the higher the number, higher the bits that
            can be transmitted.";
          reference
           "DOCSIS-RFI-SPEC: SP-RFIv1.1-I05-000714, Table 6-14.";
          smiv2:max-access "read-write";
          smiv2:oid "1.3.6.1.4.1.9.9.479.1.1.1.4";
        }

        leaf ccwbRFChannelAnnex {
          type enumeration {
            enum "unknownAnnex" {
              value "0";
            }
            enum "annexA" {
              value "1";
            }
            enum "annexB" {
              value "2";
            }
            enum "annexC" {
              value "3";
            }
          }
          description
           "The value of this object indicates the conformance of
            the implementation to important regional cable standards.
            annexA : Annex A from ITU-J83 is used.
            annexB : Annex B from ITU-J83 is used.
            annexC : Annex C from ITU-J83 is used.";
          reference
           "DOCSIS-RFI-SPEC: SP-RFIv1.1-I05-000714, Section 2.2.";
          smiv2:max-access "read-write";
          smiv2:oid "1.3.6.1.4.1.9.9.479.1.1.1.5";
        }

        leaf ccwbRFChannelMpegPkts {
          type yang:counter64;
          units "Packets";
          description
           "The number of MPEG packets transmitted on this RF
            channel.";
          smiv2:max-access "read-only";
          smiv2:oid "1.3.6.1.4.1.9.9.479.1.1.1.6";
        }

        leaf ccwbRFChannelStorageType {
          type snmpv2-tc:StorageType;
          description
           "The storage type for this conceptual row.";
          smiv2:defval "volatile";
          smiv2:max-access "read-write";
          smiv2:oid "1.3.6.1.4.1.9.9.479.1.1.1.7";
        }

        leaf ccwbRFChannelRowStatus {
          type snmpv2-tc:RowStatus;
          description
           "Controls and reflects the status of rows in this table.
            It can be used for creating and deleting
            entries in this table.
            
            The ccwbRFChannelAnnex and ccwbRFChannelModulation must
            be valid for a row to be created.";
          smiv2:max-access "read-write";
          smiv2:oid "1.3.6.1.4.1.9.9.479.1.1.1.8";
        }

        leaf ccwbRFChannelUtilization {
          type uint32 {
            range "0..100";
          }
          units "percent";
          description
           "The calculated and truncated utilization for
            this RF channel over the previous complete measuring
            interval. The configured duration of the measurement
            intervals is defined in the ccwbRFChanUtilInterval object.
            
            The utilization index is a percentage expressing the
            ratio between bytes used to transmit data versus the
            total number of bytes transmitted in the raw bandwidth
            of the RF channel.";
          smiv2:max-access "read-only";
          smiv2:oid "1.3.6.1.4.1.9.9.479.1.1.1.9";
        }

        leaf ccwbRFChannelFrequencyRev1 {
          type uint32 {
            range "0..1050000000";
          }
          units "hertz";
          description
           "The center of the downstream frequency associated with
            this RF channel. The final downstream RF frequency
            may be provided by an edge QAM device or the CMTS itself.
            See the associated compliance object for a description of
            valid frequencies that may be written to this object.";
          reference
           "DOCSIS-RFI-SPEC: SP-RFIv1.1-I05-000714, Tables 4-1, 6-14.";
          smiv2:max-access "read-write";
          smiv2:oid "1.3.6.1.4.1.9.9.479.1.1.1.10";
        }
      }
    }

    container ccwbWBtoRFMappingTable {
      description
       "A wideband channel is a logical grouping of one or more
        physical RF channels over which Wideband MPEG-TS packets
        are carried.
        
        This table contains association information of the wideband
        channels to the RF channels that are available for the WCMTS.";
      smiv2:oid "1.3.6.1.4.1.9.9.479.1.3";

      list ccwbWBtoRFMappingEntry {
        key "ifIndex entPhysicalIndex ccwbRFChannelNum";
        description
         "An entry provides a list of attributes for a single
          association between a wideband channel and a RF channel.
          
          An entry in this table exists for each association
          between a wideband channel and RF channel on the WCMTS.
          It is indexed by the ifIndex of the wideband channel
          and entPhysicalIndex and ccwbRFChannelNum which
          represents the RF channel.
          
          This object may be modified or deleted once they are
          already created.";
        smiv2:oid "1.3.6.1.4.1.9.9.479.1.3.1";

        leaf ifIndex {
          type leafref {
            path "/if-mib:IF-MIB/if-mib:ifTable/if-mib:ifEntry/if-mib:ifIndex";
          }
        }

        leaf entPhysicalIndex {
          type leafref {
            path "/entity-mib:ENTITY-MIB/entity-mib:entPhysicalTable/entity-mib:entPhysicalEntry/entity-mib:entPhysicalIndex";
          }
        }

        leaf ccwbRFChannelNum {
          type leafref {
            path "/CISCO-CABLE-WIDEBAND-MIB:CISCO-CABLE-WIDEBAND-MIB/CISCO-CABLE-WIDEBAND-MIB:ccwbRFChannelTable/CISCO-CABLE-WIDEBAND-MIB:ccwbRFChannelEntry/CISCO-CABLE-WIDEBAND-MIB:ccwbRFChannelNum";
          }
        }

        leaf ccwbWBtoRFBandwidth {
          type yang:gauge32 {
            range "1..100";
          }
          units "percent";
          description
           "The percentage of the RF channel bandwidth allocated
            for this wideband channel.";
          smiv2:defval "100";
          smiv2:max-access "read-write";
          smiv2:oid "1.3.6.1.4.1.9.9.479.1.3.1.1";
        }

        leaf ccwbWBtoRFStorageType {
          type snmpv2-tc:StorageType;
          description
           "The storage type for this conceptual row.";
          smiv2:defval "volatile";
          smiv2:max-access "read-write";
          smiv2:oid "1.3.6.1.4.1.9.9.479.1.3.1.2";
        }

        leaf ccwbWBtoRFRowStatus {
          type snmpv2-tc:RowStatus;
          description
           "Controls and reflects the status of rows in this table.
            It can be used for creating and deleting
            entries in this table.
            
            The ccwbWBtoRFBandwidth must be valid for a row to be
            created. When ccwbWBtoRFRowStatus is 'active', the object
            ccwbWBtoRFBandwidth can be modified.";
          smiv2:max-access "read-write";
          smiv2:oid "1.3.6.1.4.1.9.9.479.1.3.1.3";
        }
      }
    }

    container ccwbWBtoNBMappingTable {
      description
       "This table contains information of the mapping
        of the wideband channels to the Narrowband channels
        that are available on the WCMTS.
        
        The wideband protocol utilizes the existing narrowband
        downstream channel for carrying the MAC management and
        signaling messages and the associated narrowband upstream
        for return data traffic and signaling.";
      smiv2:oid "1.3.6.1.4.1.9.9.479.1.4";

      list ccwbWBtoNBMappingEntry {
        key "ifIndex ccwbWBtoNBifIndexForNB";
        description
         "An entry provides a list of attributes for a
          association between a wideband channel and a narrowband
          channel.
          
          An entry in this table exists for each association
          between a wideband channel and narrowband channel on the
          WCMTS. The valid ifType for the ifIndex used here is,
          ciscoDocsCableWBDownstream(224).";
        smiv2:oid "1.3.6.1.4.1.9.9.479.1.4.1";

        leaf ifIndex {
          type leafref {
            path "/if-mib:IF-MIB/if-mib:ifTable/if-mib:ifEntry/if-mib:ifIndex";
          }
        }

        leaf ccwbWBtoNBifIndexForNB {
          type if-mib:InterfaceIndex;
          description
           "The ifIndex of the narrowband cable interface
            associated with this wideband channel.";
          smiv2:max-access "not-accessible";
          smiv2:oid "1.3.6.1.4.1.9.9.479.1.4.1.1";
        }

        leaf ccwbWBtoNBStorageType {
          type snmpv2-tc:StorageType;
          description
           "The storage type for this conceptual row.";
          smiv2:defval "volatile";
          smiv2:max-access "read-write";
          smiv2:oid "1.3.6.1.4.1.9.9.479.1.4.1.2";
        }

        leaf ccwbWBtoNBRowStatus {
          type snmpv2-tc:RowStatus;
          description
           "Controls and reflects the status of rows in this table.
            It can be used for creating and deleting
            entries in this table. The object ccwbWBtoNBifIndexForNB
            must be valid in order for row to be created.";
          smiv2:max-access "read-write";
          smiv2:oid "1.3.6.1.4.1.9.9.479.1.4.1.3";
        }
      }
    }

    container ccwbWBBondGrpTable {
      description
       "This table provides information about a
        Wideband BG interface, whether its configured
        to carry multicast or non-multicast traffic.
        For multicast the BG interface type is
        Secondary and for non-multicast its non-Secondary.
        Other objects could be added to this later in
        the future.";
      smiv2:oid "1.3.6.1.4.1.9.9.479.1.5";

      list ccwbWBBondGrpEntry {
        key "ifIndex";
        description
         "An entry in this table provides information
          about each Wideband BG interface whose ifType is
          ciscoDocsCableWBDownstream(224).";
        smiv2:oid "1.3.6.1.4.1.9.9.479.1.5.1";

        leaf ifIndex {
          type leafref {
            path "/if-mib:IF-MIB/if-mib:ifTable/if-mib:ifEntry/if-mib:ifIndex";
          }
        }

        leaf ccwbWBBondGrpSecondary {
          type boolean;
          description
           "This object has the value 'true(1)' if the WB
            interface(BG) is Seconday and the value
            'false(2)' for non-Secondary.";
          smiv2:max-access "read-write";
          smiv2:oid "1.3.6.1.4.1.9.9.479.1.5.1.1";
        }
      }
    }

    container ccwbWBCmStatusTable {
      description
       "This table contains Wideband Cable Modem(WCM) connectivity state.
        A WCM connectivity state can be associated with multiple
        Wideband interfaces.";
      smiv2:oid "1.3.6.1.4.1.9.9.479.1.6";

      list ccwbWBCmStatusEntry {
        key "docsIfCmtsCmStatusIndex";
        description
         "Status information for a single Wideband Cable Modem.
          An entry in this table exists for each Wideband Cable Modem
          that is connected to the WCMTS.";
        smiv2:oid "1.3.6.1.4.1.9.9.479.1.6.1";

        leaf docsIfCmtsCmStatusIndex {
          type leafref {
            path "/docs-if:DOCS-IF-MIB/docs-if:docsIfCmtsCmStatusTable/docs-if:docsIfCmtsCmStatusEntry/docs-if:docsIfCmtsCmStatusIndex";
          }
        }

        leaf ccwbWBCmStatusValue {
          type enumeration {
            enum "offline" {
              value "1";
            }
            enum "others" {
              value "2";
            }
            enum "initRangingRcvd" {
              value "3";
            }
            enum "initDhcpReqRcvd" {
              value "4";
            }
            enum "onlineNetAccessDisabled" {
              value "5";
            }
            enum "onlineKekAssigned" {
              value "6";
            }
            enum "onlineTekAssigned" {
              value "7";
            }
            enum "rejectBadMic" {
              value "8";
            }
            enum "rejectBadCos" {
              value "9";
            }
            enum "kekRejected" {
              value "10";
            }
            enum "tekRejected" {
              value "11";
            }
            enum "online" {
              value "12";
            }
            enum "initTftpPacketRcvd" {
              value "13";
            }
            enum "initTodRequestRcvd" {
              value "14";
            }
            enum "reset" {
              value "15";
            }
            enum "rangingInProgress" {
              value "16";
            }
            enum "dhcpGotIpAddr" {
              value "17";
            }
            enum "rejStaleConfig" {
              value "18";
            }
            enum "rejIpSpoof" {
              value "19";
            }
            enum "rejClassFail" {
              value "20";
            }
            enum "rejRegNack" {
              value "21";
            }
            enum "bpiKekExpired" {
              value "22";
            }
            enum "bpiTekExpired" {
              value "23";
            }
            enum "shutdown" {
              value "24";
            }
            enum "channelChgInitRangingRcvd" {
              value "25";
            }
            enum "channelChgRangingInProgress" {
              value "26";
            }
            enum "wbOnline" {
              value "27";
            }
            enum "wbOnlinePrivacy" {
              value "28";
            }
            enum "wbOnlineKekAssigned" {
              value "29";
            }
            enum "wbOnlineTekAssigned" {
              value "30";
            }
            enum "wbOnlineNetAccessDis" {
              value "31";
            }
            enum "wbKekReject" {
              value "32";
            }
            enum "wbTekReject" {
              value "33";
            }
            enum "wbNetAccessDisReject" {
              value "34";
            }
            enum "wbPrivacyEnabReject" {
              value "35";
            }
            enum "wbKekExpire" {
              value "36";
            }
            enum "wbTekExpire" {
              value "37";
            }
            enum "wbNetAccessDisExpire" {
              value "38";
            }
            enum "wbPrivacyEnabExpire" {
              value "39";
            }
          }
          description
           "Current WB Cable Modem connectivity state, as specified
            in the RF Interface Specification. Returned status
            information is the WCM status as assumed by the WCMTS,
            and indicates the following events:
            
            The enumerations are:
            offline(1)                : modem considered offline.
            others(2)                 : states is in
                                        ccwbWBCmStatusValue.
            initRangingRcvd(3)        : modem sent initial ranging.
            initDhcpReqRcvd(4)        : dhcp request received.
            onlineNetAccessDisabled(5): modem registered, but network
                                        access for the WCM is disabled.
            onlineKekAssigned(6)      : modem registered, BPI enabled
                                        and KEK assigned.
            onlineTekAssigned(7)      : modem registered, BPI enabled
                                        and TEK assigned.
            rejectBadMic(8)           : modem did attempt to register
                                        but registration was refused
                                        due to bad mic.
            rejectBadCos(9)           : modem did attempt to register
                                        but registration was refused
                                        due to bad COS.
            kekRejected(10)           : KEK modem key assignment
                                        rejected.
            tekRejected(11)           : TEK modem key assignment
                                        rejected.
            online(12)                : modem registered, enabled for
                                        data.
            initTftpPacketRcvd(13)    : tftp packet received and option
                                        file transfer started.
            initTodRquestRcvd(14)     : Time of the Day (TOD) request
                                        received.
            reset(15)                 : modem is resetting.
            rangingInProgress(16)     : initial ranging is in progress.
            dhcpGotIpAddr(17)         : modem has got an IP address
            rejStaleConfig(18)        : modem did attempt to register
                                        but registration was refused
                                        due to stale Config.
            rejIpSpoof(19)            : modem did attempt to register
                                        but registration was refused
                                        due to IP Spoof.
            rejClassFail(20)          : modem did attempt to register
                                        but registration was refused
                                        due to Class failure.
            rejRegNack(21)            : modem did attempt to register
                                        but no acknowledgement was
                                        received.
            bpiKekExpired(22)         : KEK modem key assignment
                                        expired.
            bpiTekExpired(23)         : TEK modem key assignment
                                        expired.
            shutdown(24)              : modem is in shutdown state.
            channelChgInitRangingRcvd(25)  : modem sent initial ranging
                                              during channel change.
            channelChgRangingInProgress(26) : initial ranging is in
                                              progress during channel
                                              change.
            wbOnline(27)               : Wideband modem is online.
            wbOnlinePrivacy(28)        : Wideband modem is online Privacy
                                         enabled.
            wbOnlineKekAssigned(29)    : Wideband modem is online
                                         and KEK assigned.
            wbOnlineTekAssigned(30)    : Wideband modem is online
                                         and TEK assigned.
            wbOnlineNetAccessDis(31)   : Wideband modem registered but
                                         Network access disabled.
            wbKekReject(32)            : KEK wideband modem key assignment
                                         rejected.
            wbTekReject(33)            : TEK wideband modem key assignment
                                         rejected.
            wbNetAccessDisReject(34)   : wideband modem rejected -
                                         Net access disabled.
            wbPrivacyEnabReject(35)    : wideband modem rejected
                                         Privacy enabled.
            wbKekExpire(36)            : KEK Wideband modem key assignment
                                         expired.
            wbTekExpire(37)            : TEK wideband modem key assignment
                                         rejected.
            wbNetAccessDisExpire(38)   : wideband modem expire - Network
                                         access disabled.
            wbPrivacyEnabExpire(39)    : wideband modem expire - Privacy
                                         enabled.
            
            
            This ccwbWBCmStatusValue could return initRangingRcvd(3)
            or rangingInProgress(16) when the ccwbWBCmStatusValue
            is ranging(2).
            
            This ccwbWBCmStatusValue will return others(2) when the
            ccwbWBCmStatusValue states is either rangingAborted(3),
            rangingComplete(4), and ipComplete(5).
            
            This ccwbWBCmStatusValue could return wbonline(27), or
            onlineNetAccessDisabled(5) for WCM with BPI disabled, or
            onlineNetAccessDisabled(5) or onlineTekAssigned(7) for
            WCM with BPI enabled, when the ccwbWBCmStatusValue
            is registrationComplete(6).
            
            This ccwbWBCmStatusValue could return either rejectBadMic(8),
            rejectBadCos(9) rejStaleConfig(19) or rejRegNack(22) when
            the ccwbWBCmStatusValue is accessDenied(7) for possible
            reasons of cable modem registration abort.
            
            This ccwbWBCmStatusValue could return either onlineKekAssigned(6),
            kekRejected(10), tekRejected(11), or online(12) for the WCM with
            BPI enabled when the ccwbWBCmStatusValue is
            registeredBPIInitializing(9).
            
            The state rejectBadCos(9) is not applicable for DOCSIS1.1 modems.
            The WCMTS only needs to report states it is able to detect.";
          smiv2:max-access "read-only";
          smiv2:oid "1.3.6.1.4.1.9.9.479.1.6.1.1";
        }
      }
    }

    container ccwbWBCmStatusExtTable {
      description
       "An entry in this table exists for each Wideband
        Cable Modem which links to one or more WB interface.";
      smiv2:oid "1.3.6.1.4.1.9.9.479.1.7";

      list ccwbWBCmStatusExtEntry {
        key "docsIfCmtsCmStatusIndex ccwbWBCmStatusExtIndex";
        description
         "This entry exists for each Wideband Cable Modem(WCM)
          which links to one or more WB interface.";
        smiv2:oid "1.3.6.1.4.1.9.9.479.1.7.1";

        leaf docsIfCmtsCmStatusIndex {
          type leafref {
            path "/docs-if:DOCS-IF-MIB/docs-if:docsIfCmtsCmStatusTable/docs-if:docsIfCmtsCmStatusEntry/docs-if:docsIfCmtsCmStatusIndex";
          }
        }

        leaf ccwbWBCmStatusExtIndex {
          type int32 {
            range "1..2147483647";
          }
          description
           "The value of this object uniquely identifies an
            association between a WCM and a BG.";
          smiv2:max-access "not-accessible";
          smiv2:oid "1.3.6.1.4.1.9.9.479.1.7.1.1";
        }

        leaf ccwbWBCmWBIfindex {
          type if-mib:InterfaceIndex;
          description
           "ifIndex of the wideband channel associated with the WCM.";
          smiv2:max-access "read-only";
          smiv2:oid "1.3.6.1.4.1.9.9.479.1.7.1.2";
        }
      }
    }

    container ccwbFiberNodeDescrTable {
      description
       "This table contains the description of a Fiber Node
        on a CMTS. An entry in this table exists for each
        FiberNode ID.";
      smiv2:oid "1.3.6.1.4.1.9.9.479.1.8";

      list ccwbFiberNodeDescrEntry {
        key "ccwbFiberNodeID";
        description
         "This entry provides the description of each fiber node
          on the CMTS and it is part of the Fiber node configuration.";
        smiv2:oid "1.3.6.1.4.1.9.9.479.1.8.1";

        leaf ccwbFiberNodeID {
          type leafref {
            path "/CISCO-CABLE-WIDEBAND-MIB:CISCO-CABLE-WIDEBAND-MIB/CISCO-CABLE-WIDEBAND-MIB:ccwbFiberNodeTable/CISCO-CABLE-WIDEBAND-MIB:ccwbFiberNodeEntry/CISCO-CABLE-WIDEBAND-MIB:ccwbFiberNodeID";
          }
        }

        leaf ccwbFiberNodeDescription {
          type snmp-framework:SnmpAdminString {
            length "0..80";
          }
          description
           "This object contains the user configured
            description string of the fiber node.";
          smiv2:max-access "read-write";
          smiv2:oid "1.3.6.1.4.1.9.9.479.1.8.1.1";
        }

        leaf ccwbFiberNodeDescrStorageType {
          type snmpv2-tc:StorageType;
          description
           "The storage type for this conceptual row.";
          smiv2:defval "volatile";
          smiv2:max-access "read-write";
          smiv2:oid "1.3.6.1.4.1.9.9.479.1.8.1.2";
        }

        leaf ccwbFiberNodeDescrRowStatus {
          type snmpv2-tc:RowStatus;
          description
           "Controls and reflects the status of rows in this table.
            It can be used for creating and deleting
            entries in this table. ccwbFiberNodeDescription must
            not be null in order for row to be created.";
          smiv2:max-access "read-write";
          smiv2:oid "1.3.6.1.4.1.9.9.479.1.8.1.3";
        }
      }
    }

    container ccwbFiberNodeTable {
      description
       "This table provides configuration information of each Fiber node.
        It will provide topology information of each Fiber node, which
        includes information such as, Narrowband and Wideband QAMs.";
      smiv2:oid "1.3.6.1.4.1.9.9.479.1.9";

      list ccwbFiberNodeEntry {
        key "ccwbFiberNodeID ccwbFiberNodeGlobRFID";
        description
         "An entry in this table exists for each FiberNode ID that is in use.
          It uses two indices, i.e. ccwbFiberNodeID which is the
          Fiber node ID, and ccwbFiberNodeGlobRFID, which is the combined
          bit mask of Narrowband RF channels and Wideband
          rf-ports(rf-channels).";
        smiv2:oid "1.3.6.1.4.1.9.9.479.1.9.1";

        leaf ccwbFiberNodeID {
          type uint32 {
            range "1..1000";
          }
          description
           "This object represents the Fiber node ID.
            Each Fiber node configuration on the CMTS is
            assigned a unique Fiber node ID.";
          smiv2:max-access "not-accessible";
          smiv2:oid "1.3.6.1.4.1.9.9.479.1.9.1.1";
        }

        leaf ccwbFiberNodeGlobRFID {
          type uint32 {
            range "0..4294967295";
          }
          description
           "This is the RF ID of both Narrowband and
            Wideband QAMs(rf-channels) combined.";
          smiv2:max-access "not-accessible";
          smiv2:oid "1.3.6.1.4.1.9.9.479.1.9.1.2";
        }

        leaf ccwbFiberNodeNBIfIndx {
          type if-mib:InterfaceIndexOrZero;
          description
           "This object represents the Narrowband Ifindex
            of the  RF downstream channel which is part
            of the Fiber node configuation.";
          smiv2:defval "0";
          smiv2:max-access "read-write";
          smiv2:oid "1.3.6.1.4.1.9.9.479.1.9.1.3";
        }

        leaf ccwbFiberNodeWBContlrPhyIndx {
          type entity-mib:PhysicalIndexOrZero;
          description
           "This object represents the entity physical index of
            Wideband controller card. This card contains the RF
            port which is part of the ccwbFiberNodeGlobRFID
            bit mask. A value of zero means the index is invalid.
            ccwbFiberNodeWBRFPort and ccwbFiberNodeWBContlrPhyIndx
            are mutually inclusive.";
          smiv2:defval "0";
          smiv2:max-access "read-write";
          smiv2:oid "1.3.6.1.4.1.9.9.479.1.9.1.4";
        }

        leaf ccwbFiberNodeWBRFPort {
          type int32 {
            range "0..1024";
          }
          description
           "This object represents the RF downstream channel IDs
            (rf-ports) of the wideband controller card.
            Each Wideband controller can have 24 RF channels.
            ccwbFiberNodeWBRFPort and ccwbFiberNodeWBContlrPhyIndx
            are mutually inclusive.";
          smiv2:defval "0";
          smiv2:max-access "read-write";
          smiv2:oid "1.3.6.1.4.1.9.9.479.1.9.1.5";
        }

        leaf ccwbFiberNodeStorageType {
          type snmpv2-tc:StorageType;
          description
           "The storage type for this conceptual row.";
          smiv2:defval "volatile";
          smiv2:max-access "read-write";
          smiv2:oid "1.3.6.1.4.1.9.9.479.1.9.1.6";
        }

        leaf ccwbFiberNodeRowStatus {
          type snmpv2-tc:RowStatus;
          description
           "Controls and reflects the status of rows in this table.
            It can be used for creating and deleting
            entries in this table.";
          smiv2:max-access "read-write";
          smiv2:oid "1.3.6.1.4.1.9.9.479.1.9.1.7";
        }
      }
    }
  }

  smiv2:alias "ccwbRFChannelQamTable" {
    description
     "This table contains information of the external edge QAM
      which provide the physical RF channels which are available
      to the wideband channels.";
    smiv2:oid "1.3.6.1.4.1.9.9.479.1.2";
  }

  smiv2:alias "ccwbRFChannelQamEntry" {
    description
     "An entry provides a list of attributes for a single
      RF channel which can be physically present on an external
      edge QAM device.
      
      An entry in this table exists for each configured
      RF channel on the WCMTS module that provides the
      wideband DOCSIS functionality.";
    smiv2:oid "1.3.6.1.4.1.9.9.479.1.2.1";
  }

  augment "/CISCO-CABLE-WIDEBAND-MIB:CISCO-CABLE-WIDEBAND-MIB/CISCO-CABLE-WIDEBAND-MIB:ccwbRFChannelTable/CISCO-CABLE-WIDEBAND-MIB:ccwbRFChannelEntry" {
    description
     "An entry provides a list of attributes for a single
      RF channel which can be physically present on an external
      edge QAM device.
      
      An entry in this table exists for each configured
      RF channel on the WCMTS module that provides the
      wideband DOCSIS functionality.";
    smiv2:oid "1.3.6.1.4.1.9.9.479.1.2.1";

    leaf ccwbRFChanQamIPAddressType {
      type inet-address:InetAddressType;
      description
       "The type of internet address. This object identifies
        the internet address type specified by
        ccwbRFChanQamIPAddress object.";
      smiv2:defval "ipv4";
      smiv2:max-access "read-write";
      smiv2:oid "1.3.6.1.4.1.9.9.479.1.2.1.1";
    }

    leaf ccwbRFChanQamIPAddress {
      type inet-address:InetAddress;
      description
       "The IP address of the edge QAM device or the CMTS cable
        interface which provides the physical RF channel.
        The IP address will be of the type represented by
        object ccwbRFChanQamIPAddressType.";
      smiv2:max-access "read-write";
      smiv2:oid "1.3.6.1.4.1.9.9.479.1.2.1.2";
    }

    leaf ccwbRFChanQamMacAddress {
      type yang:mac-address;
      description
       "The MAC address of the edge QAM device or next hop router
        which might be present between the WCMTS and the edge QAM.";
      smiv2:max-access "read-write";
      smiv2:oid "1.3.6.1.4.1.9.9.479.1.2.1.3";
    }

    leaf ccwbRFChanQamUdpPort {
      type inet:port-number;
      description
       "The port number on the edge QAM associated with
        this RF channel.";
      smiv2:max-access "read-write";
      smiv2:oid "1.3.6.1.4.1.9.9.479.1.2.1.4";
    }

    leaf ccwbRFChanQamTos {
      type uint32 {
        range "0..255";
      }
      description
       "The value of the TOS field in the IP header for all
        Ethernet frames destined for the given RF channel.";
      smiv2:defval "0";
      smiv2:max-access "read-write";
      smiv2:oid "1.3.6.1.4.1.9.9.479.1.2.1.5";
    }

    leaf ccwbRFChanQamVlanId {
      type uint32 {
        range "0..4095";
      }
      description
       "The VLAN ID to be inserted in the Ethernet frames when
        using 802.1q frames instead of normal 802.1 frames for the
        given RF channel. The value of 0 indicates that 802.1 frames
        are being used and is not supported in setting this object.";
      smiv2:max-access "read-write";
      smiv2:oid "1.3.6.1.4.1.9.9.479.1.2.1.6";
    }

    leaf ccwbRFChanQamPriorityBits {
      type uint32 {
        range "0..7";
      }
      description
       "The priority bits used when inserting Ethernet 802.1q VLAN
        tags into the Ethernet frames destined for a given RF
        channel.
        Priority Bits (0=Best effort, 1=background, 2=spare,
        3=excellent effort, 4=controlled load, 5=video,
        6=voice, 7=network control).";
      smiv2:max-access "read-write";
      smiv2:oid "1.3.6.1.4.1.9.9.479.1.2.1.7";
    }

    leaf ccwbRFChanQamDepiRemoteId {
      type uint32 {
        range "0..4294967295";
      }
      description
       "The DEPI remote ID on edge QAM associated with this RF channel.";
      smiv2:max-access "read-write";
      smiv2:oid "1.3.6.1.4.1.9.9.479.1.2.1.8";
    }

    leaf ccwbRFChanQamDepiTunnel {
      type snmp-framework:SnmpAdminString {
        length "0..255";
      }
      description
       "This object specifies the name of the DEPI tunnel which determines
        the DEPI data session configuration associated with this RF channel.";
      smiv2:max-access "read-write";
      smiv2:oid "1.3.6.1.4.1.9.9.479.1.2.1.9";
    }

    leaf ccwbRFChanQamTsid {
      type uint32 {
        range "0..65535";
      }
      description
       "This object specifies the MPEG2 transport stream ID which is
        associated with this RF channel.";
      smiv2:max-access "read-write";
      smiv2:oid "1.3.6.1.4.1.9.9.479.1.2.1.10";
    }
  }

  notification ccwbSFPLinkDownNotification {
    description
     "This notification is generated when link of SFP port is
      lost. entPhysicalName identifies the SFP port.";
    smiv2:oid "1.3.6.1.4.1.9.9.479.0.1";

    container object-1 {

      leaf entPhysicalIndex {
        type leafref {
          path "/entity-mib:ENTITY-MIB/entity-mib:entPhysicalTable/entity-mib:entPhysicalEntry/entity-mib:entPhysicalIndex";
        }
      }

      leaf entPhysicalName {
        type leafref {
          path "/entity-mib:ENTITY-MIB/entity-mib:entPhysicalTable/entity-mib:entPhysicalEntry/entity-mib:entPhysicalName";
        }
      }
    }
  }

  notification ccwbSFPLinkUpNotification {
    description
     "This notification is generated when link of SFP port is
      up. entPhysicalName identifies the SFP port.";
    smiv2:oid "1.3.6.1.4.1.9.9.479.0.2";

    container object-1 {

      leaf entPhysicalIndex {
        type leafref {
          path "/entity-mib:ENTITY-MIB/entity-mib:entPhysicalTable/entity-mib:entPhysicalEntry/entity-mib:entPhysicalIndex";
        }
      }

      leaf entPhysicalName {
        type leafref {
          path "/entity-mib:ENTITY-MIB/entity-mib:entPhysicalTable/entity-mib:entPhysicalEntry/entity-mib:entPhysicalName";
        }
      }
    }
  }

  smiv2:alias "ciscoCableWidebandMIB" {
    smiv2:oid "1.3.6.1.4.1.9.9.479";
  }

  smiv2:alias "ciscoCableWidebandMIBNotifs" {
    smiv2:oid "1.3.6.1.4.1.9.9.479.0";
  }

  smiv2:alias "ciscoCableWidebandMIBObjects" {
    smiv2:oid "1.3.6.1.4.1.9.9.479.1";
  }

  smiv2:alias "ciscoCableWidebandMIBConform" {
    smiv2:oid "1.3.6.1.4.1.9.9.479.2";
  }

  smiv2:alias "ciscoCableWidebandMIBCompliances" {
    smiv2:oid "1.3.6.1.4.1.9.9.479.2.1";
  }

  smiv2:alias "ciscoCableWidebandMIBGroups" {
    smiv2:oid "1.3.6.1.4.1.9.9.479.2.2";
  }

}
