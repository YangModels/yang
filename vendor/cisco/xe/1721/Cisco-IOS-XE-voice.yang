module Cisco-IOS-XE-voice {
  namespace "http://cisco.com/ns/yang/Cisco-IOS-XE-voice";
  prefix ios-voice;

  import cisco-semver {
    prefix cisco-semver;
  }
  import Cisco-IOS-XE-native {
    prefix ios;
  }
  import Cisco-IOS-XE-interface-common {
    prefix ios-ifc;
  }
  import ietf-inet-types {
    prefix inet;
  }
  import Cisco-IOS-XE-types {
    prefix ios-types;
  }
  include Cisco-IOS-XE-voice-register;

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Native Voice Yang model.
     Copyright (c) 2016, 2018-2020 by Cisco Systems, Inc.
     All rights reserved.";

  revision 2020-03-01 {
    description
      "- Added global voice configuration
       - Added trunk group configuration
       - Added dependency of pool configuration on global and max-pool configurations in Cisco-IOS-XE-voice-register yang file";
    cisco-semver:module-version "3.0.0";
  }
  revision 2019-11-01 {
    description
      "- Added trunk group config
       - Added statement mandatory for leaves Cisco-IOS-XE-voice-register yang file";
    cisco-semver:module-version "2.0.0";
  }
  revision 2019-07-01 {
    description
      "- Establish semantic version baseline
       - Added voice class codec
       - Added voice service voip commands
       - Added the ip address trusted list option
       - Added dsapp line feature access code command
       - Added voice register mode for SRST
       - Added the dial-peer voice <tag> voip CLIs";
    cisco-semver:module-version "1.0.0";
  }
  revision 2018-10-23 {
    description
      "Added redundancy-group command in voice service voip command";
  }
  revision 2018-09-20 {
    description
      "Add SIP LINE CLI support";
  }
  revision 2017-02-07 {
    description
      "Initial revision";
  }

  typedef voice-cadence-type {
    type uint16 {
      range "50..10000";
    }
  }

  grouping config-voice-translation-profile-grouping {
    container translation-profile {
      description
        "Translation profile";
      leaf incoming {
        description
          "Translation Profile for incoming call leg";
        type leafref {
          path "/ios:native/ios-voice:voice/ios-voice:translation-profile/ios-voice:id";
        }
      }
      leaf outgoing {
        description
          "Translation Profile for outgoing call leg";
        type leafref {
          path "/ios:native/ios-voice:voice/ios-voice:translation-profile/ios-voice:id";
        }
      }
    }
  }

  grouping config-source-interface-grouping {
    container source-interface {
      description
        "Specify interface for source address of SIP packets";
      container source-interface-std {
        when "/ios:native/sip-ua";
        uses ios-ifc:interface-grouping;
      }
      leaf source-interface-string {
        when "not (/ios:native/sip-ua)";
        type string;
      }
    }
  }

  grouping config-sip-ua-grouping {
    container sip-ua {
      description
        "SIP User Agent (UA) ";
      presence "true";
    }
  }

  grouping config-session-transport-grouping {
    container transport {
      description
        "SIP session transport config";
      choice transport-choice {
        leaf udp {
          description
            "Transport Layer Protocol - UDP";
          type empty;
        }
        container tcp {
          description
            "Transport Layer Protocol - TCP";
          presence "true";
          leaf tls {
            description
              "Transport Layer Protocol - TLS over TCP";
            type empty;
          }
        }
      }
    }
  }

  grouping config-voice-grouping {
    container voice {
      description
        "Global voice configuration";
      list translation-rule {
        description
          "Translation Rule configuration commands";
        key "id";
        leaf id {
          type uint32 {
            range "1..1073741823";
          }
        }
        list rule {
          description
            "Translation rule";
          key "id";
          leaf id {
            description
              "Translation rule number";
            type uint8 {
              range "1..100";
            }
          }
          choice rule-choice {
            leaf reject {
              description
                "Call block rule";
              type string {
                pattern ".*";
                length "1..66";
              }
            }
            leaf matching-replacement-pattern {
              description
                "Matching and replacement pattern, i.e., /xxx/ /xxx/";
              type string {
                pattern ".*";
                length "1..133";
              }
            }
          }
        }
      }
      list translation-profile {
        description
          "Translation profile configuration commands";
        key "id";
        leaf id {
          type string {
            length "1..31";
          }
        }
        container translate {
          description
            "Specify numbers that should be translated";
          leaf called {
            description
              "Translation rule for the called-number";
            type leafref {
              path "../../../translation-rule/id";
            }
          }
          leaf calling {
            description
              "Translation rule for the calling-number";
            type leafref {
              path "../../../translation-rule/id";
            }
          }
        }
      }
      container class {
        description
          "Control parameters class";
        list custom-cptone {
          description
            "Configuration of customized Call Progress Tones";
          key "id";
          leaf id {
            type string {
              length "1..20";
            }
          }
          list dualtone {
            description
              "Configure call progress dual tones";
            key "id";
            leaf id {
              type enumeration {
                enum "busy";
                enum "conference";
                enum "disconnect";
                enum "number-unobtainable";
                enum "out-of-service";
                enum "reorder";
                enum "ringback";
              }
            }
            leaf-list frequency {
              description
                "Configure dual tone frequencies";
              max-elements "2";
              type uint16 {
                range "300..3600";
              }
            }
            container cadence {
              description
                "Configure dual tone cadences";
              leaf first-on-cadence {
                description
                  "First On cadence";
                type voice-cadence-type;
              }
              leaf first-off-cadence {
                description
                  "First Off cadence";
                type voice-cadence-type;
              }
              leaf second-on-cadence {
                description
                  "Second On cadence";
                type voice-cadence-type;
              }
              leaf second-off-cadence {
                description
                  "First Off cadence";
                type voice-cadence-type;
              }
              leaf third-on-cadence {
                description
                  "Third On cadence";
                type voice-cadence-type;
              }
              leaf third-off-cadence {
                description
                  "Third Off cadence";
                type voice-cadence-type;
              }
              leaf fourth-on-cadence {
                description
                  "Fourth On cadence";
                type voice-cadence-type;
              }
              leaf fourth-off-cadence {
                description
                  "Fourth Off cadence";
                type voice-cadence-type;
              }
            }
          }
        }
        list dualtone-detect-params {
          description
            "Dual tone detection parameters";
          key "id";
          leaf id {
            description
              "Voice class dual tone detect parameter tag";
            type uint32 {
              range "1..10000";
            }
          }
          leaf cadence-variation {
            description
              "Cadence variation allowed";
            type uint8 {
              range "0..200";
            }
            default "10";
          }
          leaf freq-max-delay {
            description
              "Timing difference between two frequencies";
            type uint8 {
              range "10..100";
            }
            default "10";
          }
          leaf freq-max-deviation {
            description
              "Maximum frequency deviation allowed for each frequency";
            type uint8 {
              range "10..125";
            }
            default "10";
          }
          leaf freq-max-power {
            description
              "Absolute value of upper limit for tone power per frequency";
            type uint8 {
              range "0..20";
            }
            default "10";
          }
          leaf freq-min-power {
            description
              "Absolute value of lower limit for tone power per frequency";
            type uint8 {
              range "10..35";
            }
            default "30";
          }
          leaf freq-power-twist {
            description
              "The difference between the power of two frequencies";
            type uint8 {
              range "0..15";
            }
            default "6";
          }
        }
        list codec {
          description
            "Set codec global parameters";
          max-elements "10000";
          key "codec-tag";
          leaf codec-tag {
            description
              "Voice class codec tag";
            type uint16 {
              range "1..10000";
            }
          }
          container codec {
            description
              "Set class codec parameters";
            list preference {
              description
                "Set priority order for using this codec";
              max-elements "24";
              key "preference-tag";
              unique "codec-type";
              leaf preference-tag {
                description
                  "Priority order (1 = Highest)";
                type uint8 {
                  range "1..24";
                }
              }
              leaf codec-type {
                type enumeration {
                  enum "g711ulaw";
                  enum "g711alaw";
                  enum "g729r8";
                  enum "ilbc";
                  enum "g722-64";
                }
              }
              leaf bytes {
                description
                  "Specify number of voice data bytes per frame";
                when "../codec-type = 'g711alaw' or ../codec-type = 'g711ulaw' or ../codec-type = 'g722-64' ";
                type enumeration {
                  enum "80";
                  enum "160";
                  enum "240";
                }
                default "160";
              }
              container g729r8-conf {
                when "../codec-type = 'g729r8'";
                leaf bytes {
                  description
                    "Specify number of voice data bytes per frame";
                  type enumeration {
                    enum "10";
                    enum "20";
                    enum "30";
                    enum "40";
                    enum "50";
                    enum "60";
                    enum "70";
                    enum "80";
                    enum "90";
                    enum "100";
                    enum "110";
                    enum "120";
                    enum "130";
                    enum "140";
                    enum "150";
                    enum "160";
                    enum "170";
                    enum "180";
                    enum "190";
                    enum "200";
                    enum "210";
                    enum "220";
                    enum "230";
                    enum "240";
                  }
                }
              }
              container ilbc-conf {
                when "../codec-type = 'ilbc'";
                container mode {
                  description
                    "Specify the value of the mode";
                  choice mode-choice {
                    case twenty-case {
                      container twenty {
                        leaf bytes {
                          description
                            "Specify number of voice data bytes";
                          type enumeration {
                            enum "38";
                            enum "76";
                            enum "114";
                            enum "152";
                            enum "190";
                            enum "228";
                          }
                        }
                      }
                    }
                    case thirty-case {
                      container thirty {
                        leaf bytes {
                          description
                            "Specify number of voice data bytes";
                          type enumeration {
                            enum "50";
                            enum "100";
                            enum "150";
                            enum "200";
                          }
                        }
                      }
                    }
                  }
                }
              }
            }
          }
        }
      }
      list service {
        description
          "Global packet telephony service commands";
        key "type";
        leaf type {
          type enumeration {
            enum "pots";
            enum "saf";
            enum "voatm";
            enum "vofr";
            enum "voip";
          }
        }
        leaf shutdown {
          description
            "Stop VoIP services gracefully without dropping active calls";
          when "../type = 'voip'";
          type boolean;
          default "false";
        }
        container media-recording {
          description
            "Media recording commands";
          when "../type = 'pots'";
          leaf licenses {
            description
              "Allocate media recording licenses";
            type uint16 {
              range "1..500";
            }
          }
        }
        container allow-connections {
          description
            "Allow call connection types";
          when "../type = 'voip'";
          container sip {
            description
              "from-type sip";
            container to {
              description
                "to";
              leaf sip {
                description
                  "to-type sip";
                type empty;
              }
            }
          }
        }
        container media {
          description
            "Global media setting for voip calls";
          leaf bulk-stats {
            description
              "Retrieve bulk statistics is enabled";
            must "/ios:native/voice/service[type='voip']/allow-connections/sip/to/sip" {
              error-message "Config allow-connections sip to sip";
            }
            type empty;
          }
        }
        container supplementary-service {
          description
            "Config supplementary service features";
          when "../type = 'voip'";
          container sip {
            description
              "sip supplementary service";
            leaf handle-replaces {
              description
                "Handle INVITE with REPLACES header (SIP-SIP only)";
              type empty;
            }
            leaf moved-temporarily {
              description
                "enable/disable sip moved-temporarily";
              type empty;
            }
            leaf refer {
              description
                "enable/disable sip refer";
              type empty;
            }
          }
        }
        container sip {
          description
            "SIP configuration commands";
          when "../type = 'voip'";
          presence "true";
          container registrar {
            description
              "SIP Registrar config";
            container server {
              description
                "Enable Local SIP Registrar";
              container expires {
                description
                  "Registration Expires time";
                presence "true";
                must "./min  <= ./max" {
                  error-message "Max must be greater than min";
                }
                leaf max {
                  description
                    "Default registration max expires time";
                  type uint32 {
                    range "120..86400";
                  }
                  default "3600";
                }
                leaf min {
                  description
                    "Default registration min expires time";
                  type uint16 {
                    range "60..3600";
                  }
                  default "60";
                }
              }
            }
          }
          container call {
            description
              "Global setting to start/stop processing SIP Calls";
            container service {
              description
                "SIP service configuration";
              container stop {
                description
                  "Stop SIP service - Active calls not affected";
                presence "true";
                leaf forced {
                  description
                    "Forced shutdown of SIP service - Active calls will be torn down";
                  type empty;
                }
              }
            }
          }
          container g729 {
            description
              "G729 codec interoperability settings";
            leaf annexb-all {
              description
                "g729b representing g729a and g729b to interop with CCM";
              type empty;
            }
          }
          container session {
            description
              "SIP Voice Protocol session config";
            uses config-session-transport-grouping;
          }
          container bind {
            description
              "SIP bind command";
            container control {
              description
                "bind only SIP control packets";
              uses config-source-interface-grouping;
            }
            container media {
              description
                "bind only SIP media packets";
              uses config-source-interface-grouping;
            }
          }
        }
        container ip {
          description
            "Voice service voip ip setup";
          when "../type = 'voip'";
          container address {
            description
              "Voice service voip ip address setup";
            container trusted {
              description
                "ip address trusted (toll fraud prevention) setup";
              leaf authenticate {
                description
                  "ip address trusted (toll fraud prevention) authenticate control flag";
                type empty;
              }
              leaf call-block {
                description
                  "ip address trusted (toll fraud prevention) call-block";
                type empty;
              }
              container list {
                description
                  "ip address trusted (toll fraud prevention) list setup";
                must "count(./ipv4/address) + count(./ipv6/address) <= 100" {
                  error-message "Trusted list entries has exceeded the maximum";
                }
                list ipv4 {
                  description
                    "ip address trusted (toll fraud prevention) list entry";
                  max-elements "100";
                  key "address";
                  leaf address {
                    description
                      "IPv4 Address";
                    type inet:ipv4-address;
                  }
                  leaf mask {
                    description
                      "IPv4 Address Mask";
                    type union {
                      type inet:ipv4-address;
                      type string {
                        pattern "/([0-9]|[1-2][0-9]|3[0-2])";
                      }
                    }
                  }
                }
                list ipv6 {
                  description
                    "ipv6 address trusted (toll fraud prevention) list entry";
                  max-elements "100";
                  key "address";
                  leaf address {
                    description
                      "IPv6 Prefix";
                    type ios-types:ipv6-prefix;
                  }
                }
              }
            }
          }
        }
        container fax {
          description
            "Global fax commands";
          leaf protocol {
            description
              "The system-wide fax protocol type";
            type enumeration {
              enum "cisco";
              enum "none";
              enum "pass-through";
              enum "t38";
            }
          }
          leaf fallback {
            description
              "fax transport to use if T.38 unsupported on far end";
            when "../protocol = 't38'";
            type enumeration {
              enum "cisco";
              enum "none";
              enum "pass-through";
            }
          }
          leaf codec {
            when "../protocol = 'pass-through' or ../fallback = 'pass-through'";
            type enumeration {
              enum "g711alaw";
              enum "g711ulaw";
            }
          }
          leaf ls-redundancy {
            description
              "t38 low speed redundancy";
            when "../protocol = 't38'";
            type uint8 {
              range "0..5";
            }
          }
          leaf hs-redundancy {
            description
              "t38 high speed redundancy";
            when "../protocol = 't38'";
            type uint8 {
              range "0..2";
            }
          }
          leaf version {
            description
              "t38 fax version";
            when "../protocol = 't38'";
            type enumeration {
              enum "0";
              enum "3";
            }
          }
        }
        leaf redundancy-group {
          description
            "Associate redundancy-group with voice HA";
          type uint8 {
            range "1..2";
          }
        }
        container mode {
          description
            "Global mode setting for voip calls";
          when "../type = 'voip'";
          choice mode-choice {
            case border-element-case {
              container border-element {
                description
                  "Mode setting for Border-Element";
                presence "true";
                container license {
                  description
                    "License setting for Border-Element is deprecated";
                  container periodicity {
                    description
                      "Licence periodicity setting for Border-Element";
                    choice periodicity-choice {
                      case mins-case {
                        leaf mins {
                          description
                            "Periodicity interval in mins";
                          type uint8 {
                            range "1..59";
                          }
                        }
                      }
                      case hours-case {
                        leaf hours {
                          description
                            "Periodicity interval in hours";
                          type uint8 {
                            range "1..23";
                          }
                        }
                      }
                      case days-case {
                        leaf days {
                          description
                            "Periodicity interval in days";
                          type uint8 {
                            range "1..30";
                          }
                        }
                      }
                    }
                  }
                }
              }
            }
          }
        }
      }
      uses config-voice-register-grouping;
    }
  }

  grouping config-voice-card-grouping {
    list voice-card-sb {
      description
        "Configure a specific voice-card";
      key "sb";
      leaf sb {
        type ios-types:slot-bay-type;
      }
      leaf local-bypass {
        description
          "Enable TDM hair pin";
        type boolean;
        default "true";
      }
      container dsp {
        description
          "To configure DSP service dspfarm";
        container services {
          description
            "To configure dsp services on this voice-card";
          leaf dspfarm {
            description
              "To enable dspfarm service on this voice-card";
            type empty;
          }
        }
      }
    }
    list voice-card {
      status obsolete;
      description
        "Configure a specific voice-card (OBSOLETE)";
      key "id";
      leaf id {
        status obsolete;
        type ios-types:slot-bay-type;
      }
      leaf slot {
        status obsolete;
        type uint8 {
          range "0..2";
        }
      }
    }
  }

  grouping config-dtmf-relay-grouping {
    container dtmf-relay {
      description
        "Transport digits across IP link. Enter relay options in order of preference.";
      leaf rtp-nte {
        description
          "RTP Named Telephone Event RFC 2833";
        type empty;
      }
      leaf digit-drop {
        description
          "RTP Named Telephone Event RFC 2833";
        when "../rtp-nte";
        type empty;
      }
      leaf sip-info {
        description
          "Relay via SIP INFO messages";
        type empty;
      }
      leaf sip-kpml {
        description
          "Relay over SIP SUBSCRIBE/NOTIFY";
        type empty;
      }
      leaf sip-notify {
        description
          "Relay via SIP NOTIFY messages";
        type empty;
      }
    }
  }

  grouping config-dial-peer-grouping {
    container dial-peer {
      description
        "Dial Map (Peer) configuration commands";
      list voice {
        description
          "Voice type";
        key "dialpeertag";
        leaf dialpeertag {
          description
            "Voice dial-peer tag";
          type uint32 {
            range "1..1073741823" {
              error-message "Input dial-peer tag is out of range. It should be in range of 1..1073741823";
            }
          }
        }
        leaf type {
          description
            "Dial peer type";
          type enumeration {
            enum "pots";
            enum "voip";
          }
        }
        leaf description {
          description
            "Dial peer specific description";
          when "../type = 'pots' or ../type = 'voip'";
          type string {
            pattern ".*";
            length "1..64";
          }
        }
        leaf destination-pattern {
          description
            "A full E.164 telephone number prefix";
          when "../type = 'pots' or ../type = 'voip'";
          type string {
            pattern "([0-9,A-F#*.?+%()-]*T?)" {
              error-message "Incorrect format for E.164 Number: regular expression must be of the form  [0-9,A-F#*.?+%()-]*T?";
            }
          }
        }
        leaf direct-inward-dial {
          when "../type = 'pots'";
          description
            "Use Called Number as final call destination";
          type empty;
        }
        container forward-digits {
          description
            "Configure the destination digits forward of this dial-peer";
          when "../type = 'pots'";
          choice fwd-digit-choice {
            leaf num-digits {
              description
                "Number of right-justified dial digits to be forwarded";
              type uint8 {
                range "0..32";
              }
            }
            leaf all {
              description
                "Forward all destination digits";
              type empty;
            }
            container extra {
              description
                "Extra dial digits to be forwarded";
              presence "true";
              leaf inband {
                description
                  "Digits to be forwarded inband";
                type empty;
              }
            }
          }
        }
        container incoming {
          description
            "Incoming called number";
          when "../type = 'pots' or ../type = 'voip'";
          leaf called-number {
            description
              "An incoming called number pattern";
            type string {
              pattern "([0-9,A-F#*.?+%()-]*T?)" {
                error-message "Incorrect format for E.164 Number: regular expression must be of the form  [0-9,A-F#*.?+%()-]*T?";
              }
            }
          }
        }
        container media-recording {
          description
            "Media recording commands";
          when "../type = 'pots'";
          leaf dialpeertag {
            description
              "Recording server dial peer";
            type uint32 {
              range "1..1073741823";
            }
          }
        }
        leaf port {
          description
            "Voice port associated with this peer";
          when "../type = 'pots'";
          type string;
        }
        leaf prefix {
          description
            "The pattern to be appended before the dial num";
          when "../type = 'pots'";
          type string {
            length "1..32";
          }
        }
        leaf shutdown {
          description
            "Change the Admin State of this peer to down";
          when "../type = 'pots' or ../type = 'voip'";
          type boolean;
          default "false";
        }
        uses config-voice-translation-profile-grouping;
        container voice-class {
          description
            "Set Dial-peer voice class control parameters";
          container sip {
            description
              "Set SIP parameters";
            container extension {
              description
                "Configure SIP extension";
              leaf voip_ext {
                when "../../../../type = 'voip'";
                type enumeration {
                  enum "system";
                  enum "cucm";
                  enum "gw-ana";
                }
                default "system";
              }
              leaf pots_ext {
                when "../../../../type = 'pots'";
                type enumeration {
                  enum "system";
                  enum "gw-ana";
                }
                default "system";
              }
            }
            container options-keepalive {
              description
                "send out-of-dialogue OPTIONS PING to configured proxy/session-target";
              when "../../../type = 'voip'";
              presence "true";
            }
          }
          container codec {
            description
              "Set Global Codec parameters";
            when "../../type = 'voip'";
            leaf codectag {
              type leafref {
                path "../../../../../voice/class/codec/codec-tag";
              }
            }
            leaf offer-all {
              description
                "Offer All the codec configured in this voice-class codec";
              when "../codectag > 0";
              type empty;
            }
          }
        }
        container session {
          description
            "The session [ target | protocol | transport ] for this peer";
          when "../type = 'voip'";
          uses config-session-transport-grouping;
          leaf protocol {
            description
              "The session protocol to be used in getting to this peer";
            type enumeration {
              enum "cisco" {
                description
                  "Ciso Session Protocol";
              }
              enum "sipv2" {
                description
                  "IETF Session Initiation Protocol";
              }
              enum "multicast" {
                description
                  "Multicast Session Protocol(voice conferencing)";
              }
            }
            default "cisco";
          }
          container target {
            description
              "The session target for this peer";
            when "../../session[protocol='sipv2']";
            choice target-choice {
              case address-choice {
                leaf address {
                  description
                    "WORD A string specifying the session target";
                  type string {
                    pattern "(loopback:rtp)|(dns:.*)|(sip-server)|(sip-uri)|(ipv4:[0-9]+\\.[0-9]+\\.[0-9]+\\.[0-9]+(:[0-9]+)?)|(ipv6:\\[([0-9A-Fa-f.:])+\\](:[0-9]+)?)" {
                      error-message "Must be of the form (loopback:rtp)|(dns:.*)|(sip-server)|(sip-uri)|(ipv4:[0-9]+.[0-9]+.[0-9]+.[0-9]+(:[0-9]+)?) | ((ipv6:[([0-9A-Fa-f.:])+](:[0-9]+)?))";
                    }
                  }
                }
              }
              case dhcp-choice {
                leaf dhcp {
                  description
                    "Provision session target using DHCP";
                  type empty;
                }
              }
              case registrar-choice {
                leaf registrar {
                  description
                    "Provision session target using Registration";
                  type empty;
                }
              }
            }
          }
        }
        leaf huntstop {
          description
            "Stop hunting on Dial-Peers";
          when "../type = 'pots' or ../type = 'voip'";
          type boolean;
          default "false";
        }
        leaf preference {
          description
            "Configure the preference order of this dial-peer";
          type uint16 {
            range "0..10" {
              error-message "Input Number is out of range. Should be 1..10";
            }
          }
        }
        uses config-dtmf-relay-grouping {
          when "type = 'voip' and session[protocol='sipv2']";
        }
      }
    }
  }

  grouping config-dsapp-line-grouping {
    container dsapp {
      description
        "Configure Device Service Application";
      leaf line {
        description
          "Configure DSAPP Line";
        type empty;
      }
      container dsappline {
        container line {
          description
            "Configure DSAPP Line";
          container feature {
            description
              "Specify the format of each call feature code";
            container access-code {
              description
                "Specify the format of feature access code";
              presence "true";
              leaf prefix {
                description
                  "Select feature access code prefix string";
                type string {
                  pattern "[\\*#]{1,5}";
                }
                default "**";
              }
              container call {
                description
                  "Select call forward feature";
                container forward {
                  description
                    "Select call forward all feature";
                  leaf all {
                    description
                      "Select call forward all feature code";
                    type string {
                      pattern "[0-9\\*#]{1,4}";
                    }
                    default "1";
                  }
                  leaf cancel {
                    description
                      "Select call forward cancel feature code";
                    type string {
                      pattern "[0-9\\*#]{1,4}";
                    }
                    default "2";
                  }
                }
              }
              container pickup {
                description
                  "Select call pickup feature code";
                leaf local {
                  description
                    "Select pickup local group feature code";
                  type string {
                    pattern "[0-9\\*#]{1,4}";
                  }
                  default "5";
                }
                leaf group {
                  description
                    "Select pickup different group feature code";
                  type string {
                    pattern "[0-9\\*#]{1,4}";
                  }
                  default "7";
                }
                leaf direct {
                  description
                    "Select pickup extension feature code";
                  type string {
                    pattern "[0-9\\*#]{1,4}";
                  }
                  default "6";
                }
              }
              leaf cancel-call-waiting {
                description
                  "Select cancel call waiting feature code";
                type string {
                  pattern "[0-9\\*#]{1,4}";
                }
                default "9";
              }
              leaf last-redial {
                description
                  "Select last redial feature code";
                type string {
                  pattern "[0-9\\*#]{1,4}";
                }
                default "3";
              }
            }
          }
        }
      }
    }
  }

  grouping config-ccm-manager-grouping {
    container ccm-manager {
      description
        "Call Manager";
      container sipana {
        description
          "Enable Call Manager Application SIP Line Side mode";
        container auto-config {
          description
            "SIP line side auto configuration";
          container local {
            description
              "Specify local interface to use for SIP analog device registration";
            leaf GigabitEthernet {
              description
                "GigabitEthernet IEEE 802.3z";
              type leafref {
                path "/ios:native/ios:interface/ios:GigabitEthernet/ios:name";
              }
            }
          }
        }
      }
      container config {
        description
          "XML download configuration";
        leaf server {
          description
            "set the Call Manager configuration download TFTP server address/name";
          type union {
            type inet:ipv4-address;
            type inet:ipv6-address;
            type inet:domain-name;
          }
        }
      }
    }
  }

  augment "/ios:native" {
    uses config-sip-ua-grouping;
    uses config-voice-grouping;
    uses config-voice-call-manager-fallback-grouping;
    uses config-voice-card-grouping;
    uses config-dial-peer-grouping;
    uses config-dsapp-line-grouping;
    uses config-ccm-manager-grouping;
  }
}
