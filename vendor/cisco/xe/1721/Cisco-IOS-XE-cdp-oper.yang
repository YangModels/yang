module Cisco-IOS-XE-cdp-oper {
  yang-version 1;
  namespace "http://cisco.com/ns/yang/Cisco-IOS-XE-cdp-oper";
  prefix cdp-ios-xe-oper;

  import ietf-inet-types {
    prefix inet;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for monitoring of Cisco CDP operational information.
     Copyright (c) 2016-2017, 2019 by Cisco Systems, Inc.
     All rights reserved.";

  revision 2019-05-01 {
    description
      "- Add neighbor identifier to cdp-neighbor-details.
       - Added semantic version";
    reference "2.1.0";
    cisco-semver:module-version "2.1.0";
  }
  revision 2017-09-21 {
    description
      "Rename container cdp-neighbour-details to cdp-neighbor-details";
    reference "2.0.0";
    cisco-semver:module-version "2.0.0";
  }
  revision 2017-02-07 {
    description
      "Initial revision";
    reference "1.0.0";
    cisco-semver:module-version "1.0.0";
  }

  typedef cdp-duplex {
    type enumeration {
      enum "cdp-duplex-unknown" {
        value 0;
      }
      enum "cdp-half-duplex" {
        value 1;
      }
      enum "cdp-full-duplex" {
        value 2;
      }
      enum "cdp-half-duplex-mismatch" {
        value 3;
      }
      enum "cdp-full-duplex-mismatch" {
        value 4;
      }
    }
    description
      "CDP duplex modes";
  }

  typedef cdp-adv-version {
    type enumeration {
      enum "cdp-advertised-none" {
        value 0;
      }
      enum "cdp-advertised-v1" {
        value 1;
      }
      enum "cdp-advertised-v2" {
        value 2;
      }
    }
    description
      "CDP advertized version information";
  }

  typedef cdp-unidirectional-mode {
    type enumeration {
      enum "cdp-uni-mode-off" {
        value 0;
      }
      enum "cdp-uni-mode-send-only" {
        value 1;
      }
      enum "cdp-uni-mode-recv-only" {
        value 2;
      }
      enum "cdp-uni-mode-unknown" {
        value 3;
      }
    }
    description
      "CDP unidirectional modes";
  }

  typedef cdp-yes-no {
    type enumeration {
      enum "cdp-no" {
        value 0;
      }
      enum "cdp-yes" {
        value 1;
      }
    }
    description
      "CDP type yes or no";
  }

  typedef cdp-enable-disable {
    type enumeration {
      enum "cdp-disable" {
        value 0;
      }
      enum "cdp-enable" {
        value 1;
      }
    }
    description
      "CDP type enable or disable";
  }

  grouping cdp-protocol-hello {
    description
      "CDP protocol hello";
    leaf oui {
      type string;
      description
        "OUI - org unique identifier for Cisco is 0x00000C";
    }
    leaf protocol-id {
      type string;
      description
        "Protocol identifier. This is the identifier of the cluster";
    }
    leaf payload-value {
      type string;
      description
        "Payload value - combination of the device and addresses";
    }
    leaf payload-len {
      type uint16;
      description
        "Payload length";
    }
  }

  grouping cdp-power-req {
    description
      "CDP power request information";
    leaf power-request-id {
      type uint16;
      description
        "The last power request ID received echoes the Request-ID field
         last received in a power requested TLV. It is 0 if no power
         requested TLV was received since the port last became active";
    }
    leaf power-man-id {
      type uint16;
      description
        "This field increments by 1 each time the Available-Power or Management
         Power fields change, a power requested TLV is received with a 
         Request-ID field which is different from the last received set or when 
         the port goes down";
    }
    leaf power-request-level {
      type string;
      description
        "Power to be transmitted by a powerable device in order to negotiate
         a suitable power level with the supplier of the network power";
    }
  }

  grouping cdp-power-avail {
    description
      "CDP power available";
    leaf power-request-id {
      type uint16;
      description
        "The last power request ID received echoes the Request-ID field
         last received in a power requested TLV. It is 0 if no power
         requested TLV was received since the port last became active";
    }
    leaf power-man-id {
      type uint16;
      description
        "This field increments by 1 each time the Available-Power or Management
         Power fields change, a power requested TLV is received with a 
         Request-ID field which is different from the last received set or when 
         the port goes down";
    }
    leaf power-available {
      type uint32;
      description
        "The amount of power consumed by the specified port in watts";
    }
    leaf power-man-level {
      type uint32;
      description
        "Management Power Level -- The request of the supplier to the powered
         device for the power consumption TLV. The 200/300 switches always
         display No Preference since the switch is a power provide";
    }
  }

  grouping cdp-tdl-spare-pair-poe {
    description
      "CDP spare pair PoE";
    leaf spare-pair-poe {
      type cdp-ios-xe-oper:cdp-yes-no;
      description
        "Spare pair PoE TLV is a one octet long
         this field represents 4-pair PoE Supported or not";
    }
    leaf spare-pair-detection-required {
      type cdp-ios-xe-oper:cdp-yes-no;
      description
        "Spare pair PoE TLV is a one octet long
         this field represents Spare pair Detection or
         Classification is required or not";
    }
    leaf spare-pair-pd-config {
      type cdp-ios-xe-oper:cdp-enable-disable;
      description
        "Spare pair PoE TLV is a one octet long
         this field represents Powered Device(PD) Spare Pair
         Desired State";
    }
    leaf spare-pair-pse-operational {
      type cdp-ios-xe-oper:cdp-yes-no;
      description
        "Spare pair PoE TLV is a one octet long
         this field represents Power Source Equipment(PSE) Spare
         Pair Operational State";
    }
  }

  grouping st-cdp-oper {
    description
      "CDP device operational state information";
    leaf device-id {
      type uint32;
      description
        "Device number of this device, Used as a key in the device list";
    }
    leaf device-name {
      type string;
      description
        "Device name in the form of a character string. By default
         device ID is either the device's fully-qualified host name
         (including the domain name) or the device's hardware serial number in ASCII";
    }
    leaf local-intf-name {
      type string;
      description
        "The port or interface on which CDP packets are received";
    }
    leaf port-id {
      type string;
      description
        "Neighbor device's port or interface on which the
         CDP packets are multicasted";
    }
    leaf capability {
      type string;
      description
        "Identifies the functional capability of the device.
         The capability types that can be discovered are:
         R-Router
         T-Transparent bridge
         B-Source-routing bridge
         S-Switch
         H-Host
         I-device is using IGMP
         r-Repeater";
    }
    leaf platform-name {
      type string;
      description
        "Identifies the platform information of the device.
         For example, Cisco 4500";
    }
    leaf version {
      type string;
      description
        "Version Contains the device software release information";
    }
    leaf duplex {
      type cdp-ios-xe-oper:cdp-duplex;
      description
        "Indicates the duplex configuration of the Cisco Discovery Protocol 
         broadcast interface.
         This information is used by network operators to diagnose 
         connectivity problems between adjacent network devices";
    }
    leaf adv-version {
      type cdp-ios-xe-oper:cdp-adv-version;
      description
        "CDP header version of the advertisement that last filled this cache entry";
    }
    container hello-message {
      description
        "CDP Protocol Hello message";
      uses cdp-ios-xe-oper:cdp-protocol-hello;
    }
    leaf vty-mgmt-domain {
      type string;
      description
        "Advertises the configured VLAN Trunking Protocol (VTP)-management-domain
         name of the system. This name is used by network operators to verify
         VTP-domain configuration in adjacent network nodes";
    }
    leaf native-vlan {
      type uint16;
      description
        "Indicates, per interface, the assumed VLAN for untagged packets on the
         interface. Cisco Discovery Protocol learns the native VLAN for an interface.
         This field is implemented only for interfaces that support the
         IEEE 802.1Q protocol
         Remote port's native VLAN [0..1k/4k];
         0 == not received";
    }
    leaf vvid-tag {
      type uint8;
      description
        "Appliance id for appliance vlan
         Appliance ID - Type of device attached to port advertised in the
         appliance TLV";
    }
    leaf vvid {
      type uint16;
      description
        "Appliance VLAN ID - VLAN on the device used by the appliance,
         for instance if the appliance is an IP phone, this is the voice VLAN";
    }
    leaf power {
      type uint32;
      description
        "This field shows the power in milliwatts device is using";
    }
    container power-request {
      description
        "This field used to keep inline power";
      uses cdp-ios-xe-oper:cdp-power-req;
    }
    container power-available {
      description
        "This field used to keep inline power";
      uses cdp-ios-xe-oper:cdp-power-avail;
    }
    leaf unidirectional-mode {
      type cdp-ios-xe-oper:cdp-unidirectional-mode;
      description
        "Specifies ports to unidirectionally transmit or receive traffic.
         Unidirectional Ethernet uses only one strand of fiber for either
         transmitting or receiving one-way traffic for the GigaPort, instead of 
         two strands of fiber for a full-duplex";
    }
    container spare-pair {
      description
        "Spare pair PoE TLV is a one octet long.
         This has following field:
         Bit            Function                            value/Meaning
         0    4-pair PoE Supported                           0=No/1=Yes
         1    Spare pair Detection/Classification required   0=No/1=Yes
         2    PD Spare Pair Desired State                    0=Disabled/1=Enabled
         3    PSE Spare Pair Operational State               0=No/1=Yes
         4:7   Reserved
        ";
      uses cdp-ios-xe-oper:cdp-tdl-spare-pair-poe;
    }
    leaf mgmt-address {
      type inet:ip-address;
      description
        "Device's management addresses";
    }
    leaf ip-address {
      type inet:ip-address;
      description
        "IPv4 address of the device";
    }
    leaf ipv6-address {
      type inet:ip-address;
      description
        "IPv6 address of the device";
    }
    leaf clns-address {
      type string;
      description
        "CLNS address of the device";
    }
    leaf decnet-addr {
      type string;
      description
        "DECNET address of the device";
    }
    leaf novell-addr {
      type string;
      description
        "Novell address of the device.
         It has a 4 byte net number followed by
         6 bytes of  node information";
    }
    leaf second-port-status {
      type string;
      description
        "Used to keep PC port status on IP phone";
    }
    leaf table-id {
      type uint16;
      description
        "Table id of ip routing process";
    }
    leaf neighbor-identifier {
      type string;
      description
        "Neighbor identifier received";
    }
  }

  container cdp-neighbor-details {
    config false;
    description
      "Cisco CDP neighbor operational data";
    list cdp-neighbor-detail {
      key "device-id";
      description
        "List of CDP neighbor details";
      uses cdp-ios-xe-oper:st-cdp-oper;
    }
  }
}
