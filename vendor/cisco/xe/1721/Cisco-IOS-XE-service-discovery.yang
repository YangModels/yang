module Cisco-IOS-XE-service-discovery {
  namespace "http://cisco.com/ns/yang/Cisco-IOS-XE-service-discovery";
  prefix ios-sd;

  import cisco-semver {
    prefix cisco-semver;
  }
  import Cisco-IOS-XE-native {
    prefix ios;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Native Service Discovery Yang model.
     Copyright (c) 2016 by Cisco Systems, Inc.
     All rights reserved.";

  revision 2019-07-01 {
    description
      "Establish semantic version baseline";
    cisco-semver:module-version "1.0.0";
  }
  revision 2017-02-07 {
    description
      "Initial revision";
  }

  grouping service-list-match-grouping {
    container match {
      description
        "Configure parameters for service-list name";
      leaf learnt-interface {
        description
          "match the interface where service is learnt";
        type empty;
      }
      container location {
        description
          "match location information";
        presence "true";
        leaf civic {
          description
            "Civic location";
          type string;
        }
      }
      container message-type {
        description
          "To set the message type";
        presence "true";
        leaf announcement {
          description
            "Match Announcement/Responses";
          type empty;
        }
        leaf query {
          description
            "Match Query";
          type empty;
        }
        leaf any {
          description
            "Match Any";
          type empty;
        }
      }
      leaf service-instance {
        description
          "To set the Service Instance";
        type string;
      }
      leaf service-type {
        description
          "match mDNS service type string";
        type string;
      }
    }
  }

  grouping config-service-list-grouping {
    container service-list {
      description
        "Enter the service list";
      list mdns-sd {
        description
          "Service-list for mdns-sd";
        key "service-list-name";
        leaf service-list-name {
          description
            "service-list name";
          type string;
        }
        list deny {
          description
            "Specify packets to reject";
          key "deny-pack";
          leaf deny-pack {
            type uint8 {
              range "0..100";
            }
          }
          uses service-list-match-grouping;
        }
        list permit {
          description
            "Specify packets to forward";
          key "deny-pack";
          leaf deny-pack {
            type uint8 {
              range "0..100";
            }
          }
          uses service-list-match-grouping;
        }
        container query {
          description
            "Service-list Query for mdns-sd";
          leaf service-type {
            description
              "Configure periodicity for each service-type";
            type string;
          }
        }
      }
    }
  }

  augment "/ios:native" {
    uses config-service-list-grouping;
  }
}
