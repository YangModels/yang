module Cisco-IOS-XE-wireless-rule-mdns-oper {
  yang-version 1;
  namespace "http://cisco.com/ns/yang/Cisco-IOS-XE-wireless-rule-mdns-oper";
  prefix wireless-rule-mdns-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for rule MDNS operational data.
     Copyright (c) 2017, 2020 by Cisco Systems, Inc.
     All rights reserved.";

  revision 2020-07-01 {
    description
      "Initial revision";
    reference
      "1.0.0";
    cisco-semver:module-version "1.0.0";
  }

  grouping mdns-id-info {
    description
      "MDNS ID information";
    leaf mdns-id {
      type uint32;
      description
        "MDNS ID";
    }
    leaf group-name {
      type string;
      description
        "Group name for APs";
    }
    list mdns-id-associated-ap {
      key "ap-mac";
      description
        "Associated APs for a particular MDNS ID";
      uses wireless-rule-mdns-oper:mdns-id-associated-ap;
    }
  }

  grouping mdns-id-associated-ap {
    description
      "Associated APs for a particular MDNS ID";
    leaf ap-mac {
      type yang:mac-address;
      description
        "AP MAC address";
    }
    leaf ap-name {
      type string;
      description
        "AP name";
    }
  }

  grouping rule-associated-ap {
    description
      "Associated APs for a particular rule";
    leaf ap-mac {
      type yang:mac-address;
      description
        "AP MAC address";
    }
    leaf ap-name {
      type string;
      description
        "AP name";
    }
  }

  grouping rule-info {
    description
      "Rule information";
    leaf rule-name {
      type string;
      description
        "Rule name";
    }
    leaf rule-priority {
      type uint32;
      description
        "Rule priority";
    }
    list rule-associated-ap {
      key "ap-mac";
      description
        "Associated APs for a particular rule";
      uses wireless-rule-mdns-oper:rule-associated-ap;
    }
  }

  container rule-mdns-oper-data {
    config false;
    description
      "Rule MDNS operational data";
    list mdns-id-info {
      key "mdns-id";
      description
        "MDNS ID information";
      uses wireless-rule-mdns-oper:mdns-id-info;
    }
    list rule-info {
      key "rule-name";
      description
        "Rule information";
      uses wireless-rule-mdns-oper:rule-info;
    }
  }
}
