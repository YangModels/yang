module Cisco-IOS-XE-wireless-mdns-oper {
  yang-version 1;
  namespace "http://cisco.com/ns/yang/Cisco-IOS-XE-wireless-mdns-oper";
  prefix mdns-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for MDNS gateway operational data. This operational
     data consists of consolidated MDNS packet statistics
     and per WLAN MDNS packet statistics.
     Copyright (c) 2017-2019 by Cisco Systems, Inc.
     All rights reserved.";

  revision 2019-11-01 {
    description
      "Added MDNS statistics per GLAN.";
    reference
      "1.2.0";
    cisco-semver:module-version "1.2.0";
  }
  revision 2019-05-01 {
    description
      "- Added MDNS statistics per RLAN.
       - Added attributes for MDNS query type statistics.
       - Added semantic version";
    reference
      "1.1.0";
    cisco-semver:module-version "1.1.0";
  }
  revision 2018-09-01 {
    description
      "Initial revision";
    reference
      "1.0.0";
    cisco-semver:module-version "1.0.0";
  }

  grouping mdns-stats-epoch {
    description
      "MDNS statistics reset timestamp";
    leaf last-clear-time {
      type yang:date-and-time;
      description
        "MDNS statistics reset timestamp";
    }
  }

  grouping st-mdns-packet-stats {
    description
      "MDNS packet statistics";
    leaf pak-sent {
      type yang:counter64;
      description
        "Total number of MDNS packets sent";
    }
    leaf pak-sent-v4 {
      type yang:counter64;
      description
        "Total number of IPv4 MDNS packets sent";
    }
    leaf pak-sent-advt-v4 {
      type yang:counter64;
      description
        "Total number of IPv4 MDNS advertisement packets sent";
    }
    leaf pak-sent-query-v4 {
      type yang:counter64;
      description
        "Total number of IPv4 MDNS query packets sent";
    }
    leaf pak-sent-v6 {
      type yang:counter64;
      description
        "Total number of IPv6 MDNS packets sent";
    }
    leaf pak-sent-advt-v6 {
      type yang:counter64;
      description
        "Total number of IPv6 MDNS advertisement packets sent";
    }
    leaf pak-sent-query-v6 {
      type yang:counter64;
      description
        "Total number of IPv6 MDNS query packets sent";
    }
    leaf pak-sent-mcast {
      type yang:counter64;
      description
        "Total number of MDNS multicast packets sent";
    }
    leaf pak-sent-mcast-v4 {
      type yang:counter64;
      description
        "Total number of IPv4 MDNS multicast packets sent";
    }
    leaf pak-sent-mcast-v6 {
      type yang:counter64;
      description
        "Total number of IPv6 MDNS multicast packets sent";
    }
    leaf pak-received {
      type yang:counter64;
      description
        "Total number of MDNS packets received";
    }
    leaf pak-received-advt {
      type yang:counter64;
      description
        "Total number of MDNS advertisement packets received";
    }
    leaf pak-received-query {
      type yang:counter64;
      description
        "Total number of MDNS query packets received";
    }
    leaf pak-received-v4 {
      type yang:counter64;
      description
        "Total number of IPv4 MDNS packets received";
    }
    leaf pak-received-advt-v4 {
      type yang:counter64;
      description
        "Total number of IPv4 MDNS advertisement packets received";
    }
    leaf pak-received-query-v4 {
      type yang:counter64;
      description
        "Total number of IPv4 MDNS query packets received";
    }
    leaf pak-received-v6 {
      type yang:counter64;
      description
        "Total number of IPv6 MDNS packets received";
    }
    leaf pak-received-advt-v6 {
      type yang:counter64;
      description
        "Total number of IPv6 MDNS advertisement packets received";
    }
    leaf pak-received-query-v6 {
      type yang:counter64;
      description
        "Total number of IPv6 MDNS query packets received";
    }
    leaf pak-dropped {
      type yang:counter64;
      description
        "Total number of MDNS packets dropped";
    }
    leaf ptr-query {
      type yang:counter64;
      description
        "Total number of PTR queries";
    }
    leaf srv-query {
      type yang:counter64;
      description
        "Total number of SRV queries";
    }
    leaf a-query {
      type yang:counter64;
      description
        "Total number of IPV4 queries";
    }
    leaf aaaa-query {
      type yang:counter64;
      description
        "Total number of IPV6 queries";
    }
    leaf txt-query {
      type yang:counter64;
      description
        "Total number of TEXT queries";
    }
    leaf any-query {
      type yang:counter64;
      description
        "Total number of ANY queries";
    }
    leaf other-query {
      type yang:counter64;
      description
        "Total number of OTHER queries";
    }
  }

  grouping st-mdns-wlan-stats {
    description
      "MDNS statistics per WLAN";
    leaf wlan-id {
      type uint32 {
        range "0 .. 4096";
      }
      description
        "WLAN identifier";
    }
    container stats-wlan {
      description
        "MDNS statistics for WLAN";
      uses mdns-oper:st-mdns-packet-stats;
    }
  }

  grouping st-mdns-rlan-stats {
    description
      "MDNS statistics per RLAN";
    leaf rlan-id {
      type uint32 {
        range "1 .. 128";
      }
      description
        "RLAN identifier";
    }
    container stats-rlan {
      description
        "MDNS statistics for RLAN";
      uses mdns-oper:st-mdns-packet-stats;
    }
  }

  grouping st-mdns-glan-stats {
    description
      "MDNS statistics per GLAN";
    leaf glan-id {
      type uint32 {
        range "1 .. 5";
      }
      description
        "GLAN identifier";
    }
    container stats-glan {
      description
        "MDNS statistics for GLAN";
      uses mdns-oper:st-mdns-packet-stats;
    }
  }

  grouping st-mdns-global-stats {
    description
      "Global MDNS statistics";
    container stats-global {
      description
        "Global MDNS statistics";
      uses mdns-oper:st-mdns-packet-stats;
    }
  }

  container mdns-oper-data {
    config false;
    description
      "MDNS gateway operational data";
    container mdns-global-stats {
      presence "mdns-global-stats";
      description
        "MDNS global statistics";
      uses mdns-oper:st-mdns-global-stats;
      uses mdns-oper:mdns-stats-epoch;
    }
    list mdns-wlan-stats {
      key "wlan-id";
      description
        "MDNS statistics per WLAN";
      uses mdns-oper:st-mdns-wlan-stats;
      uses mdns-oper:mdns-stats-epoch;
    }
    list mdns-rlan-stats {
      key "rlan-id";
      description
        "MDNS statistics per RLAN";
      uses mdns-oper:st-mdns-rlan-stats;
      uses mdns-oper:mdns-stats-epoch;
    }
    list mdns-glan-stats {
      key "glan-id";
      description
        "MDNS statistics per GLAN";
      uses mdns-oper:st-mdns-glan-stats;
      uses mdns-oper:mdns-stats-epoch;
    }
  }
}
