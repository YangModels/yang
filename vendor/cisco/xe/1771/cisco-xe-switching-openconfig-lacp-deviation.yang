module cisco-xe-switching-openconfig-lacp-deviation {
  namespace "http://cisco.com/ns/yang/cisco-xe-switching-openconfig-lacp-deviation";
  prefix cisco-xe-oc-switch-lacp-dev;

  import openconfig-interfaces {
    prefix oc-if;
  }
  import openconfig-lacp {
    prefix oc-lacp;
  }

  organization
    "Cisco Systems";
  description
    "This module defines deviation statements for openconfig-lacp model applicable to IOS XE Switching platforms.";

  revision 2021-04-28 {
    description
      "Initial revision";
    reference
      "RFC 6020: YANG - A Data Modeling Language for the
       Network Configuration Protocol (NETCONF)";
  }

  deviation "/oc-lacp:lacp/oc-lacp:config" {
    deviate not-supported;
  }

  deviation "/oc-lacp:lacp/oc-lacp:state" {
    deviate not-supported;
  }

  deviation "/oc-lacp:lacp/oc-lacp:interfaces/oc-lacp:interface/oc-lacp:config/oc-lacp:interval" {
    deviate not-supported;
  }

  deviation "/oc-lacp:lacp/oc-lacp:interfaces/oc-lacp:interface/oc-lacp:config/oc-lacp:lacp-mode" {
    deviate not-supported;
  }

  deviation "/oc-lacp:lacp/oc-lacp:interfaces/oc-lacp:interface/oc-lacp:config/oc-lacp:system-id-mac" {
    deviate not-supported;
  }

  deviation "/oc-lacp:lacp/oc-lacp:interfaces/oc-lacp:interface/oc-lacp:config/oc-lacp:system-priority" {
    deviate not-supported;
  }

  deviation "/oc-lacp:lacp/oc-lacp:interfaces/oc-lacp:interface/oc-lacp:state" {
    deviate not-supported;
  }

  deviation "/oc-lacp:lacp/oc-lacp:interfaces/oc-lacp:interface/oc-lacp:members/oc-lacp:member/oc-lacp:state/oc-lacp:activity" {
    deviate not-supported;
  }

  deviation "/oc-lacp:lacp/oc-lacp:interfaces/oc-lacp:interface/oc-lacp:members/oc-lacp:member/oc-lacp:state/oc-lacp:timeout" {
    deviate not-supported;
  }

  deviation "/oc-lacp:lacp/oc-lacp:interfaces/oc-lacp:interface/oc-lacp:members/oc-lacp:member/oc-lacp:state/oc-lacp:synchronization" {
    deviate not-supported;
  }

  deviation "/oc-lacp:lacp/oc-lacp:interfaces/oc-lacp:interface/oc-lacp:members/oc-lacp:member/oc-lacp:state/oc-lacp:aggregatable" {
    deviate not-supported;
  }

  deviation "/oc-lacp:lacp/oc-lacp:interfaces/oc-lacp:interface/oc-lacp:members/oc-lacp:member/oc-lacp:state/oc-lacp:collecting" {
    deviate not-supported;
  }

  deviation "/oc-lacp:lacp/oc-lacp:interfaces/oc-lacp:interface/oc-lacp:members/oc-lacp:member/oc-lacp:state/oc-lacp:distributing" {
    deviate not-supported;
  }

  deviation "/oc-lacp:lacp/oc-lacp:interfaces/oc-lacp:interface/oc-lacp:members/oc-lacp:member/oc-lacp:state/oc-lacp:partner-port-num" {
    deviate not-supported;
  }

  deviation "/oc-lacp:lacp/oc-lacp:interfaces/oc-lacp:interface/oc-lacp:members/oc-lacp:member/oc-lacp:state/oc-lacp:counters" {
    deviate not-supported;
  }
}
