module Cisco-IOS-XE-xcopy-rpc {
  yang-version 1.1;
  namespace "http://cisco.com/ns/yang/Cisco-IOS-XE-xcopy-rpc";
  prefix xcopy-ios-xe-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Copyright (c) 2020 by Cisco Systems, Inc.
     All rights reserved.";

  revision 2021-03-01 {
    description
      "Initial revision";
    reference
      "1.0.0";
    cisco-semver:module-version "1.0.0";
  }

  grouping xcopy {
    description
      "Express copy using HTTPS or SCP to copy files from or to device.
       This uses the management interface or forwarding interface in global VRF.";
    leaf uuid {
      type string;
      description
        "The UUID (universally unique identifier) is a string and is a textual
         representation of a UUID.
         UUID is used to uniquely identify the express copy action invoked via RPC
         and it is replayed back in the copy progress notifications to correlate
         them back to the original express copy operation.";
    }
    leaf source-path {
      type string {
        length "0..512";
        pattern "[\\] A-Za-z0-9!\"#%&()*+,\\-./:;<=>^?@\\\\$_`{|}\\[']+";
      }
      description
        "Source path:
         for download to device: scp://user:password@ipv4 address:/path/to/file
         or https://ipv4 address/path/to/file
         from upload from device: /path/to/file in bootflash";
    }
    leaf destination-path {
      type string {
        length "0..512";
        pattern "[\\] A-Za-z0-9!\"#%&()*+,\\-./:;<=>^?@\\\\$_`{|}\\[']+";
      }
      description
        "Destination path:
         for download to device: /path/to/file in bootflash
         for upload to device: scp://user:password@ipv4 address:/path/to/file";
    }
    leaf username {
      type string;
      description
        "Username to be used for remote device";
    }
    leaf password {
      type string;
      description
        "Password to be used for remote device";
    }
    leaf vrf {
      type string {
        length "0..32";
      }
      description
        "VRF name instance to reach remote device.
         For management or global VRF leave this field blank other wise
         specify the IOS configured VRF name.";
    }
    leaf trustpoint {
      type string {
        length "0..40";
      }
      description
        "Trust point of remote device configured in IOS.
         This is used to get the public key and provided to copy so that
         copy is more secured.";
    }
  }

  grouping xcopy-response {
    description
      "Response to action request.";
    leaf uuid {
      type string;
      description
        "The UUID (universally unique identifier) is a string and is a textual
         representation of a UUID.";
    }
  }

  rpc xcopy {
    description
      "Express copy action command";
    input {
      uses xcopy-ios-xe-rpc:xcopy;
    }
    output {
      uses xcopy-ios-xe-rpc:xcopy-response;
    }
  }
}
