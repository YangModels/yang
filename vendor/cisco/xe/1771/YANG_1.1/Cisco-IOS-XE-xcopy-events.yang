module Cisco-IOS-XE-xcopy-events {
  yang-version 1.1;
  namespace "http://cisco.com/ns/yang/Cisco-IOS-XE-xcopy-events";
  prefix xcopy-ios-xe-events;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for express copy status notification for copy events.
     Copyright (c) 2020-2021 by Cisco Systems, Inc.
     All rights reserved.";

  revision 2021-03-01 {
    description
      "Initial revision";
    reference
      "1.0.0";
    cisco-semver:module-version "1.0.0";
  }

  typedef xcopy-progress-status {
    type enumeration {
      enum xcopy-init {
        value 0;
        description
          "Express copy initialization";
      }
      enum xcopy-start {
        value 1;
        description
          "Express copy start";
      }
      enum xcopy-inprogress {
        value 2;
        description
          "Express copy in progress";
      }
      enum xcopy-success {
        value 3;
        description
          "Express copy success";
      }
      enum xcopy-failed {
        value 4;
        description
          "Copy failed";
      }
    }
    description
      "Express copy status";
  }

  typedef xcopy-errcode {
    type enumeration {
      enum xcopy-no-error {
        value 0;
        description
          "Express copy in progress or success";
      }
      enum xcopy-invalid-format {
        value 1;
        description
          "Express copy input format not valid";
      }
      enum xcopy-invalid-input {
        value 2;
        description
          "Express copy invalid input";
      }
      enum xcopy-host-not-reachable {
        value 3;
        description
          "Express copy could not reach host";
      }
      enum xcopy-utility-failed {
        value 4;
        description
          "Express copy utility failed";
      }
      enum xcopy-timeout-error {
        value 5;
        description
          "Express copy timed out";
      }
      enum xcopy-unknown-error {
        value 6;
        description
          "Express copy unknown error";
      }
    }
    description
      "Express copy error code";
  }

  grouping id-common-notification-header {
    description
      "Express copy notification header";
    leaf uuid {
      type string;
      description
        "The UUID (universally unique identifier) is a string and is a textual
         representation of a UUID.
         UUID is used to uniquely identify the copy action invoked via RPC
         and it is replayed back in the copy progress notifications to correlate
         them back to the original express copy operation.";
    }
  }

  grouping xcopy-event-fields {
    description
      "Express copy status";
    leaf status {
      type xcopy-ios-xe-events:xcopy-progress-status;
      description
        "Express copy status";
    }
    leaf percentage {
      type uint8;
      units "percent";
      description
        "Percent of completion for in-progress express copy.
         If the value is 0, the field is not applicable";
    }
    leaf download-speed {
      type uint16;
      units "MBps";
      description
        "Express copy speed";
    }
    leaf expected-duration {
      type uint16;
      units "seconds";
      description
        "Express copy expected duration ";
    }
    leaf time-left {
      type uint16;
      units "seconds";
      description
        "Express copy time left";
    }
    leaf time-spent {
      type uint16;
      units "seconds";
      description
        "Express copy time spent";
    }
    leaf filesize {
      type uint16;
      units "megabytes";
      description
        "Express copy file size";
    }
    leaf downloaded-size {
      type uint16;
      units "megabytes";
      description
        "Express copy so far";
    }
    leaf start-time {
      type yang:date-and-time;
      description
        "Start time of the express copy";
    }
    leaf event-time {
      type yang:date-and-time;
      description
        "Event post time of the express copy progress";
    }
    leaf errcode {
      type xcopy-ios-xe-events:xcopy-errcode;
      description
        "Error code of express copy failure";
    }
    leaf errstr {
      type string;
      description
        "Error string of express copy failure";
    }
  }

  notification xcopy-status {
    description
      "Express copy status notification";
    uses xcopy-ios-xe-events:id-common-notification-header;
    uses xcopy-ios-xe-events:xcopy-event-fields;
  }
}
