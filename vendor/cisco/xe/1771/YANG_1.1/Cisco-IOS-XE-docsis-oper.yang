module Cisco-IOS-XE-docsis-oper {
  yang-version 1.1;
  namespace "http://cisco.com/ns/yang/Cisco-IOS-XE-docsis-oper";
  prefix docsis-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for operational data on CMTS.
     Copyright (c) 2018-2019 by Cisco Systems, Inc.
     All rights reserved.";

  revision 2019-05-01 {
    description
      "Added semantic version";
    reference
      "1.0.1";
    cisco-semver:module-version "1.0.1";
  }
  revision 2019-03-01 {
    description
      "Initial revision";
    reference
      "1.0.0";
    cisco-semver:module-version "1.0.0";
  }

  typedef cm-state {
    type enumeration {
      enum shut-down {
        value 0;
      }
      enum offline {
        value 1;
      }
      enum resetting {
        value 2;
      }
      enum cc-pending {
        value 3;
      }
      enum init-r1 {
        value 4;
      }
      enum cc-r1 {
        value 5;
      }
      enum init-r2 {
        value 6;
      }
      enum cc-r2 {
        value 7;
      }
      enum init-rc {
        value 8;
      }
      enum eject-epk {
        value 9;
      }
      enum expire-eae {
        value 10;
      }
      enum assign-epk {
        value 11;
      }
      enum reject-ept {
        value 12;
      }
      enum expire-ept {
        value 13;
      }
      enum assign-ept {
        value 14;
      }
      enum init-d {
        value 15;
      }
      enum sinit-d {
        value 16;
      }
      enum init6-s {
        value 17;
      }
      enum sinit6-s {
        value 18;
      }
      enum init-io {
        value 19;
      }
      enum sinit-io {
        value 20;
      }
      enum init6-a {
        value 21;
      }
      enum sinit6-a {
        value 22;
      }
      enum init-dr {
        value 23;
      }
      enum sinit-dr {
        value 24;
      }
      enum init6-r {
        value 25;
      }
      enum sinit6-r {
        value 26;
      }
      enum init-i {
        value 27;
      }
      enum sinit-i {
        value 28;
      }
      enum init6-i {
        value 29;
      }
      enum sinit6-i {
        value 30;
      }
      enum init-o {
        value 31;
      }
      enum sinit-o {
        value 32;
      }
      enum init6-o {
        value 33;
      }
      enum sinit6-o {
        value 34;
      }
      enum init-tod {
        value 35;
      }
      enum eae-time-of-day-start {
        value 36;
      }
      enum init-ipv6-tod {
        value 37;
      }
      enum eae-ipv6-tod {
        value 38;
      }
      enum reject-m {
        value 39;
      }
      enum sreject-m {
        value 40;
      }
      enum reject-ts {
        value 41;
      }
      enum sreject-ts {
        value 42;
      }
      enum reject-ip {
        value 43;
      }
      enum sreject-ip {
        value 44;
      }
      enum reject-c {
        value 45;
      }
      enum sreject-c {
        value 46;
      }
      enum reject-na {
        value 47;
      }
      enum sreject-na {
        value 48;
      }
      enum online {
        value 49;
      }
      enum reject-pk {
        value 50;
      }
      enum expire-pk {
        value 51;
      }
      enum online-pk {
        value 52;
      }
      enum reject-pt {
        value 53;
      }
      enum expire-pt {
        value 54;
      }
      enum online-pt {
        value 55;
      }
      enum online-d {
        value 56;
      }
      enum reject-pkd {
        value 57;
      }
      enum expire-pkd {
        value 58;
      }
      enum online-pkd {
        value 59;
      }
      enum reject-ptd {
        value 60;
      }
      enum expire-ptd {
        value 61;
      }
      enum online-ptd {
        value 62;
      }
      enum w-online {
        value 63;
      }
      enum w-eject-pk {
        value 64;
      }
      enum w-expire-pk {
        value 65;
      }
      enum w-online-pk {
        value 66;
      }
      enum w-eject-pt {
        value 67;
      }
      enum w-expire-pt {
        value 68;
      }
      enum w-online-pt {
        value 69;
      }
      enum w-online-d {
        value 70;
      }
      enum w-eject-pkd {
        value 71;
      }
      enum w-expire-pkd {
        value 72;
      }
      enum w-online-pkd {
        value 73;
      }
      enum w-eject-ptd {
        value 74;
      }
      enum w-expire-ptd {
        value 75;
      }
      enum w-online-ptd {
        value 76;
      }
      enum p-online {
        value 77;
      }
      enum p-eject-pk {
        value 78;
      }
      enum p-expire-pk {
        value 79;
      }
      enum p-online-pk {
        value 80;
      }
      enum p-eject-pt {
        value 81;
      }
      enum p-expire-pt {
        value 82;
      }
      enum p-online-pt {
        value 83;
      }
      enum p-online-d {
        value 84;
      }
      enum p-eject-pkd {
        value 85;
      }
      enum p-expire-pkd {
        value 86;
      }
      enum p-online-pkd {
        value 87;
      }
      enum p-eject-ptd {
        value 88;
        description
          "collection";
      }
      enum p-expire-ptd {
        value 89;
        description
          "collection";
      }
      enum p-online-ptd {
        value 90;
        description
          "collection";
      }
      enum w-online-em {
        value 91;
      }
      enum w-eject-pk-em {
        value 92;
      }
      enum w-expire-pk-em {
        value 93;
      }
      enum w-online-pk-em {
        value 94;
      }
      enum w-eject-pt-em {
        value 95;
      }
      enum w-expire-pt-em {
        value 96;
      }
      enum w-online-pt-em {
        value 97;
      }
      enum w-online-d-em {
        value 98;
      }
      enum w-eject-pkd-em {
        value 99;
      }
      enum w-expire-pkd-em {
        value 100;
      }
      enum w-online-pkd-em {
        value 101;
      }
      enum w-eject-ptd-em {
        value 102;
      }
      enum w-expire-ptd-em {
        value 103;
      }
      enum w-online-ptd-em {
        value 104;
      }
      enum w-online-bm {
        value 105;
        description
          "collection";
      }
      enum w-eject-pk-bm {
        value 106;
        description
          "collection";
      }
      enum w-expire-pk-bm {
        value 107;
      }
      enum w-online-pk-bm {
        value 108;
      }
      enum w-eject-pt-bm {
        value 109;
      }
      enum w-expire-pt-bm {
        value 110;
      }
      enum w-online-pt-bm {
        value 111;
      }
      enum w-online-d-bm {
        value 112;
      }
      enum w-eject-pkd-bm {
        value 113;
      }
      enum w-expire-pkd-bm {
        value 114;
      }
      enum w-online-pkd-bm {
        value 115;
      }
      enum w-eject-ptd-bm {
        value 116;
      }
      enum w-expire-ptd-bm {
        value 117;
      }
      enum w-online-ptd-bm {
        value 118;
      }
    }
    description
      "Cable modem state";
  }

  typedef docsis-version-type {
    type enumeration {
      enum docsis1-0 {
        value 0;
      }
      enum docsis1-1 {
        value 1;
      }
      enum docsis2-0 {
        value 2;
      }
      enum docsis3-0 {
        value 3;
      }
      enum docsis3-1 {
        value 4;
      }
    }
    description
      "Cable modem DOCSIS version";
  }

  typedef rpd-state-type {
    type enumeration {
      enum shutdown {
        value 0;
      }
      enum rpd-offline {
        value 1;
      }
      enum init-auth {
        value 2;
      }
      enum init-gcp {
        value 3;
      }
      enum init-clock {
        value 4;
      }
      enum init-l2tp {
        value 5;
      }
      enum rpd-online {
        value 6;
      }
    }
    description
      "RPD state";
  }

  typedef rpd-core-role-type {
    type enumeration {
      enum core-unknown {
        value 0;
      }
      enum principal {
        value 1;
      }
      enum auxiliary {
        value 2;
      }
    }
    description
      "RPD core role";
  }

  typedef rpd-ha-role-type {
    type enumeration {
      enum active {
        value 0;
      }
      enum standby {
        value 1;
      }
      enum ha-unknown {
        value 2;
      }
    }
    description
      "RPD HA role";
  }

  typedef rpd-auth-method-type {
    type enumeration {
      enum auth-bypass {
        value 0;
      }
      enum auth-disabled {
        value 1;
      }
      enum auth-enbaled {
        value 2;
      }
    }
    description
      "RPD authentication method";
  }

  typedef rpd-conf-type {
    type enumeration {
      enum rpd-node {
        value 0;
        description
          "RPD's configuration type is node";
      }
      enum rpd-shelf {
        value 1;
        description
          "RPD's configuration type is shelf";
      }
    }
    description
      "RPD type";
  }

  typedef sbfd-conf-type {
    type enumeration {
      enum sbfd-not-configured {
        value 0;
        description
          "Seamless bidirectional forwarding detection is not enabled";
      }
      enum sbfd-configured {
        value 1;
        description
          "Seamless bidirectional forwarding detection is enabled";
      }
    }
    description
      "Seamless bidirectional forwarding detection configuration";
  }

  typedef nw-delay-static-conf-type {
    type enumeration {
      enum netork-delay-static-not-cfg {
        value 0;
        description
          "Network delay static is not set";
      }
      enum netork-delay-static {
        value 1;
        description
          "Network delay static is set";
      }
    }
    description
      "Network delay static status";
  }

  typedef ptp-clk-prof-conf-type {
    type enumeration {
      enum ptp-clock-profile-not-cfg {
        value 0;
        description
          "No precision time protocol profile configured";
      }
      enum ptp-clock-profile {
        value 1;
        description
          "Precision time protocol profile is configured";
      }
    }
    description
      "Precision time protocol profile configuration";
  }

  typedef ssf-prof-conf-type {
    type enumeration {
      enum ssd-profile-not-cfg {
        value 0;
        description
          "Secure software download profile is not configured";
      }
      enum ssd-profile {
        value 1;
        description
          "Secure software download profile configured";
      }
    }
    description
      "Secure software download profile configuration";
  }

  typedef oob-us-evt-conf-type {
    type enumeration {
      enum oob-551-us-event-profile-not-cfg {
        value 0;
        description
          "Out of bind 55-1 upstream event profile id is not configured";
      }
      enum oob-551-us-event-profile {
        value 1;
        description
          "Out of bind 55-1 upstream event profile id is configured";
      }
    }
    description
      "Out of bind 55-1 upstream event profile id configuration";
  }

  typedef rpd-event-prof-conf-type {
    type enumeration {
      enum rpd-event-profile-not-cfg {
        value 0;
        description
          "RPD event profile is not configured";
      }
      enum rpd-event-profile {
        value 1;
        description
          "RPD event profile is configured";
      }
    }
    description
      "RPD event profile configuration";
  }

  typedef pt-prof-conf-type {
    type enumeration {
      enum ds-pilot-tone-not-configured {
        value 0;
        description
          "Downstream pilot tone profile is not configured";
      }
      enum ds-pilot-tone {
        value 1;
        description
          "Downstream pilot tone profile is configured";
      }
    }
    description
      "Downstream pilot tone configuration";
  }

  typedef nw-delay-conf-type {
    type enumeration {
      enum netork-delay-sampling-interval-not-cfg {
        value 0;
        description
          "Network delay sampling interval is not set";
      }
      enum netork-delay-sampling-interval {
        value 1;
        description
          "Network delay sampling interval is set";
      }
    }
    description
      "Network delay sampling interval status";
  }

  typedef cbr-lic-conf-type {
    type enumeration {
      enum downstream-license {
        value 0;
        description
          "DOCSIS down stream";
      }
      enum upstream-license {
        value 1;
        description
          "DOCSIS upstream";
      }
      enum wan-license {
        value 2;
        description
          "WAN port";
      }
      enum subscriber-license {
        value 3;
        description
          "Subscriber";
      }
      enum lcha-license {
        value 4;
        description
          "Lice card high available";
      }
      enum video-narrowcast-license {
        value 5;
        description
          "Video narrow cast";
      }
      enum video-narrowcast-replicate-license {
        value 6;
        description
          "Video narrow cast replicate";
      }
      enum video-narrowcast-pkey-license {
        value 7;
        description
          "Video narrow cast power key";
      }
      enum video-narrowcast-pme-license {
        value 8;
        description
          "Video narrow cast privacy mode encryption";
      }
      enum video-narrowcast-dvb-license {
        value 9;
        description
          "Video narrow cast video digital video broadcasting";
      }
      enum video-broadcast-license {
        value 10;
        description
          "Video broadcast";
      }
      enum video-broadcast-enc-license {
        value 11;
        description
          "Video broadcast power key";
      }
      enum docsis31-downstream-channel-license {
        value 12;
        description
          "DOCSIS 3.1 downstream";
      }
      enum docsis31-downstream-channel-2-kqam-license {
        value 13;
        description
          "DOCSIS 3.1 downstream 2 kilo hertz QAM";
      }
      enum docsis31-downstream-channel-4-kqam-license {
        value 14;
        description
          "DOCSIS 3.1 downstream 4 kilo hertz QAM";
      }
      enum rphy-video-broadcast-license {
        value 15;
        description
          "RPD video broadcast";
      }
      enum docsis31-upstream-channel-exclusive-license {
        value 16;
        description
          "DOCSIS 3.1 upstream exclusive";
      }
      enum docsis31-upstream-channel-overlap-license {
        value 17;
        description
          "DOCSIS 3.1 upstream overlap";
      }
      enum wan-100-g-license {
        value 18;
        description
          "100 Gigabit Ethernet";
      }
      enum cpb-license {
        value 19;
        description
          "Core Peak Bandwidth";
      }
    }
    description
      "Cable license type";
  }

  typedef lic-enforced-state-type {
    type enumeration {
      enum not-enforced {
        value 0;
        description
          "No enforcement";
      }
      enum capped-enforced {
        value 1;
        description
          "Capped enforcement";
      }
      enum deact-enforced {
        value 2;
        description
          "Deactivated enforcement";
      }
    }
    description
      "Enforcement state";
  }

  typedef sup250-100g-conf-type {
    type enumeration {
      enum sup250-100-g-not-cfg {
        value 0;
        description
          "100 Gigabit Ethernet backhaul interface does not consume WAN License";
      }
      enum sup250-100-g-enabled {
        value 1;
        description
          "100 Gigabit Ethernet backhaul interface consumes WAN License";
      }
    }
    description
      "100 Gigabit Ethernet backhaul interface";
  }

  typedef license-quarter-type {
    type enumeration {
      enum first-quarter {
        value 0;
      }
      enum second-quarter {
        value 1;
      }
      enum third-quarter {
        value 2;
      }
      enum fourth-quarter {
        value 3;
      }
    }
    description
      "License quarter type";
  }

  grouping upstream-chan-type {
    description
      "Operational data for upstream channel";
    leaf chan-index {
      type uint8;
      description
        "Upstream channel index used by the CM";
    }
    leaf rx-power {
      type decimal64 {
        fraction-digits 2;
      }
      units "dBmV";
      description
        "Rx power of the upstream channel";
    }
    leaf timing-offset {
      type uint32;
      description
        "Timing offset of the upstream channel";
    }
  }

  grouping cable-modem {
    description
      "Operational data for a CM";
    leaf mac-address {
      type yang:mac-address;
      description
        "MAC address of the CM";
    }
    leaf ipv4-addr {
      type inet:ipv4-address;
      description
        "IPv4 address of the CM";
    }
    leaf ipv6-addr {
      type inet:ipv6-address;
      description
        "IPv6 address of the CM";
    }
    leaf interface {
      type string;
      description
        "Upstream interface name of the CM";
    }
    leaf state {
      type docsis-ios-xe-oper:cm-state;
      description
        "State of the CM";
    }
    leaf docsis-version {
      type docsis-ios-xe-oper:docsis-version-type;
      description
        "The maximum supported version of DOCSIS that the CM supports";
    }
    leaf primary-sid {
      type uint32;
      description
        "Primary SID of the CM";
    }
    list us-chan {
      description
        "Upstream channel list of the CM";
      uses docsis-ios-xe-oper:upstream-chan-type;
    }
    leaf cpe-number {
      type uint32;
      description
        "CPE MAC address number attached to the CM";
    }
    leaf dual-ip {
      type boolean;
      description
        "Dual IP status, TRUE indicates the CM has both IPv4 and IPv6 address,
         FALSE indicates the CM only has an IPV4 address";
    }
  }

  grouping cm-if-summary-totals {
    description
      "Summary information of CMs on one cable interface";
    leaf interface {
      type string;
      description
        "Upstream interface name";
    }
    leaf total {
      type uint32;
      description
        "Number of CMs";
    }
    leaf registered {
      type uint32;
      description
        "Number of registered CMs";
    }
    leaf operational {
      type uint32;
      description
        "Number of operational CMs";
    }
    leaf unregistered {
      type uint32;
      description
        "Number of CMs that are either offline or attempting to come online but are not yet registered";
    }
    leaf offline {
      type uint32;
      description
        "Number of CMs in offline state";
    }
    leaf wideband {
      type uint32;
      description
        "Number of wideband CMs";
    }
    leaf initrc {
      type uint32;
      description
        "Number of CMs in init(rc) state";
    }
    leaf initd {
      type uint32;
      description
        "Number of CMs in init(d) state";
    }
    leaf initio {
      type uint32;
      description
        "Number of CMs in init(io) state";
    }
    leaf inito {
      type uint32;
      description
        "Number of CMs in init(o) state";
    }
  }

  grouping cm-summary-total {
    description
      "Total modems information on CMTS";
    leaf total {
      type uint32;
      description
        "Total number of CMs on the CMTS";
    }
    leaf registered {
      type uint32;
      description
        "Total number of registered CMs on CMTS";
    }
    leaf operational {
      type uint32;
      description
        "Total number of operational CMs on CMTS";
    }
    leaf unregistered {
      type uint32;
      description
        "Total number of CMs that are either offline or attempting to come online but are not yet registered on the CMTS";
    }
    leaf offline {
      type uint32;
      description
        "Total number of CMs in offline state on CMTS";
    }
    leaf wideband {
      type uint32;
      description
        "Total number of wideband CMs on the CMTS";
    }
    leaf initrc {
      type uint32;
      description
        "Total number of CMs in init(rc) state on the CMTS";
    }
    leaf initd {
      type uint32;
      description
        "Total number of CMs in init(d) state on the CMTS";
    }
    leaf initio {
      type uint32;
      description
        "Total number of CMs in init(io) state on the CMTS";
    }
    leaf inito {
      type uint32;
      description
        "Total number of CMs in init(o) state on the CMTS";
    }
    list cm-if-summary-totals {
      key "interface";
      description
        "The list of summary information of CMs per cable interface";
      uses docsis-ios-xe-oper:cm-if-summary-totals;
    }
  }

  grouping cm-dc-summary {
    description
      "Total modems DOCSIS device class information on the CMTS";
    leaf online {
      type uint32;
      description
        "Total number of CMs currently online";
    }
    leaf unrep {
      type uint32;
      description
        "Total number of CMs for which the device class information is unreported or unavailable";
    }
    leaf cm {
      type uint32;
      description
        "Total number of CMs that have reported the device class as an embedded cable modem";
    }
    leaf e-rtr {
      type uint32;
      description
        "Total number of CMs that  have reported the device class as an embedded router";
    }
    leaf e-mta {
      type uint32;
      description
        "Total number of CMs that have reported the device class as an embedded multimedia terminal adapter";
    }
    leaf e-stb {
      type uint32;
      description
        "Total number of CMs that have reported the device class as an embedded set-top box";
    }
    leaf e-ps {
      type uint32;
      description
        "Total number of CMs that have reported the device class as embedded portal services";
    }
    leaf e-dva {
      type uint32;
      description
        "Total number of CMs that have reported the device class as embedded digital voice adapter";
    }
  }

  grouping cable-rpd-state-key {
    description
      "RPD state key";
    leaf id {
      type yang:mac-address;
      description
        "MAC address of the RPD";
    }
    leaf local-if {
      type string;
      description
        "Local ethernet interface that the RPD connected to";
    }
  }

  grouping cable-rpd-state {
    description
      "Operational state of RPD";
    leaf ip-addr {
      type inet:ip-address;
      description
        "RPD's IP address";
    }
    leaf clock-synced {
      type boolean;
      description
        "RPD's state";
    }
    leaf state {
      type docsis-ios-xe-oper:rpd-state-type;
      description
        "RPD's state";
    }
    leaf core-role {
      type docsis-ios-xe-oper:rpd-core-role-type;
      description
        "Primary or auxiliary role";
    }
    leaf ha-role {
      type docsis-ios-xe-oper:rpd-ha-role-type;
      description
        "Active or standby role";
    }
    leaf auth {
      type docsis-ios-xe-oper:rpd-auth-method-type;
      description
        "Authentication result";
    }
    leaf name {
      type string;
      description
        "Configuration name of RPD";
    }
  }

  grouping ds-chan-shutdown-conf-type {
    description
      "Downstream channel mute configuration group";
    leaf start-chan {
      type uint32;
      description
        "Start channel of this group";
    }
    leaf end-chan {
      type uint32;
      description
        "End channel number of this group";
    }
    leaf shutdown {
      type boolean;
      description
        "Shutdown configuration of the channels in this group";
    }
  }

  grouping ds-chan-power-adjust-conf-type {
    description
      "Downstream channel power adjust configuration group";
    leaf start-chan {
      type uint32;
      description
        "Start channel of this group";
    }
    leaf end-chan {
      type uint32;
      description
        "End channel number of this group";
    }
    leaf power-adjust {
      type decimal64 {
        fraction-digits 2;
      }
      description
        "Power adjust configuration parameters for the channels in this group";
    }
  }

  grouping ds-chan-mute-conf-type {
    description
      "Downstream channel mute configuration group";
    leaf start-chan {
      type uint32;
      description
        "Start channel of this group";
    }
    leaf end-chan {
      type uint32;
      description
        "End channel number of this group";
    }
    leaf mute {
      type boolean;
      description
        "Mute is enabled or disabled for the channels in this group";
    }
  }

  grouping sbfd-para-conf-type {
    description
      "Seamless bidirectional forwarding detection configuration parameters";
    leaf sbfd-interval {
      type uint32;
      description
        "Transmit interval between Seamless bidirectional forwarding detection PDUs";
    }
    leaf sbfd-multiplier {
      type uint32;
      description
        "Multiplier value used to compute holddown";
    }
  }

  grouping us-description-conf-type {
    description
      "Upstream description configuration";
    leaf us-index {
      type uint8;
      description
        "Upstream index";
    }
    leaf us-description {
      type string;
      description
        "Upstream description";
    }
  }

  grouping analog-power-conf {
    description
      "Analog power configuration parameters";
    leaf power-major-lo-th {
      type uint16;
      description
        "Power major low alarm threshold";
    }
    leaf power-minor-lo-th {
      type uint16;
      description
        "Power minor low alarm threshold";
    }
    leaf power-normal-th {
      type uint16;
      description
        "Power normal threshold";
    }
    leaf power-minor-hi-th {
      type uint16;
      description
        "Power minor high threshold";
    }
  }

  grouping rpd-shelf-ds-conf-type {
    description
      "Downstream configuration specific for RPD shelf";
    leaf max-carrier {
      type uint32;
      description
        "Max carrier";
    }
    leaf base-power {
      type decimal64 {
        fraction-digits 2;
      }
      description
        "Base power";
    }
  }

  grouping rpd-node-ds-conf-type {
    description
      "Downstream configuration specific for RPD node";
    leaf base-power {
      type decimal64 {
        fraction-digits 2;
      }
      description
        "Base power";
    }
  }

  grouping ds-port-conf {
    description
      "RPD downstream RF port configuration";
    leaf index {
      type uint32;
      description
        "Index of the downstream port";
    }
    list ds-chan-power-adjust {
      description
        "List of channel power adjust";
      uses docsis-ios-xe-oper:ds-chan-power-adjust-conf-type;
    }
    list ds-chan-mute {
      description
        "List of channel mute";
      uses docsis-ios-xe-oper:ds-chan-mute-conf-type;
    }
    list ds-chan-shutdown {
      description
        "List of channel shutdown";
      uses docsis-ios-xe-oper:ds-chan-shutdown-conf-type;
    }
    leaf tilt-slope {
      type decimal64 {
        fraction-digits 2;
      }
      description
        "Tilt slope";
    }
    leaf tilt-pivot-freq {
      type uint32;
      description
        "Tilt pivot frequency";
    }
    leaf mute {
      type boolean;
      description
        "Mute configuration";
    }
    leaf shutdown {
      type boolean;
      description
        "Shutdown";
    }
    choice pt-prof-conf-choice {
      description
        "Downstream pilot tone configuration";
      case ds-pilot-tone {
        leaf pt-prof-id {
          type uint32;
          description
            "Profile id";
        }
      }
    }
    choice rpd-type-choice {
      description
        "Configuration in downstream port based on RPD's type";
      case rpd-node {
        description
          "Node specific downstream port configuration";
        container node-ds-conf {
          description
            "Node specific downstream port configuration";
          uses docsis-ios-xe-oper:rpd-node-ds-conf-type;
        }
      }
      case rpd-shelf {
        description
          "Shelf specific configuration";
        container shelf-ds-conf {
          description
            "Shelf specific downstream port configuration";
          uses docsis-ios-xe-oper:rpd-shelf-ds-conf-type;
        }
      }
    }
  }

  grouping ds-oob-vom-conf-type {
    description
      "Downstream oob virtual OM configuration parameters";
    leaf ds-index {
      type uint8;
      description
        "Downstream index";
    }
    leaf vom-id {
      type uint32;
      description
        "Downstream oob virtual OM value";
    }
    leaf profile {
      type uint32;
      description
        "Profile id";
    }
  }

  grouping core-ds-ctlr-conf {
    description
      "Downstream controller configuration";
    leaf ds-ctrlr-index {
      type uint8;
      description
        "Downstream controller index";
    }
    leaf downstream-if {
      type string;
      description
        "Downstream interface name";
    }
    leaf profile {
      type uint32;
      description
        "Profile id";
    }
  }

  grouping core-ds-port-conf {
    description
      "Core downstream port configuration";
    leaf ds-index {
      type uint8;
      description
        "Downstream port index";
    }
    list ds-ctlr {
      description
        "List of downstream controllers";
      uses docsis-ios-xe-oper:core-ds-ctlr-conf;
    }
  }

  grouping us-oob-varpd-conf {
    description
      "Oob varpd configuration for core upstream port";
    leaf us-index {
      type uint8;
      description
        "Upstream port index of the core";
    }
    leaf varpd-id {
      type uint32;
      description
        "Varpd id";
    }
    leaf profile {
      type uint32;
      description
        "Profile id";
    }
  }

  grouping core-us-port-conf {
    description
      "Upstream port configuration for core";
    leaf us-index {
      type uint8;
      description
        "Upstream port's index";
    }
    leaf us-intf {
      type string;
      description
        "Interface name";
    }
    leaf profile-id {
      type uint32;
      description
        "Profile id";
    }
  }

  grouping pw-conf {
    description
      "Static-pseudowire configuration";
    leaf index {
      type uint8;
      description
        "Index";
    }
    leaf static-pw-name {
      type string;
      description
        "Static-pseudowire name";
    }
    leaf profile {
      type uint32;
      description
        "Profile id";
    }
  }

  grouping nw-delay-dlm-conf {
    description
      "Network delay sampling interval configuration";
    leaf sampling-interval {
      type uint32;
      description
        "Network delay sampling interval";
    }
    leaf measure-only {
      type boolean;
      description
        "Measure only is enabled or not";
    }
  }

  grouping core-conf {
    description
      "RPD core configuration";
    leaf index {
      type uint32;
      description
        "Core index";
    }
    leaf core-if {
      type string;
      description
        "Interface name";
    }
    leaf principal {
      type boolean;
      description
        "Principal role";
    }
    list core-ds-port {
      description
        "List of downstream ports";
      uses docsis-ios-xe-oper:core-ds-port-conf;
    }
    list core-ds-oob-vom {
      description
        "List of oob virtual OM for downstream ports";
      uses docsis-ios-xe-oper:ds-oob-vom-conf-type;
    }
    list core-us-port {
      description
        "List of upstream ports that belong to the core";
      uses docsis-ios-xe-oper:core-us-port-conf;
    }
    list core-us-port-varpd {
      description
        "List of oob varpd for upstream ports that belong to the core";
      uses docsis-ios-xe-oper:us-oob-varpd-conf;
    }
    list ds-pw {
      description
        "List of downstream static pseudowires that belong to the core";
      uses docsis-ios-xe-oper:pw-conf;
    }
    list us-pw {
      description
        "List of upstream static pseudowires that belong to the core";
      uses docsis-ios-xe-oper:pw-conf;
    }
    leaf depi {
      type string;
      description
        "Downstream External PHY Interface";
    }
    leaf uepi {
      type string;
      description
        "Upstream External PHY Interface";
    }
    choice nw-delay-sampling-en-choice {
      description
        "The configuration status of network delay sampling interval";
      case netork-delay-sampling-interval {
        container network-delay-dlm {
          description
            "Network delay settings";
          uses docsis-ios-xe-oper:nw-delay-dlm-conf;
        }
      }
    }
    choice nw-delay-static-en-choice {
      description
        "The configuration status of network delay static";
      case netork-delay-static {
        leaf network-delay-static {
          type uint32;
          description
            "Network delay static value";
        }
      }
    }
  }

  grouping cable-rpd-conf {
    description
      "RPD configuration";
    leaf name {
      type string;
      description
        "Configuration name";
    }
    leaf description {
      type string;
      description
        "Description name";
    }
    leaf identifier {
      type yang:mac-address;
      description
        "MAC address";
    }
    leaf type {
      type docsis-ios-xe-oper:rpd-conf-type;
      description
        "Node or shelf";
    }
    leaf auth-type {
      type docsis-ios-xe-oper:rpd-auth-method-type;
      description
        "Authentication type";
    }
    list ds-port-conf {
      key "index";
      description
        "List of downstream port configurations that belong to the RPD";
      uses docsis-ios-xe-oper:ds-port-conf;
    }
    list core-conf {
      key "index";
      description
        "List of core configurations that belong to the RPD";
      uses docsis-ios-xe-oper:core-conf;
    }
    list us-description {
      description
        "List of upstream descriptions that belong to the RPD";
      uses docsis-ios-xe-oper:us-description-conf-type;
    }
    container analog-power-rx {
      description
        "Analog power rx";
      uses docsis-ios-xe-oper:analog-power-conf;
    }
    container analog-power-tx {
      description
        "Analog power tx";
      uses docsis-ios-xe-oper:analog-power-conf;
    }
    choice rpd-event-prof-en-choice {
      description
        "The configuration status of rpd event profile";
      case rpd-event-profile {
        leaf rpd-event-profile {
          type uint8;
          description
            "Rpd event profile";
        }
      }
    }
    choice ssd-prof-en-choice {
      description
        "The configuration status of secure software download";
      case ssd-profile {
        leaf ssd-profile-id {
          type uint8;
          description
            "Secure software download profile id";
        }
      }
    }
    choice oob-us-evt-prof-en-choice {
      description
        "The configuration status of out of bind 55-1 upstream event profile";
      case oob-551-us-event-profile {
        leaf oob-55d1-us-event-prof-id {
          type uint8;
          description
            "Out of bind 55-1 upstream event profile";
        }
      }
    }
    choice sbfd-enable-choice {
      description
        "Seamless bidirectional forwarding detection configuration";
      case sbfd-configured {
        description
          "Seamless bidirectional forwarding detection enabled";
        container sbfd-parameter {
          description
            "Seamless bidirectional forwarding detection parameter";
          uses docsis-ios-xe-oper:sbfd-para-conf-type;
        }
      }
    }
    choice ptp-clk-prof-en-choice {
      description
        "The configuration status of dti profile";
      case ptp-clock-profile {
        leaf r-dti {
          type uint8;
          description
            "Dti profile id";
        }
      }
    }
  }

  grouping lic-with-conf-lock {
    description
      "Operational state of license type with config enforcement setting";
    leaf entitlement {
      type string;
      description
        "Entitlement";
    }
    leaf c-cnt {
      type uint32;
      description
        "Consumed count";
    }
    leaf reported-to-sm {
      type uint32;
      description
        "Count reported to smart agent";
    }
    leaf cfg-lock-enforced {
      type boolean;
      description
        "Configuration lock enforced status";
    }
    choice enforced-state-choice {
      description
        "Operational status of license enforcement";
      case deact-enforced {
        leaf deact-enforcement {
          type string;
          description
            "Deactivated enforcement";
        }
      }
      case capped-enforced {
        leaf capped-enforcement {
          type uint32;
          description
            "Capped enforcement";
        }
      }
      case not-enforced {
        leaf no-enforcement-state {
          type boolean;
          description
            "No enforcement";
        }
      }
    }
  }

  grouping lic-without-conf-lock {
    description
      "Operational state of license type without config enforcement setting";
    leaf entitlement {
      type string;
      description
        "Entitlement";
    }
    leaf c-cnt {
      type uint32;
      description
        "Consumed count";
    }
    leaf reported-to-sm {
      type uint32;
      description
        "Count reported to smart agent";
    }
    choice enforced-state-choice {
      description
        "Operational status of license enforcement";
      case deact-enforced {
        leaf deact-enforcement {
          type string;
          description
            "Deactivated enforcement";
        }
      }
      case capped-enforced {
        leaf capped-enforcement {
          type uint32;
          description
            "Capped enforcement";
        }
      }
      case not-enforced {
        leaf no-enforcement-state {
          type boolean;
          description
            "No enforcement";
        }
      }
    }
  }

  grouping wan-lic-state-type {
    description
      "Operational state of WAN license";
    leaf entitlement {
      type string;
      description
        "Entitlement";
    }
    leaf c-cnt {
      type uint32;
      description
        "Consumed count";
    }
    leaf reported-to-sm {
      type uint32;
      description
        "Count reported to smart agent";
    }
    leaf cfg-lock-enforced {
      type boolean;
      description
        "Configuration lock enforced status";
    }
    choice enforced-state-choice {
      description
        "Operational status of license enforcement";
      case deact-enforced {
        leaf deact-enforcement {
          type string;
          description
            "Deactivated enforcement";
        }
      }
      case capped-enforced {
        leaf capped-enforcement {
          type uint32;
          description
            "Capped enforcement";
        }
      }
      case not-enforced {
        leaf no-enforcement-state {
          type boolean;
          description
            "No enforcement";
        }
      }
    }
    choice sup250-100g-en-choice {
      description
        "Wan license for 100 gigabit backhaul interface status";
      case sup250-100-g-enabled {
        leaf backhaul-consumes-wan-lic {
          type boolean;
          description
            "100 gigabit backhaul interface consumes WAN License";
        }
      }
    }
  }

  grouping us-d31-lic-state {
    description
      "Operational state of DOCSIS 3.1 downstream license";
    leaf entitlement {
      type string;
      description
        "Entitlement";
    }
    leaf total-licensed-spectrum {
      type uint32;
      description
        "Total licensed spectrum";
    }
    leaf c-cnt {
      type uint32;
      description
        "Consumed count";
    }
    leaf reported-to-sm {
      type uint32;
      description
        "Count reported to smart agent";
    }
    leaf forced-shut-down-chan {
      type string;
      description
        "Forced shut down channel";
    }
    choice enforced-state-choice {
      description
        "Operational status of license enforcement";
      case deact-enforced {
        leaf deact-enforcement {
          type string;
          description
            "Deactivated enforcement";
        }
      }
      case capped-enforced {
        leaf capped-enforcement {
          type uint32;
          description
            "Capped enforcement";
        }
      }
      case not-enforced {
        leaf no-enforcement-state {
          type boolean;
          description
            "No enforcement";
        }
      }
    }
  }

  grouping cpb-lic-state {
    description
      "Operational state of Core Peak Bandwidth smart license feature";
    leaf entitlement {
      type string;
      description
        "Entitlement";
    }
    leaf c-cnt {
      type uint32;
      description
        "Consumed count";
    }
    leaf reported-to-sm {
      type uint32;
      description
        "Count reported to smart agent";
    }
    leaf enforced-state {
      type boolean;
      description
        "Enforced state";
    }
    leaf cfg-lock-enforced {
      type boolean;
      description
        "Configuration lock enforced status";
    }
    leaf quarterly-cpb-rate {
      type uint32;
      description
        "Quarterly Core Peak Bandwidth";
    }
    leaf quarter {
      type docsis-ios-xe-oper:license-quarter-type;
      description
        "Quarter";
    }
    leaf year {
      type uint32;
      description
        "Year of the Core Peak Bandwidth";
    }
    leaf first-monthly-cpb-bps {
      type uint32;
      description
        "bps for first monthly Core Peak Bandwidth";
    }
    leaf first-monthly-cpb-100mbps {
      type uint32;
      description
        "100 Mbps for first monthly Core Peak Bandwidth";
    }
    leaf second-monthly-cpb-bps {
      type uint32;
      description
        "bps for second monthly Core Peak Bandwidth";
    }
    leaf second-monthly-cpb-100mbps {
      type uint32;
      description
        "100 Mbps for second monthly Core Peak Bandwidth";
    }
    leaf third-monthly-cpb-bps {
      type uint32;
      description
        "bps for third monthly Core Peak Bandwidth";
    }
    leaf third-monthly-cpb-100mbps {
      type uint32;
      description
        "100 Mbps for third monthly Core Peak Bandwidth";
    }
  }

  grouping cable-license {
    description
      "Operational state of cable license";
    leaf license-type {
      type docsis-ios-xe-oper:cbr-lic-conf-type;
      description
        "Type of cable license";
    }
    choice license-state-choice {
      description
        "Operational state of specific type of cable license";
      case downstream-license {
        container ds-lic {
          description
            "DOCSIS down stream";
          uses docsis-ios-xe-oper:lic-with-conf-lock;
        }
      }
      case upstream-license {
        container us-lic {
          description
            "DOCSIS upstream";
          uses docsis-ios-xe-oper:lic-with-conf-lock;
        }
      }
      case wan-license {
        container wan-lic {
          description
            "WAN port";
          uses docsis-ios-xe-oper:wan-lic-state-type;
        }
      }
      case lcha-license {
        container lcha-lic {
          description
            "Lice card high available";
          uses docsis-ios-xe-oper:lic-with-conf-lock;
        }
      }
      case video-narrowcast-license {
        container nc-lic {
          description
            "Narrow cast video";
          uses docsis-ios-xe-oper:lic-without-conf-lock;
        }
      }
      case video-narrowcast-replicate-license {
        container nc-rpl-lic {
          description
            "Narrow cast video replicate";
          uses docsis-ios-xe-oper:lic-without-conf-lock;
        }
      }
      case video-narrowcast-pkey-license {
        container nc-pky-lic {
          description
            "Narrow cast video power key";
          uses docsis-ios-xe-oper:lic-without-conf-lock;
        }
      }
      case video-narrowcast-pme-license {
        container nc-pme-lic {
          description
            "Narrow cast video privacy mode encryption";
          uses docsis-ios-xe-oper:lic-without-conf-lock;
        }
      }
      case video-narrowcast-dvb-license {
        container nc-dvb-lic {
          description
            "Narrow cast video digital video broadcasting";
          uses docsis-ios-xe-oper:lic-without-conf-lock;
        }
      }
      case video-broadcast-license {
        container bc-lic {
          description
            "Broadcast video";
          uses docsis-ios-xe-oper:lic-without-conf-lock;
        }
      }
      case video-broadcast-enc-license {
        container bc-enc-lic {
          description
            "Broadcast video power key";
          uses docsis-ios-xe-oper:lic-without-conf-lock;
        }
      }
      case docsis31-downstream-channel-license {
        container ds-31-lic {
          description
            "DOCSIS 3.1 downstream";
          uses docsis-ios-xe-oper:lic-with-conf-lock;
        }
      }
      case rphy-video-broadcast-license {
        container rphy-bc-lic {
          description
            "RPD broadcast video";
          uses docsis-ios-xe-oper:lic-without-conf-lock;
        }
      }
      case docsis31-upstream-channel-exclusive-license {
        container us-d31-lic {
          description
            "DOCSIS 3.1 upstream exclusive";
          uses docsis-ios-xe-oper:us-d31-lic-state;
        }
      }
      case docsis31-upstream-channel-overlap-license {
        container us-d31-overlap-lic {
          description
            "DOCSIS 3.1 upstream overlap";
          uses docsis-ios-xe-oper:us-d31-lic-state;
        }
      }
      case wan-100-g-license {
        container wan-100g-lic {
          description
            "100 Gigabit Ethernet";
          uses docsis-ios-xe-oper:lic-with-conf-lock;
        }
      }
      case cpb-license {
        container cpb-lic {
          description
            "Core Peak Bandwidth";
          uses docsis-ios-xe-oper:cpb-lic-state;
        }
      }
    }
  }

  container docsis-oper-data {
    config false;
    description
      "Operational data on Cisco Cable Modem Termination System";
    container cm-summary-total {
      presence "cm-summary-total";
      description
        "A summary of all the modem information";
      uses docsis-ios-xe-oper:cm-summary-total;
    }
    list cable-modem {
      key "mac-address";
      description
        "List of cable modems";
      uses docsis-ios-xe-oper:cable-modem;
    }
    list cable-license {
      key "license-type";
      description
        "Operational state of Cable license";
      uses docsis-ios-xe-oper:cable-license;
    }
    container cm-dc-summary {
      presence "cm-dc-summary";
      description
        "A summary of DOCSIS device class information";
      uses docsis-ios-xe-oper:cm-dc-summary;
    }
    list cable-rpd-state {
      key "id local-if";
      description
        "Operational state of RPD";
      uses docsis-ios-xe-oper:cable-rpd-state-key;
      uses docsis-ios-xe-oper:cable-rpd-state;
    }
    list cable-rpd-conf {
      key "name";
      description
        "Configuration data of RPD";
      uses docsis-ios-xe-oper:cable-rpd-conf;
    }
  }
}
