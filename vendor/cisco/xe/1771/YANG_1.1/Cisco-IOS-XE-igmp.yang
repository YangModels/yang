module Cisco-IOS-XE-igmp {
  yang-version 1.1;
  namespace "http://cisco.com/ns/yang/Cisco-IOS-XE-igmp";
  prefix ios-igmp;

  import cisco-semver {
    prefix cisco-semver;
  }
  import ietf-inet-types {
    prefix inet;
  }
  import Cisco-IOS-XE-native {
    prefix ios;
  }
  import Cisco-IOS-XE-types {
    prefix ios-types;
  }
  import Cisco-IOS-XE-interface-common {
    prefix ios-ifc;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Internet Group Management Protocol (IGMP) Yang model.
     Copyright (c) 2016-2021 by Cisco Systems, Inc.
     All rights reserved.";

  revision 2021-07-01 {
    description
      "- Added leaf robustness-variable under interface
       - Added a new querier leaf under querier-conf container in igmp snooping to disable/enable querier
       - Deprecate igmp snooping querier container and added a new querier-entry to remove presence ";
    cisco-semver:module-version "2.1.0";
  }
  revision 2020-11-01 {
    description
      "- Added dependency for VRF";
    cisco-semver:module-version "2.0.2";
  }
  revision 2019-11-01 {
    description
      "- IGMP YANG hardening";
    cisco-semver:module-version "2.0.0";
  }
  revision 2019-07-01 {
    description
      "- Establish semantic version baseline
       - Added default values for some igmp leaves
       - Added ip igmp augmentation for missing interfaces
       - Modified key for igmp join-group. Added except leaf for igmp limit";
    cisco-semver:module-version "1.0.0";
  }
  revision 2019-01-22 {
    description
      "Added leaf for App-hosting Gigabit Ethernet interface";
  }
  revision 2018-10-03 {
    description
      "This revision has changes in igmp static-group";
  }
  revision 2018-09-25 {
    description
      "Updated class-map from list to leaf";
  }
  revision 2018-07-16 {
    description
      "Added config-interface-ip-igmp-grouping to interface Vif";
  }
  revision 2017-11-27 {
    description
      "Added Change 25GE name";
  }
  revision 2017-11-14 {
    description
      "This revision has changes for new 40 and 100GE interface addition";
  }
  revision 2017-09-14 {
    description
      "This revison has changes for new 2gig interface addition";
  }
  revision 2017-08-28 {
    description
      "Extend modeling for multicast";
  }
  revision 2017-08-16 {
    description
      "This revision has changes for new 5gig and 25gig interfaces addition";
  }
  revision 2017-02-07 {
    description
      "Initial revision";
  }

  grouping config-ip-igmp-ssm-map-subset {
    leaf enable {
      description
        "Enable SSM group to source mapping";
      type empty;
    }
    container query {
      description
        "Which database should we query for the source";
      leaf dns {
        description
          "Use DNS for source lookup";
        type boolean;
        default "true";
      }
    }
  }

  grouping config-ip-igmp-subset {
    container immediate-leave {
      description
        "Leave groups immediately without sending last member query,
         use for one host network only";
      leaf group-list {
        description
          "IP Access list to specify groups";
        type union {
          type uint16 {
            range "1..99";
          }
          type uint16 {
            range "1300..1999";
          }
          type string;
        }
      }
    }
    leaf limit {
      description
        "IGMP Max Allowed State";
      type uint16 {
        range "1..64000";
      }
    }
    container query {
      description
        "Global config for IGMP query";
      leaf disperse {
        description
          "When many interfaces come up simultaneously, a flurry of IGMP
           messages may temporarily overwhelm a device. Use this command to
           avoid the situation by dispersing the initial IGMP queries";
        type boolean;
      }
    }
  }

  grouping config-ip-igmp-grouping {
    container igmp {
      description
        "IGMP global configuration";
      container snooping-conf {
        leaf snooping {
          type boolean;
        }
      }
      container snooping {
        description
          "Global IGMP Snooping enable for Catalyst Vlans";
        container check {
          description
            "enforce TTL or Rtr-Alert Option checking";
          leaf rtr-alert-option {
            description
              "Only accept IGMP packets with router-alert option";
            type empty;
          }
          leaf ttl {
            description
              "Only accept IGMP packets with TTL=1";
            type empty;
          }
        }
        container explicit-tracking {
          description
            "Explicit tracking DB configuration";
          leaf limit {
            description
              "Explicit tracking DB limit";
            type uint32 {
              range "0..128000";
            }
          }
        }
        leaf l2-entry-limit {
          description
            "limit on the l2 entry that can be installed by IGMP snooping";
          type uint32 {
            range "1..100000";
          }
        }
        leaf last-member-query-count {
          description
            "Last member query count";
          type uint8 {
            range "1..7";
          }
        }
        leaf last-member-query-interval {
          description
            "Interval (milliseconds)";
          type uint16 {
            range "100..32767";
          }
        }
        container querier-conf {
          leaf querier {
            description
              "IGMP querier disable/enable";
            type empty;
          }
        }
        container querier-entry {
          description
            "IGMP querier configuration";
          leaf address {
            description
              "IGMP querier source IP address";
            type inet:ipv4-address;
          }
          leaf max-response-time {
            description
              "IGMP querier maximum response time (sec)";
            type uint8 {
              range "1..25";
            }
          }
          leaf query-interval {
            description
              "IGMP querier query interval (sec)";
            type uint16 {
              range "1..18000";
            }
          }
          container tcn {
            description
              "IGMP querier TCN related parameters";
            container query {
              leaf count {
                description
                  "IGMP querier TCN query count";
                type uint8 {
                  range "1..10";
                }
              }
              leaf interval {
                description
                  "IGMP querier TCN query interval (sec)";
                type uint8 {
                  range "1..255";
                }
              }
            }
          }
          container timer {
            description
              "IGMP other querier timer";
            leaf expiry {
              description
                "IGMP querier other querier time out (sec)";
              type uint16 {
                range "60..300";
              }
            }
          }
          leaf version {
            description
              "IGMP version";
            type uint8 {
              range "1..2";
            }
          }
        }
        container querier {
          status deprecated;
          description
            "IGMP querier configuration (DEPRECATED, use querier-entry)";
          presence "true";
          leaf address {
            status deprecated;
            description
              "IGMP querier source IP address";
            type inet:ipv4-address;
          }
          leaf max-response-time {
            status deprecated;
            description
              "IGMP querier maximum response time (sec)";
            type uint8 {
              range "1..25";
            }
          }
          leaf query-interval {
            status deprecated;
            description
              "IGMP querier query interval (sec)";
            type uint16 {
              range "1..18000";
            }
          }
          container tcn {
            description
              "IGMP querier TCN related parameters";
            container query {
              leaf count {
                status deprecated;
                description
                  "IGMP querier TCN query count";
                type uint8 {
                  range "1..10";
                }
              }
              leaf interval {
                status deprecated;
                description
                  "IGMP querier TCN query interval (sec)";
                type uint8 {
                  range "1..255";
                }
              }
            }
          }
          container timer {
            description
              "IGMP other querier timer";
            leaf expiry {
              status deprecated;
              description
                "IGMP querier other querier time out (sec)";
              type uint16 {
                range "60..300";
              }
            }
          }
          leaf version {
            status deprecated;
            description
              "IGMP version";
            type uint8 {
              range "1..2";
            }
          }
        }
        leaf report-suppression {
          description
            "Report suppression";
          type empty;
        }
        leaf robustness-variable {
          description
            "Robustness Variable number";
          type uint8 {
            range "1..3";
          }
        }
        container tcn {
          description
            "Topology change notification configuration";
          container flood {
            description
              "TCN flooding configuration";
            container query {
              description
                "TCN flooding query configuration";
              leaf count {
                description
                  "Count";
                type uint8 {
                  range "1..10";
                }
              }
            }
          }
          container query {
            description
              "TCN query configuration";
            leaf solicit {
              description
                "Solicit an IGMP general query";
              type empty;
            }
          }
        }
      }
      uses config-ip-igmp-subset;
      container ssm-map {
        description
          "SSM mapping commands";
        uses config-ip-igmp-ssm-map-subset;
        list static-list {
          description
            "SSM static group to source mapping";
          key "source-ip";
          leaf source-ip {
            description
              "SSM source address";
            type inet:ipv4-address;
          }
          leaf acl {
            description
              "SSM group named access list";
            type string;
          }
        }
        container static {
          description
            "SSM static group to source mapping
             (OBSOLETE: Use list 'static-v1' under container 'ssm-map'";
          status obsolete;
          leaf acl {
            status obsolete;
            type union {
              type uint16 {
                range "1..99";
              }
              type string;
            }
          }
          leaf source-ip {
            status obsolete;
            type inet:ipv4-address;
          }
        }
      }
      list vrf {
        description
          "Select VPN Routing/Forwarding instance";
        key "name";
        leaf name {
          description
            "VPN Routing/Forwarding instance name";
          type string;
        }
        uses config-ip-igmp-subset;
        container ssm-map {
          description
            "SSM mapping commands";
          uses config-ip-igmp-ssm-map-subset;
          list static {
            description
              "SSM static group to source mapping";
            key "srcaddress";
            leaf srcaddress {
              description
                "SSM source address";
              type inet:ipv4-address;
            }
            leaf aclname {
              description
                "SSM group named access list";
              mandatory true;
              type string;
            }
          }
        }
      }
      leaf filter {
        description
          "IGMP Filter Enable";
        type boolean;
      }
      list profile {
        description
          "IGMP Filter Profile";
        key "id";
        leaf id {
          type uint64 {
            range "1..4294967295";
          }
        }
        uses config-igmp-profile-grouping;
      }
    }
  }

  grouping config-interface-ip-igmp-grouping {
    container igmp {
      description
        "IGMP interface commands";
      container static-group {
        description
          "IGMP static multicast group";
        list with-source-groups {
          key "name source";
          leaf name {
            type union {
              type inet:ipv4-address;
              type enumeration {
                enum *;
              }
            }
          }
          leaf source {
            type union {
              type inet:ipv4-address;
              type enumeration {
                enum ssm-map;
              }
            }
          }
        }
        list without-source-groups {
          key "name";
          leaf name {
            type union {
              type inet:ipv4-address;
              type enumeration {
                enum *;
              }
            }
          }
        }
        leaf class-map {
          description
            "IGMP Class map of type multicast-flows";
          type string;
        }
      }
      list igmpv3-join-group {
        description
          "IGMP join multicast group";
        key "ip-group-address source";
        leaf ip-group-address {
          description
            "IP group address";
          type inet:ipv4-address;
        }
        leaf source {
          description
            "IP source address";
          type inet:ipv4-address;
        }
      }
      list join-group {
        description
          "IGMP join multicast group
           (OBSOLETE: Use lists igmp-join-group or igmpv3-join-group instead)";
        status obsolete;
        key "ip-group-address";
        leaf ip-group-address {
          description
            "IP group address";
          status obsolete;
          type inet:ipv4-address;
        }
        leaf source {
          description
            "IP source address";
          status obsolete;
          type inet:ipv4-address;
        }
      }
      list igmp-join-group {
        description
          "IGMP join multicast group";
        key "join-group";
        leaf join-group {
          description
            "IP group address";
          type inet:ipv4-address;
        }
      }
      leaf version {
        description
          "IGMP version";
        default "2";
        type uint8 {
          range "1..3";
        }
      }
      leaf access-group {
        description
          "IGMP group access group";
        type ios-types:exp-acl-type;
      }
      leaf explicit-tracking-leaf {
        description
          "IGMP explicit-tracking";
        type empty;
      }
      leaf explicit-tracking {
        status deprecated;
        description
          "IGMP explicit-tracking";
        type boolean;
      }
      container helper-address {
        description
          "IGMP helper address";
        leaf name {
          type inet:ipv4-address;
        }
        container udl {
          description
            "Unidirectional link to forward the report";
          uses ios-ifc:interface-grouping;
        }
      }
      container immediate-leave {
        description
          "Leave groups immediately without sending last member query,
           use for one host network only";
        leaf group-list {
          description
            "IP Access list";
          type union {
            type uint16 {
              range "1..99";
            }
            type uint16 {
              range "1300..1999";
            }
            type string;
          }
        }
      }
      leaf last-member-query-count {
        description
          "IGMP last member query count";
        default "2";
        type uint8 {
          range "1..7";
        }
      }
      leaf last-member-query-interval {
        description
          "IGMP last member query interval";
        default "1000";
        type uint16 {
          range "100..25500";
        }
      }
      container limit-container {
        leaf limit {
          description
            "IGMP Max Allowed State on this interface";
          type uint16 {
            range "1..64000";
          }
        }
        leaf except {
          description
            "Groups not to be counted";
          must '../ios-igmp:limit' {
            error-message "IGMP limit should be specified";
          }
          type union {
            type uint16 {
              range "1..199";
            }
            type string;
          }
        }
      }
      leaf limit {
        description
          "IGMP Max Allowed State on this interface
           (DEPRECATED: Use leaf 'limit' under container 'limit-container')";
        status deprecated;
        type uint16 {
          range "1..64000";
        }
      }
      container mroute-proxy {
        description
          "Mroute to IGMP proxy";
        uses ios-ifc:interface-grouping;
      }
      leaf proxy-service-leaf {
        description
          "Enable IGMP mroute proxy service";
        type empty;
      }
      leaf proxy-service {
        status deprecated;
        description
          "Enable IGMP mroute proxy service";
        type boolean;
      }
      leaf querier-timeout {
        description
          "IGMP previous querier timeout";
        type uint16 {
          range "60..300";
        }
      }
      leaf query-interval {
        description
          "IGMP host query interval";
        default "60";
        type uint16 {
          range "1..18000";
        }
      }
      leaf query-max-response-time {
        description
          "IGMP max query response value";
        default "10";
        type uint16 {
          range "1..25";
        }
      }
      container tcn {
        description
          "IGMP TCN configuration";
        container query {
          description
            "IGMP tcn query configuration";
          leaf count {
            description
              "IGMP general query count";
            default "2";
            type uint16 {
              range "1..10";
            }
          }
          leaf interval {
            description
              "IGMP general query interval";
            default "10";
            type uint16 {
              range "1..255";
            }
          }
        }
      }
      leaf unidirectional-link-leaf {
        description
          "IGMP unidirectional link multicast routing";
        type empty;
      }
      leaf unidirectional-link {
        status deprecated;
        description
          "IGMP unidirectional link multicast routing";
        type boolean;
      }
      leaf v3-query-max-response-time {
        description
          "IGMP v3 max query response value";
        default "10";
        type uint16 {
          range "1..3175";
        }
      }
      leaf v3lite-leaf {
        description
          "IGMPv3 Lite";
        type empty;
      }
      leaf v3lite {
        status deprecated;
        description
          "IGMPv3 Lite";
        type boolean;
      }
      leaf filter {
        description
          "IGMP Filter Enable";
        type uint64 {
          range "1..4294967295";
        }
      }
      container max-groups {
        description
          "Maximum number of IGMP groups that can be joined";
        leaf count {
          type uint64 {
            range "1..4294967295";
          }
        }
        container action {
          description
            "Action taken on exceeding the limit";
          leaf deny {
            description
              "Do not allow any more groups";
            type boolean;
          }
          leaf replace {
            description
              "Replace existing group with new";
            type boolean;
          }
        }
      }
      container snooping {
        description
          "IGMP snooping configuration";
        container tcn {
          description
            "STP Topology Change Notification behavior";
          leaf flood {
            description
              "Flood when a TCN is seen";
            type boolean;
          }
        }
      }
      leaf upstream-proxy {
        description
          "IGMP proxy upstream interface config";
        type string;
      }
      leaf iif-starg {
        description
          "IGMP proxy IIF update";
        type empty;
      }
      leaf proxy-report-interval {
        description
          "IGMP proxy report interval";
        type uint16 {
          range "1..18000";
        }
        default "60";
      }
      leaf robustness-variable {
        description
          "IGMP Robustness Variable";
        type uint8 {
          range "1..7";
        }
        default "2";
      }
    }
  }

  grouping config-igmp-profile-grouping {
    leaf action {
      description
        "Action for matching addresses";
      type enumeration {
        enum deny;
        enum permit;
      }
    }
    list range {
      description
        "Range of multicast addressed";
      key "low_ip";
      leaf low_ip {
        description
          "Low IP multicast address";
        type inet:ipv4-address;
      }
      leaf high_ip {
        description
          "High IP multicast address";
        type inet:ipv4-address;
      }
    }
  }

  augment "/ios:native/ios:ip" {
    uses config-ip-igmp-grouping;
  }

  augment "/ios:native/ios:interface/ios:FastEthernet/ios:ip" {
    uses config-interface-ip-igmp-grouping;
  }

  augment "/ios:native/ios:interface/ios:GigabitEthernet/ios:ip" {
    uses config-interface-ip-igmp-grouping;
  }

  augment "/ios:native/ios:interface/ios:TenGigabitEthernet/ios:ip" {
    uses config-interface-ip-igmp-grouping;
  }

  augment "/ios:native/ios:interface/ios:FiveGigabitEthernet/ios:ip" {
    uses config-interface-ip-igmp-grouping;
  }

  augment "/ios:native/ios:interface/ios:AppGigabitEthernet/ios:ip" {
    uses config-interface-ip-igmp-grouping;
  }

  augment "/ios:native/ios:interface/ios:TwentyFiveGigE/ios:ip" {
    uses config-interface-ip-igmp-grouping;
  }

  augment "/ios:native/ios:interface/ios:TwoGigabitEthernet/ios:ip" {
    uses config-interface-ip-igmp-grouping;
  }

  augment "/ios:native/ios:interface/ios:FortyGigabitEthernet/ios:ip" {
    uses config-interface-ip-igmp-grouping;
  }

  augment "/ios:native/ios:interface/ios:HundredGigE/ios:ip" {
    uses config-interface-ip-igmp-grouping;
  }

  augment "/ios:native/ios:interface/ios:Loopback/ios:ip" {
    uses config-interface-ip-igmp-grouping;
  }

  augment "/ios:native/ios:interface/ios:Port-channel/ios:ip" {
    uses config-interface-ip-igmp-grouping;
  }

  augment "/ios:native/ios:interface/ios:Port-channel-subinterface/ios:Port-channel/ios:ip" {
    uses config-interface-ip-igmp-grouping;
  }

  augment "/ios:native/ios:interface/ios:Tunnel/ios:ip" {
    uses config-interface-ip-igmp-grouping;
  }

  augment "/ios:native/ios:interface/ios:Virtual-Template/ios:ip" {
    uses config-interface-ip-igmp-grouping;
  }

  augment "/ios:native/ios:interface/ios:VirtualPortGroup/ios:ip" {
    uses config-interface-ip-igmp-grouping;
  }

  augment "/ios:native/ios:interface/ios:Vlan/ios:ip" {
    uses config-interface-ip-igmp-grouping;
  }

  augment "/ios:native/ios:interface/ios:Vif/ios:ip" {
    uses config-interface-ip-igmp-grouping;
  }

  augment "/ios:native/ios:interface/ios:Multilink/ios:ip" {
    uses config-interface-ip-igmp-grouping;
  }

  augment "/ios:native/ios:interface/ios:Cellular/ios:ip" {
    uses config-interface-ip-igmp-grouping;
  }

  augment "/ios:native/ios:interface/ios:BDI/ios:ip" {
    uses config-interface-ip-igmp-grouping;
  }
}
