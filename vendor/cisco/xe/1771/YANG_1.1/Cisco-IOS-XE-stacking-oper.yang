module Cisco-IOS-XE-stacking-oper {
  yang-version 1.1;
  namespace "http://cisco.com/ns/yang/Cisco-IOS-XE-stacking-oper";
  prefix stacking-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     monitoring all parameters of stack in a Network Element.
     Copyright (c) 2018-2019 by Cisco Systems, Inc.
     All rights reserved.";

  revision 2019-06-06 {
    description
      "- Added semantic version.
       - Model is marked deprecated.";
    reference
      "1.1.0";
    cisco-semver:module-version "1.1.0";
  }
  revision 2018-09-19 {
    description
      "Initial revision";
    reference
      "1.0.0";
    cisco-semver:module-version "1.0.0";
  }

  typedef oper-switch-role {
    type enumeration {
      enum switch-role-unknown {
        value 0;
        description
          "Switch Role: Unknown";
      }
      enum switch-state-active {
        value 1;
        description
          "Switch Role: Active";
      }
      enum switch-state-standby {
        value 2;
        description
          "Switch Role: Standby";
      }
      enum switch-state-member {
        value 3;
        description
          "Switch Role: Member";
      }
    }
    description
      "Role of the Switch in Stack or Standalone";
  }

  typedef oper-switch-state {
    type enumeration {
      enum switch-state-invalid {
        value 0;
        description
          "Switch is in Invalid state";
      }
      enum switch-state-unknown {
        value 1;
        description
          "Switch is in Unknown state";
      }
      enum switch-state-waiting {
        value 2;
        description
          "Switch is in Waiting state";
      }
      enum switch-state-initializing {
        value 3;
        description
          "Switch is in Initializing state";
      }
      enum switch-state-version-mismatch {
        value 4;
        description
          "Version Mismatch between Switches in Stack";
      }
      enum switch-state-ready {
        value 5;
        description
          "Switch is in Ready state";
      }
      enum switch-state-re-initializing {
        value 6;
        description
          "Switch is in re-initializing state";
      }
      enum switch-state-feature-mismatch {
        value 7;
        description
          "Feature Mismatch between Active and the switch in stack";
      }
      enum switch-state-progressing {
        value 8;
        description
          "Switch is in Progressing state";
      }
      enum switch-state-configured {
        value 9;
        description
          "Switch is in Configured state";
      }
      enum switch-state-created {
        value 10;
        description
          "Switch is in Created state";
      }
      enum switch-state-removed {
        value 11;
        description
          "Switch is in Removed state";
      }
      enum switch-state-deleted {
        value 12;
        description
          "Switch is in Deleted state";
      }
      enum switch-state-license-mismatch {
        value 13;
        description
          "License Mismatch between Active and the switch in stack";
      }
      enum switch-state-platform-mismatch {
        value 14;
        description
          "Platform Mismatch between Active and the switch in stack";
      }
      enum switch-state-platform-and-license-mismatch {
        value 15;
        description
          "Both Platform and License Mismatch between Active and the switch in stack";
      }
      enum switch-state-os-mismatch {
        value 16;
        description
          "OS Mismatch between Active and the switch in stack";
      }
    }
    description
      "State of the switch";
  }

  grouping stack-data {
    description
      "Details of the Stack";
    leaf stack-mac-address {
      type yang:mac-address;
      description
        "MAC address for a Stack or Standalone";
    }
    leaf is-local-mac {
      type boolean;
      description
        "Identifies if the stack MAC belongs to the Active switch's MAC(Local) or outside switch's MAC(Foreign)";
    }
    leaf mac-persistent-timer {
      type uint32;
      description
        "Persistent timer for updating the stack MAC address";
    }
  }

  grouping switch-oper-info {
    description
      "Detailed Information of Switch";
    leaf switch-num {
      type uint8;
      description
        "Switch Number";
    }
    leaf role {
      type stacking-ios-xe-oper:oper-switch-role;
      description
        "Switch Role in Stack or Standalone";
    }
    leaf state {
      type stacking-ios-xe-oper:oper-switch-state;
      description
        "Switch State in Stack or Standalone";
    }
    leaf priority {
      type uint8;
      description
        "Switch Priority in Stack or Standalone";
    }
    leaf mac-address {
      type yang:mac-address;
      description
        "MAC Address of the switch";
    }
    leaf hw-version {
      type string;
      description
        "Hardware Version of the switch";
    }
    leaf is-stackport-1-up {
      type boolean;
      description
        "Switch Stack Port link 1 Status";
    }
    leaf stackport-1-nbr-sw {
      type uint8;
      description
        "Switch Number connected to Stack port link 1";
    }
    leaf is-stackport-2-up {
      type boolean;
      description
        "Switch Stack Port link 2 Status";
    }
    leaf stackport-2-nbr-sw {
      type uint8;
      description
        "Switch Number connected to Stack port link 2";
    }
  }

  container stacking-oper-data {
    config false;
    status deprecated;
    description
      "Top-level container for Stack operational data";
    container stack-data {
      presence "stack-data";
      description
        "Details of the Stack";
      uses stacking-ios-xe-oper:stack-data;
    }
    list switch-oper-info {
      key "switch-num";
      description
        "Detailed Information of Switch";
      uses stacking-ios-xe-oper:switch-oper-info;
    }
  }
}
