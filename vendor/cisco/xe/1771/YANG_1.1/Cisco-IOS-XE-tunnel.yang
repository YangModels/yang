module Cisco-IOS-XE-tunnel {
  yang-version 1.1;
  namespace "http://cisco.com/ns/yang/Cisco-IOS-XE-tunnel";
  prefix ios-tun;

  import cisco-semver {
    prefix cisco-semver;
  }
  import ietf-inet-types {
    prefix inet;
  }
  import Cisco-IOS-XE-native {
    prefix ios;
  }
  import Cisco-IOS-XE-types {
    prefix ios-types;
  }
  import Cisco-IOS-XE-mpls {
    prefix ios-mpls;
  }
  import Cisco-IOS-XE-features {
    prefix ios-features;
  }
  import Cisco-IOS-XE-interface-common {
    prefix ios-ifc;
  }
  import Cisco-IOS-XE-policy {
    prefix ios-policy;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Tunnel Interfaces Yang model.
     Copyright (c) 2016-2019 by Cisco Systems, Inc.
     All rights reserved.";

  revision 2021-11-01 {
    description
      "- Added tunnel metadata command
       - Ipsec v4 and v6 overlay support";
    cisco-semver:module-version "2.1.0";
  }
  revision 2020-11-01 {
    description
      "- Initial revision for 17.4.1";
    cisco-semver:module-version "2.0.0";
  }
  revision 2020-03-01 {
    description
      "- Added host option for tunnel destination";
    cisco-semver:module-version "1.2.0";
  }
  revision 2019-11-01 {
    description
      "- Added route-via config";
    cisco-semver:module-version "1.1.0";
  }
  revision 2019-07-01 {
    description
      "- Establish semantic version baseline
       - Tunnel VRF model condition added
       - Enabled default values for tunnel parameters
       - Corrected various issues with the tunnel mode
       - Added Tunnel submode l2tpv3 under ethernet mode";
    cisco-semver:module-version "1.0.0";
  }
  revision 2018-11-21 {
    description
      "Cleanup spelling errors in description statements";
  }
  revision 2018-11-09 {
    description
      "added support for EoGRE P2P interfaces";
  }
  revision 2018-08-12 {
    description
      "added must constraint on tunnel source on interface Dialer";
  }
  revision 2018-03-06 {
    description
      "validate ip unnumbered and tunnel source are the same for tunnel mode sdwan";
  }
  revision 2017-08-28 {
    description
      "Extend modeling for multicast";
  }
  revision 2017-07-11 {
    description
      "add tailf dependency extension to order tunnel mode before tunnel key";
  }
  revision 2017-04-28 {
    description
      "inet:ipv6-prefix changed to ios-types:ipv6-prefix";
  }
  revision 2017-02-23 {
    description
      "This revision adds support for MPLS-TE tunnel interface mode";
  }
  revision 2017-02-07 {
    description
      "Initial revision";
  }

  grouping tunnel-mode-ip-ipv6-opt-grouping {
    choice tunmode-choice {
      leaf ip {
        description
          "over IP";
        type empty;
      }
      leaf ipv6 {
        description
          "over IPv6";
        type empty;
      }
      container multipoint {
        description
          "mode Multipoint";
        presence "true";
        leaf ipv6 {
          description
            "over IPv6 (multipoint)";
          type empty;
        }
      }
    }
  }

  grouping config-interface-tunnel-grouping {
    container nhrp {
      description
        "NHRP Interface commands";
      container event-publisher {
        description
          "Enable NHRP smart spoke feature";
        leaf max-event-timeout {
          description
            "Number of seconds";
          type uint8 {
            range "1..22";
          }
        }
      }
      leaf group {
        description
          "group name string";
        type string;
      }
      container map {
        description
          "Map group name to QoS service policy";
        container group {
          description
            "NHRP group mapping";
          list nhrp-name {
            key "nhrp-name";
            leaf nhrp-name {
              description
                "NHRP group name";
              type string;
            }
            container service-policy {
              description
                "QoS service-policy";
              leaf output {
                description
                  "QoS policy-map name";
                type string;
              }
            }
          }
        }
      }
      leaf route-watch {
        description
          "Enable NHRP route watch";
        type boolean;
      }
    }
    container tunnel {
      description
        "protocol-over-protocol tunneling";
      container tun-6rd {
        when '../ios-tun:mode/ios-tun:ipv6ip-config/ios-tun:auto-6rd';
        description
          "set tunnel 6rd parameters";
        leaf br {
          description
            "Border Relay parameters";
          type inet:ipv4-address;
        }
        container ipv4 {
          description
            "Common IPv4 transport source parameters";
          leaf prefix-len {
            description
              "Common IPv4 transport source prefix length";
            type uint8 {
              range "0..31";
            }
          }
          leaf suffix-len {
            description
              "Common IPv4 transport source suffix length";
            type uint8 {
              range "0..31";
            }
          }
        }
        leaf prefix {
          description
            "Provider selected common IPv6 prefix";
          type ios-types:ipv6-prefix;
        }
        leaf reverse-map-check-config {
          description
            "Enable source IP address and port verification";
          type boolean;
          default "true";
        }
        leaf reverse-map-check {
          description
            "Enable source IP address and port verification";
          status deprecated;
          type empty;
        }
      }
      leaf src-mac-address {
        description
          "Mac address";
        when '../ios-tun:mode/ios-tun:ethernet-config';
        type ios-types:cisco-mac-address-type;
      }
      container bandwidth {
        description
          "Set tunnel bandwidth informational parameter";
        leaf receive {
          description
            "Receive bandwidth";
          type uint32 {
            range "1..10000000";
          }
          default "8000";
        }
        leaf transmit {
          description
            "Transmit bandwidth";
          type uint32 {
            range "1..10000000";
          }
          default "8000";
        }
      }
      leaf checksum {
        description
          "enable end to end checksumming of packets";
        type empty;
      }
      leaf source {
        description
          "source of tunnel packets";
        must "starts-with(., 'Dialer') and  (number(substring-after(., 'Dialer')) = /ios:native/ios:interface/ios:Dialer/ios:name) or not (starts-with(., 'Dialer'))" {
          error-message "To use a Dialer interface, the Dialer interface has to be configured 1st, vice versa for delete";
        }
        type string;
      }
      container destination-config {
        description
          "destination of tunnel";
        choice dest-choice {
          leaf ipv4 {
            description
              "ip address or host name";
            must "not (../../ios-tun:mode/ios-tun:gre-config/ios-tun:multipoint)
                  and not (../../ios-tun:mode/ios-tun:ipv6ip-config/ios-tun:auto-6rd)
                  and not (../../ios-tun:mode/ios-tun:ipv6ip-config/ios-tun:auto-6to4)
                  and not (../../ios-tun:mode/ios-tun:ipv6ip-config/ios-tun:auto-isatap)" {
              error-message "tunnel destination and this mode cannot be configured together.";
            }
            type inet:ipv4-address;
          }
          leaf ipv6 {
            description
              "IPv6 address";
            type inet:ipv6-address;
          }
          leaf dynamic {
            description
              "destination dynamic";
            type empty;
          }
          leaf host {
            description
              "host name";
            type string;
          }
        }
      }
      container destination {
        description
          "destination of tunnel";
        status deprecated;
        leaf ipaddress-or-host {
          status deprecated;
          type inet:host;
        }
        container list {
          description
            "List of Tunnel destinations";
          status deprecated;
          container mpls {
            description
              "MPLS destination list";
            status deprecated;
            container traffic-eng {
              description
                "MPLS Traffic Engineering destination list";
              status deprecated;
              leaf name {
                description
                  "Specify a destination list by name";
                status deprecated;
                type string;
              }
            }
          }
        }
      }
      container dst-port {
        description
          "tunnel destination port";
        when '../ios-tun:mode/ios-tun:udp-config';
        choice dst-port-choice {
          case port-num-case {
            leaf port-num {
              type uint16 {
                range "0..65535";
              }
            }
          }
          case dynamic-case {
            leaf dynamic {
              description
                "Set Destination Port Dynamically";
              type empty;
            }
          }
        }
      }
      container endpoint {
        description
          "Set endpoint parameter";
        container service-policy {
          description
            "Set service-policy";
          leaf output {
            description
              "apply QoS service policy in the output direction";
            must '(/ios:native/ios:policy/ios-policy:policy-map[ios-policy:name = current()])' {
              error-message "Warning: This control policy-map does not exist";
            }
            type string;
          }
        }
      }
      leaf entropy {
        description
          "Compute hash (entropy) on payload and propagate to tunnel header";
        must "((../ios-tun:mode/ios-tun:gre-config)
              or (../ios-tun:mode/ios-tun:ethernet-config/ios-tun:gre/ios-tun:ipv4)
              or (../ios-tun:mode/ios-tun:ethernet-config/ios-tun:gre/ios-tun:ipv6))" {
          error-message "Tunnel entropy and this tunnel mode are not allowed.";
        }
        type empty;
      }
      container fixup {
        description
          "fixup on tunnel interface";
        leaf nat {
          description
            "enable post nat fixup ";
          type empty;
        }
      }
      container flow {
        description
          "flow options";
        leaf egress-records {
          description
            "enable egress flow records ";
          type empty;
        }
      }
      leaf key {
        description
          "security or selector key";
        type uint64 {
          range "0..4294967295";
        }
      }
      container mode {
        description
          "tunnel encapsulation method";
        choice mode-choice {
          leaf aurp {
            description
              "AURP TunnelTalk AppleTalk encapsulation";
            type empty;
          }
          leaf cayman {
            description
              "Cayman TunnelTalk AppleTalk encapsulation";
            type empty;
          }
          leaf dvmrp {
            description
              "DVMRP multicast tunnel";
            type empty;
          }
          leaf eon {
            description
              "EON compatible CLNS tunnel";
            type empty;
          }
          leaf iptalk {
            description
              "Apple IPTalk encapsulation";
            type empty;
          }
          leaf nos {
            description
              "IP over IP encapsulation (KA9Q/NOS compatible)";
            type empty;
          }
          leaf rbscp {
            description
              "RBSCP in IP tunnel";
            type empty;
          }
          leaf tag-switching {
            description
              "IP over Tag Switching encapsulation";
            type empty;
          }
          container ipsec {
            description
              "IPSec tunnel encapsulation";
            container ipv4 {
              description
                "over IPv4";
              presence "true";
              leaf v6-overlay {
                type empty;
              }
            }
            container ipv6 {
              description
                "over IPv6";
              presence "true";
              leaf v4-overlay {
                type empty;
              }
            }
          }
          container mpls {
            description
              "MPLS encapsulations";
            container traffic-eng {
              description
                "Traffic engineering tunnels";
              presence "true";
              leaf multilsp {
                description
                  "Multiple LSP mode";
                type empty;
              }
              leaf point-to-multipoint {
                description
                  "point-to-multipoint tunnel mode";
                type empty;
              }
            }
          }
          container ethernet-config {
            description
              "Ethernet over gre";
            choice eth-mode-choice {
              container gre {
                description
                  "Ethernet over GRE";
                choice address-family-choice {
                  container ipv4 {
                    description
                      "over ipv4";
                    presence "true";
                    leaf p2p {
                      description
                        "point-to-point over ipv4";
                      type empty;
                    }
                  }
                  container ipv6 {
                    description
                      "over ipv6";
                    presence "true";
                    leaf p2p {
                      description
                        "point-to-point over ipv6";
                      type empty;
                    }
                  }
                }
              }
              container l2tpv3 {
                description
                  "Use L2TPv3 encapsulation";
                leaf manual {
                  description
                    "Manually configure L2TP parameters";
                  type empty;
                }
              }
            }
          }
          container ethernet {
            description
              "Ethernet over gre";
            status deprecated;
            container gre {
              description
                "Ethernet over gre";
              status deprecated;
              container ipv4 {
                description
                  "Ethernet over GRE ipv4";
                status deprecated;
                presence "true";
                leaf p2p {
                  must 'count(/ios:native/ios:interface/ios:Tunnel/tunnel/mode/ethernet/gre/ipv4/p2p) + count (/ios:native/ios:interface/ios:Tunnel/tunnel/mode/ethernet/gre/ipv6/p2p) <= 10' {
                    error-message "Too many EoGRE P2P interfaces";
                  }
                  description
                    "point-to-point over ipv4";
                  status deprecated;
                  type empty;
                }
              }
              container ipv6 {
                description
                  "Ethernet over GRE ipv6";
                presence "true";
                status deprecated;
                leaf p2p {
                  must 'count(/ios:native/ios:interface/ios:Tunnel/tunnel/mode/ethernet/gre/ipv4/p2p) + count (/ios:native/ios:interface/ios:Tunnel/tunnel/mode/ethernet/gre/ipv6/p2p) <= 10' {
                    error-message "Too many EoGRE P2P interfaces";
                  }
                  description
                    "point-to-point over ipv6";
                  status deprecated;
                  type empty;
                }
              }
            }
          }
          container ipip {
            description
              "IP over IP encapsulation";
            presence "true";
            leaf decapsulate-any {
              description
                "Incoming traffic only";
              type empty;
            }
          }
          leaf ipv6 {
            description
              "Generic packet tunneling in IPv6";
            type empty;
          }
          container ipv6ip-config {
            description
              "IPv6 over IP encapsulation";
            presence "true";
            choice ipv6ip-choice {
              leaf auto-6rd {
                description
                  "IPv6 automatic tunnelling using 6rd";
                type empty;
              }
              leaf auto-6to4 {
                description
                  "IPv6 automatic tunnelling using 6to4";
                type empty;
              }
              leaf auto-isatap {
                description
                  "IPv6 automatic tunnelling using ISATAP";
                type empty;
              }
            }
          }
          container ipv6ip {
            description
              "IPv6 over IP encapsulation";
            status deprecated;
            presence "true";
            leaf auto-6rd {
              description
                "IPv6 automatic tunnelling using 6rd";
              type empty;
            }
            leaf auto-6to4 {
              description
                "IPv6 automatic tunnelling using 6to4";
              type empty;
            }
            leaf isatap {
              description
                "IPv6 automatic tunnelling using ISATAP";
              type empty;
            }
          }
          container gre-config {
            description
              "generic route encapsulation protocol";
            choice tunmode-choice {
              leaf ip {
                description
                  "over IP";
                type boolean;
                default "true";
              }
              leaf ipv6 {
                description
                  "over IPv6";
                type empty;
              }
              container multipoint {
                description
                  "mode Multipoint";
                presence "true";
                leaf ipv6 {
                  description
                    "over IPv6 (multipoint)";
                  type empty;
                }
              }
            }
          }
          container gre {
            description
              "generic route encapsulation protocol";
            status deprecated;
            leaf ip {
              description
                "over IP";
              type empty;
            }
            leaf ipv6 {
              description
                "over IPv6";
              type empty;
            }
            container multipoint {
              description
                "over IPv4 (multipoint)";
              presence "true";
              leaf ipv6 {
                description
                  "over IPv6";
                type empty;
              }
            }
          }
          container udp-config {
            description
              "UDP encapsulation protocol";
            uses tunnel-mode-ip-ipv6-opt-grouping;
          }
          leaf udp {
            description
              "UDP encapsulation protocol";
            status deprecated;
            type enumeration {
              enum ip;
              enum multipoint;
            }
          }
          container vxlan {
            description
              "VXLAN encapsulation";
            choice tunmode-choice {
              container ipv4 {
                description
                  "over ip";
                choice tun-ip-vxlan-choice {
                  leaf default-mac {
                    description
                      "default mac";
                    type empty;
                  }
                  container src-mac {
                    description
                      "Source Mac address";
                    leaf source-mac {
                      description
                        "Source Mac address";
                      type ios-types:cisco-mac-address-type;
                    }
                    leaf dst-mac {
                      description
                        "Destination Mac address";
                      must '../ios-tun:source-mac' {
                        error-message "Delete src-mac and dest-mac together";
                      }
                      type ios-types:cisco-mac-address-type;
                    }
                  }
                }
              }
              container ipv6 {
                description
                  "over IPv6";
                choice tun-ip-vxlan-choice {
                  leaf default-mac {
                    description
                      "default mac";
                    type empty;
                  }
                  container src-mac {
                    description
                      "Source Mac address";
                    leaf source-mac {
                      description
                        "Source Mac address";
                      type ios-types:cisco-mac-address-type;
                    }
                    leaf dst-mac {
                      description
                        "Destination Mac address";
                      type ios-types:cisco-mac-address-type;
                    }
                  }
                }
              }
              container multipoint {
                choice tunmode-mul-choice {
                  leaf ip {
                    description
                      "over IPv4 (multipoint)";
                    type empty;
                  }
                  leaf ipv6 {
                    description
                      "over IPv6 (multipoint)";
                    type empty;
                  }
                }
              }
            }
          }
          container vxlan-gpe {
            description
              "VXLAN gpe encapsulation";
            choice tunmode-choice {
              leaf ipv4 {
                description
                  "over ip";
                type empty;
              }
              leaf ipv6 {
                description
                  "over IPv6";
                type empty;
              }
              container multipoint {
                choice tunmode-mul-choice {
                  leaf ip {
                    description
                      "over IPv4 (multipoint)";
                    type empty;
                  }
                  leaf ipv6 {
                    description
                      "over IPv6 (multipoint)";
                    type empty;
                  }
                }
              }
            }
          }
          leaf sdwan {
            if-feature "ios-features:sdwan";
            description
              "SDWAN";
            must '../../source = /ios:native/ios:interface/ios:Tunnel/ios:ip/ios:unnumbered' {
              error-message "ip unnumbered and tunnel source are not same for tunnel mode sdwan";
            }
            type empty;
          }
        }
      }
      container network-id {
        description
          "Set network-id";
        leaf id {
          description
            "Set network-id";
          must '../ios-tun:nexthop' {
            error-message "Delete network-id and nexthop together";
          }
          must '../../ios-tun:mode/ios-tun:gre-config/ios-tun:multipoint' {
            error-message "Tunnel mode MGRE needs to be configured before configuring overlay";
          }
          must '/ios:native/ios:interface/ios:Tunnel/ios:ip/ios:address' {
            error-message "Tunnel IP address needs to be configured before configuring overlay";
          }
          type uint16 {
            range "1..65535";
          }
        }
        leaf nexthop {
          description
            "nexthop";
          must '../ios-tun:id' {
            error-message "Delete nexthop and network-id value together";
          }
          type inet:ipv4-address;
        }
        leaf weight {
          description
            "weight";
          must '../ios-tun:nexthop' {
            error-message "Delete weight with the network-id deletion";
          }
          type uint16 {
            range "1..65535";
          }
        }
        leaf qos {
          description
            "QoS profile";
          must '../ios-tun:nexthop' {
            error-message "Delete QoS profile first with the network-id deletion";
          }
          type string;
        }
      }
      container path-mtu-discovery {
        description
          "Enable Path MTU Discovery on tunnel";
        presence "true";
        leaf age-timer {
          description
            "Set PMTUD aging timer";
          type union {
            type uint8 {
              range "10..30";
            }
            type enumeration {
              enum infinite;
            }
          }
        }
        leaf min-mtu {
          description
            "Min pmtud mtu allowed";
          type uint16 {
            range "92..65535";
          }
        }
      }
      container protection {
        description
          "Enable tunnel protection";
      }
      leaf tsp-hop {
        description
          "Define a TSP hop";
        type empty;
      }
      container mpls {
        uses ios-mpls:config-tunnel-mpls-grouping;
      }
      container raw-packet-interface-config {
        description
          "physical interface for all packets entering into be tunneled and for all packets entering the tunnel to exit";
        uses ios-ifc:interface-grouping;
      }
      leaf raw-packet-interface {
        description
          "physical interface for all packets entering into be tunneled and for all packets entering the tunnel to exit";
        status deprecated;
        type string;
      }
      leaf rrr {
        description
          "RRR configuration";
        type string;
      }
      container rbscp {
        description
          "Set tunnel RBSCP parameters";
        leaf ack-split {
          description
            "ACK splitting";
          must '../../ios-tun:mode/ios-tun:rbscp' {
            error-message "Only valid in tunnel rbscp mode";
          }
          type uint8 {
            range "1..32";
          }
        }
        leaf delay {
          description
            "enable delay";
          must '../../ios-tun:mode/ios-tun:rbscp' {
            error-message "Only valid in tunnel rbscp mode";
          }
          type empty;
        }
        leaf drop-scale {
          description
            "Drop scale";
          must '../../ios-tun:mode/ios-tun:rbscp' {
            error-message "Only valid in tunnel rbscp mode";
          }
          type uint8 {
            range "1..255";
          }
        }
        leaf fuzz {
          description
            "Fuzz factor";
          must '../../ios-tun:mode/ios-tun:rbscp' {
            error-message "Only valid in tunnel rbscp mode";
          }
          type uint8 {
            range "1..255";
          }
        }
        leaf init-tsn {
          description
            "Initial TSN";
          must '../../ios-tun:mode/ios-tun:rbscp' {
            error-message "Only valid in tunnel rbscp mode";
          }
          type uint32 {
            range "1..16777215";
          }
        }
        leaf input-drop {
          description
            "max tunnel queue size (number of bw*delay)";
          must '../../ios-tun:mode/ios-tun:rbscp' {
            error-message "Only valid in tunnel rbscp mode";
          }
          type uint8 {
            range "1..10";
          }
        }
        leaf long-drop {
          description
            "Drop non-transmitted packets w/excessive delay";
          must '../../ios-tun:mode/ios-tun:rbscp' {
            error-message "Only valid in tunnel rbscp mode";
          }
          type empty;
        }
        leaf order {
          description
            "release packets in order";
          must '../../ios-tun:mode/ios-tun:rbscp' {
            error-message "Only valid in tunnel rbscp mode";
          }
          type empty;
        }
        leaf report {
          description
            "enable SCTP report chunk";
          must '../../ios-tun:mode/ios-tun:rbscp' {
            error-message "Only valid in tunnel rbscp mode";
          }
          type empty;
        }
        leaf scaling {
          description
            "ACK split scaling";
          must '../../ios-tun:mode/ios-tun:rbscp' {
            error-message "Only valid in tunnel rbscp mode";
          }
          type empty;
        }
        leaf window-stuff {
          description
            "Window stuffing";
          must '../../ios-tun:mode/ios-tun:rbscp' {
            error-message "Only valid in tunnel rbscp mode";
          }
          type uint8 {
            range "1..20";
          }
        }
      }
      leaf snooping {
        description
          "Snooping on tunnel";
        when '../ios-tun:mode/ios-tun:ethernet-config';
        type enumeration {
          enum enable;
        }
      }
      container src-port {
        description
          "tunnel source port";
        when '../ios-tun:mode/ios-tun:udp-config';
        choice src-port-choice {
          case port-num-case {
            leaf port-num {
              type uint16 {
                range "0..65535";
              }
            }
          }
          case dynamic-case {
            leaf dynamic {
              description
                "Set Source Port Dynamically";
              type empty;
            }
          }
        }
      }
      leaf tos {
        description
          "set type of service byte";
        type uint8 {
          range "0..255";
        }
      }
      container metadata {
        description
          "metadata sharing options";
        leaf src_vpn {
          description
            "enable metadata sharing src-vpn";
          type empty;
        }
      }
      leaf ttl {
        description
          "set time to live";
        type uint8 {
          range "1..255";
        }
        default "255";
      }
      container udlr-config {
        description
          "associate tunnel with unidirectional interface";
        leaf address-resolution {
          description
            "Enable ARP and NHRP over a UDLR Tunnel";
          must '(../ios-tun:send-only)' {
            error-message "UDL Tunnel ARP is for transmit-only tunnel interfaces";
          }
          type empty;
        }
        choice udlr-choice {
          container receive-only {
            description
              "Tunnel is receive-only capable";
            uses ios-ifc:interface-grouping;
          }
          container send-only {
            description
              "Tunnel is send-only capable";
            uses ios-ifc:interface-grouping;
          }
        }
      }
      container udlr {
        description
          "associate tunnel with unidirectional interface";
        status deprecated;
        leaf address-resolution {
          description
            "Enable ARP and NHRP over a UDLR Tunnel";
          type empty;
        }
        leaf receive-only {
          description
            "Tunnel is receive-only capable";
          type string;
        }
        leaf send-only {
          description
            "Tunnel is send-only capable";
          type string;
        }
      }
      container vxlan {
        description
          "Tunnel vxlan network";
        when '../ios-tun:mode/ios-tun:vxlan';
        leaf vni {
          description
            "Tunnel vxlan network identifier";
          type uint32 {
            range "1..16777215";
          }
        }
        container src-port-range {
          description
            "Tunnel vxlan source port range";
          leaf source-port-range {
            description
              "Tunnel vxlan source port number start";
            type uint16 {
              range "1..65535";
            }
          }
          leaf source-port-end {
            description
              "Tunnel vxlan source port number end";
            type uint16 {
              range "1..65535";
            }
          }
        }
      }
      container vlan {
        description
          "Set vlan-id for ethernet over gre mode";
        when '../ios-tun:mode/ios-tun:ethernet-config';
        leaf id1 {
          type uint16 {
            range "1..4094";
          }
        }
        leaf hyphen {
          type empty;
        }
        leaf id2 {
          type uint16 {
            range "1..4094";
          }
        }
      }
      container vrf-config {
        description
          "set tunnel vrf membership";
        leaf multiplexing {
          description
            "multiple vrf's multiplexing";
          type empty;
          must 'not (../vrf-common/vrf)' {
            error-message "common vrf configured already. Remove it and then try again";
          }
          must 'not (../vrf-egress/vrf) and not (../vrf-ingress/vrf)' {
            error-message "egress-only ingress-only vrf configured already. Remove it and then try again";
          }
        }
        container vrf-common {
          description
            "vrf common config";
          leaf vrf {
            type string;
            must "/ios:native/ios:vrf/ios:definition[ios:name=current()]
                  or /ios:native/ios:ip/ios:vrf[ios:name=current()]" {
              error-message "VRF is not configured";
            }
            must 'not (../../vrf-egress/vrf) and not (../../vrf-ingress/vrf)' {
              error-message "egress-only ingress-only vrf configured already. Remove it and then try again";
            }
            must 'not (../../multiplexing)' {
              error-message "vrf multiplexing configured already. Remove it and then try again";
            }
          }
        }
        container vrf-egress {
          description
            "egress-only";
          leaf vrf {
            type string;
            must 'not (../../vrf-common/vrf) and not (../../vrf-ingress/vrf=current())' {
              error-message "ingress-only and egress-only vrf should not be same";
            }
            must 'not (../../multiplexing)' {
              error-message "vrf multiplexing configured already. Remove it and then try again";
            }
            must "/ios:native/ios:vrf/ios:definition[ios:name=current()]
                  or /ios:native/ios:ip/ios:vrf[ios:name=current()]" {
              error-message "VRF is not configured";
            }
          }
          leaf egress-only {
            type empty;
          }
        }
        container vrf-ingress {
          description
            "ingress-only";
          leaf vrf {
            type string;
            must 'not (../../vrf-common/vrf) and not (../../vrf-egress/vrf=current())' {
              error-message "ingress-only and egress-only vrf should not be same";
            }
            must 'not (../../multiplexing)' {
              error-message "vrf multiplexing configured already. Remove it and then try again";
            }
            must "/ios:native/ios:vrf/ios:definition[ios:name=current()]
                  or /ios:native/ios:ip/ios:vrf[ios:name=current()]" {
              error-message "VRF is not configured";
            }
          }
          leaf ingress-only {
            type empty;
          }
        }
      }
      container route-via {
        description
          "Select subset of routes for tunnel transport";
        leaf interface {
          description
            "Routing interface for tunnel packets";
          must "starts-with(., 'Dialer') and  (number(substring-after(., 'Dialer')) = /ios:native/ios:interface/ios:Dialer/ios:name) or not (starts-with(., 'Dialer'))" {
            error-message "To use a Dialer interface, the Dialer interface has to be configured 1st, vice versa for delete";
          }
          type string;
        }
        choice route-via-choice {
          case preferred-case {
            leaf preferred {
              description
                "Preferred route, if not available, use any route";
              type empty;
            }
          }
          case mandatory-case {
            leaf mandatory {
              description
                "Mandatory route, if not available, drop traffic";
              type empty;
            }
          }
        }
      }
      leaf vrf {
        description
          "set tunnel vrf membership";
        status deprecated;
        type string;
      }
      leaf mpls-ip-only {
        description
          "Copy DF bit from MPLS header to outer GRE";
        must '../ios-tun:path-mtu-discovery' {
          error-message "tunnel path-mtu-discovery needs to be configured before configuring mpls-ip-only, vice-versa for delete";
        }
        type empty;
      }
    }
  }

  augment "/ios:native/ios:interface/ios:Tunnel" {
    uses config-interface-tunnel-grouping;
  }

  augment "/ios:native/ios:interface/ios:Virtual-Template" {
    uses config-interface-tunnel-grouping {
      if-feature "ios-features:virtual-template";
    }
  }
}
