module Cisco-IOS-XE-sm-enum-types {
  yang-version 1.1;
  namespace "http://cisco.com/ns/yang/Cisco-IOS-XE-sm-enum-types";
  prefix sm-enum-types;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for session data types.
     Copyright (c) 2019 by Cisco Systems, Inc.
     All rights reserved.";

  revision 2019-11-01 {
    description
      "Initial revision";
    reference
      "1.0.0";
    cisco-semver:module-version "1.0.0";
  }

  typedef session-events {
    type enumeration {
      enum session-event-invalid {
        value 0;
        description
          "Session event type invalid";
      }
      enum session-event-internal {
        value 1;
        description
          "Session event type internal";
      }
      enum session-event-session-create {
        value 2;
        description
          "Session event type session create";
      }
      enum session-event-session-authc-success {
        value 3;
        description
          "Session event type authentication success";
      }
      enum session-event-session-authc-failed {
        value 4;
        description
          "Session event type authentication failed";
      }
      enum session-event-session-authz-success {
        value 5;
        description
          "Session event type authorization success";
      }
      enum session-event-session-authz-failed {
        value 6;
        description
          "Session event type authorization failed";
      }
      enum session-event-start-method {
        value 7;
        description
          "Session event type start method";
      }
      enum session-event-terminate-method {
        value 8;
        description
          "Session event type terminate method";
      }
      enum session-event-aaa-request {
        value 9;
        description
          "Event raised when a request is initiated to a AAA server.";
      }
      enum session-event-aaa-success {
        value 10;
        description
          "Session event type AAA success";
      }
      enum session-event-aaa-success-no-author-data {
        value 11;
        description
          "Event raised when a success is received from AAA server without any authorization data";
      }
      enum session-event-aaa-challenge {
        value 12;
        description
          "Event raised when access-challenge is raised for a AAA server";
      }
      enum session-event-eap-req-tx {
        value 13;
        description
          "Session event type EAP request transmitted";
      }
      enum session-event-eap-resp-rx {
        value 14;
        description
          "Session event type EAP response received";
      }
      enum session-event-eapol-start-rx {
        value 15;
        description
          "Session event type EAPOL start received";
      }
      enum session-event-eapol-logoff-rx {
        value 16;
        description
          "Session event type EAPOL logoff received";
      }
      enum session-event-wa-get-request {
        value 17;
        description
          "Event raised when a web-auth session received a HTTP GET request.";
      }
      enum session-event-wa-post-request {
        value 18;
        description
          "Event raised when a web-auth session received a HTTP POST request.";
      }
      enum session-event-bm-set-client-to-orig {
        value 19;
        description
          "Event raised when message is sent to put client into original state.";
      }
      enum session-event-bm-set-client-to-fwd {
        value 20;
        description
          "Event raised when a message is sent to put client into forwarding state.";
      }
      enum session-event-policy-change {
        value 21;
        description
          "Event raised when authorization policy changes for a session.";
      }
      enum session-event-session-disconnect {
        value 22;
        description
          "Event raised when session disconnect request is received.";
      }
      enum session-event-policy-update {
        value 23;
        description
          "Event raised when change of policy attributes.";
      }
      enum session-event-coa-start {
        value 24;
        description
          "Event raised when change of authorization is received.";
      }
      enum session-event-security-violation {
        value 25;
        description
          "Event raised on security violation for a port.";
      }
    }
    description
      "Enumeration for session event type";
  }

  typedef session-event-failure-reason {
    type enumeration {
      enum session-event-reason-none {
        value 0;
        description
          "Session event reason none";
      }
      enum session-event-reason-authc-cred-fail {
        value 1;
        description
          "Session event reason authentication credential fail";
      }
      enum session-event-reason-authc-aaa-server-fail {
        value 2;
        description
          "Session event reason authentication AAA server fail";
      }
      enum session-event-reason-authc-no-response-fail {
        value 3;
        description
          "Session event reason authentication no response fail";
      }
      enum session-event-reason-authc-timeout-fail {
        value 4;
        description
          "Session event reason authentication timeout fail";
      }
      enum session-event-reason-authc-no-config-fail {
        value 5;
        description
          "Session event reason authentication no configuration fail";
      }
      enum session-event-reason-aaa-not-ready {
        value 6;
        description
          "Session event reason AAA server not ready";
      }
      enum session-event-reason-authz-vlan-fail {
        value 7;
        description
          "Session event reason authorization VLAN fail";
      }
      enum session-event-reason-authz-acl-fail {
        value 8;
        description
          "Session event reason authorization ACL fail";
      }
      enum session-event-reason-authz-punt-acl-fail {
        value 9;
        description
          "Session event reason authorization punt ACL fail";
      }
      enum session-event-reason-authz-qos-policy-fail {
        value 10;
        description
          "Session event reason authorization QOS policy fail";
      }
      enum session-event-reason-authz-accounting-fail {
        value 11;
        description
          "Session event reason authorization accounting fail";
      }
      enum session-event-reason-authz-cfg-macro-fail {
        value 12;
        description
          "Session event reason authorization config macro fail";
      }
      enum session-event-reason-authz-cts-fail {
        value 13;
        description
          "Session event reason authorization CTS fail";
      }
      enum session-event-reason-authz-fqdn-fail {
        value 14;
        description
          "Session event reason authorization FQDN fail";
      }
      enum session-event-reason-authz-mdns-fail {
        value 15;
        description
          "Session event reason authorization MDNS fail";
      }
      enum session-event-reason-authz-idle-timeout-fail {
        value 16;
        description
          "Session event reason authorization IAF fail";
      }
      enum session-event-reason-authz-interface-template-fail {
        value 17;
        description
          "Session event reason authorization interface template fail";
      }
      enum session-event-reason-authz-umbrella-fail {
        value 18;
        description
          "Session event reason authorization umbrella fail";
      }
      enum session-event-reason-authz-linksec-fail {
        value 19;
        description
          "Session event reason authorization link security fail";
      }
      enum session-event-reason-authz-misc-fail {
        value 20;
        description
          "Session event reason authorization miscellaneous fail";
      }
      enum session-event-reason-authz-autoconf-fail {
        value 21;
        description
          "Session event reason authorization autoconf fail";
      }
      enum session-event-reason-authz-tag-fail {
        value 22;
        description
          "Session event reason authorization tag fail";
      }
      enum session-event-reason-authz-tunnel-fail {
        value 23;
        description
          "Session event reason authorization tunnel fail";
      }
      enum session-event-reason-authz-voice-vlan-fail {
        value 24;
        description
          "Session event reason authorization voice VLAN fail";
      }
      enum session-event-reason-authz-reauth-fail {
        value 25;
        description
          "Session event reason authorization reauthentication fail";
      }
      enum session-event-reason-authz-supplicant-name-fail {
        value 26;
        description
          "Session event reason authorization supplicant name fail";
      }
      enum session-event-reason-authz-user-name-fail {
        value 27;
        description
          "Session event reason authorization user name fail";
      }
      enum session-event-reason-authz-service-set-id-fail {
        value 28;
        description
          "Session event reason authorization service set id fail";
      }
      enum session-event-reason-authz-interim-interval-fail {
        value 29;
        description
          "Session event reason authorization interim interval fail";
      }
      enum session-event-reason-authz-unknown-fail {
        value 30;
        description
          "Session event reason authorization unknown fail";
      }
    }
    description
      "Enumeration for session event reason";
  }

  typedef session-eap-method {
    type enumeration {
      enum session-eap-method-unknown {
        value 0;
        description
          "Session EAP method unknown";
      }
      enum session-eap-method-md5 {
        value 4;
        description
          "Session EAP method MD5";
      }
      enum session-eap-method-gtc {
        value 6;
        description
          "Session EAP method GTC";
      }
      enum session-eap-method-tls {
        value 13;
        description
          "Session EAP method TLS";
      }
      enum session-eap-method-leap {
        value 17;
        description
          "Session EAP method LEAP";
      }
      enum session-eap-method-peap {
        value 25;
        description
          "Session EAP method PEAP";
      }
      enum session-eap-method-mschapv2 {
        value 26;
        description
          "Session EAP method MSCHAPV2";
      }
      enum session-eap-method-fast {
        value 43;
        description
          "Session EAP method FAST";
      }
    }
    description
      "Enumeration for EAP method for a session";
  }

  typedef session-auth-method-id {
    type enumeration {
      enum session-auth-method-no-method-id {
        value 0;
        description
          "Session method ID is none";
      }
      enum session-auth-method-dot1x-method-id {
        value 1;
        description
          "Session method ID is DOT1X";
      }
      enum session-auth-method-mab-method-id {
        value 2;
        description
          "Session method ID is MAB";
      }
      enum session-auth-method-webauth-method-id {
        value 3;
        description
          "Session method ID is Web-Auth";
      }
      enum session-auth-method-static-method-id {
        value 4;
        description
          "Session method ID is static";
      }
      enum session-auth-method-eou-method-id {
        value 5;
        description
          "Session method ID is EOU";
      }
      enum session-auth-method-dot1x-supp-method-id {
        value 6;
        description
          "Session method ID is DOT1X Supplicant";
      }
    }
    description
      "Enumeration for Authentication method  type for a session";
  }

  typedef session-security-violation-action {
    type enumeration {
      enum session-violation-action-shutdown {
        value 0;
        description
          "Session violation action shutdown";
      }
      enum session-violation-action-restrict {
        value 1;
        description
          "Session violation action restrict";
      }
      enum session-violation-action-protect {
        value 2;
        description
          "Session violation action protect";
      }
      enum session-violation-action-replace {
        value 3;
        description
          "Session violation action replace";
      }
    }
    description
      "Enumeration for security violation action";
  }

  typedef session-coa-request-type {
    type enumeration {
      enum coa-request {
        value 32530;
        description
          "Session COA request";
      }
      enum coa-pod-request {
        value 32539;
        description
          "Session COA pod request";
      }
      enum coa-bounce-host-port-request {
        value 32534;
        description
          "Session COA bounce host port";
      }
      enum coa-disable-host-port-request {
        value 32535;
        description
          "Session COA disable host port";
      }
      enum coa-update-service-template-request {
        value 32543;
        description
          "Session COA update service template";
      }
    }
    description
      "Enumeration for COA request type";
  }
}
