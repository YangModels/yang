module Cisco-IOS-XE-qfp-resource-utilization-oper {
  yang-version 1.1;
  namespace "http://cisco.com/ns/yang/Cisco-IOS-XE-qfp-resource-utilization-oper";
  prefix datapath-utilization;

  import Cisco-IOS-XE-common-types {
    prefix common-types-ios-xe;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Quantum Flow Processor (QFP) resource utilization operational data.
     Copyright (c) 2020 by Cisco Systems, Inc.
     All rights reserved.";

  revision 2020-07-01 {
    description
      "Initial revision";
    reference
      "1.0.0";
    cisco-semver:module-version "1.0.0";
  }

  typedef cpp-period {
    type enumeration {
      enum cpp-period-5secs {
        value 0;
        description
          "Period of 5 secs";
      }
      enum cpp-period-1min {
        value 1;
        description
          "Period of 1 minutes";
      }
      enum cpp-period-5min {
        value 2;
        description
          "Period of 5 minutes";
      }
      enum cpp-period-60min {
        value 3;
        description
          "Period of 60 minutes";
      }
    }
    description
      "Time interval";
  }

  grouping cpp-dp-utilization-sum {
    description
      "Resource utilization statistics collected
       by QFP entity at time intervals 5 seconds, 1 minute,
       5 mins and 60 mins.";
    leaf cpp-num {
      type uint64;
      description
        "Cisco packet processor number";
    }
    leaf period {
      type datapath-utilization:cpp-period;
      description
        "Time interval of data collected";
    }
    leaf total-input-pkts {
      type uint64;
      description
        "Total input packets";
    }
    leaf total-input-bytes {
      type uint64;
      units "bytes";
      description
        "Total input bytes";
    }
    leaf total-output-pkts {
      type uint64;
      description
        "Total output packets";
    }
    leaf total-output-bytes {
      type uint64;
      units "bytes";
      description
        "Total output bytes";
    }
    leaf dp-stats-load {
      type uint64;
      units "percentage";
      description
        "Processed load over different time intervals";
    }
  }

  grouping stat-values {
    description
      "Statistical model of QFP resource usage readings";
    leaf total {
      type uint64;
      units "bytes";
      description
        "Total memory available";
    }
    leaf in-use {
      type uint64;
      units "bytes";
      description
        "Current in use memory";
    }
    leaf free {
      type uint64;
      units "bytes";
      description
        "Current free memory";
    }
    leaf lowest-free-water-mark {
      type uint64;
      units "bytes";
      description
        "Lowest free water mark memory";
    }
  }

  grouping qfp-exmem-stat {
    description
      "The memory utilization Information of Quantum Flow Processor";
    leaf qfp {
      type uint16;
      description
        "Quantum Flow Processor ID";
    }
    container dram {
      description
        "Dynamic memory(DRAM) memory resource statistics";
      uses datapath-utilization:stat-values;
    }
    container iram {
      description
        "Instruction memory(IRAM) memory resource statistics";
      uses datapath-utilization:stat-values;
    }
    container sram {
      description
        "Static memory(SRAM) memory resource statistics";
      uses datapath-utilization:stat-values;
    }
  }

  container qfp-resource-utilization-oper-data {
    config false;
    description
      "QFP resource utilization operational data";
    list location {
      key "fru slot bay chassis node";
      description
        "A list of data provider locations";
      uses common-types-ios-xe:extended-location;
      list qfp-exmem-stat {
        key "qfp";
        description
          "The memory utilization of Quantum Flow Processor";
        uses datapath-utilization:qfp-exmem-stat;
      }
      list qfp-dp-util {
        key "period";
        description
          "The datapath utilization of Quantum Flow Processor";
        uses datapath-utilization:cpp-dp-utilization-sum;
      }
    }
  }
}
