module Cisco-IOS-XE-ethernet-rpc {
  yang-version 1.1;
  namespace "http://cisco.com/ns/yang/Cisco-IOS-XE-ethernet-rpc";
  prefix Cisco-IOS-XE-ethernet-rpc;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Copyright (c) 2021 by Cisco Systems, Inc.
     All rights reserved.";

  revision 2021-11-01 {
    description
      "- Added Ethernet CFM(Connectivity fault management) maintenance association option";
    reference
      "1.1.0";
    cisco-semver:module-version "1.1.0";
  }
  revision 2021-07-01 {
    description
      "Initial revision";
    reference
      "1.0.0";
    cisco-semver:module-version "1.0.0";
  }

  typedef remote-loopback-actions {
    type enumeration {
      enum remote-loopback-start {
        value 0;
        description
          "Start OAM remote-loopback";
      }
      enum remote-loopback-stop {
        value 1;
        description
          "Stop OAM remote-loopback";
      }
    }
    description
      "Ethernet OAM remote-loopback start/stop action";
  }

  typedef latching-loopback-actions {
    type enumeration {
      enum latching-loopback-activate {
        value 0;
        description
          "Activate ethernet latching-loopback";
      }
      enum latching-loopback-deactivate {
        value 1;
        description
          "Deactivate ethernet latching-loopback";
      }
    }
    description
      "Ethernet latching-loopback activate/deactivate action";
  }

  typedef service-option {
    type enumeration {
      enum service-option-name {
        value 0;
        description
          "Ethernet CFM(Connectivity fault management) maintenance
           association name";
      }
      enum service-option-number {
        value 1;
        description
          "Ethernet CFM(Connectivity fault management) maintenance
           association number";
      }
      enum service-option-none {
        value 2;
        description
          "To unset Ethernet CFM(Connectivity fault management) maintenance association option";
      }
    }
    description
      "Ethernet CFM(Connectivity fault management) maintenance association option";
  }

  grouping remote-loopback {
    description
      "Ethernet OAM remote-loopback start/stop profile";
    leaf action {
      type Cisco-IOS-XE-ethernet-rpc:remote-loopback-actions;
      mandatory true;
      description
        "Start or stop action for remote-loopback";
    }
    leaf interface {
      type string {
        length "1..99";
        pattern '[0-9a-zA-Z/\-_]*';
      }
      mandatory true;
      description
        "Interface name to start/stop ethernet OAM remote-loopback";
    }
  }

  grouping latching-loopback {
    description
      "Ethernet latching-loopback activate/deactivate profile";
    leaf action {
      type Cisco-IOS-XE-ethernet-rpc:latching-loopback-actions;
      mandatory true;
      description
        "Activate/deactivate action for ethernet latching-loopback";
    }
    leaf domain {
      type string {
        length "1..64";
        pattern '[0-9a-zA-Z\-_]*';
      }
      mandatory true;
      description
        "Ethernet CFM (Connectivity fault management) domain name";
    }
    leaf id {
      type uint16 {
        range "1..8191";
      }
      mandatory true;
      description
        "Local MEP(Maintenance End Point) id";
    }
    leaf service {
      type string {
        length "1..64";
        pattern '[0-9a-zA-Z\-_\^]*';
      }
      description
        "Ethernet CFM(Connectivity fault management) maintenance
         association name";
    }
    leaf destination-mac {
      type yang:mac-address;
      mandatory true;
      description
        "MAC address of remote device";
    }
    leaf timeout {
      when "(../action = 'latching-loopback-activate')";
      type uint32 {
        range "0..90000";
      }
      units "seconds";
      default "300";
      description
        "Timeout value of latching loopback in seconds.
         0 for permanent latching loopback session";
    }
    choice svc-type-choice {
      default "service-option-none";
      description
        "Ethernet CFM(Connectivity fault management) maintenance association option";
      case service-option-name {
        leaf svc-name {
          type string {
            length "1..64";
            pattern '[0-9a-zA-Z\-_\^]*';
          }
          mandatory true;
          description
            "Ethernet CFM(Connectivity fault management) maintenance
             association name";
        }
      }
      case service-option-number {
        leaf svc-number {
          type uint32 {
            range "0..65535";
          }
          mandatory true;
          description
            "Ethernet CFM(Connectivity fault management) maintenance
             association number";
        }
      }
      case service-option-none {
        leaf svc-none {
          type boolean;
          default "true";
          description
            "No Ethernet CFM(Connectivity fault management) maintenance
             association option selected if set to true";
        }
      }
    }
  }

  rpc ethernet-oam {
    description
      "Start/Stop ethernet OAM remote-loopback on interface";
    input {
      uses Cisco-IOS-XE-ethernet-rpc:remote-loopback;
    }
  }

  rpc eth-lat-loopback {
    description
      "Ethernet latching-loopback activate/deactivate";
    input {
      uses Cisco-IOS-XE-ethernet-rpc:latching-loopback;
    }
  }
}
