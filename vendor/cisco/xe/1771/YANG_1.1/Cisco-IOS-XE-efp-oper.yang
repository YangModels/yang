module Cisco-IOS-XE-efp-oper {
  yang-version 1.1;
  namespace "http://cisco.com/ns/yang/Cisco-IOS-XE-efp-oper";
  prefix efp-stats-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for service instance (efp) stats.
     Copyright (c) 2016-2017, 2019 by Cisco Systems, Inc.
     All rights reserved.";

  revision 2019-05-01 {
    description
      "Added semantic version";
    reference
      "1.1.0";
    cisco-semver:module-version "1.1.0";
  }
  revision 2017-02-07 {
    description
      "Initial revision";
    reference
      "1.0.0";
    cisco-semver:module-version "1.0.0";
  }

  grouping efp-key {
    description
      "Each efp record is uniquely identified by interface and id";
    leaf id {
      type uint32;
      description
        "EFP id";
    }
    leaf interface {
      type string;
      description
        "Interface name";
    }
  }

  grouping efp-params {
    description
      "EFP parameters";
    leaf in-pkts {
      type yang:counter64;
      description
        "Incoming packets";
    }
    leaf in-bytes {
      type yang:counter64;
      description
        "Incoming bytes";
    }
    leaf out-pkts {
      type yang:counter64;
      description
        "Outgoing packets";
    }
    leaf out-bytes {
      type yang:counter64;
      description
        "Outgoing bytes";
    }
  }

  container efp-stats {
    config false;
    description
      "Service instance stats";
    list efp-stat {
      key "id interface";
      description
        "List of service instance stats";
      uses efp-stats-ios-xe-oper:efp-key;
      uses efp-stats-ios-xe-oper:efp-params;
    }
  }
}
