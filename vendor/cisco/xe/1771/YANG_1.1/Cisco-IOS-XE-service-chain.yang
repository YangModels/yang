module Cisco-IOS-XE-service-chain {
  yang-version 1.1;
  namespace "http://cisco.com/ns/yang/Cisco-IOS-XE-service-chain";
  prefix ios-service-chain;

  import cisco-semver {
    prefix cisco-semver;
  }
 
  import ietf-inet-types {
    prefix inet;
  }


  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Service Chain Yang model.
     Copyright (c) 2016 by Cisco Systems, Inc.
     All rights reserved.";

  // =========================================================================
  // REVISION
  // =========================================================================
  revision 2019-07-01 {
    description "Establish semantic version baseline";
    cisco-semver:module-version "1.0.0";
  }
  revision 2017-02-07 {
    description
      "Initial revision";
  }

  grouping service-chain-grouping {
      leaf description {
        description
          "Service function forwarder description";
        type string {
          length "1..256";
        }
      }
      container ip {
        description
          "IP address for Service Function Forwarder";
        leaf address {
          description
            "Set IPv4 address";
          type inet:ipv4-address;
        }
      }
  }

  grouping config-service-chain-grouping {
    list service-function {
      description
        "Service function details";
      key "name";
      leaf name {
        description
          "WORD;;Service function name";
        type string;
      }
      container config-service-chain-sf-mode {
        leaf description {
          description
            "Service function description";
          type string {
            length "1..256";
          }
        }
        container encapsulation {
          description
            "Service node encapsulation";
          choice mode-choice {
            container gre {
              description
                "Service node encapsulation type";
              presence "true";
              leaf enhanced {
                description
                  "Add enhanced NSH TLV information";
                type enumeration {
                  enum "copy";
                  enum "divert";
                }
              }
            }
            leaf none {
              description
                "Service node encapsulation type";
              type empty;
            }
          }
        }
        container ip {
          description
            "Service node";
          leaf address {
            type inet:ipv4-address;
          }
        }
      }
    }
    container service-function-forwarder {
      description
        "Service function forwarder details";
      list service-ff-name {
        key "name";
        leaf name {
          description
            "WORD;;Service function forwarder name";
          type string;
        }
        uses service-chain-grouping;
      }
      container local {
        description
          "Local service function forwarder";
        presence "true";
        uses service-chain-grouping;
      }
    }
    list service-path {
      description
        "Service Path Entries";
      key "service-path-id";
      leaf service-path-id {
        type uint32 {
          range "0..16777215";
        }
      }
      container config-service-chain-path-mode {
        leaf description {
          description
            "Path Description";
          type string {
            length "1..256";
          }
        }
        container service-index {
          description
            "Service Index";
          list services {
            key "service-index-id";
            leaf service-index-id {
              type uint8 {
                range "2..255";
              }
            }
            choice service-type-choice {
              leaf service-function {
                description
                  "Service Function name";
                type string;
              }
              leaf service-function-forwarder {
                description
                  "Service Function Forwarder name";
                type string;
              }
              leaf terminate {
                description
                  "Terminate(Proxy)";
                type empty;
              }
            }
          }
        }
      }
    }
  }

  /////////////////////////////////////////////////////////
  // native / service-chain
  /////////////////////////////////////////////////////////
  augment "/ios:native/ios:service-chain" {
    uses config-service-chain-grouping;
  }
}
