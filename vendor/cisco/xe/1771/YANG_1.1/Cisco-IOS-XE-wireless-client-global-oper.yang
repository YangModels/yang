module Cisco-IOS-XE-wireless-client-global-oper {
  yang-version 1.1;
  namespace "http://cisco.com/ns/yang/Cisco-IOS-XE-wireless-client-global-oper";
  prefix wireless-client-global-oper;

  import Cisco-IOS-XE-wireless-client-types {
    prefix wireless-client-types;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains client operational data aggregated across wireless processes.
     Copyright (c) 2021 by Cisco Systems, Inc.
     All rights reserved.";

  revision 2021-11-01 {
    description
      "- Added statistics information for clients 802.1x,
         clients exclusion and wireless trace statistics";
    reference
      "1.1.0";
    cisco-semver:module-version "1.1.0";
  }
  revision 2021-07-01 {
    description
      "Initial revision";
    reference
      "1.0.0";
    cisco-semver:module-version "1.0.0";
  }

  grouping client-statistics {
    description
      "Client statistics";
    container co-client-del-reason {
      description
        "Client delete reason statistics";
      uses wireless-client-types:co-delete-reason;
    }
  }

  grouping client-live-stats {
    description
      "Statistics of clients/mobile stations current state";
    leaf auth-state-clients {
      type uint32;
      description
        "Number of clients in authenticating state";
    }
    leaf mobility-state-clients {
      type uint32;
      description
        "Number of clients in mobility state";
    }
    leaf iplearn-state-clients {
      type uint32;
      description
        "Number of clients in IP learn state";
    }
    leaf webauth-state-clients {
      type uint32;
      description
        "Number of clients in web authenticating state";
    }
    leaf run-state-clients {
      type uint32;
      description
        "Number of clients in run state";
    }
    leaf delete-state-clients {
      type uint32;
      description
        "Number of clients in deletion state";
    }
    leaf random-mac-clients {
      type uint32;
      description
        "Number of clients using random MAC address";
    }
  }

  grouping sm-dot1x-global-stats {
    description
      "Session manager 802.1x global statistics";
    leaf eapol-rx {
      type uint32;
      description
        "Total EAPoL frames received";
    }
    leaf eapol-rx-start {
      type uint32;
      description
        "Total EAPoL Start frames received";
    }
    leaf eapol-rx-logoff {
      type uint32;
      description
        "Total EAPoL Logoff frames received";
    }
    leaf eapol-rx-resp {
      type uint32;
      description
        "Total EAPoL Response frames received";
    }
    leaf eapol-rx-resp-id {
      type uint32;
      description
        "Total EAPoL Response identifier frames received";
    }
    leaf eapol-rx-req {
      type uint32;
      description
        "Total EAPoL Request frames received";
    }
    leaf eapol-rx-invalid {
      type uint32;
      description
        "Total Invalid EAPoL frames received";
    }
    leaf eapol-rx-len-error {
      type uint32;
      description
        "Total EAPoL frames with length error received";
    }
    leaf eapol-tx {
      type uint32;
      description
        "Total EAPoL frames transmitted";
    }
    leaf eapol-tx-start {
      type uint32;
      description
        "Total EAPoL Start frames transmitted";
    }
    leaf eapol-tx-logoff {
      type uint32;
      description
        "Total EAPoL Logoff frames transmitted";
    }
    leaf eapol-tx-resp {
      type uint32;
      description
        "Total EAPoL Response frames transmitted";
    }
    leaf eapol-tx-req {
      type uint32;
      description
        "Total EAPoL Request frames transmitted";
    }
    leaf eapol-retx-req {
      type uint32;
      description
        "Total EAPoL Request frames re-transmitted";
    }
    leaf eapol-retx-req-fail {
      type uint32;
      description
        "Total EAPoL Request frames re-transmitted failed";
    }
    leaf eapol-tx-req-id {
      type uint32;
      description
        "Total EAPoL Request identifier frames transmitted";
    }
    leaf eapol-retx-req-id {
      type uint32;
      description
        "Total EAPoL Request identifier frames re-transmitted";
    }
    leaf eapol-retx-req-id-fail {
      type uint32;
      description
        "Total EAPoL Request identifier frames re-transmitted fail";
    }
  }

  grouping st-tof {
    description
      "Wireless trace statistics";
    leaf-list tof-tag {
      type uint64;
      ordered-by user;
      description
        "Wireless trace on failure statistics";
    }
  }

  grouping st-client-exclusion-stats {
    description
      "Clients exclusion statistics";
    leaf excluded-clients {
      type uint32;
      description
        "Total excluded clients";
    }
    leaf disabled-clients {
      type uint32;
      description
        "Total disabled clients";
    }
  }

  container client-global-oper-data {
    config false;
    description
      "Root container for client operational data aggregated across wireless processes";
    container client-live-stats {
      presence "client-live-stats";
      description
        "Snapshot of statistics of current state of wireless clients";
      uses wireless-client-global-oper:client-live-stats;
    }
    container client-stats {
      presence "client-stats";
      description
        "Summary of client statistics";
      uses wireless-client-global-oper:client-statistics;
    }
    container dot1x-global-stats {
      presence "dot1x-global-stats";
      description
        "Dot1x global statistics";
      uses wireless-client-global-oper:sm-dot1x-global-stats;
    }
    container client-exclusion-stats {
      presence "client-exclusion-stats";
      description
        "Client exclusion statistics";
      uses wireless-client-global-oper:st-client-exclusion-stats;
    }
    container tof-stats {
      presence "tof-stats";
      description
        "Wireless trace statistics";
      uses wireless-client-global-oper:st-tof;
    }
  }
}
