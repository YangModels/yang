module Cisco-IOS-XE-ptp {
  yang-version 1.1;
  namespace "http://cisco.com/ns/yang/Cisco-IOS-XE-ptp";
  prefix ios-ptp;

  import cisco-semver {
    prefix cisco-semver;
  }
  import ietf-inet-types {
    prefix inet;
  }
  import Cisco-IOS-XE-native {
    prefix ios;
  }
  import Cisco-IOS-XE-switch {
    prefix ios-sw;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Precision Time Protocol (PTP) Yang Model.
     Copyright (c) 2016-2017, 2019 by Cisco Systems, Inc.
     All rights reserved.";

  revision 2020-07-01 {
    description
      "- Prepend switchport-config to switchport";
    cisco-semver:module-version "3.0.0";
  }
  revision 2019-12-01 {
    description
      "Adding Transport and Interface level CLIs";
    cisco-semver:module-version "2.0.0";
  }
  revision 2019-07-01 {
    description
      "Establish semantic version baseline";
    cisco-semver:module-version "1.0.0";
  }
  revision 2017-09-19 {
    description
      "Extension for edison";
  }
  revision 2017-02-07 {
    description
      "Initial revision";
  }

  grouping config-ptp-grouping {
    container ptp {
      description
        "Precision Time Protocol";
      container clock {
        description
          "Configure PTP clock";
        container ordinary {
          description
            "Configure PTP Ordinary clock";
          leaf domain {
            description
              "PTP domain";
            type int8 {
              range "0..127";
            }
          }
        }
        container clock-port {
          description
            "Configure clock port";
          leaf name {
            description
              "Port name";
            type string;
          }
          leaf slave {
            description
              "Configure as Slave";
            type empty;
          }
          leaf master {
            description
              "Configure as Master";
            type empty;
          }
          container transport {
            description
              "Set port transport parameters";
            leaf ipv4 {
              description
                "Use IPv4 encapsulation";
              type empty;
            }
            container unicast {
              description
                "Use unicast communication channel";
              leaf interface {
                type string;
              }
              leaf negotiation {
                description
                  "Enable unicast negotiation";
                type empty;
              }
            }
          }
          container clock {
            leaf source {
              type inet:ipv4-address;
            }
          }
        }
      }
    }
  }

  grouping config-ptp-grouping2 {
    leaf domain {
      description
        "Clock domain number";
      type uint8;
    }
    container profile {
      leaf dot1as {
        when 'not(../../transport/ipv4/udp)';
        type empty;
      }
    }
    leaf neighbor-propagation-delay-threshold {
      description
        "in nanoseconds";
      type uint32 {
        range "1..2147483646";
      }
    }
    leaf priority1 {
      description
        "clock priority1 number";
      type uint8 {
        range "0..255";
      }
    }
    leaf priority2 {
      description
        "clock priority2 number";
      type uint8 {
        range "0..255";
      }
    }
    container mode {
      container boundary {
        leaf delay-req {
          type empty;
        }
        leaf pdelay-req {
          type empty;
        }
      }
      leaf e2etransparent {
        type empty;
      }
      leaf p2ptransparent {
        type empty;
      }
    }
    container transport {
      description
        "Set transport mode";
      when 'not((/ios:native/ios:ptp/ios-ptp:mode/ios-ptp:boundary/ios-ptp:pdelay-req) or (/ios:native/ios:ptp/ios-ptp:mode/ios-ptp:boundary/ios-ptp:delay-req) or (/ios:native/ios:ptp/ios-ptp:mode/ios-ptp:e2etransparent) or (/ios:native/ios:ptp/ios-ptp:profile/ios-ptp:dot1as) or (/ios:native/ios:ptp/ios-ptp:mode/ios-ptp:p2ptransparent))';
      container ipv4 {
        description
          "Transport IPv4";
        leaf udp {
          description
            "Transport IPv4 UDP";
          type empty;
        }
      }
    }
  }

  grouping config-interface-ptp-grouping {
    container ptp {
      description
        "PTP related interface configuration";
      leaf enable {
        description
          "Enable PTP";
        type empty;
      }
      container announce {
        when '(/ios:native/ios:ptp/ios-ptp:mode/ios-ptp:boundary/ios-ptp:delay-req) or (/ios:native/ios:ptp/ios-ptp:mode/ios-ptp:boundary/ios-ptp:pdelay-req)';
        leaf interval {
          description
            "log mean value of announce message transmit interval";
          type uint8 {
            range "0..4";
          }
          default "0";
        }
        leaf timeout {
          description
            "number of announce message transmit before timeout";
          type uint8 {
            range "2..10";
          }
          default "3";
        }
      }
      container sync {
        when '(/ios:native/ios:ptp/ios-ptp:mode/ios-ptp:boundary/ios-ptp:delay-req) or (/ios:native/ios:ptp/ios-ptp:mode/ios-ptp:boundary/ios-ptp:pdelay-req)';
        leaf interval {
          description
            "log mean value of sync message transmit interval";
          type int8 {
            range "-3..1";
          }
          default "0";
        }
      }
      container pdelay-req {
        when '(/ios:native/ios:ptp/ios-ptp:mode/ios-ptp:boundary/ios-ptp:pdelay-req)';
        leaf interval {
          description
            "log mean value of peer delay-req message transmit interval";
          type int8 {
            range "-1..5";
          }
          default "0";
        }
      }
      container delay-req {
        when '(/ios:native/ios:ptp/ios-ptp:mode/ios-ptp:boundary/ios-ptp:delay-req)';
        leaf interval {
          description
            "log mean value of delay request message transmit interval";
          type int8 {
            range "-1..5";
          }
          default "0";
        }
      }
      leaf vlan {
        description
          "PTP vlan id";
        when '(../../ios:switchport-config/ios:switchport/ios-sw:mode/ios-sw:trunk) and ((/ios:native/ios:ptp/ios-ptp:mode/ios-ptp:boundary/ios-ptp:delay-req) or (/ios:native/ios:ptp/ios-ptp:mode/ios-ptp:boundary/ios-ptp:pdelay-req))';
        type uint16 {
          range "1..4094";
        }
      }
    }
  }

  augment "/ios:native/ios:ptp" {
    uses config-ptp-grouping2;
  }

  augment "/ios:native/ios:interface/ios:GigabitEthernet" {
    uses config-interface-ptp-grouping;
  }

  augment "/ios:native/ios:interface/ios:TenGigabitEthernet" {
    uses config-interface-ptp-grouping;
  }

  augment "/ios:native/ios:interface/ios:FiveGigabitEthernet" {
    uses config-interface-ptp-grouping;
  }

  augment "/ios:native/ios:interface/ios:TwentyFiveGigE" {
    uses config-interface-ptp-grouping;
  }

  augment "/ios:native/ios:interface/ios:TwoGigabitEthernet" {
    uses config-interface-ptp-grouping;
  }

  augment "/ios:native/ios:interface/ios:FortyGigabitEthernet" {
    uses config-interface-ptp-grouping;
  }

  augment "/ios:native/ios:interface/ios:HundredGigE" {
    uses config-interface-ptp-grouping;
  }
}
