module Cisco-IOS-XE-lacp-oper {
  yang-version 1.1;
  namespace "http://cisco.com/ns/yang/Cisco-IOS-XE-lacp-oper";
  prefix lacp-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of yang definitions
     for LACP operational data.
     Copyright (c) 2019 by Cisco Systems, Inc.
     All rights reserved.";

  revision 2021-11-01 {
    description
      "Added LACP port channel operational data";
    reference
      "1.1.0";
    cisco-semver:module-version "1.1.0";
  }
  revision 2020-03-01 {
    description
      "Initial revision";
    reference
      "1.0.0";
    cisco-semver:module-version "1.0.0";
  }

  typedef etherchannel-layer {
    type enumeration {
      enum l2-etherchannel {
        value 0;
        description
          "Layer 2 Etherchannel";
      }
      enum l3-etherchannel {
        value 1;
        description
          "Layer 3 Etherchannel";
      }
    }
    description
      "Layer 2 or Layer 3 Etherchannel";
  }

  grouping lag-oper-data {
    description
      "LAG oper data";
    leaf channel-group {
      type uint32;
      description
        "Channel-group or port-channel number";
    }
    leaf total-no-of-links {
      type uint32;
      description
        "Total number of links configured as part of the channel-group";
    }
    leaf total-no-of-links-bundled {
      type uint32;
      description
        "Total number of links bundled";
    }
    leaf total-no-of-links-standby {
      type uint32;
      description
        "Total number of links in standby";
    }
    leaf total-no-of-links-down {
      type uint32;
      description
        "Total number of links down";
    }
    leaf port-channel-up {
      type boolean;
      description
        "Port channel status is UP";
    }
    leaf layer-type {
      type lacp-ios-xe-oper:etherchannel-layer;
      description
        "Layer 2 or Layer 3 Etherchannel";
    }
    leaf total-no-of-links-suspended {
      type uint32;
      description
        "Total number of suspended links";
    }
  }

  grouping lacp-member-stats {
    description
      "LACP packet statistics for the member interfaces";
    leaf lacp-in-pkts {
      type uint64;
      description
        "Number of packets received";
    }
    leaf lacp-out-pkts {
      type uint64;
      description
        "Number of packets transmitted";
    }
    leaf lacp-rx-errors {
      type uint64;
      description
        "Number of receive packet errors";
    }
    leaf lacp-tx-errors {
      type uint64;
      description
        "Number of transmit packet errors";
    }
    leaf lacp-errors {
      type uint64;
      description
        "Number of illegal packet errors";
    }
    leaf lacp-unknown-errors {
      type uint64;
      description
        "Number of unknown packet errors";
    }
  }

  grouping lacp-member-state {
    description
      "Operational state data for aggregate members";
    leaf if-name {
      type string;
      description
        "List of aggregate interfaces managed by LACP";
    }
    leaf system-id {
      type yang:mac-address;
      description
        "The MAC address portion of the node's System ID";
    }
    leaf partner-id {
      type yang:mac-address;
      description
        "The MAC address representing the protocol partner's interface system ID";
    }
    leaf partner-key {
      type uint16;
      description
        "Operational value of the protocol partner's key";
    }
    leaf oper-key {
      type uint16;
      description
        "Current operational value of the key for the aggregate interface";
    }
    leaf port-num {
      type uint16;
      description
        "Port number of the local (actor) aggregation member";
    }
    container counters {
      description
        "LACP member interface statistics";
      uses lacp-ios-xe-oper:lacp-member-stats;
    }
  }

  grouping lacp-port-channel {
    description
      "Ethernet Channel of interfaces oper model data";
    leaf channel-group {
      type uint32;
      description
        "Port-channel interface number";
    }
    list lacp-member-state {
      key "if-name";
      description
        "LACP Operational state data for aggregate members";
      uses lacp-ios-xe-oper:lacp-member-state;
    }
  }

  container lag-oper-data {
    config false;
    description
      "LACP operational data";
    list lag-info {
      key "channel-group";
      description
        "LAG operational information details";
      uses lacp-ios-xe-oper:lag-oper-data;
    }
    list lacp-port-channel {
      key "channel-group";
      description
        "LACP channel group details";
      uses lacp-ios-xe-oper:lacp-port-channel;
    }
  }
}
