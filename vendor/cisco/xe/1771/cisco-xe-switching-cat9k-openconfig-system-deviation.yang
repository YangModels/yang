module cisco-xe-switching-cat9k-openconfig-system-deviation {
  namespace "http://openconfig.net/yang/cisco-xe-switching-cat9k-openconfig-system-deviation";
  prefix cisco-xe-switching-cat9k-oc-system-devs;

  import openconfig-system {
    prefix oc-sys;
  }
  import openconfig-inet-types {
    prefix oc-inet;
  }

  organization
    "Cisco Systems, Inc.";
  contact
    " Cisco Systems, Inc.
     Customer Service

     Postal: 170 W Tasman Drive
     San Jose, CA 95134

     Tel: +1 1800 553-NETS

     E-mail: cs-yang@cisco.com";
  description
    "This module defines deviation statements for openconfig-system module.";

  revision 2018-07-01 {
    description
      "Add deviations to the Auth and Acc radius default port and NTP iburst values";
  }
  revision 2018-06-08 {
    description
      "aaa/authentication/users/user/config/ssh-key and
       aaa/authentication/users/user/state/ssh-key not supported in 16.9.1";
  }
  revision 2018-03-23 {
    description
      "logging/remote-servers/selectors are not supported in 16.9.1";
  }
  revision 2018-03-17 {
    description
      "Add deviation to restrict logging remote-server host type to ip addresses";
  }
  revision 2018-03-16 {
    description
      "Add deviation to remove telnet-server/session-limit which is not supported in IOS-XE";
  }
  revision 2018-03-15 {
    description
      "Add deviation to require that the severity level for all selectors on a host must be the same
       this is currently the limitation of IOS feature code that only allows one discriminator
       to be applied to a logging host";
  }
  revision 2018-03-11 {
    description
      "Remove source interface augmentations for ntp, radius and tackacs";
  }
  revision 2018-03-07 {
    description
      "Deviate out ntp/source-address leaf";
  }
  revision 2018-03-06 {
    description
      "Enable logging/remote-servers in 16.9.1";
  }
  revision 2018-02-08 {
    description
      "Remove additional nodes supported in 16.9.1";
  }
  revision 2018-02-02 {
    description
      "Remove deviations for nodes supported in 16.9.1";
  }
  revision 2018-01-10 {
    description
      "The aaa server source ip address can't be configured in IOS-XE";
  }
  revision 2018-01-07 {
    description
      "The ntp server port number can't be configured in IOS-XE";
  }
  revision 2017-11-28 {
    description
      "Add deviations to remove authorization-method from aaa:authorization config section";
  }
  revision 2017-11-08 {
    description
      "Remvoed deviations to remove openconfig-system-logging features";
  }
  revision 2017-10-11 {
    description
      "Add deviations to remove openconfig-system features not implemented in 16.8.1";
    reference
      "RFC 6020: YANG - A Data Modeling Language for the
       Network Configuration Protocol (NETCONF)";
  }

  deviation "/oc-sys:system/oc-sys:aaa/oc-sys:authentication/oc-sys:users/oc-sys:user/oc-sys:config/oc-sys:ssh-key" {
    deviate not-supported;
    description
      "user ssh-key is not supported in 16.9.1";
  }

  deviation "/oc-sys:system/oc-sys:aaa/oc-sys:authentication/oc-sys:users/oc-sys:user/oc-sys:state/oc-sys:ssh-key" {
    deviate not-supported;
    description
      "user ssh-key is not supported in 16.9.1";
  }

  deviation "/oc-sys:system/oc-sys:logging/oc-sys:remote-servers/oc-sys:remote-server/oc-sys:config/oc-sys:host" {
    deviate replace {
      type oc-inet:ip-address;
    }
    description
      "For IOS-XE logging remote-server hostnames must be ip addresses";
  }

  deviation "/oc-sys:system/oc-sys:logging/oc-sys:remote-servers/oc-sys:remote-server/oc-sys:selectors" {
    deviate not-supported;
    description
      "oc-system logging selectors not supported in 16.9.1";
  }

  deviation "/oc-sys:system/oc-sys:dns/oc-sys:host-entries/oc-sys:host-entry/oc-sys:config/oc-sys:alias" {
    deviate not-supported;
    description
      "oc-system dns alias not supported in IOS-XE";
  }

  deviation "/oc-sys:system/oc-sys:dns/oc-sys:host-entries/oc-sys:host-entry/oc-sys:state/oc-sys:alias" {
    deviate not-supported;
    description
      "oc-system dns alias not supported in IOS-XE";
  }

  deviation "/oc-sys:system/oc-sys:aaa/oc-sys:server-groups/oc-sys:server-group/oc-sys:servers/oc-sys:server/oc-sys:config/oc-sys:name" {
    deviate not-supported;
    description
      "oc-system aaa server name can't be directly configured in IOS-XE";
  }

  deviation "/oc-sys:system/oc-sys:aaa/oc-sys:server-groups/oc-sys:server-group/oc-sys:servers/oc-sys:server/oc-sys:radius/oc-sys:config/oc-sys:auth-port" {
    deviate replace {
      default "1646";
    }
    description
      "AAA Auth port default value is different in IOS XE";
  }

  deviation "/oc-sys:system/oc-sys:aaa/oc-sys:server-groups/oc-sys:server-group/oc-sys:servers/oc-sys:server/oc-sys:radius/oc-sys:config/oc-sys:acct-port" {
    deviate replace {
      default "1645";
    }
    description
      "AAA Acct port default value is different in IOS XE";
  }

  deviation "/oc-sys:system/oc-sys:aaa/oc-sys:server-groups/oc-sys:server-group/oc-sys:servers/oc-sys:server/oc-sys:state/oc-sys:name" {
    deviate not-supported;
    description
      "oc-system aaa server name can't be directly configured in IOS-XE";
  }

  deviation "/oc-sys:system/oc-sys:ntp/oc-sys:servers/oc-sys:server/oc-sys:config/oc-sys:port" {
    deviate not-supported;
    description
      "oc-system ntp/.../port configuration not supported in IOS-XE, is always port 123.";
  }

  deviation "/oc-sys:system/oc-sys:ntp/oc-sys:servers/oc-sys:server/oc-sys:config/oc-sys:iburst" {
    deviate replace {
      default "true";
    }
    description
      "The default value for oc-system ntp/.../iburst is true in IOS-XE.";
  }

  deviation "/oc-sys:system/oc-sys:ssh-server/oc-sys:config/oc-sys:rate-limit" {
    deviate not-supported;
    description
      "ssh-server rate limiting not supported on Cisco devices";
  }

  deviation "/oc-sys:system/oc-sys:ssh-server/oc-sys:state/oc-sys:rate-limit" {
    deviate not-supported;
    description
      "ssh-server rate limiting not supported on Cisco devices";
  }

  deviation "/oc-sys:system/oc-sys:telnet-server/oc-sys:config/oc-sys:session-limit" {
    deviate not-supported;
    description
      "telnet-server session limiting not supported on Cisco devices";
  }

  deviation "/oc-sys:system/oc-sys:telnet-server/oc-sys:state/oc-sys:session-limit" {
    deviate not-supported;
    description
      "telnet-server session limiting not supported on Cisco devices";
  }

  deviation "/oc-sys:system/oc-sys:telnet-server/oc-sys:config/oc-sys:rate-limit" {
    deviate not-supported;
    description
      "telnet-server rate limiting not supported on Cisco devices";
  }

  deviation "/oc-sys:system/oc-sys:telnet-server/oc-sys:state/oc-sys:rate-limit" {
    deviate not-supported;
    description
      "telnet-server rate limiting not supported on Cisco devices";
  }

  deviation "/oc-sys:system/oc-sys:processes/oc-sys:process/oc-sys:state/oc-sys:args" {
    deviate not-supported;
    description
      "oc-system processes state args not supported in 16.8.1.";
  }

  deviation "/oc-sys:system/oc-sys:processes/oc-sys:process/oc-sys:state/oc-sys:start-time" {
    deviate not-supported;
    description
      "oc-system processes state start-time not supported in 16.8.1.";
  }

  deviation "/oc-sys:system/oc-sys:processes/oc-sys:process/oc-sys:state/oc-sys:uptime" {
    deviate not-supported;
    description
      "oc-system processes state uptime not supported in 16.8.1.";
  }

  deviation "/oc-sys:system/oc-sys:processes/oc-sys:process/oc-sys:state/oc-sys:cpu-usage-system" {
    deviate not-supported;
    description
      "oc-system processes state cpu-usage-system not supported in 16.8.1.";
  }

  deviation "/oc-sys:system/oc-sys:ntp/oc-sys:state/oc-sys:auth-mismatch" {
    deviate not-supported;
    description
      "oc-system ntp auth-mismatch state not supported in 16.9.1.";
  }

  deviation "/oc-sys:system/oc-sys:logging/oc-sys:console" {
    deviate not-supported;
    description
      "oc-system logging console is not supported in 16.9.1.";
  }

  deviation "/oc-sys:system/oc-sys:alarms" {
    deviate not-supported;
    description
      "oc-system alarms are not supported in 16.9.1.";
  }

  deviation "/oc-sys:system/oc-sys:cpus" {
    deviate not-supported;
    description
      "oc-system cpu is not supported in 16.9.1.";
  }
}
