module Cisco-IOS-XE-cts-switching-deviation {
  namespace "http://cisco.com/ns/yang/Cisco-IOS-XE-cts-switching-deviation";
  prefix ios-cts-d;

  import Cisco-IOS-XE-native {
    prefix ios;
  }
  import Cisco-IOS-XE-cts {
    prefix ios-cts;
  }
  import cisco-semver {
    prefix cisco-semver;
  }

  organization
    "Cisco Systems";
  description
    "Cisco XE Native Deviation YANG module for IOS
     Copyright (c) 2021 by Cisco Systems, Inc.
     All rights reserved.";

  revision 2021-07-01 {
    description
      "Added enforcement deviation for LISP interface";
    cisco-semver:module-version "1.0.0";
  }

  deviation "/ios:native/ios:interface/ios:LISP/ios-cts:cts/ios-cts:role-based/ios-cts:enforcement-switching" {
    deviate delete {
      default "true";
    }
    description
      "cts role-based enforcement configuration by default is not supported";
  }
}
