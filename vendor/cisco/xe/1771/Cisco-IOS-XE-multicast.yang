module Cisco-IOS-XE-multicast {
  namespace "http://cisco.com/ns/yang/Cisco-IOS-XE-multicast";
  prefix ios-mc;

  import cisco-semver {
    prefix cisco-semver;
  }
  import ietf-inet-types {
    prefix inet;
  }
  import Cisco-IOS-XE-types {
    prefix ios-types;
  }
  import Cisco-IOS-XE-native {
    prefix ios;
  }
  import Cisco-IOS-XE-interface-common {
    prefix ios-ifc;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Multicast Yang model.
     Copyright (c) 2016-2021 by Cisco Systems, Inc.
     All rights reserved.";

  revision 2021-11-01 {
    description
      "- Introduced transit-core-group-range
       - Changed the range for core-group-range
       - Added must constraint for core-group-range";
    cisco-semver:module-version "5.0.0";
  }
  revision 2021-07-01 {
    description
      "- Change the ipv6 mroute limit range";
    cisco-semver:module-version "4.0.0";
  }
  revision 2021-03-01 {
    description
      "- Introduced route-limit";
    cisco-semver:module-version "3.0.0";
  }
  revision 2020-07-01 {
    description
      "- Deprecated pim-mode-choice and its leaves
       - Introduced pim-mode-choice-cfg";
    cisco-semver:module-version "2.2.0";
  }
  revision 2020-03-01 {
    description
      "- Added rp-address-conf and rp-address-list and deprecated rp-address";
    cisco-semver:module-version "2.1.0";
  }
  revision 2019-11-01 {
    description
      "- Added new config for multicast";
    cisco-semver:module-version "2.0.0";
  }
  revision 2019-07-01 {
    description
      "- Establish semantic version baseline
       - Added default values for few multicast nodes
       - Added multicast and pim augmentation for few missing interfaces
       - Added scope list for ipv6 pim bsr
       - Added lisp command augmentation for LISP subinterface
       - Added IP multicast commands in global and interface level
       - Addressed IPv4 modelling gaps for MLDP, PIM and MSDP";
    cisco-semver:module-version "1.0.0";
  }
  revision 2019-01-29 {
    description
      "Added fix for delete of last leaf in 'ip pim' and 'ipv6 pim' vrf list";
  }
  revision 2019-01-22 {
    description
      "Added leaf for App-hosting Gigabit Ethernet interface";
  }
  revision 2018-11-29 {
    description
      "Added ip pim lisp commands under LISP interface and sub-interfaces";
  }
  revision 2018-11-07 {
    description
      "Cleanup spelling errors in description statements";
  }
  revision 2018-08-23 {
    description
      "Added Augment of config-interface-ip-pim-grouping to
              Multilink and Cellular interface";
  }
  revision 2018-08-20 {
    description
      "Reused register-source container for ip-pim-grouping";
  }
  revision 2018-07-16 {
    description
      "Added config-interface-ip-pim-grouping to interface Vif";
  }
  revision 2018-07-02 {
    description
      "Added change ipv6 pim register-source and
            ipv6 pim lisp transport unicast";
  }
  revision 2018-06-28 {
    description
      "Added must constraints for deleting vrf";
  }
  revision 2018-06-08 {
    description
      "Added change for peer to list and used interface-grouping in connect-source";
  }
  revision 2018-05-11 {
    description
      "Added change for pim under LISP interface and sub-interfaces";
  }
  revision 2017-11-27 {
    description
      "Added Change 25GE name";
  }
  revision 2017-11-14 {
    description
      "This revision has changes for new 100GE interface addition";
  }
  revision 2017-09-15 {
    description
      "This revision has changes for new 2gig interface addition";
  }
  revision 2017-08-28 {
    description
      "Extend modeling for multicast";
  }
  revision 2017-08-16 {
    description
      "This revision has changes for new 5gig and 25gig interfaces addition";
  }
  revision 2017-05-16 {
    description
      "Models under ip pim are missing for FortyGig interface";
  }
  revision 2017-04-24 {
    description
      "certain format of ip pim rpc is not able to push to the device";
  }
  revision 2017-02-07 {
    description
      "Initial revision";
  }

  grouping ip-multicast-multipath-group {
    container multipath {
      description
        "RPF across equal-cost paths";
      presence "true";
      leaf s-g-hash {
        description
          "Per-(source, group) load sharing algorithm selection";
        type enumeration {
          enum basic;
          enum next-hop-based;
        }
      }
    }
  }

  grouping ip-mcast-topology-grouping {
    list word {
      key "topology-name";
      leaf topology-name {
        description
          "Routing topology instance name";
        type string;
      }
      leaf access-list-id {
        description
          "Extended IP access-list
            reference for multicast address";
        mandatory true;
        type uint8 {
          range "100..199";
        }
      }
    }
  }

  grouping config-ip-mcast-rpf {
    leaf default-distance {
      description
        "Distance for the default RPF interface";
      type uint8 {
        range "0..255";
      }
    }
    container mofrr {
      description
        "Enable multicast only fast re-route";
      leaf list {
        type ios-types:ext-acl-type;
      }
      leaf sticky {
        type empty;
      }
    }
    container proxy {
      description
        "PIM proxy options";
      leaf disable {
        description
          "Don't accept PIM proxy/attribute RPF info";
        type empty;
      }
      leaf vector {
        description
          "Insert BGP next-hop as vector in PIM Joins";
        type empty;
      }
    }
    container select {
      description
        "Select table for RPF check";
      container global {
        description
          "Global routing table for RPF lookup";
        leaf-list group-list {
          description
            "Group access-list";
          type ios-types:mcast-std-acl-type;
        }
      }
      container topology {
        description
          "Select topology";
        container multicast {
          description
            "Select multicast topology";
          uses ip-mcast-topology-grouping;
        }
        container unicast {
          description
            "Select unicast topology";
          uses ip-mcast-topology-grouping;
        }
      }
      list vrf-list {
        description
          "Select VPN Routing/Forwarding instance";
        key "group-list";
        leaf name {
          description
            "VPN Routing/Forwarding instance name";
          type string;
        }
        leaf group-list {
          description
            "Group access-list";
          type ios-types:mcast-std-acl-type;
        }
      }
      list vrf {
        status obsolete;
        description
          "Select VPN Routing/Forwarding instance";
        key "name";
        leaf name {
          status obsolete;
          description
            "VPN Routing/Forwarding instance name";
          type string;
        }
        list group-list {
          status obsolete;
          description
            "Group access-list";
          key "group-list-name";
          leaf group-list-name {
            status obsolete;
            type union {
              type uint16 {
                range "1..99";
              }
              type string;
            }
          }
        }
      }
    }
  }

  grouping config-ip-mcast-rpf-multitopology {
    leaf multitopology {
      description
        "Enable Multicast-Specific RPF Topology";
      type empty;
    }
  }

  grouping config-ip-mcast-rpf-grouping {
    container rpf {
      description
        "RPF check configuration";
      uses config-ip-mcast-rpf;
      uses config-ip-mcast-rpf-multitopology;
    }
  }

  grouping config-ip-mcast-vrf-rpf-grouping {
    container rpf {
      description
        "Per-VRF RPF check configuration";
      uses config-ip-mcast-rpf;
    }
  }

  grouping config-ip-mcast-grouping-subset {
    leaf auto-enable {
      description
        "Support for AAA enabling of ipmulticast";
      type empty;
    }
    leaf default-rpf-distance {
      description
        "Distance for the default RPF interface";
      type uint8 {
        range "0..255";
      }
    }
    leaf group-range {
      description
        "Enable/disable multicast for selected group ranges";
      type ios-types:mcast-std-acl-type;
    }
    list heartbeat {
      description
        "Monitor multicast heartbeat";
      key "group-address";
      leaf group-address {
        description
          "Group address of the heartbeat";
        type inet:ipv4-address;
      }
      leaf min-interval {
        mandatory true;
        description
          "Minimal number of intervals where the
             heartbeats must be seen";
        type uint8 {
          range "1..100";
        }
      }
      leaf num-interval {
        mandatory true;
        description
          "Number of intervals to monitor for
             heartbeats";
        type uint8 {
          range "1..100";
        }
      }
      leaf length {
        mandatory true;
        description
          "Length of intervals in seconds";
        type uint16 {
          range "10..3600";
        }
      }
    }
    container limit {
      description
        "Configure global multicast mroute limit";
      list cost {
        description
          "Configure cost for multicast interface mroute limit";
        key "access-list";
        leaf access-list {
          description
            "Standard or Extended IP access list number";
          type union {
            type uint8 {
              range "1..199";
            }
            type string;
          }
        }
        leaf cost {
          mandatory true;
          description
            "Cost associated with Access list";
          type uint32 {
            range "0..2147483647";
          }
        }
      }
    }
    leaf longest-match {
      description
        "Do longest match RPF lookups across tables";
      type empty;
    }
    container mpls {
      description
        "IP multicast mpls commands";
      leaf mldp {
        description
          "MLDP commands";
        type empty;
      }
      container traffic-eng {
        description
          "Traffic engineering commands";
        presence "true";
        leaf range {
          description
            "Configure multicast RPF range";
          type union {
            type uint8 {
              range "100..199";
            }
            type string;
          }
        }
      }
    }
    leaf mrinfo-filter {
      description
        "Multicast router info source filter";
      type ios-types:mcast-std-acl-type;
    }
    container topology {
      description
        "topology selection";
      list multicast {
        description
          "Select multicast topology";
        key "word";
        leaf word {
          description
            "Routing topology instance name";
          type string;
        }
        leaf tid {
          description
            "Configuring the multicast topology tid";
          mandatory true;
          type uint16 {
            range "1..4095";
          }
        }
      }
      list unicast {
        description
          "Select unicast topology";
        key "word";
        leaf word {
          description
            "Routing topology instance name";
          type string;
        }
        leaf tid {
          description
            "Configuring the unicast topology tid";
          mandatory true;
          type uint16 {
            range "1..4095";
          }
        }
      }
    }
    uses ip-multicast-multipath-group;
  }

  grouping config-ip-mcast-grouping {
    uses config-ip-mcast-grouping-subset;
    uses config-ip-mcast-rpf-grouping;
    container route-limit-container {
      leaf routelimit {
        description
          "Maximum number of multicast routes";
        type uint32 {
          range "1..2147483647";
        }
        default "2147483647";
      }
      leaf warning-threshold {
        description
          "Threshold at which to generate warning message";
        type uint32 {
          range "1..2147483647";
        }
      }
    }
    leaf route-limit {
      status deprecated;
      description
        "Maximum number of multicast routes";
      type uint32 {
        range "1..2147483647";
      }
    }
    container redundancy {
      container nsf {
        leaf holdtime {
          type uint16 {
            range "0..1800";
          }
        }
      }
      container routeflush {
        leaf maxtime {
          type uint16 {
            range "0..3600";
          }
          default "30";
        }
      }
    }
    list vrf {
      description
        "Select VPN Routing/Forwarding instance";
      key "name";
      leaf name {
        type string;
      }
      container route-limit {
        leaf no-routes {
          description
            "Number of routes";
          type uint32 {
            range "1..2147483647";
          }
          default "2147483647";
        }
        leaf warning-threshold {
          description
            "Threshold at which to generate warning message";
          type uint32 {
            range "1..2147483647";
          }
        }
      }
      uses config-ip-mcast-grouping-subset;
      uses config-ip-mcast-vrf-rpf-grouping;
    }
  }

  grouping config-interface-limit-grouping {
    list access-list {
      key "access-list";
      leaf access-list {
        description
          "Standard or Extended IP access list number";
        type union {
          type uint8 {
            range "1..199";
          }
          type string;
        }
      }
      leaf max-state {
        description
          "Max Allowed State on this interface";
        mandatory true;
        type uint32 {
          range "0..2147483647";
        }
      }
    }
  }

  grouping config-interface-ip-mcast-grouping {
    container multicast {
      container boundary {
        description
          "Boundary for administrative multicast addresses";
        container block {
          description
            "Block source";
          leaf source {
            description
              "Block source";
            type empty;
          }
        }
        container filter-type-autorp {
          leaf access-list {
            description
              "Specify an access-list";
            type union {
              type ios-types:exp-acl-type;
              type ios-types:ext-acl-type;
            }
          }
          leaf filter-autorp {
            description
              "Filter AutoRP packet contents";
            type empty;
          }
        }
        list filter-type-in-out {
          description
            "Specify filter type in or out";
          key "filter-type";
          max-elements 2;
          leaf filter-type {
            description
              "Filter type";
            type enumeration {
              enum in;
              enum out;
            }
          }
          leaf access-list {
            description
              "Specify an access-list";
            type union {
              type ios-types:exp-acl-type;
              type ios-types:ext-acl-type;
            }
          }
        }
      }
      container limit {
        description
          "Limit multicast mroute state";
        uses config-interface-limit-grouping;
        container connected {
          description
            "Limit connected incoming state";
          uses config-interface-limit-grouping;
        }
        container out {
          description
            "Limit outgoing state";
          uses config-interface-limit-grouping;
        }
        container rpf {
          description
            "Limit incoming state";
          uses config-interface-limit-grouping;
        }
      }
    }
  }

  grouping config-ipv6-mcast-config-grouping {
    container route-limit {
      leaf routelimit {
        description
          "Maximum number of multicast routes";
        type uint32 {
          range "100..2147483647";
        }
      }
      leaf threshold {
        description
          "Mroute threshold at which to generate warning message";
        type uint32 {
          range "100..2147483647";
        }
      }
    }
  }

  grouping config-ipv6-mcast-grouping {
    uses config-ipv6-mcast-config-grouping;
    list vrf-name {
      description
        "Select VPN Routing/Forwarding instance";
      key "name";
      leaf name {
        must '(/ios:native/ios:vrf/ios:definition[ios:name=current()] and /ios:native/ios:vrf/ios:definition[ios:name=current()]/ios:address-family/ios:ipv6)' {
          error-message "Ipv6 VRF must be created 1st, deleted last";
        }
        type string;
      }
      uses config-ipv6-mcast-config-grouping;
    }
    leaf vrf {
      description
        "Select VPN Routing/Forwarding instance";
      type string;
      status obsolete;
    }
    container rpf {
      description
        "Configure multicast RPF related commands";
      container backoff {
        description
          "Back off delay after unicast routing change";
        leaf initial-delay {
          default "500";
          type uint16 {
            range "200..65535";
          }
        }
        leaf max-delay {
          default "5000";
          type uint16 {
            range "200..65535";
          }
        }
      }
      leaf use-bgp {
        default "true";
        status obsolete;
        description
          "Obsolete: Use BGP routes for multicast RPF lookup";
        type boolean;
      }
    }
  }

  grouping ip-pim-grouping {
    container accept-register {
      description
        "Registers accept filter";
      leaf list {
        description
          "Access list";
        type ios-types:ext-acl-type;
      }
    }
    container accept-rp {
      description
        "RP accept filter";
      list rp_list {
        key "ip_addr";
        leaf ip_addr {
          description
            "IP address of RP for group";
          type inet:ipv4-address;
        }
        leaf acl {
          description
            "Access-list reference for group (expanded range)";
          type ios-types:std-acl-type;
        }
      }
      container auto-rp {
        description
          "only RP-mapping from Auto-RP";
        presence "true";
        leaf acl {
          description
            "Access-list reference for group (expanded range)";
          type ios-types:std-acl-type;
        }
      }
    }
    container allow-rp {
      description
        "Sparse-Mode RP addresses to be allowed";
      presence "true";
      leaf rp-list {
        description
          "Access-list for allowed RP addresses";
        type ios-types:mcast-std-acl-type;
      }
      leaf group-list {
        description
          "Access-list for allowed group ranges";
        type ios-types:mcast-std-acl-type;
      }
    }
    container autorp-container {
      leaf autorp {
        description
          "Configure AutoRP global operations";
        default "true";
        type boolean;
      }
      leaf listener {
        description
          "Allow AutoRP packets across sparse mode interface";
        type empty;
      }
    }
    container autorp {
      status obsolete;
      description
        "Configure AutoRP global operations";
      presence "true";
      leaf listener {
        status obsolete;
        description
          "Allow AutoRP packets across sparse mode interface";
        type empty;
      }
    }
    leaf bidir-backoff-interval {
      description
        "DF election backoff delay";
      type uint16 {
        range "1..3600";
      }
    }
    container bidir-offer-interval {
      description
        "DF election offer message interval";
      choice seconds-milliseconds {
        default "milliseconds";
        case seconds-interval {
          leaf interval {
            type uint16 {
              range "1..20000";
            }
          }
        }
        case milliseconds {
          leaf milliseconds-interval {
            default "100";
            type uint16 {
              range "100..20000";
            }
          }
          leaf msec {
            description
              "Interval in milliseconds";
            default "true";
            type boolean;
          }
        }
      }
    }
    leaf bidir-offer-limit {
      description
        "Number of unanswered offers before becoming DF";
      default "3";
      type uint16 {
        range "3..100";
      }
    }
    leaf bidir-winner-interval {
      description
        "DF periodic winner message interval";
      type uint16 {
        range "1..3600";
      }
    }
    container bsr-candidate {
      description
        "Candidate bootstrap router (candidate BSR)";
      uses ios-ifc:interface-grouping;
      leaf mask {
        description
          "Hash Mask length for RP selection";
        type uint8 {
          range "0..32";
        }
      }
      leaf priority {
        description
          "Priority value for candidate bootstrap router";
        when '../mask';
        type uint8 {
          range "0..255";
        }
      }
      leaf accept-rp-candidate {
        description
          "BSR RP candidate filter";
        when '../priority';
        type ios-types:exp-acl-type;
      }
    }
    leaf dm-fallback {
      description
        "Fallback group mode is Dense";
      default "true";
      type boolean;
    }
    leaf fast-register-stop {
      description
        "Immediately send register-stops on registers";
      type empty;
    }
    leaf log-neighbor-changes {
      description
        "Log PIM neighbor up/down and DR changes";
      default "true";
      type boolean;
    }
    container maximum {
      description
        "Maximum state limits";
      container group-mappings {
        description
          "PIM group mapping ranges";
        leaf autorp {
          description
            "Group mappings learnt from Auto-RP";
          type uint16 {
            range "1..10000";
          }
        }
        leaf bsr {
          description
            "Group mappings learnt from BSR";
          type uint16 {
            range "1..10000";
          }
        }
      }
    }
    container mpls {
      description
        "pim mpls commands";
      container source {
        description
          "Configure source interface for multicast RPF";
        uses ios-ifc:interface-grouping;
      }
    }
    leaf old-register-checksum {
      description
        "Generate Register checksum on whole packet";
      type empty;
    }
    leaf register-rate-limit {
      description
        "Rate limit for PIM data registers";
      type uint32 {
        range "8000..2000000000";
      }
    }
    container register-source {
      description
        "Configure register source";
      uses ios-ifc:interface-grouping;
    }
    container rp-address-conf {
      description
        "PIM RP-address (Rendezvous Point)";
      leaf address {
        description
          "IP address of Rendezvous-point for group";
        type inet:ipv4-address;
      }
      leaf override {
        description
          "Overrides dynamically learnt RP mappings";
        type empty;
      }
      leaf bidir {
        description
          "Group range treated in bidirectional shared-tree mode";
        type empty;
      }
    }
    list rp-address-list {
      description
        "PIM RP-address (Rendezvous Point)";
      key "access-list";
      leaf rp-address {
        description
          "IP address of Rendezvous-point for group";
        type inet:ipv4-address;
      }
      leaf access-list {
        description
          "IP Access-list";
        type ios-types:std-acl-type;
      }
      leaf override {
        description
          "Overrides dynamically learnt RP mappings";
        type empty;
      }
      leaf bidir {
        description
          "Group range treated in bidirectional shared-tree mode";
        type empty;
      }
    }
    list rp-address {
      status deprecated;
      description
        "PIM RP-address (Rendezvous Point)";
      key "address";
      leaf address {
        status deprecated;
        description
          "IP address of Rendezvous-point for group";
        type inet:ipv4-address;
      }
      leaf access-list {
        status deprecated;
        description
          "IP Access-list";
        type ios-types:std-acl-type;
      }
      leaf override {
        status deprecated;
        description
          "Overrides dynamically learnt RP mappings";
        type empty;
      }
      leaf bidir {
        status deprecated;
        description
          "Group range treated in bidirectional shared-tree mode";
        type empty;
      }
    }
    container rp-announce-filter {
      description
        "Auto-RP announce message filter";
      list group-list {
        description
          "Group address access-list";
        key "acl";
        leaf acl {
          description
            "IP Access list";
          type ios-types:mcast-std-acl-type;
        }
      }
      container rp-list {
        description
          "RP address access-list";
        list rp {
          description
            "RP address access-list";
          key "acl";
          leaf acl {
            description
              "Access-list reference for RP";
            type ios-types:mcast-std-acl-type;
          }
          list group-list {
            description
              "Group address access-list";
            key "acl";
            leaf acl {
              description
                "IP Access list";
              type ios-types:mcast-std-acl-type;
            }
          }
        }
      }
    }
    list rp-candidate {
      description
        "To be a PIM version 2 RP candidate";
      key "interface";
      leaf interface {
        description
          "Autonomic-Networking virtual interface";
        type string;
      }
      leaf group-list {
        description
          "IP Access list";
        type ios-types:mcast-std-acl-type;
      }
      leaf interval {
        description
          "RP candidate advertisement interval";
        type uint16 {
          range "1..16383";
        }
      }
      leaf priority {
        description
          "RP candidate priority";
        type uint8 {
          range "0..255";
        }
      }
      leaf bidir {
        description
          "Group range treated in bidirectional shared-tree mode";
        type empty;
      }
    }
    leaf rp-proxy-join {
      description
        "RP always proxy joins for sources";
      type empty;
    }
    list spt-threshold-list {
      description
        "Source-tree switching threshold";
      key "group-list";
      leaf how {
        mandatory true;
        type enumeration {
          enum 0;
          enum infinity;
        }
      }
      leaf group-list {
        description
          "Group address access-list";
        type ios-types:std-acl-type;
      }
    }
    list spt-threshold {
      status obsolete;
      description
        "Source-tree switching threshold";
      key "how group-list";
      leaf how {
        status obsolete;
        type enumeration {
          enum 0;
          enum infinity;
        }
      }
      leaf group-list {
        status obsolete;
        description
          "Group address access-list";
        type ios-types:std-acl-type;
      }
    }
    container spt-threshold-container {
      container spt-threshold {
        description
          "Source-tree switching threshold";
        leaf how {
          type enumeration {
            enum 0;
            enum infinity;
          }
        }
      }
    }
    container send-rp-announce {
      description
        "Auto-RP send RP announcement";
      list send-rp-announce-list {
        description
          "Auto-RP send RP announcement";
        key "if-name";
        leaf if-name {
          description
            "IP address or interface name";
          type union {
            type inet:ipv4-address;
            type string;
          }
        }
        leaf scope {
          description
            "RP announcement scope";
          mandatory true;
          type uint8 {
            range "1..255";
          }
        }
        leaf group-list {
          description
            "Group access-list";
          type ios-types:mcast-std-acl-type;
        }
        leaf interval {
          description
            "RP announcement interval";
          type uint16 {
            range "1..16383";
          }
        }
        leaf bidir {
          description
            "Group range treated in bidirectional shared-tree mode";
          type empty;
        }
      }
      list interface_list {
        status deprecated;
        key "if-name";
        leaf if-name {
          status deprecated;
          type string;
        }
        container scope {
          status deprecated;
          description
            "RP announcement scope";
          leaf pkt-ttl {
            status deprecated;
            description
              "TTL of the RP announce packet";
            type uint8 {
              range "1..255";
            }
          }
          container group-list {
            status deprecated;
            description
              "Group access-list";
            leaf acl-ref {
              status deprecated;
              description
                "Access-list reference for multicast groups";
              type uint8 {
                range "1..99";
              }
            }
            leaf std-acl {
              status deprecated;
              description
                "IP Named Standard Access list";
              type string;
            }
          }
        }
      }
      list Port-channel {
        status obsolete;
        description
          "Ethernet Channel of interfaces";
        key "name";
        leaf name {
          status obsolete;
          type uint32 {
            range "1..512";
          }
        }
        leaf scope {
          status obsolete;
          description
            "RP announcement scope";
          type uint8 {
            range "1..255";
          }
        }
      }
    }
    container sparse {
      description
        "This command is specific to PIM-Sparse Mode";
      container accept-source-reports {
        description
          "Accept and process source specific host reports";
        presence "true";
        leaf range {
          description
            "ACL for group range";
          type ios-types:mcast-std-acl-type;
        }
      }
      container sg-expiry-timer {
        description
          "Specify the expiry timer for the entry";
        leaf timer {
          description
            "Timer Value in seconds";
          type uint16 {
            range "181..57600";
          }
        }
        leaf sg-list {
          description
            "Access list number (expanded range)";
          type ios-types:ext-acl-type;
        }
      }
    }
    container send-rp-discovery {
      description
        "Auto-RP send RP discovery message (as RP-mapping agent)";
      container interface {
        uses ios-ifc:interface-grouping;
      }
      leaf scope {
        description
          "Scope of the RP discovery packets: TTL";
        type uint8 {
          range "1..255";
        }
      }
      leaf interval {
        description
          "number of seconds";
        type uint16 {
          range "1..16383";
        }
      }
    }
    container ssm {
      description
        "Configure Source Specific Multicast";
      leaf range {
        description
          "ACL for group range to be used for SSM";
        type ios-types:mcast-std-acl-type;
      }
      leaf default {
        description
          "Use 232/8 group range for SSM";
        type empty;
      }
    }
    container state-refresh {
      description
        "PIM DM State-Refresh configuration";
      leaf disable {
        description
          "Disable PIM State-Refresh processing";
        type empty;
      }
    }
    container cache {
      description
        "PIM cache configuration";
      leaf rpf-oif {
        description
          "Cache outgoing interface RPF info";
        type empty;
      }
    }
  }

  grouping config-ip-pim-grouping {
    uses ip-pim-grouping;
    leaf bidir-enable {
      description
        "Enable Bidir-PIM";
      type empty;
    }
    list vrf {
      description
        "Select VPN Routing/Forwarding instance";
      key "id";
      leaf id {
        type string;
      }
      uses ip-pim-grouping;
    }
  }

  grouping ipv6-pim-grouping {
    container bsr {
      description
        "Configure BSR";
      container candidate {
        description
          "Configure BSR related candidates";
        container bsr {
          description
            "Configure Candidate BSR";
          container global-scope {
            leaf name-addr {
              type union {
                type inet:ipv6-address;
                type string;
              }
            }
            leaf hash-mask-length {
              description
                "BSR Hash mask length";
              type uint8 {
                range "0..128";
              }
            }
            leaf priority {
              description
                "Priority for this is Candidate BSR";
              default "0";
              type uint8 {
                range "0..255";
              }
            }
            leaf accept-rp-candidate {
              description
                "RP candidate filter";
              type string;
            }
          }
          list user-defined-scope-list {
            key "scope";
            leaf name-addr {
              mandatory true;
              type union {
                type inet:ipv6-address;
                type string;
              }
            }
            leaf hash-mask-length {
              description
                "BSR Hash mask length";
              type uint8 {
                range "0..128";
              }
            }
            leaf priority {
              description
                "Priority for this is Candidate BSR";
              default "0";
              type uint8 {
                range "0..255";
              }
            }
            leaf scope {
              description
                "Scope for which this is Candidate BSR";
              type uint8 {
                range "3..14";
              }
            }
            leaf accept-rp-candidate {
              description
                "RP candidate filter";
              type string;
            }
          }
        }
        list rp {
          description
            "Configure Candidate RP";
          key "name-addr";
          leaf name-addr {
            type union {
              type inet:ipv6-address;
              type string;
            }
          }
        }
      }
    }
    container rp-address {
      description
        "Configure Sparse-Mode Rendezvous Point";
      leaf address {
        type union {
          type inet:ipv6-address;
          type string;
        }
      }
      leaf access-list {
        type union {
          type string;
        }
      }
      leaf bidir {
        description
          "Specify keyword bidir to configure a bidir RP";
        type empty;
      }
    }
    container register-source {
      description
        "Configure register source";
      uses ios-ifc:interface-grouping;
    }
    list anycast-rp {
      description
        "Configure PIM Anycast-RP";
      key "ipv6_RP_address ipv6_RP_peer_address";
      leaf ipv6_RP_address {
        type union {
          type inet:ipv6-address;
          type string;
        }
      }
      leaf ipv6_RP_peer_address {
        type union {
          type inet:ipv6-address;
          type string;
        }
      }
    }
  }

  grouping config-ipv6-pim-grouping {
    uses ipv6-pim-grouping;
    list vrf {
      description
        "Select VPN Routing/Forwarding instance";
      key "id";
      leaf id {
        type string;
      }
      uses ipv6-pim-grouping;
    }
  }

  grouping config-interface-ip-pim-grouping {
    container accept-register {
      leaf list {
        type string;
      }
    }
    leaf bfd {
      description
        "Configure BFD";
      type empty;
    }
    leaf bidir-neighbor-filter {
      description
        "PIM bidir capable peering filter";
      type ios-types:mcast-std-acl-type;
    }
    leaf border {
      description
        "Border of PIM domain";
      type empty;
    }
    leaf bsr-border {
      description
        "Border of PIM domain";
      type empty;
    }
    container pim-mode-choice-cfg {
      choice pim-mode-choice {
        case passive-mode {
          leaf passive {
            description
              "Enable PIM passive interface operation";
            type empty;
          }
        }
        case dense {
          container dense-mode {
            description
              "Enable PIM dense-mode operation";
            presence "true";
            container proxy-register {
              description
                "Send proxy registers";
              leaf list {
                description
                  "Access list";
                type ios-types:ext-acl-type;
              }
              leaf route-map {
                description
                  "Route-map";
                type string;
              }
            }
          }
        }
        case sparse {
          container sparse-mode {
            description
              "Enable PIM sparse-mode operation";
            presence "true";
            container encap-helper {
              description
                "Configure encap-helper UDLR tunnel";
              leaf Tunnel {
                description
                  "Tunnel interface";
                type leafref {
                  path "/ios:native/ios:interface/ios:Tunnel/ios:name";
                }
              }
            }
          }
        }
        case sparse-dense {
          leaf sparse-dense-mode {
            description
              "Enable PIM sparse-dense-mode operation";
            type empty;
          }
        }
      }
    }
    choice pim-mode-choice {
      status deprecated;
      case passive-mode {
        leaf passive {
          status deprecated;
          description
            "Enable PIM passive interface operation";
          type empty;
        }
      }
      case dense {
        container dense-mode {
          status deprecated;
          description
            "Enable PIM dense-mode operation";
          presence "true";
          container proxy-register {
            description
              "Send proxy registers";
            status deprecated;
            leaf list {
              description
                "Access list";
              status deprecated;
              type ios-types:ext-acl-type;
            }
            leaf route-map {
              status deprecated;
              description
                "Route-map";
              type string;
            }
          }
        }
      }
      case sparse {
        leaf sparse-mode {
          status deprecated;
          description
            "Enable PIM sparse-mode operation";
          type empty;
        }
      }
      case sparse-dense {
        leaf sparse-dense-mode {
          status deprecated;
          description
            "Enable PIM sparse-dense-mode operation";
          type empty;
        }
      }
    }
    leaf pim-mode {
      status deprecated;
      type enumeration {
        enum passive;
        enum dense-mode;
        enum sparse-mode;
        enum sparse-dense-mode;
      }
    }
    leaf nbma-mode {
      description
        "Enable PIM nbma-mode operation";
      type empty;
    }
    leaf dr-priority {
      description
        "PIM router DR priority";
      default "1";
      type uint32;
    }
    container drlb {
      description
        "Enable DR Load-balancing operation";
      leaf rp-mask {
        description
          "RP Hash Mask";
        type union {
          type inet:ipv4-address;
          type enumeration {
            enum any;
          }
        }
      }
      leaf grp-mask {
        description
          "Group Hash Mask";
        type union {
          type inet:ipv4-address;
          type enumeration {
            enum any;
          }
        }
      }
      leaf src-mask {
        description
          "Source Mask";
        type union {
          type inet:ipv4-address;
          type enumeration {
            enum any;
          }
        }
      }
    }
    leaf join-prune-interval {
      description
        "PIM periodic Join-Prune interval";
      default "60";
      type uint16 {
        range "10..600";
      }
    }
    leaf neighbor-filter {
      description
        "PIM peering filter";
      type ios-types:mcast-std-acl-type;
    }
    leaf non-dr-join {
      description
        "Enable PIM Non-DR-Join";
      type empty;
    }
    container query-interval {
      description
        "PIM router query interval";
      choice seconds-milliseconds {
        default "seconds";
        case seconds {
          leaf seconds-interval {
            default "30";
            type uint16 {
              range "1..18725";
            }
          }
        }
        case milliseconds {
          leaf milliseconds-interval {
            type uint16 {
              range "100..65535";
            }
          }
          leaf msec {
            description
              "Query interval in milliseconds";
            mandatory true;
            type empty;
          }
        }
      }
      leaf neighbor-holdtime {
        description
          "PIM hello neighbor holdtime";
        type uint16 {
          range "1..65535";
        }
      }
    }
    list redundancy {
      description
        "Enable PIM redundancy operation";
      key "group-name";
      leaf group-name {
        description
          "Standby group name";
        type string;
      }
      leaf protocol {
        description
          "\"HSRP\" or \"VRRP\". Default is HSRP";
        default "hsrp";
        type enumeration {
          enum hsrp;
          enum vrrp;
        }
      }
      leaf dr-priority {
        description
          "Redundancy DR priority for active router";
        type uint32 {
          range "0..4294967294";
        }
      }
    }
    container state-refresh {
      description
        "PIM DM State-Refresh configuration";
      container origination-interval {
        description
          "PIM State-Refresh origination interval";
        presence "true";
        leaf interval {
          description
            "Interval in seconds";
          type uint8 {
            range "1..100";
          }
        }
      }
    }
    leaf spt-threshold {
      type enumeration {
        enum infinity;
      }
    }
  }

  grouping config-interface-ipv6-pim-grouping {
    container pim-conf {
      leaf pim {
        description
          "PIM interface commands";
        default "true";
        type boolean;
      }
    }
    container pim-container {
      description
        "PIM interface commands";
      leaf bfd {
        description
          "Configure BFD";
        type empty;
      }
      container bsr {
        description
          "Configure BSR";
        leaf border {
          description
            "Border of PIM BSR domain";
          type empty;
        }
      }
      leaf dr-priority {
        description
          "PIM Hello DR priority";
        default "1";
        type uint32;
      }
    }
    choice ipv6-pim-choice {
      status deprecated;
      container no-pim {
        status deprecated;
        leaf pim {
          status deprecated;
          description
            "PIM interface commands";
          default "true";
          type boolean;
        }
      }
      container pim {
        status deprecated;
        description
          "PIM interface commands";
        leaf bfd {
          status deprecated;
          description
            "Configure BFD";
          type empty;
        }
        container bsr {
          status deprecated;
          description
            "Configure BSR";
          leaf border {
            status deprecated;
            description
              "Border of PIM BSR domain";
            type empty;
          }
        }
        leaf dr-priority {
          status deprecated;
          description
            "PIM Hello DR priority";
          default "1";
          type uint32;
        }
      }
    }
  }

  grouping config-interface-lisp-ip-pim-grouping {
    container lisp {
      description
        "Configure LISP";
      container core-group-range {
        description
          "Configure group range to be used in the core";
        leaf addr {
          description
            "Start group address of the range. Should be configured along with group range";
          must '../ios-mc:range' {
            error-message "Core group range must be specified";
          }
          type inet:ipv4-address;
        }
        leaf range {
          description
            "Size of the group range. Should be configured along with start group address";
          must '../ios-mc:addr' {
            error-message "Core group start address must be specified";
          }
          type uint16 {
            range "1..1000";
          }
        }
      }
      container transit-core-group-range {
        description
          "Configure transit group range to be used in the core";
        leaf addr {
          description
            "Start group address of the range. Should be configured along with group range";
          must '../ios-mc:range' {
            error-message "Transit group range must be specified";
          }
          type inet:ipv4-address;
        }
        leaf range {
          description
            "Size of the group range. Should be configured along with start group address";
          must '../ios-mc:addr' {
            error-message "Transit group start address must be specified";
          }
          type uint16 {
            range "1..1000";
          }
        }
      }
      container transport {
        description
          "Enable PIM LISP transport";
        choice transport-type {
          case multicast {
            container multicast {
              description
                "LISP transport multicast";
              presence "true";
              leaf ipv4 {
                description
                  "IPv4 LISP transport";
                type empty;
              }
            }
          }
          case unicast {
            container unicast {
              description
                "LISP transport unicast";
              presence "true";
              leaf ipv4 {
                description
                  "IPv4 LISP transport";
                type empty;
              }
            }
          }
        }
      }
    }
  }

  grouping config-interface-lisp-ipv6-pim-grouping {
    container pim {
      container lisp {
        description
          "Configure LISP";
        container transport-container {
          description
            "Enable PIM LISP transport";
          choice lisp-v4-choice {
            container unicast {
              description
                "Enable PIM LISP transport unicast";
              presence "true";
              leaf ipv4 {
                description
                  "Enable lisp transport unicast ipv4";
                type empty;
              }
            }
          }
        }
        container transport {
          status deprecated;
          description
            "Enable PIM LISP transport";
          choice lisp-v4-choice {
            status deprecated;
            container unicast {
              status deprecated;
              leaf ipv4 {
                status deprecated;
                description
                  "Enable lisp transport unicast ipv4";
                type empty;
              }
              leaf cr {
                status obsolete;
                description
                  "Enable lisp transport unicast";
                type empty;
              }
            }
          }
        }
      }
    }
  }

  grouping config-mcr-conf-grouping {
    container mcr-conf {
      leaf multicast-routing {
        description
          "Enable IP multicast forwarding";
        type empty;
      }
    }
  }

  grouping config-multicast-routing-grouping {
    container multicast-routing {
      description
        "Enable IP multicast forwarding";
      presence "true";
      list vrf {
        description
          "Select VPN Routing/Forwarding instance";
        key "name";
        leaf name {
          must '/ios:native/ios:vrf/ios:definition[ios:name=current()] or /ios:native/ios:ip/ios:vrf[ios:name=current()]' {
            error-message "VRF must be created 1st, deleted last";
          }
          type string;
        }
        leaf distributed {
          description
            "Distributed multicast switching";
          type empty;
        }
      }
      leaf distributed {
        description
          "Distributed multicast switching";
        type empty;
      }
    }
  }

  grouping config-ipv6-mcr-conf-grouping {
    container mcr-conf {
      leaf multicast-routing {
        description
          "Enable IPV6 multicast forwarding";
        type empty;
      }
    }
  }

  grouping config-ipv6-multicast-routing-grouping {
    container multicast-routing-container {
      description
        "Enable IPV6 multicast forwarding";
      list vrf {
        description
          "Select VPN Routing/Forwarding instance";
        key "name";
        leaf name {
          must '/ios:native/ios:vrf/ios:definition[ios:name=current()]' {
            error-message "VRF must be created 1st, deleted last";
          }
          type string;
        }
      }
    }
    container multicast-routing {
      status deprecated;
      description
        "Enable IPv6 multicast";
      presence "true";
      leaf vrf {
        status deprecated;
        description
          "Select VPN Routing/Forwarding instance";
        type string;
      }
    }
  }

  grouping ip-msdp-grouping {
    container border {
      description
        "Configure MSDP DM/SM Border Router";
      container sa-address {
        description
          "Address to use in SA message";
        uses ios-ifc:interface-grouping;
      }
    }
    list peer {
      description
        "Configure an MSDP peer";
      key "addr";
      leaf addr {
        type union {
          type inet:ipv4-address;
          type string;
        }
      }
      container connect-source {
        description
          "Configure source address used for MSDP connection";
        uses ios-ifc:interface-grouping;
      }
      leaf remote-as {
        description
          "Configured AS number";
        type uint16 {
          range "1..65535";
        }
      }
    }
    leaf cache-rejected-sa {
      description
        "Store rejected SAs from all peers";
      type uint32 {
        range "1..32766";
      }
    }
    leaf cache-sa-state {
      description
        "OBSOLETE: Cache SA state for MSDP peers, is an implicit configuration.
         This leaf is made obsolete as this is not user configurable.";
      type empty;
    }
    list default-peer-list {
      description
        "Default MSDP peer to accept SA messages from";
      key "name-addr";
      leaf name-addr {
        type leafref {
          path "../../peer/addr";
        }
      }
      leaf prefix-list {
        description
          "Prefix list";
        type string;
      }
    }
    container default-peer {
      status obsolete;
      description
        "Default MSDP peer to accept SA messages from";
      leaf name-addr {
        status obsolete;
        type union {
          type string;
          type inet:ipv4-address;
        }
      }
      leaf prefix-list {
        status obsolete;
        description
          "Prefix list";
        type string;
      }
    }
    list description-list {
      description
        "Peer specific description";
      key "name-addr";
      leaf name-addr {
        type leafref {
          path "../../peer/addr";
        }
      }
      leaf description {
        mandatory true;
        type string;
      }
    }
    container description {
      status obsolete;
      description
        "Peer specific description";
      leaf name-addr {
        status obsolete;
        type union {
          type string;
          type inet:ipv4-address;
        }
      }
      leaf description {
        status obsolete;
        type string;
      }
    }
    list filter-sa-request-list {
      description
        "Filter SA-Requests from peer";
      key "name-addr";
      leaf name-addr {
        type leafref {
          path "../../peer/addr";
        }
      }
      leaf list {
        description
          "Access-list";
        type ios-types:std-acl-type;
      }
    }
    container filter-sa-request {
      status obsolete;
      description
        "Filter SA-Requests from peer";
      leaf name-addr {
        status obsolete;
        type union {
          type string;
          type inet:ipv4-address;
        }
      }
      leaf list {
        status obsolete;
        description
          "Access-list";
        type ios-types:std-acl-type;
      }
    }
    list keepalive-list {
      description
        "Configure keepalive parameters for a peer";
      key "name-addr";
      leaf name-addr {
        type leafref {
          path "../../peer/addr";
        }
      }
      leaf keepalive {
        mandatory true;
        description
          "Send keepalive period in seconds";
        type uint8 {
          range "1..60";
        }
      }
      leaf max-wait {
        mandatory true;
        description
          "Maximum time in seconds to wait for a message";
        type uint8 {
          range "1..75";
        }
      }
    }
    container keepalive {
      status obsolete;
      description
        "Configure keepalive parameters for a peer";
      leaf name-addr {
        status obsolete;
        type union {
          type string;
          type inet:ipv4-address;
        }
      }
      leaf keepalive {
        status obsolete;
        description
          "Send keepalive period in seconds";
        type uint8 {
          range "1..60";
        }
      }
      leaf max-wait {
        status obsolete;
        description
          "Maximum time in seconds to wait for a message";
        type uint8 {
          range "1..75";
        }
      }
    }
    list mesh-group-list {
      description
        "Configure an MSDP mesh-group";
      key "addr";
      leaf name {
        mandatory true;
        type string;
      }
      leaf addr {
        type leafref {
          path "../../peer/addr";
        }
      }
    }
    container mesh-group {
      status obsolete;
      description
        "Configure an MSDP mesh-group";
      leaf name {
        status obsolete;
        type string;
      }
      leaf addr {
        status obsolete;
        type union {
          type string;
          type inet:ipv4-address;
        }
      }
    }
    leaf new-rpf-rules {
      description
        "Configure new MSDP rpf rules";
      type empty;
    }
    leaf originator-id {
      description
        "Configure MSDP Originator ID";
      type string;
    }
    container password {
      description
        "Configure an MSDP password";
      list peer-list {
        description
          "MSDP peer on which the password is to be set";
        key "addr";
        leaf addr {
          type leafref {
            path "../../../peer/addr";
          }
        }
        leaf encryption {
          type uint8 {
            range "0..7";
          }
        }
        leaf password {
          mandatory true;
          type string;
        }
      }
      container peer {
        status obsolete;
        description
          "MSDP peer on which the password is to be set";
        leaf addr {
          status obsolete;
          type union {
            type string;
            type inet:ipv4-address;
          }
        }
        leaf encryption {
          status obsolete;
          type uint8;
        }
        leaf password {
          status obsolete;
          type string;
        }
      }
    }
    container redistribute-container {
      description
        "Inject multicast route entries into MSDP";
      presence "true";
      leaf list {
        description
          "Access-list";
        type ios-types:ext-acl-type;
      }
      leaf asn {
        description
          "AS number. ASN = <1-500> or value '0' to Allow all AS'es";
        type uint16 {
          range "0..500";
        }
      }
      leaf route-map {
        description
          "Route-map";
        type string;
      }
    }
    container redistribute {
      status deprecated;
      description
        "Inject multicast route entries into MSDP";
      leaf list {
        status deprecated;
        description
          "Access-list";
        type ios-types:ext-acl-type;
      }
      leaf asn {
        status deprecated;
        description
          "AS access-list";
        type uint16;
      }
      leaf route-map {
        status deprecated;
        description
          "Route-map";
        type string;
      }
    }
    leaf rpf {
      description
        "MSDP rpf";
      type enumeration {
        enum rfc3618;
      }
    }
    container sa-filter {
      description
        "Filter SA messages from peer";
      list in-list {
        description
          "Enable incoming SA filtering";
        key "addr";
        leaf addr {
          type leafref {
            path "../../../peer/addr";
          }
        }
        leaf list {
          description
            "Access list";
          type ios-types:ext-acl-type;
        }
        leaf route-map {
          description
            "Route map";
          type string;
        }
        leaf rp-list {
          description
            "Access-list for originating RP";
          type ios-types:mcast-std-acl-type;
        }
        leaf rp-route-map {
          description
            "Route map for originating RP";
          type string;
        }
      }
      container in {
        status obsolete;
        description
          "Enable incoming SA filtering";
        leaf addr {
          status obsolete;
          type union {
            type string;
            type inet:ipv4-address;
          }
        }
        leaf list {
          status obsolete;
          description
            "Access list";
          type ios-types:ext-acl-type;
        }
        leaf route-map {
          status obsolete;
          description
            "Route map";
          type string;
        }
        leaf rp-list {
          status obsolete;
          description
            "Access-list for originating RP";
          type union {
            type uint16 {
              range "1..99";
            }
            type string;
          }
        }
        leaf rp-route-map {
          status obsolete;
          description
            "Route map for originating RP";
          type string;
        }
      }
      list out-list {
        description
          "Enable outgoing SA filtering";
        key "addr";
        leaf addr {
          type leafref {
            path "../../../peer/addr";
          }
        }
        leaf list {
          description
            "Access list";
          type ios-types:ext-acl-type;
        }
        leaf route-map {
          description
            "Route map";
          type string;
        }
        leaf rp-list {
          description
            "Access-list for originating RP";
          type ios-types:mcast-std-acl-type;
        }
        leaf rp-route-map {
          description
            "Route map for originating RP";
          type string;
        }
      }
      container out {
        status obsolete;
        description
          "Enable outgoing SA filtering";
        leaf addr {
          status obsolete;
          type union {
            type string;
            type inet:ipv4-address;
          }
        }
        leaf list {
          status obsolete;
          description
            "Access list";
          type ios-types:ext-acl-type;
        }
        leaf route-map {
          status obsolete;
          description
            "Route map";
          type string;
        }
        leaf rp-list {
          status obsolete;
          description
            "Access-list for originating RP";
          type union {
            type uint16 {
              range "1..99";
            }
            type string;
          }
        }
        leaf rp-route-map {
          status obsolete;
          description
            "Route map for originating RP";
          type string;
        }
      }
    }
    list sa-limit-list {
      description
        "Configure SA limit for a peer";
      key "name-addr";
      leaf name-addr {
        type leafref {
          path "../../peer/addr";
        }
      }
      leaf limit {
        description
          "Limit of SAs";
        mandatory true;
        type uint32 {
          range "1..2147483646";
        }
      }
    }
    container sa-limit {
      status obsolete;
      description
        "Configure SA limit for a peer";
      leaf name-addr {
        status obsolete;
        type union {
          type string;
          type inet:ipv4-address;
        }
      }
      leaf limit {
        status obsolete;
        description
          "Limit of SAs";
        type uint32 {
          range "1..2147483646";
        }
      }
    }
    list shutdown-list {
      description
        "Administratively shutdown MSDP peer";
      key "name-addr";
      leaf name-addr {
        type leafref {
          path "../../peer/addr";
        }
      }
    }
    container shutdown {
      status obsolete;
      description
        "Administratively shutdown MSDP peer";
      leaf name-addr {
        status obsolete;
        type union {
          type string;
          type inet:ipv4-address;
        }
      }
    }
    leaf timer {
      description
        "MSDP timer";
      default "30";
      type uint8 {
        range "1..60";
      }
    }
    list ttl-threshold-list {
      description
        "Configure TTL Threshold for MSDP Peer";
      key "name-addr";
      leaf name-addr {
        type leafref {
          path "../../peer/addr";
        }
      }
      leaf threshold {
        description
          "TTL Threshold Value";
        mandatory true;
        type uint8;
      }
    }
    container ttl-threshold {
      status obsolete;
      description
        "Configure TTL Threshold for MSDP Peer";
      leaf name-addr {
        status obsolete;
        type union {
          type string;
          type inet:ipv4-address;
        }
      }
      leaf threshold {
        status obsolete;
        description
          "TTL Threshold Value";
        type uint8;
      }
    }
  }

  grouping config-ip-msdp-grouping {
    container msdp {
      description
        "MSDP global commands";
      uses ip-msdp-grouping;
      list vrf {
        description
          "Select VPN Routing/Forwarding instance";
        key "name";
        leaf name {
          type string;
        }
        uses ip-msdp-grouping;
      }
    }
  }

  grouping confif-ip-mroute-grouping {
    container mroute {
      description
        "Configure static multicast routes";
      leaf source-address {
        type inet:ipv4-address;
      }
      leaf subnet-mask {
        type inet:ipv4-address;
      }
      leaf Tunnel {
        description
          "Tunnel interface";
        type int32 {
          range "0..2147483647";
        }
      }
    }
  }

  grouping config-mpls-mldp-grouping {
    leaf mldp {
      default "true";
      type boolean;
    }
    container mldp-conf {
      container mldp {
        description
          "Configure MLDP routing protocol parameters";
        list fec {
          description
            "MLDP Forwarding Equivalence Class(FEC)";
          key "fecid";
          leaf fecid {
            description
              "FEC identifier";
            type uint8 {
              range "1..99";
            }
          }
          container opaque-type {
            description
              "FEC Opaque type";
            choice type {
              case ipv4-type {
                container ipv4 {
                  description
                    "IPv4 opaque type";
                  leaf source_address {
                    description
                      "IP source address";
                    mandatory true;
                    type inet:ipv4-address;
                  }
                  leaf group_address {
                    description
                      "IP group address";
                    mandatory true;
                    type inet:ipv4-address;
                  }
                }
              }
              case vpnv4-type {
                container vpnv4 {
                  description
                    "VPNv4 opaque type";
                  leaf source_address {
                    description
                      "IP source address";
                    mandatory true;
                    type inet:ipv4-address;
                  }
                  leaf group_address {
                    description
                      "IP group address";
                    mandatory true;
                    type inet:ipv4-address;
                  }
                  leaf vpnid {
                    description
                      "VPN Route Distinguisher (ASN:nn, IP-address:nn or 4BASN:nn)";
                    mandatory true;
                    type string;
                  }
                }
              }
              case ipv6-type {
                container ipv6 {
                  description
                    "IPv6 opaque type";
                  leaf source_address {
                    description
                      "IPv6 source address";
                    mandatory true;
                    type inet:ipv6-address;
                  }
                  leaf group_address {
                    description
                      "IPv6 group address";
                    mandatory true;
                    type inet:ipv6-address;
                  }
                }
              }
              case vpnv6-type {
                container vpnv6 {
                  description
                    "VPNv6 opaque type";
                  leaf source_address {
                    description
                      "IPv6 source address";
                    mandatory true;
                    type inet:ipv6-address;
                  }
                  leaf group_address {
                    description
                      "IPv6 group address";
                    mandatory true;
                    type inet:ipv6-address;
                  }
                  leaf vpnid {
                    description
                      "VPN Route Distinguisher (ASN:nn, IP-address:nn or 4BASN:nn)";
                    mandatory true;
                    type string;
                  }
                }
              }
              case mdt-type {
                container mdt {
                  description
                    "MDT opaque type";
                  container vpn-id {
                    description
                      "MDT VPN Id in rfc2685 format";
                    leaf vpnid {
                      description
                        ", format (hex) <3 bytes OUI:4 bytes VPN Index";
                      mandatory true;
                      type union {
                        type enumeration {
                          enum any;
                        }
                        type string;
                      }
                    }
                    leaf scope {
                      description
                        "MDT scope";
                      mandatory true;
                      type union {
                        type uint16 {
                          range "0..65535";
                        }
                        type enumeration {
                          enum any;
                        }
                      }
                    }
                  }
                }
              }
            }
          }
        }
        list filter {
          description
            "MLDP filter";
          key "fecid";
          leaf fecid {
            description
              "FEC identifier";
            type uint8 {
              range "1..99";
            }
          }
          leaf peer-list {
            description
              "MLDP filter peer list";
            mandatory true;
            type ios-types:std-acl-type;
          }
        }
        container forwarding {
          description
            "Multicast LDP forwarding commands";
          leaf recursive {
            description
              "Enable recursion on unicast LSPs";
            default "true";
            type boolean;
          }
        }
        leaf limit {
          description
            "Limit the number of LSPs";
          type uint32 {
            range "0..1000000";
          }
        }
        container logging {
          description
            "Multicast LDP logging";
          leaf internal {
            description
              "Log internal notifications";
            type empty;
          }
          leaf notifications {
            description
              "Log notifications";
            type empty;
          }
        }
        container make-before-break {
          description
            "Enable make-before-break";
          leaf delay {
            description
              "Delay in milliseconds";
            type uint32 {
              range "0..60000";
            }
          }
        }
        container path {
          description
            "Configure mLDP path options";
          container multipath {
            description
              "Enable mLDP multipath";
            leaf upstream {
              description
                "Enable mLDP multipath for upstream LDP neighbors";
              default "true";
              type boolean;
            }
            leaf downstream {
              description
                "Enable mLDP multipath for downstream LDP neighbors";
              default "true";
              type boolean;
            }
          }
          leaf traffic-eng {
            description
              "Allow mLDP to use traffic-eng tunnels";
            type empty;
          }
        }
        container static {
          description
            "Static LSP";
          list mp2mp {
            description
              "Static MP2MP LSP";
            key "root_address";
            leaf root_address {
              description
                "IP root address";
              type inet:ipv4-address;
            }
            leaf lsp_instances {
              description
                "Number of LSPs";
              mandatory true;
              type uint32 {
                range "0..100000";
              }
            }
          }
          list p2mp {
            description
              "Static P2MP LSP";
            key "root_address";
            leaf root_address {
              description
                "IP root address";
              type inet:ipv4-address;
            }
            leaf lsp_instances {
              description
                "Number of LSPs";
              mandatory true;
              type uint32 {
                range "0..100000";
              }
            }
          }
        }
      }
    }
  }

  grouping config-service-reflect-grouping {
    leaf destination {
      description
        "Packets with destination address";
      type inet:ip-address;
    }
    leaf to {
      description
        "Modify destination address in reflected packets to";
      type inet:ip-address;
    }
    leaf mask-len {
      description
        "Mask length";
      type uint8 {
        range "1..32";
      }
    }
    leaf source {
      description
        "Modify source address in reflected packets";
      type inet:ip-address;
    }
  }

  grouping config-service-reflect-source-grouping {
    leaf to_src {
      description
        "Modify source address in reflected packets to";
      type inet:ip-address;
    }
    leaf src-mask-len {
      description
        "Source Mask length";
      type uint8 {
        range "1..32";
      }
    }
  }

  grouping config-service-reflect-list-grouping {
    container service {
      description
        "IP service";
      container reflect {
        description
          "Reflect service";
        list service_reflect_source_list {
          description
            "List of service reflect entries";
          key "destination to mask-len source to_src src-mask-len";
          uses config-service-reflect-grouping;
          uses config-service-reflect-source-grouping;
        }
        list service_reflect_list {
          description
            "List of service reflect entries";
          key "destination to mask-len source";
          uses config-service-reflect-grouping;
        }
        list service_reflect_interface_source_list {
          description
            "List of service reflect entries";
          key "interface destination to mask-len source to_src src-mask-len";
          leaf interface {
            description
              "Specify service reflect interface";
            type string;
          }
          uses config-service-reflect-grouping;
          uses config-service-reflect-source-grouping;
        }
        list service_reflect_interface_list {
          description
            "List of service reflect entries";
          key "interface destination to mask-len source";
          leaf interface {
            description
              "Specify service reflect interface";
            type string;
          }
          uses config-service-reflect-grouping;
        }
      }
    }
  }

  augment "/ios:native/ios:ip/ios:multicast" {
    uses config-ip-mcast-grouping;
  }

  augment "/ios:native/ios:interface/ios:FastEthernet/ios:ip" {
    uses config-interface-ip-mcast-grouping;
  }

  augment "/ios:native/ios:interface/ios:GigabitEthernet/ios:ip" {
    uses config-interface-ip-mcast-grouping;
  }

  augment "/ios:native/ios:interface/ios:TwoGigabitEthernet/ios:ip" {
    uses config-interface-ip-mcast-grouping;
  }

  augment "/ios:native/ios:interface/ios:FiveGigabitEthernet/ios:ip" {
    uses config-interface-ip-mcast-grouping;
  }

  augment "/ios:native/ios:interface/ios:AppGigabitEthernet/ios:ip" {
    uses config-interface-ip-mcast-grouping;
  }

  augment "/ios:native/ios:interface/ios:TenGigabitEthernet/ios:ip" {
    uses config-interface-ip-mcast-grouping;
  }

  augment "/ios:native/ios:interface/ios:TwentyFiveGigE/ios:ip" {
    uses config-interface-ip-mcast-grouping;
  }

  augment "/ios:native/ios:interface/ios:FortyGigabitEthernet/ios:ip" {
    uses config-interface-ip-mcast-grouping;
  }

  augment "/ios:native/ios:interface/ios:HundredGigE/ios:ip" {
    uses config-interface-ip-mcast-grouping;
  }

  augment "/ios:native/ios:interface/ios:Port-channel/ios:ip" {
    uses config-interface-ip-mcast-grouping;
  }

  augment "/ios:native/ios:interface/ios:Loopback/ios:ip" {
    uses config-interface-ip-mcast-grouping;
  }

  augment "/ios:native/ios:interface/ios:Tunnel/ios:ip" {
    uses config-interface-ip-mcast-grouping;
  }

  augment "/ios:native/ios:interface/ios:Virtual-Template/ios:ip" {
    uses config-interface-ip-mcast-grouping;
  }

  augment "/ios:native/ios:interface/ios:VirtualPortGroup/ios:ip" {
    uses config-interface-ip-mcast-grouping;
  }

  augment "/ios:native/ios:interface/ios:Vlan/ios:ip" {
    uses config-interface-ip-mcast-grouping;
  }

  augment "/ios:native/ios:interface/ios:Port-channel-subinterface/ios:Port-channel/ios:ip" {
    uses config-interface-ip-mcast-grouping;
  }

  augment "/ios:native/ios:interface/ios:LISP/ios:ip" {
    uses config-interface-ip-mcast-grouping;
  }

  augment "/ios:native/ios:interface/ios:LISP-subinterface/ios:LISP/ios:ip" {
    uses config-interface-ip-mcast-grouping;
  }

  augment "/ios:native/ios:interface/ios:Vif/ios:ip" {
    uses config-interface-ip-mcast-grouping;
  }

  augment "/ios:native/ios:interface/ios:Multilink/ios:ip" {
    uses config-interface-ip-mcast-grouping;
  }

  augment "/ios:native/ios:interface/ios:Cellular/ios:ip" {
    uses config-interface-ip-mcast-grouping;
  }

  augment "/ios:native/ios:interface/ios:BDI/ios:ip" {
    uses config-interface-ip-mcast-grouping;
  }

  augment "/ios:native/ios:ipv6/ios:multicast" {
    uses config-ipv6-mcast-grouping;
  }

  augment "/ios:native/ios:ip/ios:pim" {
    uses config-ip-pim-grouping;
  }

  augment "/ios:native/ios:ipv6/ios:pim" {
    uses config-ipv6-pim-grouping;
  }

  augment "/ios:native/ios:mpls" {
    uses config-mpls-mldp-grouping;
  }

  augment "/ios:native/ios:interface/ios:FastEthernet/ios:ip/ios:pim" {
    uses config-interface-ip-pim-grouping;
  }

  augment "/ios:native/ios:interface/ios:GigabitEthernet/ios:ip/ios:pim" {
    uses config-interface-ip-pim-grouping;
  }

  augment "/ios:native/ios:interface/ios:TwoGigabitEthernet/ios:ip/ios:pim" {
    uses config-interface-ip-pim-grouping;
  }

  augment "/ios:native/ios:interface/ios:FiveGigabitEthernet/ios:ip/ios:pim" {
    uses config-interface-ip-pim-grouping;
  }

  augment "/ios:native/ios:interface/ios:AppGigabitEthernet/ios:ip/ios:pim" {
    uses config-interface-ip-pim-grouping;
  }

  augment "/ios:native/ios:interface/ios:TenGigabitEthernet/ios:ip/ios:pim" {
    uses config-interface-ip-pim-grouping;
  }

  augment "/ios:native/ios:interface/ios:TwentyFiveGigE/ios:ip/ios:pim" {
    uses config-interface-ip-pim-grouping;
  }

  augment "/ios:native/ios:interface/ios:FortyGigabitEthernet/ios:ip/ios:pim" {
    uses config-interface-ip-pim-grouping;
  }

  augment "/ios:native/ios:interface/ios:HundredGigE/ios:ip/ios:pim" {
    uses config-interface-ip-pim-grouping;
  }

  augment "/ios:native/ios:interface/ios:Port-channel/ios:ip/ios:pim" {
    uses config-interface-ip-pim-grouping;
  }

  augment "/ios:native/ios:interface/ios:Loopback/ios:ip/ios:pim" {
    uses config-interface-ip-pim-grouping;
  }

  augment "/ios:native/ios:interface/ios:Tunnel/ios:ip/ios:pim" {
    uses config-interface-ip-pim-grouping;
  }

  augment "/ios:native/ios:interface/ios:Virtual-Template/ios:ip/ios:pim" {
    uses config-interface-ip-pim-grouping;
  }

  augment "/ios:native/ios:interface/ios:VirtualPortGroup/ios:ip/ios:pim" {
    uses config-interface-ip-pim-grouping;
  }

  augment "/ios:native/ios:interface/ios:Vlan/ios:ip/ios:pim" {
    uses config-interface-ip-pim-grouping;
  }

  augment "/ios:native/ios:interface/ios:Port-channel-subinterface/ios:Port-channel/ios:ip/ios:pim" {
    uses config-interface-ip-pim-grouping;
  }

  augment "/ios:native/ios:interface/ios:LISP/ios:ip/ios:pim" {
    uses config-interface-ip-pim-grouping;
    uses config-interface-lisp-ip-pim-grouping;
  }

  augment "/ios:native/ios:interface/ios:LISP-subinterface/ios:LISP/ios:ip/ios:pim" {
    uses config-interface-ip-pim-grouping;
    uses config-interface-lisp-ip-pim-grouping;
  }

  augment "/ios:native/ios:interface/ios:Vif/ios:ip/ios:pim" {
    uses config-interface-ip-pim-grouping;
  }

  augment "/ios:native/ios:interface/ios:Multilink/ios:ip/ios:pim" {
    uses config-interface-ip-pim-grouping;
  }

  augment "/ios:native/ios:interface/ios:Cellular/ios:ip/ios:pim" {
    uses config-interface-ip-pim-grouping;
  }

  augment "/ios:native/ios:interface/ios:BDI/ios:ip/ios:pim" {
    uses config-interface-ip-pim-grouping;
  }

  augment "/ios:native/ios:interface/ios:FastEthernet/ios:ipv6" {
    uses config-interface-ipv6-pim-grouping;
  }

  augment "/ios:native/ios:interface/ios:GigabitEthernet/ios:ipv6" {
    uses config-interface-ipv6-pim-grouping;
  }

  augment "/ios:native/ios:interface/ios:TwoGigabitEthernet/ios:ipv6" {
    uses config-interface-ipv6-pim-grouping;
  }

  augment "/ios:native/ios:interface/ios:FiveGigabitEthernet/ios:ipv6" {
    uses config-interface-ipv6-pim-grouping;
  }

  augment "/ios:native/ios:interface/ios:AppGigabitEthernet/ios:ipv6" {
    uses config-interface-ipv6-pim-grouping;
  }

  augment "/ios:native/ios:interface/ios:TenGigabitEthernet/ios:ipv6" {
    uses config-interface-ipv6-pim-grouping;
  }

  augment "/ios:native/ios:interface/ios:TwentyFiveGigE/ios:ipv6" {
    uses config-interface-ipv6-pim-grouping;
  }

  augment "/ios:native/ios:interface/ios:FortyGigabitEthernet/ios:ipv6" {
    uses config-interface-ipv6-pim-grouping;
  }

  augment "/ios:native/ios:interface/ios:HundredGigE/ios:ipv6" {
    uses config-interface-ipv6-pim-grouping;
  }

  augment "/ios:native/ios:interface/ios:Port-channel/ios:ipv6" {
    uses config-interface-ipv6-pim-grouping;
  }

  augment "/ios:native/ios:interface/ios:Port-channel-subinterface/ios:Port-channel/ios:ipv6" {
    uses config-interface-ipv6-pim-grouping;
  }

  augment "/ios:native/ios:interface/ios:Loopback/ios:ipv6" {
    uses config-interface-ipv6-pim-grouping;
  }

  augment "/ios:native/ios:interface/ios:Tunnel/ios:ipv6" {
    uses config-interface-ipv6-pim-grouping;
  }

  augment "/ios:native/ios:interface/ios:Virtual-Template/ios:ipv6" {
    uses config-interface-ipv6-pim-grouping;
  }

  augment "/ios:native/ios:interface/ios:VirtualPortGroup/ios:ipv6" {
    uses config-interface-ipv6-pim-grouping;
  }

  augment "/ios:native/ios:interface/ios:Vif/ios:ipv6" {
    uses config-interface-ipv6-pim-grouping;
  }

  augment "/ios:native/ios:interface/ios:Vlan/ios:ipv6" {
    uses config-interface-ipv6-pim-grouping;
  }

  augment "/ios:native/ios:interface/ios:LISP/ios:ipv6" {
    uses config-interface-lisp-ipv6-pim-grouping;
  }

  augment "/ios:native/ios:interface/ios:LISP-subinterface/ios:LISP/ios:ipv6" {
    uses config-interface-lisp-ipv6-pim-grouping;
  }

  augment "/ios:native/ios:interface/ios:Multilink/ios:ipv6" {
    uses config-interface-ipv6-pim-grouping;
  }

  augment "/ios:native/ios:interface/ios:Cellular/ios:ipv6" {
    uses config-interface-ipv6-pim-grouping;
  }

  augment "/ios:native/ios:interface/ios:BDI/ios:ipv6" {
    uses config-interface-ipv6-pim-grouping;
  }

  augment "/ios:native/ios:ip" {
    uses config-ip-msdp-grouping;
  }

  augment "/ios:native/ios:ip" {
    uses config-mcr-conf-grouping;
    uses config-multicast-routing-grouping;
  }

  augment "/ios:native/ios:ip" {
    uses confif-ip-mroute-grouping;
  }

  augment "/ios:native/ios:ipv6" {
    uses config-ipv6-mcr-conf-grouping;
    uses config-ipv6-multicast-routing-grouping;
  }

  augment "/ios:native/ios:interface/ios:Vif/ios:ip" {
    uses config-service-reflect-list-grouping;
  }
}
