module cisco-xe-ietf-event-notifications-deviation {
  namespace "http://cisco.com/ns/yang/cisco-xe-ietf-event-notifications-deviation";

  prefix notif-bis-devs;

  import ietf-event-notifications {
    prefix notif-bis;
  }

  organization
    "Cisco Systems, Inc.";

  contact
    " Cisco Systems, Inc.
    Customer Service

    Postal: 170 W Tasman Drive
    San Jose, CA 95134

    Tel: +1 1800 553-NETS

    E-mail: cs-yang@cisco.com";

  description
    "This module defines deviation statements for ietf-event-notifications
     module.
     Copyright (c) 2017-2018 by Cisco Systems, Inc.
     All rights reserved.";

  revision 2018-12-03 {
    description
      "Added deviations for source-vrf to accept string and source-address to
       be optional.";
  }

  revision 2017-08-22 {
    description
      "Added all deviations for all unsupported elements for direct access to
       tables subscriptions, subscription-config";
  }

  revision 2017-02-22 {
    description
      "Initial Revision";

    reference
      "RFC 6020: YANG - A Data Modeling Language for the
       Network Configuration Protocol (NETCONF)";

  }

  /*
   *
  deviation "/notif-bis:establish-subscription/notif-bis:input" +
            "/notif-bis:filter-type/notif-bis:rfc5277" {
    deviate not-supported;
    description  "Currently not supported.";
  }
  */

  deviation "/notif-bis:establish-subscription/notif-bis:input" +
            "/notif-bis:filter-type/notif-bis:by-reference" {
    deviate not-supported;
    description  "Currently not supported.";
  }

  deviation "/notif-bis:establish-subscription/notif-bis:input" +
            "/notif-bis:startTime" {
    deviate not-supported;
    description  "Currently not supported.";
  }

  deviation "/notif-bis:establish-subscription/notif-bis:input" +
            "/notif-bis:stopTime" {
    deviate not-supported;
    description  "Currently not supported.";
  }

  /*
   *
  deviation "/notif-bis:establish-subscription/notif-bis:output" +
            "/notif-bis:result/notif-bis:no-success" +
            "/notif-bis:filter-type/notif-bis:rfc5277" {
    deviate not-supported;
    description  "Currently not supported.";
  }
  */

  deviation "/notif-bis:establish-subscription/notif-bis:output" +
            "/notif-bis:result/notif-bis:no-success" +
            "/notif-bis:filter-type/notif-bis:by-reference" {
    deviate not-supported;
    description  "Currently not supported.";
  }

  /*
   * =========================
   * subscription-config...
   * =========================
   */
  deviation "/notif-bis:subscription-config/notif-bis:subscription" +
            "/notif-bis:startTime" {
    deviate not-supported;
    description  "Currently not supported.";
  }

  deviation "/notif-bis:subscription-config/notif-bis:subscription" +
            "/notif-bis:stopTime" {
    deviate not-supported;
    description  "Currently not supported.";
  }

  /*
   *
  deviation "/notif-bis:subscription-config/notif-bis:subscription" +
            "/notif-bis:filter-type/notif-bis:rfc5277" {
    deviate not-supported;
    description  "Currently not supported.";
  }
  */

  deviation "/notif-bis:subscription-config/notif-bis:subscription" +
            "/notif-bis:filter-type/notif-bis:by-reference" {
    deviate not-supported;
    description  "Currently not supported.";
  }

  deviation "/notif-bis:subscription-config/notif-bis:subscription" +
            "/notif-bis:push-source/notif-bis:interface-originated" {
    deviate not-supported;
    description  "Currently not supported.";
  }

  deviation "/notif-bis:subscription-config/notif-bis:subscription" +
            "/notif-bis:push-source/notif-bis:address-originated" +
            "/notif-bis:source-vrf" {
    deviate replace {
        type string;
    }
    description  "String is supported.";
  }

  deviation "/notif-bis:subscription-config/notif-bis:subscription" +
            "/notif-bis:push-source/notif-bis:address-originated" +
            "/notif-bis:source-address" {
    deviate replace {
        mandatory false;
    }
    description  "Source-address doesn't have to be mandatory.";
  }

  /*
   * =========================
   * subscriptions...
   * =========================
   */
  deviation "/notif-bis:subscriptions/notif-bis:subscription" +
            "/notif-bis:configured-subscription" {
    deviate not-supported;
    description  "Currently not supported.";
  }

  deviation "/notif-bis:subscriptions/notif-bis:subscription" +
            "/notif-bis:startTime" {
    deviate not-supported;
    description  "Currently not supported.";
  }

  deviation "/notif-bis:subscriptions/notif-bis:subscription" +
            "/notif-bis:stopTime" {
    deviate not-supported;
    description  "Currently not supported.";
  }

  /*
   *
  deviation "/notif-bis:subscriptions/notif-bis:subscription" +
            "/notif-bis:filter-type/notif-bis:rfc5277" {
    deviate not-supported;
    description  "Currently not supported.";
  }
  */

  deviation "/notif-bis:subscriptions/notif-bis:subscription" +
            "/notif-bis:filter-type/notif-bis:by-reference" {
    deviate not-supported;
    description  "Currently not supported.";
  }

  deviation "/notif-bis:subscriptions/notif-bis:subscription" +
            "/notif-bis:push-source/notif-bis:interface-originated" {
    deviate not-supported;
    description  "Currently not supported.";
  }

  deviation "/notif-bis:subscriptions/notif-bis:subscription" +
            "/notif-bis:push-source/notif-bis:address-originated" +
            "/notif-bis:source-vrf" {
    deviate replace {
        type string;
    }
    description  "String is supported.";
  }

  deviation "/notif-bis:subscriptions/notif-bis:subscription" +
            "/notif-bis:push-source/notif-bis:address-originated" +
            "/notif-bis:source-address" {
    deviate replace {
        mandatory false;
    }
    description  "Source-address doesn't have to be mandatory.";
  }
}
