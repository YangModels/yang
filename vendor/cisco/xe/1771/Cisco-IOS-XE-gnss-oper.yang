module Cisco-IOS-XE-gnss-oper {
  yang-version 1;
  namespace "http://cisco.com/ns/yang/Cisco-IOS-XE-gnss-oper";
  prefix gnss-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for IOS-XE GNSS (Global Navigation Satellite System)
     operational data.
     Copyright (c) 2019 by Cisco Systems, Inc.
     All rights reserved.";

  revision 2020-03-01 {
    description
      "Initial revision";
    reference
      "1.0.0";
    cisco-semver:module-version "1.0.0";
  }

  typedef gnss-module-status {
    type enumeration {
      enum gnss-module-status-unknown {
        value 0;
        description
          "Module presence status unknown";
      }
      enum gnss-module-status-absent {
        value 1;
        description
          "Module presence status absent";
      }
      enum gnss-module-status-present {
        value 2;
        description
          "Module presence status present";
      }
      enum gnss-module-status-invalid {
        value 3;
        description
          "Module presence status invalid";
      }
    }
    description
      "GNSS (Global Navigation Satellite System) module presence status";
  }

  typedef gnss-module-lock-status {
    type enumeration {
      enum gnss-module-lock-status-unknown {
        value 0;
        description
          "Module lock status unknown";
      }
      enum gnss-module-lock-status-down {
        value 1;
        description
          "Module lock status down";
      }
      enum gnss-module-lock-status-up {
        value 2;
        description
          "Module lock status up";
      }
      enum gnss-module-lock-status-invalid {
        value 3;
        description
          "Module lock status invalid";
      }
    }
    description
      "GNSS (Global Navigation Satellite System) module lock status";
  }

  typedef gnss-sv-type {
    type enumeration {
      enum gnss-sv-type-gps {
        value 0;
        description
          "Satellite type 0";
      }
      enum gnss-sv-type-sbas {
        value 1;
        description
          "Satellite type 1";
      }
      enum gnss-sv-type-galileo {
        value 2;
        description
          "Satellite type 2";
      }
      enum gnss-sv-type-beidou {
        value 3;
        description
          "Satellite type 3";
      }
      enum gnss-sv-type-imes {
        value 4;
        description
          "Satellite type 4";
      }
      enum gnss-sv-type-qzss {
        value 5;
        description
          "Satellite type 5";
      }
      enum gnss-sv-type-glonass {
        value 6;
        description
          "Satellite type 6";
      }
    }
    description
      "GNSS (Global Navigation Satellite System) satellite types";
  }

  typedef gnss-module-sv-tracking-status {
    type enumeration {
      enum satellite-tracking-status-bad {
        value 0;
        description
          "Satellite tracking status bad";
      }
      enum satellite-tracking-status-good {
        value 1;
        description
          "Satellite tracking status good";
      }
    }
    description
      "GNSS (Global Navigation Satellite System) module satellite
       tracking status. If tracking minimum 3 satellites with more
       than 30 decibel milliwatts then good, if not bad";
  }

  typedef gnss-module-alarm-status {
    type enumeration {
      enum alarm-disable {
        value 0;
        description
          "Alarm disable";
      }
      enum alarm-enable {
        value 1;
        description
          "Alarm enable";
      }
    }
    description
      "GNSS (Global Navigation Satellite System) module alarm status";
  }

  typedef rsp-slot-state {
    type enumeration {
      enum active-rsp {
        value 0;
        description
          "Active RSP (Route Switch Processor)";
      }
      enum standby-rsp {
        value 1;
        description
          "Standby RSP (Route Switch Processor)";
      }
    }
    description
      "Slot state";
  }

  typedef satellite-acq-flag-type {
    type enumeration {
      enum never-acquired {
        value 0;
        description
          "Never acquired";
      }
      enum acquired {
        value 1;
        description
          "Acquired";
      }
      enum reopened-search {
        value 2;
        description
          "Reopened search";
      }
    }
    description
      "GNSS (Global Navigation Satellite System) satellite acquisition flag types";
  }

  grouping gnss-satellite-info {
    description
      "Satellite information data";
    leaf sv-prn {
      type int32;
      description
        "Satellite number";
    }
    leaf channel {
      type uint8;
      description
        "Channel number";
    }
    leaf acq-flag {
      type gnss-ios-xe-oper:satellite-acq-flag-type;
      description
        "Acquisition flag";
    }
    leaf eph-flag {
      type uint8;
      description
        "Ephemeris flag";
    }
    leaf signal-level {
      type int64;
      description
        "Signal strength SNR in decibel Hertz ";
    }
    leaf sv-type {
      type gnss-ios-xe-oper:gnss-sv-type;
      description
        "Satellite type";
    }
    leaf elevation {
      type int64;
      description
        "Satellite elevation angle";
    }
    leaf azimuth {
      type int64;
      description
        "Satellite azimuth angle";
    }
  }

  grouping gnss-data {
    description
      "GNSS (Global Navigation Satellite System) data";
    leaf slot {
      type uint16;
      description
        "Router slot number where
         GNSS (Global Navigation Satellite System) module is inserted";
    }
    leaf slot-state {
      type gnss-ios-xe-oper:rsp-slot-state;
      description
        "Router slot state (active or standby) where
         GNSS (Global Navigation Satellite System) module is inserted";
    }
    leaf presence-status {
      type gnss-ios-xe-oper:gnss-module-status;
      description
        "GNSS (Global Navigation Satellite System)
         card presence status";
    }
    leaf lock-status {
      type gnss-ios-xe-oper:gnss-module-lock-status;
      description
        "GNSS (Global Navigation Satellite System)
         card lock status";
    }
    leaf survey-progress-status {
      type uint8;
      description
        "GNSS (Global Navigation Satellite System)
         card survey progress status";
    }
    leaf satellite-tracking-status {
      type gnss-ios-xe-oper:gnss-module-sv-tracking-status;
      description
        "GNSS (Global Navigation Satellite System)
         satellite tracking status";
    }
    leaf gnss-antenna-open-alarm-status {
      type gnss-ios-xe-oper:gnss-module-alarm-status;
      description
        "GNSS (Global Navigation Satellite System)
         module antenna open alarm status";
    }
    leaf gnss-antenna-short-alarm-status {
      type gnss-ios-xe-oper:gnss-module-alarm-status;
      description
        "GNSS (Global Navigation Satellite System)
         module antenna short alarm status";
    }
    leaf satellite-cnt {
      type uint8;
      description
        "Number of satellites visible at a particular time";
    }
    list satellite-info {
      max-elements 32;
      description
        "Satellite info data";
      uses gnss-ios-xe-oper:gnss-satellite-info;
    }
  }

  container gnss-oper-data {
    config false;
    description
      "GNSS (Global Navigation Satellite System) operational data";
    list gnss-data {
      key "slot";
      description
        "GNSS (Global Navigation Satellite System) data";
      uses gnss-ios-xe-oper:gnss-data;
    }
  }
}
