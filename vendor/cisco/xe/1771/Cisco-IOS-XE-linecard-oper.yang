module Cisco-IOS-XE-linecard-oper {
  yang-version 1;
  namespace "http://cisco.com/ns/yang/Cisco-IOS-XE-linecard-oper";
  prefix linecard-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     monitoring linecards in a Network Element.
     Copyright (c) 2018-2019 by Cisco Systems, Inc.
     All rights reserved.";

  revision 2019-05-01 {
    description
      "- Adding slot-id.
       - Added semantic version";
    reference
      "1.1.0";
    cisco-semver:module-version "1.1.0";
  }
  revision 2018-03-26 {
    description
      "Initial revision";
    reference
      "1.0.0";
    cisco-semver:module-version "1.0.0";
  }

  grouping linecard {
    description
      "Attributes of linecard";
    leaf name {
      type string;
      description
        "Physical location description of the linecard";
    }
    leaf power-admin-state {
      type boolean;
      description
        "Power provided to the linecard: Enabled/Disabled";
    }
    leaf slot-id {
      type uint16;
      description
        "Identifier for the slot or chassis position in which the linecard is installed";
    }
  }

  container linecard-oper-data {
    config false;
    description
      "Top-level container for linecard operational data";
    list linecard {
      key "name";
      description
        "List of linecard instances, keyed by slot";
      uses linecard-ios-xe-oper:linecard;
    }
  }
}
