/*
 * Generated by confdc --mib2yang-std
 * Source: mgmt/dmi/model/mib/src/patched/DOCS-IF3-MIB.mib
 */
/*
 * This YANG module has been generated by smidump 0.5.0:
 *
 *      smidump -f yang DOCS-IF3-MIB
 *
 * Do not edit. Edit the source file instead!
 */

module DOCS-IF3-MIB {

  namespace "urn:ietf:params:xml:ns:yang:smiv2:DOCS-IF3-MIB";
  prefix DOCS-IF3-MIB;

  import CLAB-TOPO-MIB {
    prefix "clab-topo";
  }

  import DOCS-CABLE-DEVICE-MIB {
    prefix "docs-cable";
  }

  import DOCS-IF-MIB {
    prefix "docs-if";
  }

  import IF-MIB {
    prefix "if-mib";
  }

  import INET-ADDRESS-MIB {
    prefix "inet-address";
  }

  import SNMP-FRAMEWORK-MIB {
    prefix "snmp-framework";
  }

  import SNMP-TARGET-MIB {
    prefix "snmp-target";
  }

  import SNMPv2-MIB {
    prefix "snmpv2-mib";
  }

  import SNMPv2-TC {
    prefix "snmpv2-tc";
  }

  import ietf-yang-smiv2 {
    prefix "smiv2";
  }

  import ietf-yang-types {
    prefix "yang";
  }

  organization
   "Cable Television Laboratories, Inc.";

  contact
   "
    Postal: Cable Television Laboratories, Inc.
    858 Coal Creek Circle
    Louisville, Colorado 80027-9750
    U.S.A.
    Phone: +1 303-661-9100
    Fax:   +1 303-661-9199
    E-mail: mibs@cablelabs.com";

  description
   "This MIB module contains the management objects for the
    management of DOCSIS 3.0 features, primarily channel bonding,
    interface topology and enhanced signal quality monitoring.
    Copyright 1999-2016 Cable Television Laboratories, Inc.
    All rights reserved.";

  revision 2016-05-05 {
    description
     "Revised Version includes ECNs
      CCAP-OSSIv3.1-N-1509-1 and OSSIv3.0-N-15.1398-1;
      supersedes CCAP-OSSIv3.1-N-16.1431-1";
  }

  revision 2015-05-20 {
    description
     "Revised Version includes ECN
      CM-OSSIv3.1-N-15.1309-1";
  }

  revision 2015-04-08 {
    description
     "Revised Version includes ECN
      CM-OSSIv3.1-N-14.1222-3";
  }

  revision 2013-11-19 {
    description
     "Revised Version includes ECN 
      OSSIv3.0-N-13.1119-3 and published as I22";
  }

  revision 2013-04-04 {
    description
     "Revised Version includes ECNs
      OSSIv3.0-N-12.1083 and OSSIv3.0-N-13.1093
      and published as I21";
  }

  revision 2012-11-13 {
    description
     "Revised Version includes ECN
      OSSIv3.0-N-12.1079-4 and published as I20";
  }

  revision 2012-08-09 {
    description
     "Revised Version includes ECN
      OSSIv3.0-N-12.1064-3 and published as I19";
  }

  revision 2011-02-10 {
    description
     "Revised Version includes ECNs
      OSSIv3.0-N-10.0962-5 and OSSIv3.0-N-10.0984-1
      and published as I14";
  }

  revision 2010-06-11 {
    description
     "Revised Version includes ECN
      OSSIv3.0-N-10.0906-2
      and published as I12";
  }

  revision 2010-01-15 {
    description
     "Revised Version includes ECNs
      OSSIv3.0-N-09.0871-4
      OSSIv3.0-N-09.0872-4
      OSSIv3.0-N-09.0881-3
      and published as I11";
  }

  revision 2009-05-29 {
    description
     "Revised Version includes ECN
      OSSIv3.0-N-09.0775-3
      and published as I09";
  }

  revision 2009-01-21 {
    description
     "Revised Version includes ECNs
      OSSIv3.0-N-08.0651-3
      OSSIv3.0-N-08.0700-4
      and published as I08";
  }

  revision 2008-05-22 {
    description
     "Revised Version includes ECN OSSIv3.0-N-08.0645-4
      and published as I07";
  }

  revision 2008-02-15 {
    description
     "Revised Version includes ECN OSSIv3.0-N-07.0605-1
      and published as I06";
  }

  revision 2007-12-06 {
    description
     "Revised Version includes ECNs
      OSSIv3.0-N-07.0522-6
      OSSIv3.0-N-07.0554-4
      and published as I05";
  }

  revision 2007-08-03 {
    description
     "Revised Version includes ECNs
      OSSIv3.0-N-07.0481-2
      OSSIv3.0-N-07.0480-3
      and published as I04";
  }

  revision 2007-05-18 {
    description
     "Revised Version includes ECNs
      OSSIv3.0-N-07.0447-2
      OSSIv3.0-N-07.0446-4
      OSSIv3.0-N-07.0445-3
      OSSIv3.0-N-07.0441-4
      OSSIv3.0-N-07.0422-5
      OSSIv3.0-N-07.0413-3
      OSSIv3.0-N-07.0410-4
      OSSIv3.0-N-07.0392-1
      OSSIv3.0-N-07.0384-1
      OSSIv3.0-N-06.0357-1
      and published as I03";
  }

  revision 2007-02-23 {
    description
     "Revised Version includes ECN OSSIv3.0-N-06.0357-1
      and published as IO2";
  }

  revision 2006-12-07 {
    description
     "Initial version, published as part of the CableLabs
      OSSIv3.0 specification CM-SP-OSSIv3.0-I01-061207";
  }

  typedef CmRegState {
    type enumeration {
      enum "other" {
        value "1";
      }
      enum "notReady" {
        value "2";
      }
      enum "notSynchronized" {
        value "3";
      }
      enum "phySynchronized" {
        value "4";
      }
      enum "usParametersAcquired" {
        value "5";
      }
      enum "rangingComplete" {
        value "6";
      }
      enum "dhcpv4Complete" {
        value "7";
      }
      enum "todEstablished" {
        value "8";
      }
      enum "securityEstablished" {
        value "9";
      }
      enum "configFileDownloadComplete" {
        value "10";
      }
      enum "registrationComplete" {
        value "11";
      }
      enum "operational" {
        value "12";
      }
      enum "accessDenied" {
        value "13";
      }
      enum "eaeInProgress" {
        value "14";
      }
      enum "dhcpv4InProgress" {
        value "15";
      }
      enum "dhcpv6InProgress" {
        value "16";
      }
      enum "dhcpv6Complete" {
        value "17";
      }
      enum "registrationInProgress" {
        value "18";
      }
      enum "bpiInit" {
        value "19";
      }
      enum "forwardingDisabled" {
        value "20";
      }
      enum "dsTopologyResolutionInProgress" {
        value "21";
      }
      enum "rangingInProgress" {
        value "22";
      }
      enum "rfMuteAll" {
        value "23";
      }
    }
    description
     "This data type defines the CM connectivity state as reported
      by the CM.
      The enumerated values associated with the CmRegState are:
      'other'
       indicates any state not described below.
      'notReady'
       indicates that the CM has not started the registration process
       yet.
      'notSynchronized'
       indicates that the CM has not initiated or completed the
       synchronization of the downstream physical layer
      'phySynchronized'
       indicates that the CM has completed the synchronization of
       the downstream physical layer
      'dsTopologyResolutionInProgress'
       indicates that the CM is attempting to determine its MD-DS-SG
      'usParametersAcquired'
       indicates that the CM has completed the upstream parameters
       acquisition or have completed the downstream and upstream
       service groups resolution, whether the CM is registering in
       a pre-3.0 or a 3.0 CMTS.
      'rangingInProgress'
       indicates that the CM has initiated the ranging process. 
      'rangingComplete'
       indicates that the CM has completed initial ranging and
       received a Ranging Status of success from the CMTS in the
       RNG-RSP message.
      'eaeInProgress'
       indicates that the CM has sent an Auth Info message for EAE.
      'dhcpv4InProgress'
       indicates that the CM has sent a DHCPv4 DISCOVER to gain 
       IP connectivity.
      'dhcpv6InProgress'
       indicates that the CM has sent an DHCPv6 Solicit message.
      'dhcpv4Complete'
       indicates that the CM has received a DHCPv4 ACK message from
       the CMTS.
      'dhcpv6Complete'
       indicates that the CM has received a DHCPv6 Reply message from
       the CMTS.
      'todEstablished'
       indicates that the CM has successfully acquired time of day.
       If the ToD is acquired after the CM is operational, this
       value should not be reported.
      'securityEstablished'
       indicates that the CM has successfully completed the BPI
       initialization process.
      'configFileDownloadComplete'
       indicates that the CM has completed the config file download
       process.
      'registrationInProgress'
       indicates that the CM has sent a Registration Request
       (REG-REQ or REG-REQ-MP)
      'registrationComplete'
       indicates that the CM has successfully completed the
       Registration process with the CMTS.
      'accessDenied'
       indicates that the CM has received a registration aborted
       notification from the CMTS
      'operational'
       indicates that the CM has completed all necessary
       initialization steps and is operational.
      'bpiInit'
       indicates that the CM has started the BPI initialization
       process as indicated in the CM config file. If the CM already
       performed EAE, this state is skipped by the CM.
      'forwardingDisabled'
       indicates that the registration process was completed, but 
       the network access option in the received configuration file
       prohibits forwarding.
      'rfMuteAll'
       indicates that the CM is instructed to mute all channels 
       in the CM-CTRL-REQ message from CMTS.";
    reference
     "DOCSIS 3.0 MAC and Upper Layer Protocols Interface
      Specification CM-SP-MULPIv3.0-I08-080522, Cable Modem -
      CMTS Interaction section.";
  }

  typedef CmtsCmRegState {
    type enumeration {
      enum "other" {
        value "1";
      }
      enum "initialRanging" {
        value "2";
      }
      enum "rangingAutoAdjComplete" {
        value "4";
      }
      enum "dhcpv4Complete" {
        value "5";
      }
      enum "registrationComplete" {
        value "6";
      }
      enum "operational" {
        value "8";
      }
      enum "bpiInit" {
        value "9";
      }
      enum "startEae" {
        value "10";
      }
      enum "startDhcpv4" {
        value "11";
      }
      enum "startDhcpv6" {
        value "12";
      }
      enum "dhcpv6Complete" {
        value "13";
      }
      enum "startConfigFileDownload" {
        value "14";
      }
      enum "configFileDownloadComplete" {
        value "15";
      }
      enum "startRegistration" {
        value "16";
      }
      enum "forwardingDisabled" {
        value "17";
      }
      enum "rfMuteAll" {
        value "18";
      }
    }
    description
     "This data type defines the CM connectivity states as reported
      by the CMTS.
      The enumerated values associated with the CmtsCmRegState are:
      
      'other'
       indicates any state not described below.
      'initialRanging'
       indicates that the CMTS has received an Initial Ranging
       Request message from the CM, and the ranging process is not yet
       complete.
      'rangingAutoAdjComplete'
       indicates that the CM has completed initial ranging and the
       CMTS sends  a Ranging Status of success in the RNG-RSP.
      'startEae'
       indicates that the CMTS has received an Auth Info message for
       EAE from the CM.
      'startDhcpv4'
       indicates that the CMTS has received a DHCPv4 DISCOVER message
       from the CM.
      'startDhcpv6'
       indicates that the CMTS has received a DHCPv6 Solicit message
       from the CM.
      'dhcpv4Complete'
       indicates that the CMTS has sent a DHCPv4 ACK message to the
       CM.
      'dhcpv6Complete'
       indicates that the CMTS has sent a DHCPv6 Reply message to the
       CM.
      'startConfigFileDownload'
       indicates that the CM has started the config file download.
       If the TFTP Proxy feature is not enabled, the CMTS may not
       report this state.
      'configFileDownloadComplete'
       indicates that the CM has completed the config file download
       process.  If the TFTP Proxy feature is not enabled, the CMTS
       is not required to report this state.
      'startRegistration'
       indicates that the CMTS has received a Registration
       Request (REG-REQ or REG-REQ-MP) from the CM.
      'registrationComplete'
       indicates that the CMTS has received a Registration Acknowledge
       (REG-ACK) with a confirmation code of okay/success.
      'operational'
       indicates that the CM has completed all necessary
       initialization steps and is operational.
      'bpiInit'
       indicates that the CMTS has received an Auth Info or Auth
       Request message as part of BPI Initialization.
      'forwardingDisabled'
       indicates that the registration process was completed, but 
       the network access option in the received configuration 
       file prohibits forwarding.
      'rfMuteAll'
       indicates that the CM is instructed to mute all channels 
       in the CM-CTRL-REQ message from CMTS.";
    reference
     "DOCSIS 3.0 MAC and Upper Layer Protocols Interface
      Specification CM-SP-MULPIv3.0-I08-080522, Cable Modem -
      CMTS Interaction section.";
  }

  typedef ScdmaSelectionString {
    type binary {
      length "0|16";
    }
    description
     "This data type represents the S-CDMA selection string
      for active codes used with Selectable Active Codes Mode 2.
      A 128-bit string indicating which codes are active.
      The first element in the string corresponds to code 0
      (the all-ones code), and the last element in the string
      corresponds to code 127.  A '1' element in the string
      indicates an active code, and a '0' indicates an unused
      code. A zero-length string is returned for an unknown
      or non-applicable value.";
    reference
     "DOCSIS 3.0 Physical Layer Specification
      CM-SP-PHYv3.0-I05-070803, Mini-slot Numbering Parameters
      in UCD section.";
  }

  typedef AmplitudeData {
    type binary {
      length "0|2..4116";
    }
    description
     "This data type represents a sequence of spectral amplitudes.
      Each spectral amplitude value corresponds to a bin.
      The format of the bin measurement is as follows.
      Sequence of:
        4 bytes: ChCenterFreq
                 The center frequency of the upstream channel.
        4 bytes: FreqSpan
                 The width in Hz of the band across which the spectral
                 amplitudes characterizing the channel are measured.
        4 bytes: NumberOfBins
                 The number of data points or bins that compose the
                 spectral data. The leftmost bin corresponds to the
                 lower band edge, the rightmost bin corresponds to the
                 upper band edge, and the middle bin center is aligned
                 with the center frequency of the analysis span.
        4 bytes: BinSpacing
                 The frequency separation between adjacent bin
                 centers. It is derived from the frequency span and
                 the number of bins or data points.
                 The bin spacing is computed as:
      
                          BinSpacing = FrequencySpan/(NumberOfBins -1)
      
                 The larger the number of bins the finer the
                 resolution.
        4 bytes: ResolutionBW
                 The resolution bandwidth or equivalent noise
                 bandwidth of each bin. If spectral windowing is used
                 (based on vendor implementation), the bin spacing and
                 resolution bandwidth would not generally be the same.
        n bytes: Amplitude (2 bytes * NumberOfBins)
                 A sequence of two byte elements. Each element
                 represents the spectral amplitudes in relation to the
                 expected received signal power of a bin, in units of
                 0.01dB. That is, a test CMTS input signal with
                 square-root raised-cosine spectrum, bandwidth equal
                 to the expected received signal bandwidth, and power
                 equal to the expected received signal power, which
                 is present for the entire spectrum sampling period,
                 will exhibit a spectrum measurement of 0 dB average
                 power in each bin of the signal passband.
                 Each bin element amplitude value format is 2's
                 complement which provides a range of -327.68 dB to
                 327.67 dB amplitude value for the bin measurement.";
  }

  typedef SpectrumAnalysisWindowFunction {
    type enumeration {
      enum "other" {
        value "0";
      }
      enum "hann" {
        value "1";
      }
      enum "blackmanHarris" {
        value "2";
      }
      enum "rectangular" {
        value "3";
      }
      enum "hamming" {
        value "4";
      }
      enum "flatTop" {
        value "5";
      }
      enum "gaussian" {
        value "6";
      }
      enum "chebyshev" {
        value "7";
      }
    }
    description
     "This object controls the windowing function which will be used 
      when performing the discrete fourier transform for the analysis.  
      Note that all window functions may not be supported by all 
      devices.  If an attempt is made to set the object to an 
      unsupported window function, an error of inconsistentValue will
      be returned.";
    reference
     "Harris, Fredric J. (Jan 1978). 'On the use of Windows for 
      Harmonic Analysis with the Discrete Fourier Transform'. 
      Proceedings of the IEEE, Vol 66, Issue 1, Jan 1978 
      doi:10.1109/PROC.1978.10837";
  }

  typedef Tlv8 {
    type binary {
      length "0|2..255";
    }
    description
     "This data type represents a single TLV encoding.
      This first octet represents the Type of the TLV.
      The second octet represents an unsigned 8-bit Length of the
      subsequent Value part of the TLV.  The remaining octets
      represent the value. The Value could be an atomic value or a
      sequence of one or more sub-TLVs.";
    reference
     "DOCSIS 3.0 MAC and Upper Layer Protocols Interface
      Specification CM-SP-MULPIv3.0-I08-080522, Common Radio
      Frequency Interface Encodings Annex.";
  }

  typedef ChId {
    type uint32 {
      range "0..255";
    }
    description
     "This data type is an 8-bit number that represents a provisioned
      Downstream Channel ID (DCID) or a provisioned Upstream Channel
      ID (UCID). A Channel Id is unique per direction within a MAC
      Domain. The value zero is reserved for use when the channel ID
      is unknown.";
    reference
     "DOCSIS 3.0 MAC and Upper Layer Protocols Interface
      Specification CM-SP-MULPIv3.0-I08-080522, Upstream Channel
      Descriptor (UCD) section.";
    smiv2:display-hint "d";
  }

  typedef ChSetId {
    type uint32;
    description
     "This data type is a CMTS-derived unique number within a MAC
      Domain used to reference a Channel Set within the CMTS.
      Values in the range of 1 to 255 define a single-channel Channel
      Set and correspond to either the Downstream Channel ID (DCID)
      or an Upstream Channel ID (UCID) of that channel.
      Values greater than 255 indicate a Channel Set consisting of two
      or more channels in the same direction within the MAC Domain.
      The value zero is reserved for use when the Channel Set is
      unknown.";
    reference
     "DOCSIS 3.0 MAC and Upper Layer Protocols Interface
      Specification CM-SP-MULPIv3.0-I08-080522, Channel
      Bonding section.";
    smiv2:display-hint "d";
  }

  typedef ChannelList {
    type string;
    description
     "This data type represents a unique set of channel IDs in
      either the upstream or the downstream direction.  Each octet
      represents a UCID or DCID depending on the direction of the
      channels within the list.  The CMTS must ensure that this
      combination of channels is unique per direction within the MAC
      Domain.
      
      In order to facilitate Channel ID combinatorial uniqueness
      across all channel lists, a query to retrieve the value of
      an attribute of this type, returns the set of channels in
      the channel list in ascending order of Channel Ids.";
    smiv2:display-hint "1d,";
  }

  typedef AttributeMask {
    type bits {
      bit bonding {
        position "0";
      }
      bit lowLatency {
        position "1";
      }
      bit highAvailability {
        position "2";
      }
      bit reservedBit3 {
        position "3";
      }
      bit reservedBit4 {
        position "4";
      }
      bit reservedBit5 {
        position "5";
      }
      bit reservedBit6 {
        position "6";
      }
      bit reservedBit7 {
        position "7";
      }
      bit reservedBit8 {
        position "8";
      }
      bit reservedBit9 {
        position "9";
      }
      bit reservedBit10 {
        position "10";
      }
      bit reservedBit11 {
        position "11";
      }
      bit reservedBit12 {
        position "12";
      }
      bit reservedBit13 {
        position "13";
      }
      bit reservedBit14 {
        position "14";
      }
      bit reservedBit15 {
        position "15";
      }
      bit reservedBit16 {
        position "16";
      }
      bit reservedBit17 {
        position "17";
      }
      bit reservedBit18 {
        position "18";
      }
      bit reservedBit19 {
        position "19";
      }
      bit reservedBit20 {
        position "20";
      }
      bit reservedBit21 {
        position "21";
      }
      bit reservedBit22 {
        position "22";
      }
      bit reservedBit23 {
        position "23";
      }
      bit reservedBit24 {
        position "24";
      }
      bit reservedBit25 {
        position "25";
      }
      bit reservedBit26 {
        position "26";
      }
      bit reservedBit27 {
        position "27";
      }
      bit reservedBit28 {
        position "28";
      }
      bit reservedBit29 {
        position "29";
      }
      bit reservedBit30 {
        position "30";
      }
      bit reservedBit31 {
        position "31";
      }
    }
    description
     "This data type consists of a sequence of 32-bit positions used
      to select the bonding group or the channel to which a service
      flow is assigned. DOCSIS defines three types of Attribute Masks
      for which this type applies: The Provisionied Attribute Mask
      that is configured to a Bonding Group or a single-channel,
      whereas the Required Attribute and the Forbidden Attribute
      Mask are part of the Service Flow QOS Parameter Set to be
      matched with the Provisioned Attribute Mask of CMTS-configured
      Bonding Groups or single-channels. DOCSIS reserves the
      assignment of the meaning of the first 8 bit positions
      (left to right) as follows:
          Bit 0: 'bonding'
          Bit 1: 'lowLatency'
          Bit 2: 'highAvailability'
          Bit positions 3-15 are reserved.
      
      Bit positions 16-31 are freely assigned by operators to
      represent their own constraints on the channel(s) selection
      for a particular service flow.";
    reference
     "DOCSIS 3.0 MAC and Upper Layer Protocols Interface
      Specification CM-SP-MULPIv3.0-I08-080522, Service Flow
      Assignment section.";
  }

  typedef AttrAggrRuleMask {
    type binary {
      length "4";
    }
    description
     "This data type represents a sequence of 32-bit positions that
      defines logical (e.g., AND, OR) operations to match against the
      channel list Provisioned Mask and Service Flow Required Mask
      bit positions when the CMTS is determining the service flow
      for assignment to a bonding group not configured by the
      management system.";
    reference
     "DOCSIS 3.0 MAC and Upper Layer Protocols Interface
      Specification CM-SP-MULPIv3.0-I08-080522, Service Flow
      Assignment section.";
  }

  typedef RcpId {
    type binary {
      length "5";
    }
    description
     "This data type defines a 'Receive Channel Profile Identifier'
      (RCP-ID). An RCP-ID consists of 5-octet length string where the
      first 3-bytes (from left to right corresponds to the
      Organizational Unique ID (OUI) followed by a two-byte
      vendor-maintained identifier to represent multiple versions or
      models of RCP-IDs.";
    reference
     "DOCSIS 3.0 MAC and Upper Layer Protocols Interface
      Specification CM-SP-MULPIv3.0-I08-080522, RCP-ID section in
      the Common Radio Frequency Interface Encodings Annex.";
  }

  typedef Dsid {
    type uint32 {
      range "0..1048575";
    }
    description
     "This data type defines the 20-bit Downstream Service Identifier
      (DSID) used by the CM for downstream resequencing, filtering,
      and forwarding. The value zero is reserved for use when the
      DSID is unknown or does not apply.";
    reference
     "DOCSIS 3.0 MAC and Upper Layer Protocols Interface
      Specification CM-SP-MULPIv3.0-I08-080522, DSID Definition
      section.";
    smiv2:display-hint "d";
  }

  typedef RangingState {
    type enumeration {
      enum "unknown" {
        value "0";
      }
      enum "other" {
        value "1";
      }
      enum "aborted" {
        value "2";
      }
      enum "retriesExceeded" {
        value "3";
      }
      enum "success" {
        value "4";
      }
      enum "continue" {
        value "5";
      }
      enum "timeoutT4" {
        value "6";
      }
    }
    description
     "This data type defines the CM ranging state as reported
      by the CMTS.
      The enumerated values associated with the RangingState are:
      
      'other'
       indicates any state not described below.
      'aborted'
       indicates that the CMTS has sent a ranging abort.
      'retriesExceeded'
       indicates that the CM ranging retry limit has exceeded. 
      'success'
       indicates that the CMTS has sent a ranging success in the
       ranging response.
      'continue'
       indicates that the CMTS has sent a ranging continue in the
       ranging response.
      'timeoutT4'
       indicates that the T4 timer expired on the CM.";
    reference
     "DOCSIS 3.0 MAC and Upper Layer Protocols Interface
      Specification CM-SP-MULPIv3.0-I08-080522, Cable Modem - 
      CMTS Interaction section.";
  }

  typedef IfDirection {
    type enumeration {
      enum "downstream" {
        value "1";
      }
      enum "upstream" {
        value "2";
      }
    }
    description
     "Indicates a direction on an RF MAC interface.
      
      The value downstream(1) is from Cable Modem
      Termination System to Cable Modem.
      
      The value upstream(2) is from Cable Modem to
      Cable Modem Termination System.";
  }


  container DOCS-IF3-MIB {
    config false;

    container docsIf3CmCapabilities {
      smiv2:oid "1.3.6.1.4.1.4491.2.1.20.1.21";

      leaf docsIf3CmCapabilitiesReq {
        type DOCS-IF3-MIB:Tlv8;
        description
         "This attribute contains the TLV encoding for TLV-5
          sent in a REG-REQ.  The first byte of this encoding is
          expected to be '05'H.";
        reference
         "DOCSIS 3.0 MAC and Upper Layer Protocols Interface
          Specification CM-SP-MULPIv3.0-I08-080522, Modem Capabilities
          Encoding section in the Common Radio Frequency Interface
          Encodings Annex.";
        smiv2:max-access "read-only";
        smiv2:oid "1.3.6.1.4.1.4491.2.1.20.1.21.1";
      }

      leaf docsIf3CmCapabilitiesRsp {
        type DOCS-IF3-MIB:Tlv8;
        description
         "This attribute contains the TLV encoding for TLV-5
          received in a REG-RSP.
          The first byte of this encoding is expected to be '05'H.";
        reference
         "DOCSIS 3.0 MAC and Upper Layer Protocols Interface
          Specification CM-SP-MULPIv3.0-I08-080522, Modem Capabilities
          Encoding section in the Common Radio Frequency Interface
          Encodings Annex.";
        smiv2:max-access "read-only";
        smiv2:oid "1.3.6.1.4.1.4491.2.1.20.1.21.2";
      }
    }

    container docsIf3CmtsCmCtrl {
      smiv2:oid "1.3.6.1.4.1.4491.2.1.20.1.27";

      leaf docsIf3CmtsCmCtrlCmdMacAddr {
        type yang:mac-address;
        description
         "This attribute represents the MAC Address of the CM which the 
          CMTS is instructed to send the CM-CTRL-REQ message.";
        reference
         "DOCSIS 3.0 MAC and Upper Layer Protocols Interface
          Specification CM-SP-MULPIv3.0-I08-080522,
          Media Access Control Specification section.";
        smiv2:defval "'000000000000'H";
        smiv2:max-access "read-write";
        smiv2:oid "1.3.6.1.4.1.4491.2.1.20.1.27.1";
      }

      leaf docsIf3CmtsCmCtrlCmdMuteUsChId {
        type DOCS-IF3-MIB:ChId;
        description
         "This attribute represents the Upstream Channel ID (UCID) to 
          mute or unmute.  A value of zero indicates all upstream 
          channels.  This attribute is only applicable when the 
          docsIf3CmtsCmCtrlCmdCommit attribute is set to 
          'mute'.";
        reference
         "DOCSIS 3.0 MAC and Upper Layer Protocols Interface
          Specification CM-SP-MULPIv3.0-I08-080522, 
          Media Access Control Specification section.";
        smiv2:defval "0";
        smiv2:max-access "read-write";
        smiv2:oid "1.3.6.1.4.1.4491.2.1.20.1.27.2";
      }

      leaf docsIf3CmtsCmCtrlCmdMuteInterval {
        type uint32;
        units "milliseconds";
        description
         "This attribute represents the length of time that the mute 
          operation is in effect.  This attribute is only applicable 
          when the docsIf3CmtsCmCtrlCmdCommit attribute is set to 
          'mute'.  A value of 0 is an indication to unmute the
          channel referenced by the docsIf3CmtsCmCtrlCmdMuteUsChId
          attribute while a value of 0xFFFFFFFF is used to mute
          the channel referenced by the docsIf3CmtsCmCtrlCmdMuteUsChId
          attribute indefinitely.";
        reference
         "DOCSIS 3.0 MAC and Upper Layer Protocols Interface
          Specification CM-SP-MULPIv3.0-I08-080522, 
          Media Access Control Specification section.";
        smiv2:defval "1";
        smiv2:max-access "read-write";
        smiv2:oid "1.3.6.1.4.1.4491.2.1.20.1.27.3";
      }

      leaf docsIf3CmtsCmCtrlCmdDisableForwarding {
        type boolean;
        description
         "When set to 'true', this attribute disables data forwarding 
          to the CMCI when the docsIf3CmtsCmCtrlCmdCommit attribute is
          set to 'disableForwarding'. 
          When set to 'false', this attribute enables data forwarding
          to the CMCI when the docsIf3CmtsCmCtrlCmdCommit attribute is
          set to 'disableForwarding'. 
          This attribute is only applicable when the 
          docsIf3CmtsCmCtrlCmdCommit attribute is set to 
          'disableForwarding'.";
        reference
         "DOCSIS 3.0 MAC and Upper Layer Protocols Interface
          Specification CM-SP-MULPIv3.0-I08-080522, 
          Media Access Control Specification section.";
        smiv2:defval "false";
        smiv2:max-access "read-write";
        smiv2:oid "1.3.6.1.4.1.4491.2.1.20.1.27.4";
      }

      leaf docsIf3CmtsCmCtrlCmdCommit {
        type enumeration {
          enum "mute" {
            value "1";
          }
          enum "cmReinit" {
            value "2";
          }
          enum "disableForwarding" {
            value "3";
          }
        }
        description
         "This attribute indicates the type of command for the 
          CMTS to trigger in the CM-CTRL-REQ message.
          This attribute will return the value of the last operation 
          performed or the default value if no operation has been 
          performed.";
        reference
         "DOCSIS 3.0 MAC and Upper Layer Protocols Interface
          Specification CM-SP-MULPIv3.0-I08-080522, 
          Media Access Control Specification section.";
        smiv2:defval "mute";
        smiv2:max-access "read-write";
        smiv2:oid "1.3.6.1.4.1.4491.2.1.20.1.27.5";
      }
    }

    container docsIf3CmEnergyMgtCfg {
      smiv2:oid "1.3.6.1.4.1.4491.2.1.20.1.32";

      leaf docsIf3CmEnergyMgtCfgFeatureEnabled {
        type bits {
          bit em1x1Feature {
            position "0";
          }
        }
        description
         "This attribute indicates which energy savings features have
          been enabled in the Cable Modem. The CM enables use of Energy
          Management Features only if both the Energy Management Feature
          Control TLV and Energy Management Modem Capability Response from
          the CMTS indicate that the feature is enabled.  If bit 0 is set, 
          the Energy Management 1x1 Mode feature is enabled.";
        reference
         "DOCSIS 3.0 MAC and Upper Layer Protocols Interface
          Specification CM-SP-MULPIv3.0-I20-121113,
          Energy Management Features section.";
        smiv2:max-access "read-only";
        smiv2:oid "1.3.6.1.4.1.4491.2.1.20.1.32.1";
      }

      leaf docsIf3CmEnergyMgtCfgCyclePeriod {
        type uint32 {
          range "0..65535";
        }
        units "seconds";
        description
         "This attribute specifies a minimum time period (in seconds) 
          that must elapse between EM-REQ transactions in certain 
          situations: 
          - In the case of Energy Management 1x1 Mode, this attribute
            sets the minimum cycle time that a CM will use for sending
            requests to enter Energy Management 1x1 Mode.
          
          - In the case that the CM fails to receive an EM-RSP message
            after the maximum number of retries, this attribute sets 
            the minimum amount of time to elapse before the CM can 
            attempt another EM-REQ transaction.";
        reference
         "DOCSIS 3.0 MAC and Upper Layer Protocols Interface
          Specification CM-SP-MULPIv3.0-I20-121113, 
          Energy Management Cycle Period section.";
        smiv2:defval "900";
        smiv2:max-access "read-only";
        smiv2:oid "1.3.6.1.4.1.4491.2.1.20.1.32.2";
      }
    }

    container docsIf3CmSpectrumAnalysisCtrlCmd {
      smiv2:oid "1.3.6.1.4.1.4491.2.1.20.1.34";

      leaf docsIf3CmSpectrumAnalysisCtrlCmdEnable {
        type boolean;
        description
         "This attribute is used to enable or disable the spectrum 
          analyzer feature. Setting this attribute to true triggers the CM
          to initiate measurements for the spectrum analyzer feature based
          on the other configuration attributes for the feature. By 
          default, the feature is disabled unless explicitly enabled.
          
          Note that the feature may be disabled by the system under 
          certain circumstances if the spectrum analyzer would affect 
          critical services. In such a case, the attribute will return
          'false' when read, and will reject sets to 'true' with an 
          error. Once the feature is enabled, any Set operation on 
          the docsIf3CmSpectrumAnalysisCtrlCmd MIB group might not 
          be effective until the feature is re-enabled again.";
        smiv2:defval "false";
        smiv2:max-access "read-write";
        smiv2:oid "1.3.6.1.4.1.4491.2.1.20.1.34.1";
      }

      leaf docsIf3CmSpectrumAnalysisCtrlCmdInactivityTimeout {
        type int32 {
          range "0..86400";
        }
        units "seconds";
        description
         "This attribute controls the length of time after the last 
          spectrum analysis measurement before the feature is 
          automatically disabled. If set to a value of 0, the feature will
          remain enabled until it is explicitly disabled.";
        smiv2:defval "300";
        smiv2:max-access "read-write";
        smiv2:oid "1.3.6.1.4.1.4491.2.1.20.1.34.2";
      }

      leaf docsIf3CmSpectrumAnalysisCtrlCmdFirstSegmentCenterFrequency {
        type uint32;
        units "Hz";
        description
         "This attribute controls the center frequency of the
          first segment for the spectrum analysis measurement.
          The frequency bins for this segment lie symmetrically
          to the left and right of this center frequency.  
          
          If the number of bins in a segment is odd, the segment
          center frequency lies directly on the center bin.  
          
          If the number of bins in a segment is even, the segment
          center frequency lies halfway between two bins.
          
          Changing the value of this attribute may result in 
          changes to the docsIf3CmSpectrumAnalysisMeasTable.
          Note that if this attribute is set to an invalid value, 
          the device may return an error, or may adjust the 
          value of the attribute to the closest valid value.";
        smiv2:defval "93000000";
        smiv2:max-access "read-write";
        smiv2:oid "1.3.6.1.4.1.4491.2.1.20.1.34.3";
      }

      leaf docsIf3CmSpectrumAnalysisCtrlCmdLastSegmentCenterFrequency {
        type uint32;
        units "Hz";
        description
         "This attribute controls the center frequency of
          the last segment of the spectrum analysis measurement.
          
          The frequency bins for this segment lie symmetrically
          to the left and right of this center frequency.  
          If the number of bins in a segment is odd, the segment
          center frequency lies directly on the center bin.  
          If the number of bins in a segment is even, the segment
          center frequency lies halfway between two bins.
          
          The value of the LastSegmentCenterFrequency attribute 
          should be equal to the FirstSegmentCenterFrequency 
          plus and integer number of segment spans as determined 
          by the SegmentFrequencySpan.
          
          Changing the value of this attribute may result in changes
          to the docsIf3CmSpectrumAnalysisMeasTable.
          
          Note that if this attribute is set to an invalid value, 
          the device may return an error, or may adjust the 
          value of the attribute to the closest valid value.";
        smiv2:defval "993000000";
        smiv2:max-access "read-write";
        smiv2:oid "1.3.6.1.4.1.4491.2.1.20.1.34.4";
      }

      leaf docsIf3CmSpectrumAnalysisCtrlCmdSegmentFrequencySpan {
        type uint32 {
          range "1000000..900000000";
        }
        units "Hz";
        description
         "This attribute controls the frequency span of each 
          segment (instance) in the docsIf3CmSpectrumAnalysisMeasTable.  
          
          If set to a value of 0, then a default span will be
          chosen based on the hardware capabilities of the 
          device. Segments are contiguous from the 
          FirstSegementCenterFrequency to the 
          LastSegmentCenterFrequency and the center frequency 
          for each successive segment is incremented by the 
          SegmentFequencySpan. 
          The number of segments is (LastSegmentCenterFrequency -
          FirstSegmentCenterFrequency)/SegmentFrequencySpan + 1. 
          A segment is equivalent to an instance in the 
          docsIf3CmSpectrumAnalysisMeasTable. The chosen 
          SegmentFrequencySpan affects the number of entries in 
          the docsIf3CmSpectrumAnalysisMeasTable. A more granular 
          SegmentFrequencySpan may adversely affect the amount of 
          time needed to query the table entries in addition to 
          possibly increasing the acquisition time.
          
          Changing the value of this attribute may result in 
          changes to the docsIf3CmSpectrumAnalysisMeasTable.
          
          Note that if this attribute is set to an invalid value,
          the device may return an error, or may adjust the value 
          of the object to the closest valid value.";
        smiv2:defval "7500000";
        smiv2:max-access "read-write";
        smiv2:oid "1.3.6.1.4.1.4491.2.1.20.1.34.5";
      }

      leaf docsIf3CmSpectrumAnalysisCtrlCmdNumBinsPerSegment {
        type uint32 {
          range "2..2048";
        }
        units "bins-per-segment";
        description
         "This attribute controls the number of bins collected 
          by the measurement performed for each segment (instance) 
          in the docsIf3CmSpectrumAnalysisMeasTable.  
          
          Note that if this attribute is set to an invalid value, 
          the device may return an error, or may adjust the value
          of the attribute to the closest valid value.";
        smiv2:defval "256";
        smiv2:max-access "read-write";
        smiv2:oid "1.3.6.1.4.1.4491.2.1.20.1.34.6";
      }

      leaf docsIf3CmSpectrumAnalysisCtrlCmdEquivalentNoiseBandwidth {
        type uint32 {
          range "50..500";
        }
        units "hundredthsbin";
        description
         "This attribute allows the user to request an equivalent 
          noise bandwidth for the resolution bandwidth filter used 
          in the spectrum analysis.  This corresponds to the 
          spectral width of the window function used when performing
          a discrete Fourier transform for the analysis.  
          
          The window function which corresponds to a value written 
          to this object may be obtained by reading the value of the
          WindowFunction attribute.
          
          If an unsupported value is requested, the device may 
          return an error, or choose the closest valid value to the 
          one which is requested.  
          If the closest value is chosen, then a subsequent read of 
          this attribute will return the actual value which is in use.";
        smiv2:defval "150";
        smiv2:max-access "read-write";
        smiv2:oid "1.3.6.1.4.1.4491.2.1.20.1.34.7";
      }

      leaf docsIf3CmSpectrumAnalysisCtrlCmdWindowFunction {
        type DOCS-IF3-MIB:SpectrumAnalysisWindowFunction;
        description
         "This attribute controls or indicates the windowing function 
          which will be used when performing the discrete Fourier
          transform for the analysis.  The WindowFunction and the
          Equivalent Noise Bandwidth are related. If a particular
          WindowFunction is selected, then the EquivalentNoiseBandwidth 
          for the function which is in use, will be reported by the
          EquivalentNoiseBandwidth attribute. Alternatively if
          an EquivalentNoiseBandwidth value is chosen then if a
          WindowFunction function representing that 
          EquivalentNoiseBandwidth is defined in the CM, that value will
          be reported in the WindowFunction MIB object, or a value of 
          'other' will be reported. Use of 'modern' windowing
          functions not yet defined will likely be reported as 'other'.
          
          Note that all window functions may not be supported by all 
          devices.  If an attempt is made to set the object to an 
          unsupported window function, or if writing of the 
          WindowFunction is not supported, an error will be returned.";
        smiv2:max-access "read-write";
        smiv2:oid "1.3.6.1.4.1.4491.2.1.20.1.34.8";
      }

      leaf docsIf3CmSpectrumAnalysisCtrlCmdNumberOfAverages {
        type uint32 {
          range "1..1000";
        }
        description
         "This attribute controls the number of averages 
          that will be performed on spectral bins.  
          The average will be computed using the 'leaky integrator'
          method, where:
            reported bin value = alpha*accumulated bin values + 
                                 (1-alpha)*current bin value.  
          
          Alpha is one minus the reciprocal of the number of averages.
          For example, if N=25, then alpha = 0.96.  
          A value of 1 indicates no averaging.  
          Re-writing the number of averages will restart the averaging
          process.  If there are no accumulated values, the 
          accumulators are made equal to the first measured bin 
          amplitudes.
          
          If an attempt is made to set the attribute to an unsupported 
          number of averages, an error will be returned.";
        smiv2:defval "1";
        smiv2:max-access "read-write";
        smiv2:oid "1.3.6.1.4.1.4491.2.1.20.1.34.9";
      }
    }

    container docsIf3CmStatusTable {
      description
       "This object defines attributes of the CM connectivity
        status. This object provides CM connectivity status
        information of the CM previously available in
        the SNMP table docsIfCmStatusTable.";
      reference
       "RFC 4546";
      smiv2:oid "1.3.6.1.4.1.4491.2.1.20.1.1";

      list docsIf3CmStatusEntry {
        key "ifIndex";
        description
         "The conceptual row of docsIf3CmStatusTable.
          An instance exist for the CM MAC Domain Interface.";
        smiv2:oid "1.3.6.1.4.1.4491.2.1.20.1.1.1";

        leaf ifIndex {
          type leafref {
            path "/if-mib:IF-MIB/if-mib:ifTable/if-mib:ifEntry/if-mib:ifIndex";
          }
        }

        leaf docsIf3CmStatusValue {
          type DOCS-IF3-MIB:CmRegState;
          description
           "This attribute denotes the current CM connectivity
            state. For the case of IP acquisition related states,
            this attribute reflects states for the current CM
            provisioning mode, not the other DHCP process associated
            with dual stack operation.";
          reference
           "DOCSIS 3.0 MAC and Upper Layer Protocols Interface
            Specification CM-SP-MULPIv3.0-I08-080522, Establishing
            IP Connectivity section.";
          smiv2:max-access "read-only";
          smiv2:oid "1.3.6.1.4.1.4491.2.1.20.1.1.1.1";
        }

        leaf docsIf3CmStatusCode {
          type binary {
            length "0|5..7";
          }
          description
           "This attribute denotes the status code for CM as defined
            in the OSSI Specification. The status code consists
            of a single character indicating error groups,
            followed by a two- or three-digit number indicating
            the status condition, followed by a decimal. An example
            of a returned value could be 'T101.0'. The zero-length
            hex string indicates no status code yet registered.";
          reference
           "DOCSIS 3.0 Operations Support System Interface
            Specification CM-SP-OSSIv3.0-I09-090529, Format and Content
            for Event, Syslog, and SNMP Notification Annex.";
          smiv2:max-access "read-only";
          smiv2:oid "1.3.6.1.4.1.4491.2.1.20.1.1.1.2";
        }

        leaf docsIf3CmStatusResets {
          type yang:counter32;
          units "resets";
          description
           "This attribute denotes the number of times the CM reset
            or initialized this interface. Discontinuities
            in the value of this counter can occur at re-initialization
            of the managed system, and at other times as
            indicated by the value of ifCounterDiscontinuityTime
            for the CM MAC Domain interface.";
          reference
           "RFC 2863.";
          smiv2:max-access "read-only";
          smiv2:oid "1.3.6.1.4.1.4491.2.1.20.1.1.1.3";
        }

        leaf docsIf3CmStatusLostSyncs {
          type yang:counter32;
          units "messages";
          description
           "This attribute denotes the number of times the CM lost
            synchronization with the downstream channel. Discontinuities
            in the value of this counter can occur
            at re-initialization of the managed system, and at
            other times as indicated by the value of
            ifCounterDiscontinuityTime for the CM MAC Domain interface.";
          reference
           "RFC 2863.";
          smiv2:max-access "read-only";
          smiv2:oid "1.3.6.1.4.1.4491.2.1.20.1.1.1.4";
        }

        leaf docsIf3CmStatusInvalidMaps {
          type yang:counter32;
          units "maps";
          description
           "This attribute denotes the number of times the CM received
            invalid MAP messages. Discontinuities in the
            value of this counter can occur at re-initialization
            of the managed system, and at other times as indicated
            by the value of ifCounterDiscontinuityTime for
            the CM MAC Domain interface.";
          reference
           "RFC 2863.";
          smiv2:max-access "read-only";
          smiv2:oid "1.3.6.1.4.1.4491.2.1.20.1.1.1.5";
        }

        leaf docsIf3CmStatusInvalidUcds {
          type yang:counter32;
          units "messages";
          description
           "This attribute denotes the number of times the CM received
            invalid UCD messages. Discontinuities in the
            value of this counter can occur at re-initialization
            of the managed system, and at other times as indicated
            by the value of ifCounterDiscontinuityTime for
            the CM MAC Domain interface.";
          reference
           "RFC 2863.";
          smiv2:max-access "read-only";
          smiv2:oid "1.3.6.1.4.1.4491.2.1.20.1.1.1.6";
        }

        leaf docsIf3CmStatusInvalidRangingRsps {
          type yang:counter32;
          units "messages";
          description
           "This attribute denotes the number of times the CM received
            invalid ranging response messages. Discontinuities
            in the value of this counter can occur at re-initialization
            of the managed system, and at other
            times as indicated by the value of ifCounterDiscontinuityTime
            for the CM MAC Domain interface.";
          reference
           "RFC 2863.";
          smiv2:max-access "read-only";
          smiv2:oid "1.3.6.1.4.1.4491.2.1.20.1.1.1.7";
        }

        leaf docsIf3CmStatusInvalidRegRsps {
          type yang:counter32;
          units "messages";
          description
           "This attribute denotes the number of times the CM received
            invalid registration response messages. Discontinuities
            in the value of this counter can occur
            at re-initialization of the managed system, and at
            other times as indicated by the value of
            ifCounterDiscontinuityTime for the CM MAC Domain interface.";
          reference
           "RFC 2863.";
          smiv2:max-access "read-only";
          smiv2:oid "1.3.6.1.4.1.4491.2.1.20.1.1.1.8";
        }

        leaf docsIf3CmStatusT1Timeouts {
          type yang:counter32;
          units "timeouts";
          description
           "This attribute denotes the number of times counter
            T1 expired in the CM. Discontinuities in the value of
            this counter can occur at re-initialization of the
            managed system, and at other times as indicated by the
            value of ifCounterDiscontinuityTime for the CM MAC
            Domain interface.";
          reference
           "RFC 2863.";
          smiv2:max-access "read-only";
          smiv2:oid "1.3.6.1.4.1.4491.2.1.20.1.1.1.9";
        }

        leaf docsIf3CmStatusT2Timeouts {
          type yang:counter32;
          units "timeouts";
          description
           "This attribute denotes the number of times counter
            T2 expired in the CM. Discontinuities in the value of
            this counter can occur at re-initialization of the
            managed system, and at other times as indicated by the
            value of ifCounterDiscontinuityTime for the CM MAC
            Domain interface.";
          reference
           "RFC 2863.";
          smiv2:max-access "read-only";
          smiv2:oid "1.3.6.1.4.1.4491.2.1.20.1.1.1.10";
        }

        leaf docsIf3CmStatusUCCsSuccesses {
          type yang:counter32;
          units "attempts";
          status obsolete;
          description
           "This attribute denotes the number of successful Upstream
            Channel Change transactions. Discontinuities
            in the value of this counter can occur at re-initialization
            of the managed system, and at other times
            as indicated by the value of ifCounterDiscontinuityTime
             for the CM MAC Domain interface.";
          reference
           "RFC 2863.";
          smiv2:max-access "read-only";
          smiv2:oid "1.3.6.1.4.1.4491.2.1.20.1.1.1.11";
        }

        leaf docsIf3CmStatusUCCFails {
          type yang:counter32;
          units "attempts";
          status obsolete;
          description
           "This attribute denotes the number of failed Upstream
            Channel Change transactions. Discontinuities
            in the value of this counter can occur at re-initialization
            of the managed system, and at other times as indicated
            by the value of ifCounterDiscontinuityTime
            for the CM MAC Domain interface.";
          reference
           "RFC 2863.";
          smiv2:max-access "read-only";
          smiv2:oid "1.3.6.1.4.1.4491.2.1.20.1.1.1.12";
        }

        leaf docsIf3CmStatusEnergyMgt1x1OperStatus {
          type boolean;
          description
           "This attribute indicates whether the CM is currently operating
            in Energy Management 1x1 Mode. If this attribute returns 'true', 
            the CM is operating in Energy Management 1x1 Mode.";
          reference
           "DOCSIS 3.0 MAC and Upper Layer Protocols Interface
            Specification CM-SP-MULPIv3.0-I20-121155,
            Energy Management Mode Indicator section.";
          smiv2:max-access "read-only";
          smiv2:oid "1.3.6.1.4.1.4491.2.1.20.1.1.1.13";
        }
      }
    }

    container docsIf3CmStatusUsTable {
      description
       "This object defines PHY and MAC information about
        the CM's upstream channels operating in Multiple Transmit
        Channel (MTC) mode or in a Pre-3.0 DOSCIS transmit
        channel mode. This object provides per-CM Upstream
        channel information previously available in the
        SNMP table docsIfCmStatusTable.";
      smiv2:oid "1.3.6.1.4.1.4491.2.1.20.1.2";

      list docsIf3CmStatusUsEntry {
        key "ifIndex";
        description
         "The conceptual row of docsIf3CmStatusUsTable.
          An instance exist for each of the CM's SC-QAM upstream channels 
          which are configured for data transmission.";
        smiv2:oid "1.3.6.1.4.1.4491.2.1.20.1.2.1";

        leaf ifIndex {
          type leafref {
            path "/if-mib:IF-MIB/if-mib:ifTable/if-mib:ifEntry/if-mib:ifIndex";
          }
        }

        leaf docsIf3CmStatusUsTxPower {
          type docs-if:TenthdBmV;
          units "TenthdBmV";
          description
           "This attribute represents the operational CM transmit
            power for this SC-QAM upstream channel.
            In order for this attribute to provide consistent information 
            under all circumstances, a 3.1 CM will report the average total 
            power for the SC-QAM channel the same as was done for 
            DOCSIS 3.0, regardless of whether it is operating with a 3.1 or 
            a 3.0 CMTS. The value that is reported was referred to as Pr in 
            the DOCSIS 3.0 PHY Spec. This attribute is not applicable for 
            OFDMA channels.";
          smiv2:max-access "read-only";
          smiv2:oid "1.3.6.1.4.1.4491.2.1.20.1.2.1.1";
        }

        leaf docsIf3CmStatusUsT3Timeouts {
          type yang:counter32;
          units "timeouts";
          description
           "This attribute denotes the number of times counter
            T3 expired in the CM for this upstream channel. Discontinuities
            in the value of this counter can occur at
            re-initialization of the managed system, and at other
            times as indicated by the value of ifCounterDiscontinuityTime
            for the associated upstream channel.";
          reference
           "RFC 2863.";
          smiv2:max-access "read-only";
          smiv2:oid "1.3.6.1.4.1.4491.2.1.20.1.2.1.2";
        }

        leaf docsIf3CmStatusUsT4Timeouts {
          type yang:counter32;
          units "timeouts";
          description
           "This attribute denotes the number of times counter
            T4 expired in the CM for this upstream channel. Discontinuities
            in the value of this counter can occur at
            re-initialization of the managed system, and at other
            times as indicated by the value of ifCounterDiscontinuityTime
            for the associated upstream channel.";
          reference
           "RFC 2863.";
          smiv2:max-access "read-only";
          smiv2:oid "1.3.6.1.4.1.4491.2.1.20.1.2.1.3";
        }

        leaf docsIf3CmStatusUsRangingAborteds {
          type yang:counter32;
          units "attempts";
          description
           "This attribute denotes the number of times the ranging
            process was aborted by the CMTS. Discontinuities
            in the value of this counter can occur at re-initialization
            of the managed system, and at other times as
            indicated by the value of ifCounterDiscontinuityTime
            ([RFC2863]) for the associated upstream channel.";
          reference
           "RFC 2863.";
          smiv2:max-access "read-only";
          smiv2:oid "1.3.6.1.4.1.4491.2.1.20.1.2.1.4";
        }

        leaf docsIf3CmStatusUsModulationType {
          type docs-if:DocsisUpstreamType;
          description
           "This attribute indicates modulation type status
            currently used by the CM for this upstream channel. Since
            this object specifically identifies PHY Layer
            mode, the shared upstream channel type 'tdmaAndAtdma'
            is not permitted.";
          reference
           "RFC 2863.";
          smiv2:max-access "read-only";
          smiv2:oid "1.3.6.1.4.1.4491.2.1.20.1.2.1.5";
        }

        leaf docsIf3CmStatusUsEqData {
          type docs-if:DocsEqualizerData;
          description
           "This attribute indicates the pre-equalization data
            for the specified upstream Channel on this CM after
            convolution with data indicated in the RNG-RSP. This
            data is valid when docsIfUpChannelPreEqEnable
            RFC 4546 is set to true.";
          reference
           "RFC 2863.
            RFC 4546.";
          smiv2:max-access "read-only";
          smiv2:oid "1.3.6.1.4.1.4491.2.1.20.1.2.1.6";
        }

        leaf docsIf3CmStatusUsT3Exceededs {
          type yang:counter32;
          units "timeouts";
          description
           "This attribute denotes the number of times for excessive
            T3 timeouts. Discontinuities in the value of
            this counter can occur at re-initialization of the managed
            system, and at other times as indicated by the
            value of ifCounterDiscontinuityTime for the associated
            upstream channel.";
          reference
           "RFC 2863.";
          smiv2:max-access "read-only";
          smiv2:oid "1.3.6.1.4.1.4491.2.1.20.1.2.1.7";
        }

        leaf docsIf3CmStatusUsIsMuted {
          type boolean;
          description
           "This attribute denotes whether the upstream
            channel is muted.";
          reference
           "DOCSIS 3.0 MAC and Upper Layer Protocols Interface
            Specification CM-SP-MULPIv3.0-I08-080522 section
            Media Access Control specification.";
          smiv2:max-access "read-only";
          smiv2:oid "1.3.6.1.4.1.4491.2.1.20.1.2.1.8";
        }

        leaf docsIf3CmStatusUsRangingStatus {
          type DOCS-IF3-MIB:RangingState;
          description
           "This attribute denotes the ranging state of the CM.";
          reference
           "DOCSIS 3.0 MAC and Upper Layer Protocols Interface
            Specification CM-SP-MULPIv3.0-I08-080522, section
            Media Access Control specification.";
          smiv2:max-access "read-only";
          smiv2:oid "1.3.6.1.4.1.4491.2.1.20.1.2.1.9";
        }
      }
    }

    container docsIf3CmtsCmRegStatusTable {
      description
       "This object defines attributes that represent the CM's
        registration status as tracked by the CMTS.
        Refer to the individual attribute definitions for 
        applicability to 3.0 and 3.1 Cable Modems.";
      smiv2:oid "1.3.6.1.4.1.4491.2.1.20.1.3";

      list docsIf3CmtsCmRegStatusEntry {
        key "docsIf3CmtsCmRegStatusId";
        description
         "The conceptual row of docsIf3CmtsCmRegStatusTable.";
        smiv2:oid "1.3.6.1.4.1.4491.2.1.20.1.3.1";

        leaf docsIf3CmtsCmRegStatusId {
          type uint32 {
            range "1..4294967295";
          }
          description
           "This attribute uniquely identifies a CM.  The CMTS
            must assign a single id value for each CM MAC address seen
            by the CMTS.  The CMTS should ensure that the association
            between an Id and MAC Address remains constant
            during CMTS uptime.";
          smiv2:max-access "not-accessible";
          smiv2:oid "1.3.6.1.4.1.4491.2.1.20.1.3.1.1";
        }

        leaf docsIf3CmtsCmRegStatusMacAddr {
          type yang:mac-address;
          description
           "This attribute represents the MAC address of the CM.
            If the CM has multiple MAC addresses, this is the MAC
            address associated with the MAC Domain interface.";
          smiv2:max-access "read-only";
          smiv2:oid "1.3.6.1.4.1.4491.2.1.20.1.3.1.2";
        }

        leaf docsIf3CmtsCmRegStatusIPv6Addr {
          type inet-address:InetAddressIPv6;
          description
           "This attribute represents the IPv6 address of the
            CM. If the CM has no Internet address assigned, or the
            Internet address is unknown, the value of this attribute
            is the all zeros address.";
          smiv2:max-access "read-only";
          smiv2:oid "1.3.6.1.4.1.4491.2.1.20.1.3.1.3";
        }

        leaf docsIf3CmtsCmRegStatusIPv6LinkLocal {
          type inet-address:InetAddressIPv6;
          description
           "This attribute represents the IPv6 local scope address
            of the CM. If the CM has no link local address assigned,
            or the Internet address is unknown, the value
            of this attribute is the all zeros address.";
          smiv2:max-access "read-only";
          smiv2:oid "1.3.6.1.4.1.4491.2.1.20.1.3.1.4";
        }

        leaf docsIf3CmtsCmRegStatusIPv4Addr {
          type inet-address:InetAddressIPv4;
          description
           "This attribute represents the IPv4 address of this
            CM. If the CM has no IP address assigned, or the IP address
            is unknown, this object returns 0.0.0.0.";
          smiv2:max-access "read-only";
          smiv2:oid "1.3.6.1.4.1.4491.2.1.20.1.3.1.5";
        }

        leaf docsIf3CmtsCmRegStatusValue {
          type DOCS-IF3-MIB:CmtsCmRegState;
          description
           "This attribute represents the current CM connectivity
            state.";
          reference
           "DOCSIS 3.0 MAC and Upper Layer Protocols Interface
            Specification CM-SP-MULPIv3.0-I08-080522, Cable Modem
            Initialization and Reinitialization section.";
          smiv2:max-access "read-only";
          smiv2:oid "1.3.6.1.4.1.4491.2.1.20.1.3.1.6";
        }

        leaf docsIf3CmtsCmRegStatusMdIfIndex {
          type if-mib:InterfaceIndexOrZero;
          description
           "This attribute represents the interface Index of
            the CMTS MAC Domain where the CM is active. If the interface
            is unknown, the CMTS returns a value of zero.";
          smiv2:max-access "read-only";
          smiv2:oid "1.3.6.1.4.1.4491.2.1.20.1.3.1.7";
        }

        leaf docsIf3CmtsCmRegStatusMdCmSgId {
          type uint32;
          description
           "This attribute represents the ID of the MAC Domain
            CM Service Group Id (MD-CM-SG-ID) in which the CM is registered.
            If the ID is unknown, the CMTS returns a value
            of zero.";
          reference
           "DOCSIS 3.0 MAC and Upper Layer Protocols Interface
            Specification CM-SP-MULPIv3.0-I08-080522, Cable Modem
            Service Group (CM-SG) section.";
          smiv2:max-access "read-only";
          smiv2:oid "1.3.6.1.4.1.4491.2.1.20.1.3.1.8";
        }

        leaf docsIf3CmtsCmRegStatusRcpId {
          type DOCS-IF3-MIB:RcpId;
          description
           "This attribute represents the RCP-ID associated
            with the CM if the CM is in DOCSIS 3.0 mode. If the 
            RCP-ID is unknown or the CM is in DOCSIS 3.1 mode,
            the CMTS returns a five octet long string of zeros.";
          reference
           "DOCSIS 3.0 MAC and Upper Layer Protocols Interface
            Specification CM-SP-MULPIv3.0-I08-080522, RCP-ID
            section in the Common Radio Frequency Interface
            Encodings Annex.";
          smiv2:max-access "read-only";
          smiv2:oid "1.3.6.1.4.1.4491.2.1.20.1.3.1.9";
        }

        leaf docsIf3CmtsCmRegStatusRccStatusId {
          type uint32;
          description
           "This attribute represents the RCC Id the CMTS used
            to configure the CM receive channel set during the registration
            process, if the CM is in DOCSIS 3.0 mode. If unknown or the CM
            is in DOCSIS 3.1 mode, the CMTS returns the value zero.";
          smiv2:max-access "read-only";
          smiv2:oid "1.3.6.1.4.1.4491.2.1.20.1.3.1.10";
        }

        leaf docsIf3CmtsCmRegStatusRcsId {
          type DOCS-IF3-MIB:ChSetId;
          description
           "This attribute represents the Receive Channel Set
            (RCS) that the CM is currently using. If the RCS is unknown,
            the CMTS returns the value zero.";
          reference
           "DOCSIS 3.0 MAC and Upper Layer Protocols Interface
            Specification CM-SP-MULPIv3.0-I08-080522, Cable Modem
            Physical Receive Channel Configuration section and the
            Receive Channels section in the Common Radio Frequency
            Interface Encodings Annex.";
          smiv2:max-access "read-only";
          smiv2:oid "1.3.6.1.4.1.4491.2.1.20.1.3.1.11";
        }

        leaf docsIf3CmtsCmRegStatusTcsId {
          type DOCS-IF3-MIB:ChSetId;
          description
           "This attribute represents Transmit Channel Set (TCS)
            the CM is currently using. If the TCS is unknown,
            the CMTS returns the value zero.";
          reference
           "DOCSIS 3.0 MAC and Upper Layer Protocols Interface
            Specification CM-SP-MULPIv3.0-I08-080522, Changes to
            the Transmit Channel Set section.";
          smiv2:max-access "read-only";
          smiv2:oid "1.3.6.1.4.1.4491.2.1.20.1.3.1.12";
        }

        leaf docsIf3CmtsCmRegStatusQosVersion {
          type docs-if:DocsisQosVersion;
          description
           "This attribute denotes the queuing services the CM 
            registered, either DOCSIS 1.1 QoS or DOCSIS 1.0 CoS mode.";
          smiv2:max-access "read-only";
          smiv2:oid "1.3.6.1.4.1.4491.2.1.20.1.3.1.13";
        }

        leaf docsIf3CmtsCmRegStatusLastRegTime {
          type snmpv2-tc:DateAndTime;
          description
           "This attribute represents the last time the CM registered.";
          smiv2:max-access "read-only";
          smiv2:oid "1.3.6.1.4.1.4491.2.1.20.1.3.1.14";
        }

        leaf docsIf3CmtsCmRegStatusAddrResolutionReqs {
          type yang:counter32;
          description
           "This attribute counts the number of upstream
            packets received on the SIDs assigned to a CM that
            are any of the following:
            Upstream IPv4 ARP Requests
            Upstream IPv6 Neighbor Solicitation Requests
            (For Routing CMTSs) Upstream IPv4 or IPv6 packets to
            unresolved destinations in locally connected downstream
            subnets in the HFC.
            Discontinuities in the value of this counter can occur
            at re-initialization of the managed system, and at
            other times as indicated by the value of
            ifCounterDiscontinuityTime for the associated MAC Domain
            interface.";
          reference
           "DOCSIS 3.0 Security Specification CM-SP-SECv3.0-I13-100611,
            Secure Provisioning section.
            RFC 2863.";
          smiv2:max-access "read-only";
          smiv2:oid "1.3.6.1.4.1.4491.2.1.20.1.3.1.15";
        }

        leaf docsIf3CmtsCmRegStatusEnergyMgtEnabled {
          type bits {
            bit em1x1Mode {
              position "0";
            }
            bit dlsMode {
              position "1";
            }
          }
          description
           "This attribute indicates which, if any, of the Energy 
            Management Features are enabled for this CM. If this attribute
            returns the em1x1Mode(0) bit set, the CM is configured with the 
            Energy Management 1x1 Feature enabled. If this attribute returns
            the dlsMode(1) bit set, the CM is configured with the DLS Feature
            enabled. If this attribute returns all bits cleared, the CM will 
            not request to operate in any Energy Management mode of operation.  
            
            Note: This attribute only indicates if an Energy Management Feature 
            is enabled/disabled via the CM config file and registration 
            request/response exchange and does not indicate whether the CM is 
            actively operating in an Energy Management Mode.";
          reference
           "DOCSIS 3.1 MAC and Upper Layer Protocols Interface
            Specification CM-SP-MULPIv3.1-I03-140610,
            Energy Management Features section.";
          smiv2:max-access "read-only";
          smiv2:oid "1.3.6.1.4.1.4491.2.1.20.1.3.1.16";
        }

        leaf docsIf3CmtsCmRegStatusEnergyMgtOperStatus {
          type bits {
            bit em1x1Mode {
              position "0";
            }
            bit dlsMode {
              position "1";
            }
          }
          description
           "This attribute indicates whether the CM is currently operating
            in an Energy Management Mode. If this attribute returns the
            em1x1Mode(0) bit set, the CM is operating in Energy Management
            1x1 Mode. If this attribute returns the dlsMode(1) bit set, the
            CM is operating in DLS Mode. If this attribute returns all bits 
            cleared, the CM is not operating in any Energy Management Mode. 
            This attribute always returns 0x00 (no bits set) in the case when 
            docsIf3CmtsCmRegStatusEnergyMgtEnabled is set to 0x00 (no Energy 
            Management Features enabled).
            
            Note: dlsMode(1) and em1x1Mode(0) are mutually exclusive, thus 
            a return value where both of these bits are 'true' is invalid.";
          reference
           "DOCSIS 3.1 MAC and Upper Layer Protocols Interface
            Specification CM-SP-MULPIv3.1-I03-140610,
            Energy Management Mode Indicator section.";
          smiv2:max-access "read-only";
          smiv2:oid "1.3.6.1.4.1.4491.2.1.20.1.3.1.17";
        }
      }
    }

    container docsIf3CmtsCmUsStatusTable {
      description
       "This object defines status information of the CM
        currently in use Upstream Logical Channels, as reported
        by the CMTS.";
      smiv2:oid "1.3.6.1.4.1.4491.2.1.20.1.4";

      list docsIf3CmtsCmUsStatusEntry {
        key "docsIf3CmtsCmRegStatusId docsIf3CmtsCmUsStatusChIfIndex";
        description
         "The conceptual row of docsIf3CmtsCmUsStatusTable.";
        smiv2:oid "1.3.6.1.4.1.4491.2.1.20.1.4.1";

        leaf docsIf3CmtsCmRegStatusId {
          type leafref {
            path "/DOCS-IF3-MIB:DOCS-IF3-MIB/DOCS-IF3-MIB:docsIf3CmtsCmRegStatusTable/DOCS-IF3-MIB:docsIf3CmtsCmRegStatusEntry/DOCS-IF3-MIB:docsIf3CmtsCmRegStatusId";
          }
        }

        leaf docsIf3CmtsCmUsStatusChIfIndex {
          type if-mib:InterfaceIndex;
          description
           "This attribute is a key that represents the ifIndex
            of the upstream interface.";
          smiv2:max-access "not-accessible";
          smiv2:oid "1.3.6.1.4.1.4491.2.1.20.1.4.1.1";
        }

        leaf docsIf3CmtsCmUsStatusModulationType {
          type docs-if:DocsisUpstreamType;
          description
           "This attribute represents the modulation type currently
            used by this upstream channel.";
          smiv2:max-access "read-only";
          smiv2:oid "1.3.6.1.4.1.4491.2.1.20.1.4.1.2";
        }

        leaf docsIf3CmtsCmUsStatusRxPower {
          type docs-if:TenthdBmV;
          units "TenthdBmV";
          description
           "This attribute represents the receive power of this
            upstream channel.
            The reported value represents the total average power for the 
            channel regardless of whether the CM is reporting Pr, total 
            average power, or P1.6r, the power spectral density in an 
            equivalent 1.6 MHz spectrum.";
          smiv2:max-access "read-only";
          smiv2:oid "1.3.6.1.4.1.4491.2.1.20.1.4.1.3";
        }

        leaf docsIf3CmtsCmUsStatusSignalNoise {
          type docs-if:TenthdB;
          units "TenthdB";
          description
           "This attribute represents Signal/Noise ratio as
            perceived for upstream data from the CM on this upstream
            channel.";
          smiv2:max-access "read-only";
          smiv2:oid "1.3.6.1.4.1.4491.2.1.20.1.4.1.4";
        }

        leaf docsIf3CmtsCmUsStatusMicroreflections {
          type uint32 {
            range "0..65535";
          }
          units "-dBc";
          description
           "This attribute represents microreflections received
            on this upstream channel.";
          smiv2:max-access "read-only";
          smiv2:oid "1.3.6.1.4.1.4491.2.1.20.1.4.1.5";
        }

        leaf docsIf3CmtsCmUsStatusEqData {
          type docs-if:DocsEqualizerData;
          description
           "This attribute represents the equalization data
            for the CM on this upstream channel.";
          smiv2:max-access "read-only";
          smiv2:oid "1.3.6.1.4.1.4491.2.1.20.1.4.1.6";
        }

        leaf docsIf3CmtsCmUsStatusUnerroreds {
          type yang:counter32;
          description
           "This attribute represents the codewords received
            without error from the CM on this interface. Discontinuities
            in the value of this counter can occur at re-initialization
            of the managed system, and at other
            times as indicated by the value of ifCounterDiscontinuityTime
            for the associated upstream channel.";
          reference
           "RFC 2863.";
          smiv2:max-access "read-only";
          smiv2:oid "1.3.6.1.4.1.4491.2.1.20.1.4.1.7";
        }

        leaf docsIf3CmtsCmUsStatusCorrecteds {
          type yang:counter32;
          description
           "This attribute represents the codewords received
            with correctable errors from the CM on this upstream
            channel. Discontinuities in the value of this counter
            can occur at re-initialization of the managed system,
            and at other times as indicated by the value of
            ifCounterDiscontinuityTime for the associated upstream
            channel.";
          reference
           "RFC 2863.";
          smiv2:max-access "read-only";
          smiv2:oid "1.3.6.1.4.1.4491.2.1.20.1.4.1.8";
        }

        leaf docsIf3CmtsCmUsStatusUncorrectables {
          type yang:counter32;
          description
           "This attribute represents the codewords received
            with uncorrectable errors from the CM on this upstream
            channel. Discontinuities in the value of this counter
            can occur at re-initialization of the managed
            system, and at other times as indicated by the value of
            ifCounterDiscontinuityTime for the associated upstream
            channel.";
          reference
           "RFC 2863.";
          smiv2:max-access "read-only";
          smiv2:oid "1.3.6.1.4.1.4491.2.1.20.1.4.1.9";
        }

        leaf docsIf3CmtsCmUsStatusHighResolutionTimingOffset {
          type int32;
          units "time tick/(64*256)";
          description
           "This attribute represents the current measured round
            trip time on this CM's upstream channel in units
            of (6.25 microseconds/(64*256)).  This attribute returns
            zero if the value is unknown.";
          smiv2:max-access "read-only";
          smiv2:oid "1.3.6.1.4.1.4491.2.1.20.1.4.1.10";
        }

        leaf docsIf3CmtsCmUsStatusIsMuted {
          type int32 {
            range "0..2";
          }
          description
           "This attribute has a value 'true' to indicate that 
            the CM's upstream channel has been muted via 
            CM-CTRL-REQ/CM-CTRL-RSP message exchange.";
          reference
           "DOCSIS 3.0 MAC and Upper Layer Protocols Interface
            Specification CM-SP-MULPIv3.0-I08-080522, section
            Media Access Control specification.";
          smiv2:max-access "read-only";
          smiv2:oid "1.3.6.1.4.1.4491.2.1.20.1.4.1.11";
        }

        leaf docsIf3CmtsCmUsStatusRangingStatus {
          type DOCS-IF3-MIB:RangingState;
          description
           "This attribute denotes the ranging state of the CM.";
          reference
           "DOCSIS 3.0 MAC and Upper Layer Protocols Interface
            Specification CM-SP-MULPIv3.0-I08-080522, section
            Media Access Control specification.";
          smiv2:max-access "read-only";
          smiv2:oid "1.3.6.1.4.1.4491.2.1.20.1.4.1.12";
        }
      }
    }

    container docsIf3MdChCfgTable {
      description
       "This object configures the association of downstream
        and upstream channels to a particular MAC Domain
        (MD) on a CMTS.  The creation of channels and MAC domain
        object interface instances is vendor-specific.
        In particular, the assignment of the channel interface
        index is normally vendor-specific. Therefore,
        this object is intended only for associating channels
        to a MAC Domain and assumes that those channels were
        previously configured.
        The CMTS may have restrictions on which channels can
        be configured in the same MAC Domain.  For example, it
        could require the upstream channels to be from the same
        line card.
        This object supports the creation and deletion of multiple
        instances.
        Creation of a new instance of this object requires the
        ChId attribute to be set.";
      smiv2:oid "1.3.6.1.4.1.4491.2.1.20.1.5";

      list docsIf3MdChCfgEntry {
        key "ifIndex docsIf3MdChCfgChIfIndex";
        description
         "The conceptual row of docsIf3MdChCfgTable.
          The ifIndex key corresponds to the MAC Domain interface
          where the channel is configured.
          The CMTS persists all instances of MdChCfg across
          reinitializations.";
        smiv2:oid "1.3.6.1.4.1.4491.2.1.20.1.5.1";

        leaf ifIndex {
          type leafref {
            path "/if-mib:IF-MIB/if-mib:ifTable/if-mib:ifEntry/if-mib:ifIndex";
          }
        }

        leaf docsIf3MdChCfgChIfIndex {
          type if-mib:InterfaceIndex;
          description
           "This key represents the interface index of an existing
            upstream or downstream channel that is configured
            to be part of the MAC Domain.
            For the case of upstream interfaces the CMTS could reject
            the assignment of upstream logical channels under
            the same physical upstream interface to different
            MAC Domains.";
          smiv2:max-access "not-accessible";
          smiv2:oid "1.3.6.1.4.1.4491.2.1.20.1.5.1.1";
        }

        leaf docsIf3MdChCfgIsPriCapableDs {
          type boolean;
          description
           "If set to 'true', this attribute configures the downstream
            channel as Primary-Capable. 
            The default value for a downstream channel is 'true'.
            This attribute is not relevant for upstream interfaces, 
            therefore it reports the value 'false' for such interfaces.
            A CMTS may restrict the permitted value of this attribute
            based upon physical channel capabilities.";
          smiv2:max-access "read-write";
          smiv2:oid "1.3.6.1.4.1.4491.2.1.20.1.5.1.2";
        }

        leaf docsIf3MdChCfgChId {
          type DOCS-IF3-MIB:ChId {
            range "0..255";
          }
          description
           "This attribute contains the 8-bit Downstream Channel
            ID (DCID) or Upstream Channel ID (UCID) configured
            for the channel in the MAC Domain.";
          smiv2:max-access "read-write";
          smiv2:oid "1.3.6.1.4.1.4491.2.1.20.1.5.1.3";
        }

        leaf docsIf3MdChCfgSfProvAttrMask {
          type DOCS-IF3-MIB:AttributeMask;
          description
           "This attribute contains Provisioned Attribute Mask
            of non-bonded service flow assignment to this channel.";
          smiv2:max-access "read-write";
          smiv2:oid "1.3.6.1.4.1.4491.2.1.20.1.5.1.4";
        }

        leaf docsIf3MdChCfgRowStatus {
          type snmpv2-tc:RowStatus;
          description
           "The status of this instance.";
          smiv2:max-access "read-write";
          smiv2:oid "1.3.6.1.4.1.4491.2.1.20.1.5.1.5";
        }
      }
    }

    container docsIf3RccCfgTable {
      status obsolete;
      description
       "This object identifies the scope of the Receive Channel
        Configuration (RCC) and provides a top level container
        for the Receive Module and Receive Channel
        objects.  The CMTS selects an instance of this object
        to assign to a CM when it registers.
        This object supports the creation and deletion of multiple
        instances.";
      smiv2:oid "1.3.6.1.4.1.4491.2.1.20.1.6";

      list docsIf3RccCfgEntry {
        key "ifIndex docsIf3RccCfgRcpId docsIf3RccCfgRccCfgId";
        status obsolete;
        description
         "The conceptual row of docsIf3RccCfgTable.
          The ifIndex key corresponds to the MAC Domain interface
          where the RCC is configured.
           The CMTS persists all instances of RccCfg across
           reinitializations.";
        smiv2:oid "1.3.6.1.4.1.4491.2.1.20.1.6.1";

        leaf ifIndex {
          type leafref {
            path "/if-mib:IF-MIB/if-mib:ifTable/if-mib:ifEntry/if-mib:ifIndex";
          }
        }

        leaf docsIf3RccCfgRcpId {
          type DOCS-IF3-MIB:RcpId;
          status obsolete;
          description
           "This key represents the 'Receive Channel Profile
            Identifier' (RCP-ID) configured for the MAC Domain
            indicated by this instance.";
          reference
           "DOCSIS 3.0 MAC and Upper Layer Protocols Interface
            Specification CM-SP-MULPIv3.0-I08-080522, Standard
            Receive Channel Profile Encodings Annex.";
          smiv2:max-access "not-accessible";
          smiv2:oid "1.3.6.1.4.1.4491.2.1.20.1.6.1.1";
        }

        leaf docsIf3RccCfgRccCfgId {
          type uint32 {
            range "1..4294967295";
          }
          status obsolete;
          description
           "This key denotes an RCC combination assignment for
            a particular RcpId and is unique per combination of
            MAC Domain and RcpId.";
          smiv2:max-access "not-accessible";
          smiv2:oid "1.3.6.1.4.1.4491.2.1.20.1.6.1.2";
        }

        leaf docsIf3RccCfgVendorSpecific {
          type binary {
            length "0..252";
          }
          status obsolete;
          description
           "This attribute contains vendor-specific information
            of the CM Receive Channel configuration.";
          reference
           "DOCSIS 3.0 MAC and Upper Layer Protocols Interface
            Specification CM-SP-MULPIv3.0-I08-080522, Receive Channel
            Profile/Configuration Vendor Specific Parameters section
            in the Common Radio Frequency Interface Encodings Annex.";
          smiv2:defval "";
          smiv2:max-access "read-write";
          smiv2:oid "1.3.6.1.4.1.4491.2.1.20.1.6.1.3";
        }

        leaf docsIf3RccCfgDescription {
          type snmp-framework:SnmpAdminString {
            length "0..15";
          }
          status obsolete;
          description
           "This attribute contains a human-readable description
            of the CM RCP Configuration.";
          smiv2:defval "";
          smiv2:max-access "read-write";
          smiv2:oid "1.3.6.1.4.1.4491.2.1.20.1.6.1.4";
        }

        leaf docsIf3RccCfgRowStatus {
          type snmpv2-tc:RowStatus;
          status obsolete;
          description
           "The status of this instance.";
          smiv2:max-access "read-write";
          smiv2:oid "1.3.6.1.4.1.4491.2.1.20.1.6.1.5";
        }
      }
    }

    container docsIf3RccStatusTable {
      description
       "The RCC Status object provides a read-only view of
        the statically-configured (from the RccCfg object)
        and dynamically-created RCCs.
        The CMTS creates an RCC Status instance for each unique
        MAC Domain Cable Modem Service Group (MD-CM-SG) to
        which it signals an RCC to the CM.";
      smiv2:oid "1.3.6.1.4.1.4491.2.1.20.1.7";

      list docsIf3RccStatusEntry {
        key "ifIndex docsIf3RccStatusRcpId docsIf3RccStatusRccStatusId";
        description
         "The conceptual row of docsIf3RccStatusTable.
          The ifIndex key corresponds to the MAC Domain interface
          where the RCC is configured.";
        smiv2:oid "1.3.6.1.4.1.4491.2.1.20.1.7.1";

        leaf ifIndex {
          type leafref {
            path "/if-mib:IF-MIB/if-mib:ifTable/if-mib:ifEntry/if-mib:ifIndex";
          }
        }

        leaf docsIf3RccStatusRcpId {
          type DOCS-IF3-MIB:RcpId;
          description
           "This key represents the RCP-ID to which this instance
            applies.";
          smiv2:max-access "not-accessible";
          smiv2:oid "1.3.6.1.4.1.4491.2.1.20.1.7.1.1";
        }

        leaf docsIf3RccStatusRccStatusId {
          type uint32 {
            range "1..4294967295";
          }
          description
           "This key represents an RCC combination for a particular
            RcpId either from an RCC configuration object
            or a CMTS-determined RCC and is unique per combination
            of MAC Domain IfIndex and RcpId.";
          smiv2:max-access "not-accessible";
          smiv2:oid "1.3.6.1.4.1.4491.2.1.20.1.7.1.2";
        }

        leaf docsIf3RccStatusRccCfgId {
          type uint32 {
            range "0..65535";
          }
          description
           "This attribute identifies an RCC-Configured combination
            from which this instance was defined. If nonzero,
            it corresponds to the RccCfg instance from which
            the RCC was created. Zero means that the  RCC was dynamically
            created by the CMTS.";
          smiv2:max-access "read-only";
          smiv2:oid "1.3.6.1.4.1.4491.2.1.20.1.7.1.3";
        }

        leaf docsIf3RccStatusValidityCode {
          type enumeration {
            enum "other" {
              value "1";
            }
            enum "valid" {
              value "2";
            }
            enum "invalid" {
              value "3";
            }
            enum "wrongPrimaryDs" {
              value "4";
            }
            enum "missingPrimaryDs" {
              value "5";
            }
            enum "multiplePrimaryDs" {
              value "6";
            }
            enum "duplicateDs" {
              value "7";
            }
            enum "wrongFrequencyRange" {
              value "8";
            }
            enum "wrongConnectivity" {
              value "9";
            }
          }
          description
           "This attribute indicates whether the RCC instance
            of this object is valid or not. An RCC Status instance
            from a configured or a dynamic RCC could become invalid,
            for example, due changes in the topology.";
          smiv2:max-access "read-only";
          smiv2:oid "1.3.6.1.4.1.4491.2.1.20.1.7.1.4";
        }

        leaf docsIf3RccStatusValidityCodeText {
          type snmp-framework:SnmpAdminString;
          description
           "This attribute contains the CMTS vendor-specific
            log information from the Receive Channel Configuration
            Status encoding.";
          smiv2:max-access "read-only";
          smiv2:oid "1.3.6.1.4.1.4491.2.1.20.1.7.1.5";
        }
      }
    }

    container docsIf3RxChCfgTable {
      status obsolete;
      description
       "The Receive Channel Configuration object permits
        an operator to configure how CMs registered with certain
        Receive Channel Profiles will configure the Receive
        Channels within their profile. When a CM registers
        with an RCP for which all Receive Channel Indices
        (RcIds) are configured in the Receive Module object
        and all Receive Channels are configured within this
        object, the CMTS should use the configuration within
        these objects to set the Receive Channel Configuration
        returned to the CM in a REG-RSP message.  A CMTS
        may require configuration of all pertinent Receive
        Module and Receive Channel instances in order to register
        a CM that reports a Receive Channel Profile (RCP),
        including any standard Receive Channel Profiles.
        If the CM reports multiple RCPs, and Receive Module
        and Receive Channel objects have instances for more
        than one RCP, the particular RCP selected by the CMTS
        is not specified.  A CMTS is not restricted to assigning
        Receive Modules based only on the contents of this
        object.
        This object supports the creation and deletion of multiple
        instances.
        Creation of a new instance of this object requires the
        ChIfIndex attribute to be set and a valid reference of
        a RccCfg instance.";
      smiv2:oid "1.3.6.1.4.1.4491.2.1.20.1.8";

      list docsIf3RxChCfgEntry {
        key "ifIndex docsIf3RccCfgRcpId docsIf3RccCfgRccCfgId docsIf3RxChCfgRcId";
        status obsolete;
        description
         "The conceptual row of docsIf3RxChCfgTable.
          The ifIndex key corresponds to the MAC Domain interface
          where the RCC is configured.
          The CMTS persists all instances of ReceiveChannelCfg across
          reinitializations.";
        smiv2:oid "1.3.6.1.4.1.4491.2.1.20.1.8.1";

        leaf ifIndex {
          type leafref {
            path "/if-mib:IF-MIB/if-mib:ifTable/if-mib:ifEntry/if-mib:ifIndex";
          }
        }

        leaf docsIf3RccCfgRcpId {
          type leafref {
            path "/DOCS-IF3-MIB:DOCS-IF3-MIB/DOCS-IF3-MIB:docsIf3RccCfgTable/DOCS-IF3-MIB:docsIf3RccCfgEntry/DOCS-IF3-MIB:docsIf3RccCfgRcpId";
          }
          status obsolete;
        }

        leaf docsIf3RccCfgRccCfgId {
          type leafref {
            path "/DOCS-IF3-MIB:DOCS-IF3-MIB/DOCS-IF3-MIB:docsIf3RccCfgTable/DOCS-IF3-MIB:docsIf3RccCfgEntry/DOCS-IF3-MIB:docsIf3RccCfgRccCfgId";
          }
          status obsolete;
        }

        leaf docsIf3RxChCfgRcId {
          type uint32 {
            range "1..255";
          }
          status obsolete;
          description
           "This key represents an identifier for the parameters
            of the Receive Channel instance within the Receive
            Channel Profile.";
          reference
           "DOCSIS 3.0 MAC and Upper Layer Protocols Interface
            Specification CM-SP-MULPIv3.0-I08-080522, Receive
            Channel Index section in the Common Radio Frequency
            Interface Encodings Annex.";
          smiv2:max-access "not-accessible";
          smiv2:oid "1.3.6.1.4.1.4491.2.1.20.1.8.1.1";
        }

        leaf docsIf3RxChCfgChIfIndex {
          type if-mib:InterfaceIndex;
          status obsolete;
          description
           "This attribute contains the interface index of a Downstream
            Channel that this Receive Channel Instance
            defines.";
          smiv2:max-access "read-write";
          smiv2:oid "1.3.6.1.4.1.4491.2.1.20.1.8.1.2";
        }

        leaf docsIf3RxChCfgPrimaryDsIndicator {
          type boolean;
          status obsolete;
          description
           "If set to 'true', this attribute indicates the Receive
            Channel is to be the primary-capable downstream
            channel for the CM receiving this RCC. Otherwise, the
            downstream channel is to be a non-primary-capable
            channel.";
          reference
           "DOCSIS 3.0 MAC and Upper Layer Protocols Interface
            Specification CM-SP-MULPIv3.0-I08-080522, Receive Channel
            Primary Downstream Channel Indicator section in the Common
            Radio Frequency Interface Encodings Annex.";
          smiv2:defval "false";
          smiv2:max-access "read-write";
          smiv2:oid "1.3.6.1.4.1.4491.2.1.20.1.8.1.3";
        }

        leaf docsIf3RxChCfgRcRmConnectivityId {
          type uint32 {
            range "0..255";
          }
          status obsolete;
          description
           "This attribute indicates the Receive Module (via
            the RmId from the ReceiveModule object) to which this
            Receive Channel connects.  If this object contains
            a zero value (and thus no Receive Channel Connectivity),
            the Receive Channel Connectivity TLV is omitted
            from the RCC.";
          reference
           "DOCSIS 3.0 MAC and Upper Layer Protocols Interface
            Specification CM-SP-MULPIv3.0-I08-080522, Receive
            Channel Connectivity section in the Common Radio
            Frequency Interface Encodings Annex.";
          smiv2:defval "0";
          smiv2:max-access "read-write";
          smiv2:oid "1.3.6.1.4.1.4491.2.1.20.1.8.1.4";
        }

        leaf docsIf3RxChCfgRowStatus {
          type snmpv2-tc:RowStatus;
          status obsolete;
          description
           "The status of this instance.";
          smiv2:max-access "read-write";
          smiv2:oid "1.3.6.1.4.1.4491.2.1.20.1.8.1.5";
        }
      }
    }

    container docsIf3RxChStatusTable {
      description
       "The Receive Channel Status object reports the status
        of the statically-configured and dynamically-created
        Receive Channels within an RCC.";
      smiv2:oid "1.3.6.1.4.1.4491.2.1.20.1.9";

      list docsIf3RxChStatusEntry {
        key "ifIndex docsIf3RccStatusRcpId docsIf3RccStatusRccStatusId docsIf3RxChStatusRcId";
        description
         "The conceptual row of docsIf3RxChStatusTable.
          The ifIndex key corresponds to the MAC Domain interface
          where the RCC is configured. When this object is defined
          on the CM, the value of RccStatusId is always 1.";
        smiv2:oid "1.3.6.1.4.1.4491.2.1.20.1.9.1";

        leaf ifIndex {
          type leafref {
            path "/if-mib:IF-MIB/if-mib:ifTable/if-mib:ifEntry/if-mib:ifIndex";
          }
        }

        leaf docsIf3RccStatusRcpId {
          type leafref {
            path "/DOCS-IF3-MIB:DOCS-IF3-MIB/DOCS-IF3-MIB:docsIf3RccStatusTable/DOCS-IF3-MIB:docsIf3RccStatusEntry/DOCS-IF3-MIB:docsIf3RccStatusRcpId";
          }
        }

        leaf docsIf3RccStatusRccStatusId {
          type leafref {
            path "/DOCS-IF3-MIB:DOCS-IF3-MIB/DOCS-IF3-MIB:docsIf3RccStatusTable/DOCS-IF3-MIB:docsIf3RccStatusEntry/DOCS-IF3-MIB:docsIf3RccStatusRccStatusId";
          }
        }

        leaf docsIf3RxChStatusRcId {
          type uint32 {
            range "1..255";
          }
          description
           "This key represents an identifier for the parameters
            of the Receive Channel instance within the Receive
            Channel Profile.";
          smiv2:max-access "not-accessible";
          smiv2:oid "1.3.6.1.4.1.4491.2.1.20.1.9.1.1";
        }

        leaf docsIf3RxChStatusChIfIndex {
          type if-mib:InterfaceIndexOrZero;
          description
           "This attribute contains the interface index of the
            Downstream Channel that this Receive Channel Instance
            defines.";
          smiv2:max-access "read-only";
          smiv2:oid "1.3.6.1.4.1.4491.2.1.20.1.9.1.2";
        }

        leaf docsIf3RxChStatusPrimaryDsIndicator {
          type boolean;
          description
           "If set to 'true', this attribute indicates the Receive
            Channel is to be the primary-capable downstream
            channel for the CM receiving this RCC. Otherwise, the
            downstream channel is to be a non-primary-capable
            channel.";
          smiv2:max-access "read-only";
          smiv2:oid "1.3.6.1.4.1.4491.2.1.20.1.9.1.3";
        }

        leaf docsIf3RxChStatusRcRmConnectivityId {
          type uint32 {
            range "0..255";
          }
          description
           "This attribute identifies the Receive Module to which
            this Receive Channel connects.  A value a zero indicates
            that the Receive Channel Connectivity TLV is
            omitted from the RCC.";
          smiv2:max-access "read-only";
          smiv2:oid "1.3.6.1.4.1.4491.2.1.20.1.9.1.4";
        }
      }
    }

    container docsIf3RxModuleCfgTable {
      status obsolete;
      description
       "The Receive Module Configuration object permits
        an operator to configure how CMs with certain Receive
        Channel Profiles (RCPs) will configure the Receive
        Modules within their profile upon CM registration.
         When a CM registers with an RCP for which all Receive
        Module Indices (RmIds) are configured in this object
        and all Receive Channels are configured within the
        Receive Channel (ReceiveChannel) object, the CMTS
        should use the configuration within these objects to
        set the Receive Channel Configuration assigned to
        the CM in a REG-RSP message.  A CMTS may require configuration
        of all pertinent Receive Module and Receive
        Channel instances (i.e., MIB table entries) in order
        to register a CM that reports a Receive Channel Profile.
         If the CM reports multiple RCPs, and Receive Module
        and Receive Channel objects have instances (i.e.,
        MIB table entries) for more than one RCP reported by
        the CM, the particular RCP selected by the CMTS is not
        specified.  A CMTS is not restricted to assigning Receive
        Modules based only on the contents of this object.
        
        This object supports the creation and deletion of multiple
        instances.
        Creation of a new instance of this object requires the
        reference of a valid RccCfg instance.";
      smiv2:oid "1.3.6.1.4.1.4491.2.1.20.1.10";

      list docsIf3RxModuleCfgEntry {
        key "ifIndex docsIf3RccCfgRcpId docsIf3RccCfgRccCfgId docsIf3RxModuleCfgRmId";
        status obsolete;
        description
         "The conceptual row of docsIf3RxModuleCfgTable.
          The ifIndex key corresponds to the MAC Domain interface
          where the RCC is configured.";
        smiv2:oid "1.3.6.1.4.1.4491.2.1.20.1.10.1";

        leaf ifIndex {
          type leafref {
            path "/if-mib:IF-MIB/if-mib:ifTable/if-mib:ifEntry/if-mib:ifIndex";
          }
        }

        leaf docsIf3RccCfgRcpId {
          type leafref {
            path "/DOCS-IF3-MIB:DOCS-IF3-MIB/DOCS-IF3-MIB:docsIf3RccCfgTable/DOCS-IF3-MIB:docsIf3RccCfgEntry/DOCS-IF3-MIB:docsIf3RccCfgRcpId";
          }
          status obsolete;
        }

        leaf docsIf3RccCfgRccCfgId {
          type leafref {
            path "/DOCS-IF3-MIB:DOCS-IF3-MIB/DOCS-IF3-MIB:docsIf3RccCfgTable/DOCS-IF3-MIB:docsIf3RccCfgEntry/DOCS-IF3-MIB:docsIf3RccCfgRccCfgId";
          }
          status obsolete;
        }

        leaf docsIf3RxModuleCfgRmId {
          type uint32 {
            range "1..255";
          }
          status obsolete;
          description
           "This key represents an identifier of a Receive Module
            instance within the Receive Channel Profile.";
          reference
           "DOCSIS 3.0 MAC and Upper Layer Protocols Interface
            Specification CM-SP-MULPIv3.0-I08-080522, Receive Module
            Index in the Common Radio Frequency Interface Encodings
            Annex.";
          smiv2:max-access "not-accessible";
          smiv2:oid "1.3.6.1.4.1.4491.2.1.20.1.10.1.1";
        }

        leaf docsIf3RxModuleCfgRmRmConnectivityId {
          type uint32 {
            range "0..255";
          }
          status obsolete;
          description
           "This attribute represents the higher level (i.e.,
            closer to RF) Receive Module to which this Receive Module
            connects.  If this object contains a zero value (and
            thus no Receive Module Connectivity), the Receive
            Module Connectivity TLV is omitted from the RCC.
            Within a single instance of the ReceiveModule object,
            the RmRmConnectivityId attribute cannot contain
            the same value as the RmId attribute.  The RmRmConnectivityId
            attribute points to a separate ReceiveModule
            object instance with the same value of RccCfgId.";
          reference
           "DOCSIS 3.0 MAC and Upper Layer Protocols Interface
            Specification CM-SP-MULPIv3.0-I08-080522, Receive Module
            Connectivity section in the Common Radio Frequency Interface
            Encodings Annex.";
          smiv2:defval "0";
          smiv2:max-access "read-write";
          smiv2:oid "1.3.6.1.4.1.4491.2.1.20.1.10.1.2";
        }

        leaf docsIf3RxModuleCfgFirstCenterFrequency {
          type uint32;
          units "Hz";
          status obsolete;
          description
           "This attribute represents the center frequency,
            in Hz, and a multiple of 62500, that indicates the lowest
            frequency channel of the Receive Module, or 0 if not
            applicable to the Receive Module.";
          reference
           "DOCSIS 3.0 MAC and Upper Layer Protocols Interface
            Specification CM-SP-MULPIv3.0-I08-080522, Receive Module
            First Channel Center Frequency Assignment section in the
            Common Radio Frequency Interface Encodings Annex.";
          smiv2:max-access "read-write";
          smiv2:oid "1.3.6.1.4.1.4491.2.1.20.1.10.1.3";
        }

        leaf docsIf3RxModuleCfgRowStatus {
          type snmpv2-tc:RowStatus;
          status obsolete;
          description
           "The status of this instance.";
          smiv2:max-access "read-write";
          smiv2:oid "1.3.6.1.4.1.4491.2.1.20.1.10.1.4";
        }
      }
    }

    container docsIf3RxModuleStatusTable {
      description
       "The Receive Module Status object provides a read-only
        view of the statically configured and dynamically
        created Receive Modules within an RCC.";
      smiv2:oid "1.3.6.1.4.1.4491.2.1.20.1.11";

      list docsIf3RxModuleStatusEntry {
        key "ifIndex docsIf3RccStatusRcpId docsIf3RccStatusRccStatusId docsIf3RxModuleStatusRmId";
        description
         "The conceptual row of docsIf3RxModuleStatusTable.
          The ifIndex key corresponds to the MAC Domain interface
          where the RCC is configured. When this object is defined
          on the CM, the value of RccStatusId is always 1.";
        smiv2:oid "1.3.6.1.4.1.4491.2.1.20.1.11.1";

        leaf ifIndex {
          type leafref {
            path "/if-mib:IF-MIB/if-mib:ifTable/if-mib:ifEntry/if-mib:ifIndex";
          }
        }

        leaf docsIf3RccStatusRcpId {
          type leafref {
            path "/DOCS-IF3-MIB:DOCS-IF3-MIB/DOCS-IF3-MIB:docsIf3RccStatusTable/DOCS-IF3-MIB:docsIf3RccStatusEntry/DOCS-IF3-MIB:docsIf3RccStatusRcpId";
          }
        }

        leaf docsIf3RccStatusRccStatusId {
          type leafref {
            path "/DOCS-IF3-MIB:DOCS-IF3-MIB/DOCS-IF3-MIB:docsIf3RccStatusTable/DOCS-IF3-MIB:docsIf3RccStatusEntry/DOCS-IF3-MIB:docsIf3RccStatusRccStatusId";
          }
        }

        leaf docsIf3RxModuleStatusRmId {
          type uint32 {
            range "1..255";
          }
          description
           "This key represents an identifier of a Receive Module
            instance within the Receive Channel Profile.";
          reference
           "DOCSIS 3.0 MAC and Upper Layer Protocols Interface
            Specification CM-SP-MULPIv3.0-I08-080522, Receive
            Module Index section in the Common Radio Frequency
            Interface Encodings Annex.";
          smiv2:max-access "not-accessible";
          smiv2:oid "1.3.6.1.4.1.4491.2.1.20.1.11.1.1";
        }

        leaf docsIf3RxModuleStatusRmRmConnectivityId {
          type uint32 {
            range "0..255";
          }
          description
           "This attribute represents the Receive Module to which
            this Receive Module connects. Requirements for
            module connectivity are detailed in the RmRmConnectivityId
            of the RccCfg object. A value of zero indicates that the
            Receive Module TLV is omitted from the RCC.";
          smiv2:max-access "read-only";
          smiv2:oid "1.3.6.1.4.1.4491.2.1.20.1.11.1.2";
        }

        leaf docsIf3RxModuleStatusFirstCenterFrequency {
          type uint32;
          units "Hz";
          description
           "This attribute represents the low frequency channel
            of the Receive Module, or 0 if not applicable to the
            Receive Module.";
          smiv2:max-access "read-only";
          smiv2:oid "1.3.6.1.4.1.4491.2.1.20.1.11.1.3";
        }
      }
    }

    container docsIf3MdNodeStatusTable {
      description
       "This object reports the MD-DS-SG-ID and MD-US-SG-ID
        associated with a MD-CM-SG-ID within a MAC Domain
        and the Fiber Nodes reached by the MD-CM-SG.";
      smiv2:oid "1.3.6.1.4.1.4491.2.1.20.1.12";

      list docsIf3MdNodeStatusEntry {
        key "ifIndex docsIf3MdNodeStatusNodeName docsIf3MdNodeStatusMdCmSgId";
        description
         "The conceptual row of docsIf3MdNodeStatusTable.
          The ifIndex key corresponds to the MAC Domain interface
          where the MD-CM-SG-ID is configured.";
        smiv2:oid "1.3.6.1.4.1.4491.2.1.20.1.12.1";

        leaf ifIndex {
          type leafref {
            path "/if-mib:IF-MIB/if-mib:ifTable/if-mib:ifEntry/if-mib:ifIndex";
          }
        }

        leaf docsIf3MdNodeStatusNodeName {
          type clab-topo:NodeName;
          description
           "This key represents the name of a fiber node associated
            with a MD-CM-SG of a MAC Domain.";
          smiv2:max-access "not-accessible";
          smiv2:oid "1.3.6.1.4.1.4491.2.1.20.1.12.1.1";
        }

        leaf docsIf3MdNodeStatusMdCmSgId {
          type uint32 {
            range "1..4294967295";
          }
          description
           "This attribute is a key and indicates the MD-CM-SG-ID
            of this instance. A particular MdCmSgId in a MAC Domain
            is associated with one or more Fiber Nodes.";
          smiv2:max-access "not-accessible";
          smiv2:oid "1.3.6.1.4.1.4491.2.1.20.1.12.1.2";
        }

        leaf docsIf3MdNodeStatusMdDsSgId {
          type uint32 {
            range "1..255";
          }
          description
           "This attribute corresponds to the MD-DS-SG-ID of
            the MD-CM-SG of this object instance. The MdDsSgId values
            are unique within a MAC Domain.";
          smiv2:max-access "read-only";
          smiv2:oid "1.3.6.1.4.1.4491.2.1.20.1.12.1.3";
        }

        leaf docsIf3MdNodeStatusMdUsSgId {
          type uint32 {
            range "1..255";
          }
          description
           "This attribute corresponds to the MD-US-SG-ID of
            the MD-CM-SG of this object instance. The MdUsSgId values
            are unique within a MAC Domain.";
          smiv2:max-access "read-only";
          smiv2:oid "1.3.6.1.4.1.4491.2.1.20.1.12.1.4";
        }
      }
    }

    container docsIf3MdDsSgStatusTable {
      description
       "This object returns the list of downstream channel
        associated with a MAC Domain MD-DS-SG-ID.";
      smiv2:oid "1.3.6.1.4.1.4491.2.1.20.1.13";

      list docsIf3MdDsSgStatusEntry {
        key "ifIndex docsIf3MdDsSgStatusMdDsSgId";
        description
         "The conceptual row of docsIf3MdDsSgStatusTable.
          The ifIndex key corresponds to the MAC Domain interface
          where the MD-DS-SG-ID is configured.
          The CMTS is not required to persist instances of this
          object across reinitializations.";
        smiv2:oid "1.3.6.1.4.1.4491.2.1.20.1.13.1";

        leaf ifIndex {
          type leafref {
            path "/if-mib:IF-MIB/if-mib:ifTable/if-mib:ifEntry/if-mib:ifIndex";
          }
        }

        leaf docsIf3MdDsSgStatusMdDsSgId {
          type uint32 {
            range "1..255";
          }
          description
           "This key represents a MD-DS-SG-ID in a Mac Domain.";
          smiv2:max-access "not-accessible";
          smiv2:oid "1.3.6.1.4.1.4491.2.1.20.1.13.1.1";
        }

        leaf docsIf3MdDsSgStatusChSetId {
          type DOCS-IF3-MIB:ChSetId;
          description
           "This attribute represents a reference to the list
            of downstream channels of the MD-DS-SG-ID.";
          smiv2:max-access "read-only";
          smiv2:oid "1.3.6.1.4.1.4491.2.1.20.1.13.1.2";
        }
      }
    }

    container docsIf3MdUsSgStatusTable {
      description
       "This object returns the list of upstream channels
        associated with a MAC Domain MD-US-SG-ID.";
      smiv2:oid "1.3.6.1.4.1.4491.2.1.20.1.14";

      list docsIf3MdUsSgStatusEntry {
        key "ifIndex docsIf3MdUsSgStatusMdUsSgId";
        description
         "The conceptual row of docsIf3MdUsSgStatusTable.
          The ifIndex key corresponds to the MAC Domain interface
          where the MD-DS-SG-ID is configured.
          The CMTS is not required to persist instances of this
          object across reinitializations.";
        smiv2:oid "1.3.6.1.4.1.4491.2.1.20.1.14.1";

        leaf ifIndex {
          type leafref {
            path "/if-mib:IF-MIB/if-mib:ifTable/if-mib:ifEntry/if-mib:ifIndex";
          }
        }

        leaf docsIf3MdUsSgStatusMdUsSgId {
          type uint32 {
            range "1..255";
          }
          description
           "This key represents a MD-US-SG-ID in a Mac Domain.";
          smiv2:max-access "not-accessible";
          smiv2:oid "1.3.6.1.4.1.4491.2.1.20.1.14.1.1";
        }

        leaf docsIf3MdUsSgStatusChSetId {
          type DOCS-IF3-MIB:ChSetId;
          description
           "This attribute represents a reference to the list
            of upstream channels of the MD-US-SG-ID.";
          smiv2:max-access "read-only";
          smiv2:oid "1.3.6.1.4.1.4491.2.1.20.1.14.1.2";
        }
      }
    }

    container docsIf3MdUsToDsChMappingTable {
      description
       "This object returns the set of downstream channels
        that carry UCDs and MAPs for a particular upstream channel
        in a MAC Domain.";
      smiv2:oid "1.3.6.1.4.1.4491.2.1.20.1.15";

      list docsIf3MdUsToDsChMappingEntry {
        key "docsIf3MdUsToDsChMappingUsIfIndex docsIf3MdUsToDsChMappingDsIfIndex docsIf3MdUsToDsChMappingMdIfIndex";
        description
         "The conceptual row of docsIf3MdUsToDsChMappingTable.";
        smiv2:oid "1.3.6.1.4.1.4491.2.1.20.1.15.1";

        leaf docsIf3MdUsToDsChMappingUsIfIndex {
          type if-mib:InterfaceIndex;
          description
           "This key represents the interface index of the upstream
            channel to which this instance applies.";
          smiv2:max-access "not-accessible";
          smiv2:oid "1.3.6.1.4.1.4491.2.1.20.1.15.1.1";
        }

        leaf docsIf3MdUsToDsChMappingDsIfIndex {
          type if-mib:InterfaceIndex;
          description
           "This key represents the interface index of a downstream
            channel carrying in UCDs and Maps associated with
            the upstream channel defined by this instance.";
          smiv2:max-access "not-accessible";
          smiv2:oid "1.3.6.1.4.1.4491.2.1.20.1.15.1.2";
        }

        leaf docsIf3MdUsToDsChMappingMdIfIndex {
          type if-mib:InterfaceIndex;
          description
           "This key represents the MAC domain of the upstream
            and downstream channels of this instance.";
          smiv2:max-access "read-only";
          smiv2:oid "1.3.6.1.4.1.4491.2.1.20.1.15.1.3";
        }
      }
    }

    container docsIf3MdCfgTable {
      description
       "This object contains MAC domain level control and
        configuration attributes.";
      smiv2:oid "1.3.6.1.4.1.4491.2.1.20.1.16";

      list docsIf3MdCfgEntry {
        key "ifIndex";
        description
         "The conceptual row of docsIf3MdCfgTable.
          The CMTS persists all instances of MdCfg across
          reinitializations.
          The ifIndex key corresponds to the MAC Domain interface.";
        smiv2:oid "1.3.6.1.4.1.4491.2.1.20.1.16.1";

        leaf ifIndex {
          type leafref {
            path "/if-mib:IF-MIB/if-mib:ifTable/if-mib:ifEntry/if-mib:ifIndex";
          }
        }

        leaf docsIf3MdCfgMddInterval {
          type uint32 {
            range "1..2000";
          }
          units "milliseconds";
          description
           "This attribute configures the interval for the insertion
            of MDD messages in each downstream channel of
            a MAC Domain.";
          reference
           "DOCSIS 3.0 MAC and Upper Layer Protocols Interface
            Specification CM-SP-MULPIv3.0-I08-080522, Parameters
            and Constants Annex.";
          smiv2:defval "2000";
          smiv2:max-access "read-write";
          smiv2:oid "1.3.6.1.4.1.4491.2.1.20.1.16.1.1";
        }

        leaf docsIf3MdCfgIpProvMode {
          type enumeration {
            enum "ipv4Only" {
              value "0";
            }
            enum "ipv6Only" {
              value "1";
            }
            enum "alternate" {
              value "2";
            }
            enum "dualStack" {
              value "3";
            }
          }
          description
           "This attribute configures the CMTS IP provisioning
            mode for a MAC Domain. 
            When this attribute is set to 'ipv4Only' the CM will acquire
            a single IPv4 address for the CM management stack.
            When this attribute is set to 'ipv6Only' the CM will acquire
            a single IPv6 address for the CM management stack.
            When this attribute is set to 'alternate' the CM will acquire a
            single IPv6 address for the CM management stack and, if failures
            occur, the CM will fall back to provision and operation with
            an IPv4 address.
            When this attribute is set to 'dualStack' the CM will acquire both
            an IPv6 and IPv4 address for provisioning and operation.";
          reference
           "DOCSIS 3.0 MAC and Upper Layer Protocols Interface
            Specification CM-SP-MULPIv3.0-I08-080522, IP Initialization
            Parameters TLV section.";
          smiv2:defval "ipv6Only";
          smiv2:max-access "read-write";
          smiv2:oid "1.3.6.1.4.1.4491.2.1.20.1.16.1.2";
        }

        leaf docsIf3MdCfgCmStatusEvCtlEnabled {
          type boolean;
          description
           "If set to 'true', this attribute enables the signaling
            of the CM-Status Event reporting mechanism.";
          reference
           "DOCSIS 3.0 MAC and Upper Layer Protocols Interface
            Specification CM-SP-MULPIv3.0-I08-080522, CM-STATUS
            Event Control section ";
          smiv2:defval "true";
          smiv2:max-access "read-write";
          smiv2:oid "1.3.6.1.4.1.4491.2.1.20.1.16.1.3";
        }

        leaf docsIf3MdCfgUsFreqRange {
          type enumeration {
            enum "standard" {
              value "0";
            }
            enum "extended" {
              value "1";
            }
          }
          description
           "This attribute indicates in MDD messages the upstream
            frequency upper band edge of an upstream Channel.
            
            A value 'standard' means Standard Frequency Range and
            a value 'extended' means Extended Frequency Range.";
          reference
           "DOCSIS 3.0 MAC and Upper Layer Protocols Interface
            Specification CM-SP-MULPIv3.0-I08-080522, Upstream
            Frequency Upper Band Edge TLV section.";
          smiv2:defval "standard";
          smiv2:max-access "read-write";
          smiv2:oid "1.3.6.1.4.1.4491.2.1.20.1.16.1.4";
        }

        leaf docsIf3MdCfgMcastDsidFwdEnabled {
          type boolean;
          description
           "If set to 'true', this attribute enables the CMTS to
            use IP Multicast DSID Forwarding (MDF) for the MAC domain.";
          reference
           "DOCSIS 3.0 MAC and Upper Layer Protocols Interface
            Specification CM-SP-MULPIv3.0-I08-080522, Multicast
            DSID-based Forwarding (MDF) Modes section in the
            Compatibility with Previous Versions of DOCSIS Annex.";
          smiv2:defval "true";
          smiv2:max-access "read-write";
          smiv2:oid "1.3.6.1.4.1.4491.2.1.20.1.16.1.5";
        }

        leaf docsIf3MdCfgMultRxChModeEnabled {
          type boolean;
          description
           "If set to 'true', this attribute enables Downstream
            Channel Bonding for the MAC Domain.";
          reference
           "DOCSIS 3.0 MAC and Upper Layer Protocols Interface
            Specification CM-SP-MULPIv3.0-I08-080522, Downstream
            Channel Bonding section.";
          smiv2:defval "true";
          smiv2:max-access "read-write";
          smiv2:oid "1.3.6.1.4.1.4491.2.1.20.1.16.1.6";
        }

        leaf docsIf3MdCfgMultTxChModeEnabled {
          type boolean;
          description
           "If set to 'true', this attribute enables Multiple
            Transmit Channel (MTC) Mode for the MAC Domain.";
          reference
           "DOCSIS 3.0 MAC and Upper Layer Protocols Interface
            Specification CM-SP-MULPIv3.0-I08-080522, Upstream
            Channel Bonding section.";
          smiv2:defval "true";
          smiv2:max-access "read-write";
          smiv2:oid "1.3.6.1.4.1.4491.2.1.20.1.16.1.7";
        }

        leaf docsIf3MdCfgEarlyAuthEncrCtrl {
          type enumeration {
            enum "disableEae" {
              value "1";
            }
            enum "enableEaeRangingBasedEnforcement" {
              value "2";
            }
            enum "enableEaeCapabilityBasedEnforcement" {
              value "3";
            }
            enum "enableEaeTotalEnforcement" {
              value "4";
            }
          }
          description
           "This attribute enables or disables early authentication
            and encryption (EAE) signaling for the MAC Domain.
            It also defines the type of EAE enforcement in
            the case that EAE is enabled.
            If set to 'disableEAE', EAE is disabled for the MAC Domain.
            
            If set to 'enableEaeRangingBasedEnforcement',
            'enableEaeCapabilityBasedEnforcement'
            or 'enableEaeTotalEnforcement',
            EAE is enabled for the MAC Domain.
            
            The following EAE enforcement methods are defined in
            the case where EAE signaling is enabled:
            The option 'enableEaeRangingBasedEnforcement' indicates
            EAE is enforced on CMs that perform ranging
            with a B-INIT-RNG-REQ message.
            The option 'enableEaeCapabilityBasedEnforcement'
            indicates EAE is enforced on CMs that perform ranging
            with a B-INIT-RNG-REQ message in which the EAE capability
            flag is set.
            The option 'enableEaeTotalEnforcement' indicates
            EAE is enforced on all CMs regardless of their EAE
            capabilities.";
          reference
           "DOCSIS 3.0 Security Specification CM-SP-SECv3.0-I06-071206,
            Early Authentication and Encryption section.";
          smiv2:defval "enableEaeRangingBasedEnforcement";
          smiv2:max-access "read-write";
          smiv2:oid "1.3.6.1.4.1.4491.2.1.20.1.16.1.8";
        }

        leaf docsIf3MdCfgTftpProxyEnabled {
          type boolean;
          description
           "If set to 'true', this attribute enables TFTP Proxy
            functionality for the MAC Domain.";
          reference
           "DOCSIS 3.0 Security Specification CM-SP-SECv3.0-I06-071206,
            TFTP Configuration File Security section.";
          smiv2:defval "true";
          smiv2:max-access "read-write";
          smiv2:oid "1.3.6.1.4.1.4491.2.1.20.1.16.1.9";
        }

        leaf docsIf3MdCfgSrcAddrVerifEnabled {
          type boolean;
          description
           "If set to 'true', this attribute enables Source Address
            Verification (SAV) functionality for the MAC
            Domain.";
          reference
           "DOCSIS 3.0 Security Specification CM-SP-SECv3.0-I06-071206,
            Source Address Verification section.";
          smiv2:defval "true";
          smiv2:max-access "read-write";
          smiv2:oid "1.3.6.1.4.1.4491.2.1.20.1.16.1.10";
        }

        leaf docsIf3MdCfgDownChannelAnnex {
          type enumeration {
            enum "unknown" {
              value "1";
            }
            enum "other" {
              value "2";
            }
            enum "annexA" {
              value "3";
            }
            enum "annexB" {
              value "4";
            }
            enum "annexC" {
              value "5";
            }
          }
          description
           "This attribute defines the ITU-J-83 Annex being used 
            for this MAC Domain.  The value of this attribute 
            indicates the conformance of the implementation to 
            important regional cable standards.  
            Valid enumerations for the attribute are:
            unknown
            other
            annexA : Annex A from ITU-J83 is used.
            annexB : Annex B from ITU-J83 is used.
            annexC : Annex C from ITU-J83 is used. 
            Values 6-255 are reserved.";
          smiv2:defval "unknown";
          smiv2:max-access "read-only";
          smiv2:oid "1.3.6.1.4.1.4491.2.1.20.1.16.1.11";
        }

        leaf docsIf3MdCfgCmUdcEnabled {
          type boolean;
          description
           "If set to 'true', this attribute instructs the CMTS MAC 
            Domain to enable Upstream Drop Classifiers (UDC) for the 
            CMs attempting registration in this MAC Domain.";
          reference
           "DOCSIS 3.0 MAC and Upper Layer Protocols Interface
            Specification CM-SP-MULPIv3.0-I08-080522, Subscriber Management
            TLVs section in the Common Radio Frequency Interface Encodings
            Annex.";
          smiv2:defval "false";
          smiv2:max-access "read-write";
          smiv2:oid "1.3.6.1.4.1.4491.2.1.20.1.16.1.12";
        }

        leaf docsIf3MdCfgSendUdcRulesEnabled {
          type boolean;
          description
           "If set to 'true' and when the CM signals to the CMTS
            'Upstream Drop Classifier Group ID' encodings, this attribute
            instructs the CMTS MAC Domain to send the Subscriber 
            Management Filters rules associated with the 'Upstream Drop
            Classifier Group ID' encodings to the CM in the form of UDCs 
            when the following conditions occurs:
            - The attribute CmUdcEnabled value for this MAC Domain 
              is set to 'true', and 
            - The CM has the UDC capability advertised as supported. 
            If there is no a single Subscriber Management Filter 
            configured in the CMTS for the CM's signaled UDC Group ID,
            the CMTS does not send UDC encodings to the CM.
            
            It is vendor specific whether the CMTS maintains enforcement
            of the CM signaled or default Subscriber Management Filter 
            groups in the upstream direction.";
          reference
           "DOCSIS 3.0 MAC and Upper Layer Protocols Interface
            Specification CM-SP-MULPIv3.0-I08-080522, Subscriber Management
            TLVs section in the Common Radio Frequency Interface Encodings
            Annex.";
          smiv2:defval "false";
          smiv2:max-access "read-write";
          smiv2:oid "1.3.6.1.4.1.4491.2.1.20.1.16.1.13";
        }

        leaf docsIf3MdCfgServiceTypeIdList {
          type snmp-target:SnmpTagList;
          description
           "This attribute indicates the list of Service Type IDs 
            associated with the MAC Domain. 
            During the CM registration process the CMTS will attempt to
            redirect the CM to a MAC Domain where the CM' Service Type TLV
            is contained in this attribute.";
          reference
           "DOCSIS 3.0 MAC and Upper Layer Protocols Interface
            Specification CM-SP-MULPIv3.0-I08-080522, Service Type 
            Identifier section in the Common Radio Frequency Interface 
            Encodings Annex.";
          smiv2:defval "";
          smiv2:max-access "read-write";
          smiv2:oid "1.3.6.1.4.1.4491.2.1.20.1.16.1.14";
        }

        leaf docsIf3MdCfgBpi2EnforceCtrl {
          type enumeration {
            enum "disable" {
              value "0";
            }
            enum "qosCfgFileWithBpi2AndCapabPrivSupportEnabled" {
              value "1";
            }
            enum "qosCfgFileWithBpi2Enabled" {
              value "2";
            }
            enum "qosCfgFile" {
              value "3";
            }
            enum "total" {
              value "4";
            }
          }
          description
           "This attribute indicates the level of BPI+ enforcement
            policies with the MAC Domain.
            
            The following BPI+ enforcement policies are defined in
            the case where BPI+ is enabled:
            
            The option 'disable' indicates the CMTS does not enforce BPI+.
            
            The option 'qosCfgFileWithBpi2AndCapabPrivSupportEnabled' 
            indicates the CMTS enforces BPI+ on CMs that register with a 
            DOCSIS 1.1 style configuration file with parameters indicating
            BPI+ is enabled (missing TLV 29 or containing TLV 29 set to 
            enable) and with a Modem Capabilities Privacy Support TLV (5.6) 
            set to BPI+ support.
            
            The option 'qosCfgFileWithBpi2Enabled' indicates the CMTS 
            enforces BPI+ on CMs that register with a DOCSIS 1.1 style 
            configuration file with parameters indicating BPI+ is enabled 
            (missing TLV 29 or containing TLV 29 set to enable).
            
            The option 'qosCfgFile' indicates the CMTS enforces BPI+ on CMs
            that register with a DOCSIS 1.1 style configuration file.
            
            The option 'total' indicates the CMTS enforces BPI+ on all CMs.";
          reference
           "DOCSIS 3.0 Security Specification CM-SP-SECv3.0-I12-100115,
            BPI+ Enforce section.";
          smiv2:defval "qosCfgFileWithBpi2Enabled";
          smiv2:max-access "read-write";
          smiv2:oid "1.3.6.1.4.1.4491.2.1.20.1.16.1.15";
        }

        leaf docsIf3MdCfgEnergyMgt1x1Enabled {
          type int32 {
            range "0..1";
          }
          description
           "This attribute indicates whether the CMTS is configured for 
            1x1 Energy Management Mode of operation on a per MAC Domain 
            basis. If this attribute is set to 'true', the CMTS is 
            configured for 1x1 Energy Management Mode of operation on this
            MAC Domain. If this attribute is set to 'false', the Energy 
            Management 1x1 Mode of operation is disabled in the CMTS on 
            this MAC Domain";
          reference
           "DOCSIS 3.0 MAC and Upper Layer Protocols Interface
            Specification CM-SP-MULPIv3.0-I20-121113,
            Energy Management Capabilities section.";
          smiv2:defval "0";
          smiv2:max-access "read-write";
          smiv2:oid "1.3.6.1.4.1.4491.2.1.20.1.16.1.16";
        }
      }
    }

    container docsIf3BondingGrpCfgTable {
      description
       "This object defines statically configured Downstream
        Bonding Groups and Upstream Bonding Groups on
        the CMTS.
        This object supports the creation and deletion of multiple
        instances.
        Creation of a new instance of this object requires the
        ChList attribute to be set.";
      smiv2:oid "1.3.6.1.4.1.4491.2.1.20.1.17";

      list docsIf3BondingGrpCfgEntry {
        key "ifIndex docsIf3BondingGrpCfgDir docsIf3BondingGrpCfgCfgId";
        description
         "The conceptual row of docsIf3BondingGrpCfgTable.
          The ifIndex key corresponds to the MAC Domain interface
          where the Bonding Group is configured.
          The CMTS persists all instances of BondingGrpCfg
          across reinitializations.";
        smiv2:oid "1.3.6.1.4.1.4491.2.1.20.1.17.1";

        leaf ifIndex {
          type leafref {
            path "/if-mib:IF-MIB/if-mib:ifTable/if-mib:ifEntry/if-mib:ifIndex";
          }
        }

        leaf docsIf3BondingGrpCfgDir {
          type DOCS-IF3-MIB:IfDirection;
          description
           "This attribute defines the ordered list of channels
            that comprise the channel set";
          smiv2:max-access "not-accessible";
          smiv2:oid "1.3.6.1.4.1.4491.2.1.20.1.17.1.1";
        }

        leaf docsIf3BondingGrpCfgCfgId {
          type uint32 {
            range "1..65535";
          }
          description
           "This key represents the configured bonding group
            identifier in the indicated direction for the MAC Domain.
            This attribute is used for the sole purpose of tracking
            bonding groups defined by management systems.";
          smiv2:max-access "not-accessible";
          smiv2:oid "1.3.6.1.4.1.4491.2.1.20.1.17.1.2";
        }

        leaf docsIf3BondingGrpCfgChList {
          type DOCS-IF3-MIB:ChannelList {
            length "2..255";
          }
          description
           "This attribute contains the list of channels of the
            bonding group.";
          smiv2:max-access "read-write";
          smiv2:oid "1.3.6.1.4.1.4491.2.1.20.1.17.1.3";
        }

        leaf docsIf3BondingGrpCfgSfProvAttrMask {
          type binary {
            length "0..16";
          }
          description
           "This attribute represents the Provisioned Attribute
            Mask encoding for the bonding group.";
          smiv2:defval "'80000000'H";
          smiv2:max-access "read-write";
          smiv2:oid "1.3.6.1.4.1.4491.2.1.20.1.17.1.4";
        }

        leaf docsIf3BondingGrpCfgDsidReseqWaitTime {
          type uint32 {
            range "0..180|255";
          }
          units "hundredMicroseconds";
          description
           "For a Downstream Bonding Group, this attribute provides
            the DSID Resequencing Wait Time that is to be used
            for all DSIDs associated with this Downstream Bonding
            Group.  The value of 255 indicates that the DSID
            Resequencing Wait Time is determined by the CMTS. The
            value zero in not supported for downstream  bonding
            groups.
            For an Upstream Bonding Group, this attribute has no
            meaning and returns the value 0.";
          reference
           "DOCSIS 3.0 MAC and Upper Layer Protocols Interface
            Specification CM-SP-MULPIv3.0-I08-080522, Service Flow
            Assignment section.";
          smiv2:defval "255";
          smiv2:max-access "read-write";
          smiv2:oid "1.3.6.1.4.1.4491.2.1.20.1.17.1.5";
        }

        leaf docsIf3BondingGrpCfgDsidReseqWarnThrshld {
          type uint32 {
            range "0..179|255";
          }
          units "hundredMicroseconds";
          description
           "For a Downstream Bonding Group, this attribute provides
            the DSID Resequencing Warning Threshold that
            is to be used for all DSIDs associated with this Downstream
            Bonding Group. The value of 255 indicates that
            the DSID Resequencing Warning Threshold is determined
            by the CMTS.  The value of 0 indicates that the threshold
            warnings are disabled.  When 
            the value of DsidReseqWaitTime is not equal to 0 or 255,
            the CMTS must ensure that the value of this object is either 
            255 or less than the value of DsidReseqWaitTime.";
          smiv2:defval "255";
          smiv2:max-access "read-write";
          smiv2:oid "1.3.6.1.4.1.4491.2.1.20.1.17.1.6";
        }

        leaf docsIf3BondingGrpCfgRowStatus {
          type snmpv2-tc:RowStatus;
          description
           "The status of this instance.";
          smiv2:max-access "read-write";
          smiv2:oid "1.3.6.1.4.1.4491.2.1.20.1.17.1.7";
        }
      }
    }

    container docsIf3DsBondingGrpStatusTable {
      description
       "This object returns administratively-configured
        and CMTS defined downstream bonding groups.";
      smiv2:oid "1.3.6.1.4.1.4491.2.1.20.1.18";

      list docsIf3DsBondingGrpStatusEntry {
        key "ifIndex docsIf3DsBondingGrpStatusChSetId";
        description
         "The conceptual row of docsIf3DsBondingGrpStatusTable.
          The ifIndex key corresponds to the MAC Domain interface
          where the Bonding Group is configured.";
        smiv2:oid "1.3.6.1.4.1.4491.2.1.20.1.18.1";

        leaf ifIndex {
          type leafref {
            path "/if-mib:IF-MIB/if-mib:ifTable/if-mib:ifEntry/if-mib:ifIndex";
          }
        }

        leaf docsIf3DsBondingGrpStatusChSetId {
          type DOCS-IF3-MIB:ChSetId;
          description
           "This key represents the identifier for the Downstream
            Bonding Group or the single-downstream channel
            of this instance.";
          smiv2:max-access "not-accessible";
          smiv2:oid "1.3.6.1.4.1.4491.2.1.20.1.18.1.1";
        }

        leaf docsIf3DsBondingGrpStatusMdDsSgId {
          type uint32 {
            range "0..255";
          }
          description
           "This attribute corresponds to the MD-DS-SG-ID that
            includes all the downstream channels of the Downstream
            Bonding Group. The value zero indicates that the
            bonding group does not contain channels from a single
            MD-DS-SG and therefore the bonding group is not valid
            and usable.";
          smiv2:max-access "read-only";
          smiv2:oid "1.3.6.1.4.1.4491.2.1.20.1.18.1.2";
        }

        leaf docsIf3DsBondingGrpStatusCfgId {
          type uint32 {
            range "0..65535";
          }
          description
           "This attribute provides the BondingGrpCfgId for
            the downstream bonding group if it was configured.
            Otherwise, the zero value indicates that the CMTS will
            define the bonding group.";
          smiv2:max-access "read-only";
          smiv2:oid "1.3.6.1.4.1.4491.2.1.20.1.18.1.3";
        }
      }
    }

    container docsIf3UsBondingGrpStatusTable {
      description
       "This object returns administratively-configured
        and CMTS-defined upstream bonding groups.";
      smiv2:oid "1.3.6.1.4.1.4491.2.1.20.1.19";

      list docsIf3UsBondingGrpStatusEntry {
        key "ifIndex docsIf3UsBondingGrpStatusChSetId";
        description
         "The conceptual row of docsIf3UsBondingGrpStatusTable.
          The ifIndex key corresponds to the MAC Domain interface
          where the Bonding Group is configured.";
        smiv2:oid "1.3.6.1.4.1.4491.2.1.20.1.19.1";

        leaf ifIndex {
          type leafref {
            path "/if-mib:IF-MIB/if-mib:ifTable/if-mib:ifEntry/if-mib:ifIndex";
          }
        }

        leaf docsIf3UsBondingGrpStatusChSetId {
          type DOCS-IF3-MIB:ChSetId;
          description
           "This key represents the identifier for the Upstream
            Bonding Group or the single-upstream channel of this
            instance.";
          smiv2:max-access "not-accessible";
          smiv2:oid "1.3.6.1.4.1.4491.2.1.20.1.19.1.1";
        }

        leaf docsIf3UsBondingGrpStatusMdUsSgId {
          type uint32 {
            range "0..255";
          }
          description
           "This attribute corresponds to the MD-US-SG-ID that
            includes all the upstream channels of the Upstream
            Bonding Group. The value zero indicates that the bonding
            group does not contain channels from a single MD-US-SG
            and therefore the bonding group is not valid
            and usable.";
          smiv2:max-access "read-only";
          smiv2:oid "1.3.6.1.4.1.4491.2.1.20.1.19.1.2";
        }

        leaf docsIf3UsBondingGrpStatusCfgId {
          type uint32 {
            range "0..4294967295";
          }
          description
           "This attribute provides the BondingGrpCfgId for
            the upstream bonding group if it was configured.
            Otherwise, the zero value indicates that the CMTS
            defines the bonding group.";
          smiv2:max-access "read-only";
          smiv2:oid "1.3.6.1.4.1.4491.2.1.20.1.19.1.3";
        }
      }
    }

    container docsIf3UsChExtTable {
      description
       "This object defines management extensions for upstream
        channels, in particular SCDMA parameters.";
      smiv2:oid "1.3.6.1.4.1.4491.2.1.20.1.20";

      list docsIf3UsChExtEntry {
        key "ifIndex";
        description
         "The conceptual row of docsIf3UsChExtTable.
          The ifIndex key corresponds to each of the upstream
          channels.";
        smiv2:oid "1.3.6.1.4.1.4491.2.1.20.1.20.1";

        leaf ifIndex {
          type leafref {
            path "/if-mib:IF-MIB/if-mib:ifTable/if-mib:ifEntry/if-mib:ifIndex";
          }
        }

        leaf docsIf3UsChExtSacCodeHoppingSelectionMode {
          type enumeration {
            enum "none" {
              value "0";
            }
            enum "sac1NoCodeHopping" {
              value "1";
            }
            enum "sac1CodeHoppingMode1" {
              value "2";
            }
            enum "sac2CodeHoppingMode2" {
              value "3";
            }
            enum "sac2NoCodeHopping" {
              value "4";
            }
          }
          description
           "This attribute indicates the selection mode for active
            codes and code hopping.
            'none'
               Non-SCDMA channel
            'sac1NoCodeHopping'
               Selectable active codes mode 1 and code hopping disabled
            
            'sac1CodeHoppingMode1'
               Selectable active codes mode 1 and code hopping mode
            1
            'sac2CodeHoppingMode2'
              Selectable active codes mode 2 and code hopping mode
            2
            'sac2NoCodeHopping'
              Selectable active codes mode 2 and code hopping disabled.";
          reference
           "DOCSIS 3.0 Physical Layer Specification
            CM-SP-PHYv3.0-I05-070803, Mini-slot Numbering
            Parameters in UCD section.";
          smiv2:max-access "read-only";
          smiv2:oid "1.3.6.1.4.1.4491.2.1.20.1.20.1.1";
        }

        leaf docsIf3UsChExtScdmaSelectionStringActiveCodes {
          type DOCS-IF3-MIB:ScdmaSelectionString;
          description
           "This attribute represents the active codes of the
            upstream channel and it is applicable only when
            SacCodeHoppingSelectionMode is 'sac2CodeHoppingMode2.";
          reference
           "DOCSIS 3.0 Physical Layer Specification
            CM-SP-PHYv3.0-I05-070803, Mini-slot Numbering
            Parameters in UCD section.";
          smiv2:max-access "read-only";
          smiv2:oid "1.3.6.1.4.1.4491.2.1.20.1.20.1.2";
        }
      }
    }

    container docsIf3UsChSetTable {
      description
       "This object defines a set of upstream channels. These
        channel sets may be associated with channel bonding
        groups, MD-US-SGs, MD-CM-SGs, or any other channel
        set that the CMTS may derive from other CMTS processes.";
      reference
       "DOCSIS 3.0 MAC and Upper Layer Protocols Interface
        Specification CM-SP-MULPIv3.0-I08-080522, Partial
        Service Encoding section and Cable Modem Attribute
        Masks section in the Common Radio Frequency Interface
        Encodings Annex.";
      smiv2:oid "1.3.6.1.4.1.4491.2.1.20.1.22";

      list docsIf3UsChSetEntry {
        key "ifIndex docsIf3UsChSetId";
        description
         "The conceptual row of docsIf3UsChSetTable.
          The ifIndex key corresponds to the MAC Domain interface
          where the upstream channel set is defined.";
        smiv2:oid "1.3.6.1.4.1.4491.2.1.20.1.22.1";

        leaf ifIndex {
          type leafref {
            path "/if-mib:IF-MIB/if-mib:ifTable/if-mib:ifEntry/if-mib:ifIndex";
          }
        }

        leaf docsIf3UsChSetId {
          type DOCS-IF3-MIB:ChSetId;
          description
           "This key defines a reference identifier for the upstream
            channel set within the MAC Domain.";
          smiv2:max-access "not-accessible";
          smiv2:oid "1.3.6.1.4.1.4491.2.1.20.1.22.1.1";
        }

        leaf docsIf3UsChSetChList {
          type DOCS-IF3-MIB:ChannelList {
            length "0|2..255";
          }
          description
           "This attribute defines the ordered list of channels
            that comprise the upstream channel set";
          smiv2:max-access "read-only";
          smiv2:oid "1.3.6.1.4.1.4491.2.1.20.1.22.1.2";
        }
      }
    }

    container docsIf3DsChSetTable {
      description
       "This object defines a set of downstream channels.
        These channel sets may be associated with channel bonding
        groups, MD-DS-SGs, MD-CM-SGs, or any other channel
        set that the CMTS may derive from other CMTS processes.";
      reference
       "DOCSIS 3.0 MAC and Upper Layer Protocols Interface
        Specification CM-SP-MULPIv3.0-I08-080522, Partial
        Service Encoding section and Cable Modem Attribute
        Masks section in the Common Radio Frequency Interface
        Encodings Annex.";
      smiv2:oid "1.3.6.1.4.1.4491.2.1.20.1.23";

      list docsIf3DsChSetEntry {
        key "ifIndex docsIf3DsChSetId";
        description
         "The conceptual row of docsIf3DsChSetTable.
          The ifIndex key corresponds to the MAC Domain interface
          where the downstream channel set is defined.";
        smiv2:oid "1.3.6.1.4.1.4491.2.1.20.1.23.1";

        leaf ifIndex {
          type leafref {
            path "/if-mib:IF-MIB/if-mib:ifTable/if-mib:ifEntry/if-mib:ifIndex";
          }
        }

        leaf docsIf3DsChSetId {
          type DOCS-IF3-MIB:ChSetId;
          description
           "This key defines a reference identifier for the downstream
            channel set within the MAC Domain.";
          smiv2:max-access "not-accessible";
          smiv2:oid "1.3.6.1.4.1.4491.2.1.20.1.23.1.1";
        }

        leaf docsIf3DsChSetChList {
          type DOCS-IF3-MIB:ChannelList {
            length "0|2..255";
          }
          description
           "This attribute defines the ordered list of channels
            that comprise the downstream channel set.";
          smiv2:max-access "read-only";
          smiv2:oid "1.3.6.1.4.1.4491.2.1.20.1.23.1.2";
        }
      }
    }

    container docsIf3SignalQualityExtTable {
      description
       "This object provides an in-channel received modulation
        error ratio metric for CM and CMTS.";
      smiv2:oid "1.3.6.1.4.1.4491.2.1.20.1.24";

      list docsIf3SignalQualityExtEntry {
        key "ifIndex";
        description
         "The conceptual row of docsIf3SignalQualityExtTable.
          At the CM, this object describes the received modulation 
          error ratio of each downstream channel. At the CMTS, 
          it describes the received modulation error ratio of each
          logical upstream channel. 
          An entry in this table exists for each ifEntry with an
          ifType of docsCableDownstream(128) for Cable Modems.
          For Cable Modem Termination Systems, an entry exists for 
          each ifEntry with an ifType of docsCableUpstreamChannel(205).";
        smiv2:oid "1.3.6.1.4.1.4491.2.1.20.1.24.1";

        leaf ifIndex {
          type leafref {
            path "/if-mib:IF-MIB/if-mib:ifTable/if-mib:ifEntry/if-mib:ifIndex";
          }
        }

        leaf docsIf3SignalQualityExtRxMER {
          type docs-if:TenthdB {
            range "-2147483648..2147483647";
          }
          units "TenthdB";
          description
           "RxMER provides an in-channel received Modulation
            Error Ratio (MER). RxMER is defined as an estimate,
            provided by the demodulator, of the ratio:
            (average constellation energy with equally likely
            symbols) / (average squared magnitude of error vector)
            
            RxMER is measured just prior to FEC (trellis/Reed-Solomon)
            decoding. RxMER includes the effects of the
            HFC channel as well as implementation effects of the
            modulator and demodulator. Error vector estimation
            may vary among demodulator implementations.  The CMTS
            RxMER is averaged over a given number of bursts at
            the burst receiver, which may correspond to transmissions
            from multiple users. In the case of S-CDMA mode,
            RxMER is measured on the de-spread signal.";
          smiv2:max-access "read-only";
          smiv2:oid "1.3.6.1.4.1.4491.2.1.20.1.24.1.1";
        }

        leaf docsIf3SignalQualityExtRxMerSamples {
          type uint32;
          description
           "RxMerSamples is a statistically significant number
            of symbols for the CM, or bursts for the CMTS, processed
            to arrive at the RxMER value. For the CMTS, the MER
            measurement includes only valid bursts that are not
            in contention regions.";
          smiv2:max-access "read-only";
          smiv2:oid "1.3.6.1.4.1.4491.2.1.20.1.24.1.2";
        }
      }
    }

    container docsIf3CmtsSignalQualityExtTable {
      description
       "This object provides metrics and parameters associated
        with received carrier, noise and interference
        power levels in the upstream channels of the CMTS.";
      smiv2:oid "1.3.6.1.4.1.4491.2.1.20.1.25";

      list docsIf3CmtsSignalQualityExtEntry {
        key "ifIndex";
        description
         "The conceptual row of docsIf3CmtsSignalQualityExtTable.
          The ifIndex key corresponds to each of the upstream
          channels.
          The CMTS is not required to persist the values of all 
          instances of CmtsSignalQualityExt across reinitialization.";
        smiv2:oid "1.3.6.1.4.1.4491.2.1.20.1.25.1";

        leaf ifIndex {
          type leafref {
            path "/if-mib:IF-MIB/if-mib:ifTable/if-mib:ifEntry/if-mib:ifIndex";
          }
        }

        leaf docsIf3CmtsSignalQualityExtCNIR {
          type docs-if:TenthdB;
          description
           "This attribute provides an upstream in-channel Carrier-to-Noise
            plus Interference Ratio (CNIR). CNIR
            is defined as the ratio of the expected commanded
            received signal power at the CMTS input, assuming
            QPSK0 modulation, to the noise plus
            interference in the channel.
            This measurement occurs prior to the point at which 
            the desired CM signal, when present, is demodulated.
            The measurement includes the effect of the receive matched
            filter but does not include the effect of any ingress filtering.
            Both the signal power and noise/interference power
            are referenced to the same point, e.g., CMTS input.";
          smiv2:max-access "read-only";
          smiv2:oid "1.3.6.1.4.1.4491.2.1.20.1.25.1.1";
        }

        leaf docsIf3CmtsSignalQualityExtExpectedRxSignalPower {
          type docs-if:TenthdBmV;
          description
           "ExpectedReceivedSignalPower is the power of the
            expected commanded received signal in the channel,
            referenced to the CMTS input.";
          smiv2:max-access "read-only";
          smiv2:oid "1.3.6.1.4.1.4491.2.1.20.1.25.1.2";
        }
      }
    }

    container docsIf3CmtsSpectrumAnalysisMeasTable {
      description
       "This object is used to configure the logical upstream
        interfaces to perform the spectrum measurements.
        This object supports creation and deletion of instances.";
      smiv2:oid "1.3.6.1.4.1.4491.2.1.20.1.26";

      list docsIf3CmtsSpectrumAnalysisMeasEntry {
        key "ifIndex";
        description
         "The conceptual row of docsIf3CmtsSpectrumAnalysisMeasTable.
          The ifIndex key corresponds to each of the upstream
          channels.
          The CMTS is not required to persist instances of this
          object across reinitializations.";
        smiv2:oid "1.3.6.1.4.1.4491.2.1.20.1.26.1";

        leaf ifIndex {
          type leafref {
            path "/if-mib:IF-MIB/if-mib:ifTable/if-mib:ifEntry/if-mib:ifIndex";
          }
        }

        leaf docsIf3CmtsSpectrumAnalysisMeasAmplitudeData {
          type DOCS-IF3-MIB:AmplitudeData;
          description
           "This attribute provides a list of the spectral amplitudes
            corresponding to the frequency bins ordered
            from lowest to highest frequencies covering the frequency
            span. Information about the center frequency,
            frequency span, number of bins and resolution bandwidth
            are included to provide context to the measurement
            point
            The CMTS must support the number of bins as an odd number
            in order to provide a spectrum representation that
            is symmetric about the middle data point or bin. The
            CMTS must support a number of bins greater than or equal
            to 257 for frequency spans greater than or equal to
            6.4 MHz.
            
            The CMTS must not exceed 25 kHz bin spacing for measurement
            of frequency spans less than or equal to 6.4 MHz.
            
            The bins measurements are updated periodically at time
            intervals given by the TimeInterval attribute.";
          smiv2:max-access "read-only";
          smiv2:oid "1.3.6.1.4.1.4491.2.1.20.1.26.1.1";
        }

        leaf docsIf3CmtsSpectrumAnalysisMeasTimeInterval {
          type uint32;
          units "milliseconds";
          description
           "TimeInterval is the CMTS estimated average repetition
            period of measurements. This attribute defines
            the average rate at which new spectra can be retrieved.";
          smiv2:max-access "read-only";
          smiv2:oid "1.3.6.1.4.1.4491.2.1.20.1.26.1.2";
        }

        leaf docsIf3CmtsSpectrumAnalysisMeasRowStatus {
          type snmpv2-tc:RowStatus;
          description
           "The status of this instance.";
          smiv2:max-access "read-write";
          smiv2:oid "1.3.6.1.4.1.4491.2.1.20.1.26.1.3";
        }
      }
    }

    container docsIf3CmDpvStatsTable {
      description
       "This object represents the DOCSIS Path Verify Statistics
        collected in the cable modem device.
        The CMTS controls the logging of DPV statistics in the
        cable modem. Therefore the context and nature of the
        measurements are governed by the CMTS and not self-descriptive
        when read from the CM.";
      smiv2:oid "1.3.6.1.4.1.4491.2.1.20.1.28";

      list docsIf3CmDpvStatsEntry {
        key "ifIndex docsIf3CmDpvStatsGrpId";
        description
         "The conceptual row of docsIf3CmDpvStatsTable.";
        smiv2:oid "1.3.6.1.4.1.4491.2.1.20.1.28.1";

        leaf ifIndex {
          type leafref {
            path "/if-mib:IF-MIB/if-mib:ifTable/if-mib:ifEntry/if-mib:ifIndex";
          }
        }

        leaf docsIf3CmDpvStatsGrpId {
          type uint32 {
            range "1..2";
          }
          description
           "This key represents the DPV Group ID. The CM reports
            two instance of DPV statistics per downstream normally
            referred as Statistical Group 1 and Statistical
            Group 2.";
          smiv2:max-access "not-accessible";
          smiv2:oid "1.3.6.1.4.1.4491.2.1.20.1.28.1.1";
        }

        leaf docsIf3CmDpvStatsLastMeasLatency {
          type uint32;
          units "nanoseconds";
          description
           "This attribute represents the last latency measurement
            for this statistical group.";
          smiv2:max-access "read-only";
          smiv2:oid "1.3.6.1.4.1.4491.2.1.20.1.28.1.2";
        }

        leaf docsIf3CmDpvStatsLastMeasTime {
          type snmpv2-tc:DateAndTime;
          description
           "This attribute represents the last measurement time
            of the last latency measurement for this statistical
            group.
            This attribute reports the EPOC time value when no measurements
            are being reported or after the statistics
            were cleared.";
          smiv2:max-access "read-only";
          smiv2:oid "1.3.6.1.4.1.4491.2.1.20.1.28.1.3";
        }

        leaf docsIf3CmDpvStatsMinLatency {
          type uint32;
          units "nanoseconds";
          description
           "This attribute represents the minimum latency measurement
            for this statistical group since the last
            time statistics were cleared.";
          smiv2:max-access "read-only";
          smiv2:oid "1.3.6.1.4.1.4491.2.1.20.1.28.1.4";
        }

        leaf docsIf3CmDpvStatsMaxLatency {
          type uint32;
          units "nanoseconds";
          description
           "This attribute represents the maximum latency measurement
            for this statistical group since the last
            time statistics were cleared.";
          smiv2:max-access "read-only";
          smiv2:oid "1.3.6.1.4.1.4491.2.1.20.1.28.1.5";
        }

        leaf docsIf3CmDpvStatsAvgLatency {
          type uint32;
          units "nanoseconds";
          description
           "This attribute represents the average latency measurement
            for this statistical group since the last
            time statistics were cleared. The averaging mechanism
            is controlled by the CMTS, and can be a simple average
            (mean) or an exponential moving average.";
          reference
           "DOCSIS 3.0 MAC and Upper Layer Protocols Interface
            Specification CM-SP-MULPIv3.0-I08-080522, DOCSIS Path 
            Verification section.";
          smiv2:max-access "read-only";
          smiv2:oid "1.3.6.1.4.1.4491.2.1.20.1.28.1.6";
        }

        leaf docsIf3CmDpvStatsNumMeas {
          type uint32;
          units "measurements";
          description
           "This attribute represents the number of latency measurements
            made for this statistical group since the
            last time statistics were cleared.";
          smiv2:max-access "read-only";
          smiv2:oid "1.3.6.1.4.1.4491.2.1.20.1.28.1.7";
        }

        leaf docsIf3CmDpvStatsLastClearTime {
          type snmpv2-tc:DateAndTime;
          description
           "This attribute represents the last time statistics
            were cleared for this statistical group.";
          smiv2:max-access "read-only";
          smiv2:oid "1.3.6.1.4.1.4491.2.1.20.1.28.1.8";
        }
      }
    }

    container docsIf3CmEventCtrlTable {
      description
       "This object represents the control mechanism to enable the
        dispatching of events based on the event Id. The following
        rules define the event control behavior:
        
        - The CmEventCtrl object has no instances or contains an 
          instance with Event ID 0. All events matching the Local Log
          settings of docsDevEvReporting are sent to local log ONLY.
        
        - The CmEventCtrl object contains configured instances
          Only events matching the Event Ids configured in the object
          are sent according to the settings of the docsDevEvReporting
          object. 
          
          The CM does not persist instances of CmEventCtrl across 
          reinitializations.";
      reference
       "DOCSIS 3.0 Operations Support System Interface
        Specification CM-SP-OSSIv3.0-I11-100115, Section N.2.2.5 
        CmEventCtrl Object.";
      smiv2:oid "1.3.6.1.4.1.4491.2.1.20.1.29";

      list docsIf3CmEventCtrlEntry {
        key "docsIf3CmEventCtrlEventId";
        description
         "The conceptual row of docsIf3CmEventCtrlTable.";
        smiv2:oid "1.3.6.1.4.1.4491.2.1.20.1.29.1";

        leaf docsIf3CmEventCtrlEventId {
          type uint32;
          description
           "This key represents the Event ID of the event being 
            enabled for delivery to a dispatch mechanism (e.g., syslog).";
          reference
           "DOCSIS 3.0 Operations Support System Interface
            Specification CM-SP-OSSIv3.0-I07-080522, Format and Content
            for Event, Syslog, and SNMP Notification Annex.";
          smiv2:max-access "not-accessible";
          smiv2:oid "1.3.6.1.4.1.4491.2.1.20.1.29.1.1";
        }

        leaf docsIf3CmEventCtrlStatus {
          type snmpv2-tc:RowStatus;
          description
           "The status of this instance.";
          smiv2:max-access "read-write";
          smiv2:oid "1.3.6.1.4.1.4491.2.1.20.1.29.1.2";
        }
      }
    }

    container docsIf3CmtsEventCtrlTable {
      description
       "This object represents the control mechanism to enable the
        dispatching of  events based on the event Id. The following
        rules define the event control behavior:
        
        - The CmtsEventCtrl object has no instances or contains an 
          instance with Event ID 0. All events matching the Local Log 
          settings of docsDevEvReporting are sent to local log ONLY.
        
        - The CmtsEventCtrl object contains configured instances
          Only events matching the Event Ids configured in the object
          are sent according to the settings of the docsDevEvReporting
          object. 
          
        - The CMTS persists all instances of CmtsEventCtrl across 
          reinitializations.";
      reference
       "DOCSIS 3.0 Operations Support System Interface Specification 
        CM-SP-OSSIv3.0-I11-100115, Section N.2.3.4 CmtsEventCtrl Object.";
      smiv2:oid "1.3.6.1.4.1.4491.2.1.20.1.30";

      list docsIf3CmtsEventCtrlEntry {
        key "docsIf3CmtsEventCtrlEventId";
        description
         "The conceptual row of docsIf3CmtsEventCtrlTable.";
        smiv2:oid "1.3.6.1.4.1.4491.2.1.20.1.30.1";

        leaf docsIf3CmtsEventCtrlEventId {
          type uint32;
          description
           "This key represents the Event ID of the event being 
            enabled for delivery to a dispatch mechanism (e.g., syslog).";
          reference
           "DOCSIS 3.0 Operations Support System Interface
            Specification CM-SP-OSSIv3.0-I07-080522, Format and Content
            for Event, Syslog, and SNMP Notification Annex.";
          smiv2:max-access "not-accessible";
          smiv2:oid "1.3.6.1.4.1.4491.2.1.20.1.30.1.1";
        }

        leaf docsIf3CmtsEventCtrlStatus {
          type snmpv2-tc:RowStatus;
          description
           "The status of this instance.";
          smiv2:max-access "read-write";
          smiv2:oid "1.3.6.1.4.1.4491.2.1.20.1.30.1.2";
        }
      }
    }

    container docsIf3CmMdCfgTable {
      description
       "This object contains CM MAC domain level control and
        configuration attributes.";
      smiv2:oid "1.3.6.1.4.1.4491.2.1.20.1.31";

      list docsIf3CmMdCfgEntry {
        key "ifIndex";
        description
         "The conceptual row of docsIf3CmMdCfgTable.
          The ifIndex key corresponds to the MAC Domain interface.";
        smiv2:oid "1.3.6.1.4.1.4491.2.1.20.1.31.1";

        leaf ifIndex {
          type leafref {
            path "/if-mib:IF-MIB/if-mib:ifTable/if-mib:ifEntry/if-mib:ifIndex";
          }
        }

        leaf docsIf3CmMdCfgIpProvMode {
          type enumeration {
            enum "ipv4Only" {
              value "0";
            }
            enum "ipv6Only" {
              value "1";
            }
            enum "honorMdd" {
              value "4";
            }
          }
          description
           "This attribute specifies whether the CM honors or ignores the 
            CMTS MDD TLV 5.1 setting in order to configure its IP provisioning 
            mode. The CM relies upon the CMTS to facilitate the successful 
            IP address acquisition independently of the MDD. When this attribute
            is set to 'ipv4Only' the CM will initiate the acquisition of a single 
            IPv4 address for the CM management stack.
            When this attribute is set to 'ipv6Only' the CM will initiate the 
            acquisition of a single IPv6 address for the CM management stack.
            When this attribute is set to 'honorMdd' the CM will initiate the 
            acquisition of an IPv6 or IPv4 address as directed by the MDD 
            message for provisioning and operation.";
          reference
           "DOCSIS 3.0 MAC and Upper Layer Protocols Interface
            Specification CM-SP-MULPIv3.0-I14-101008, IP Initialization
            Parameters TLV section.";
          smiv2:defval "honorMdd";
          smiv2:max-access "read-write";
          smiv2:oid "1.3.6.1.4.1.4491.2.1.20.1.31.1.1";
        }

        leaf docsIf3CmMdCfgIpProvModeResetOnChange {
          type boolean;
          description
           "This attribute determines if the CM is to automatically
            reset upon change of the IpProvMode attribute. The attribute has a
            default value of 'false' (2) which means that the CM does not reset
            upon change to IpProvMode attribute.  When this attribute is set to
            'true' (1), the CM resets upon a change to the IpProvMode attribute.";
          reference
           "DOCSIS 3.0 MAC and Upper Layer Protocols Interface
            Specification CM-SP-MULPIv3.0-I14-101008, IP Initialization
            Parameters TLV section.";
          smiv2:defval "false";
          smiv2:max-access "read-write";
          smiv2:oid "1.3.6.1.4.1.4491.2.1.20.1.31.1.2";
        }

        leaf docsIf3CmMdCfgIpProvModeResetOnChangeHoldOffTimer {
          type uint32 {
            range "0..300";
          }
          units "seconds";
          description
           "This attribute determines how long a CM with 
            IpProvModeResetOnChange set to 'true' waits to reset. When the 
            IpProvModeResetOnChange attribute is set to 'true' (1), the CM
            will decrement from the configured timer value before resetting.
            The default value of the IpProvModeResetOnChangeHoldOffTimer is 0 
            seconds which is equivalent to an immediate reset.";
          reference
           "DOCSIS 3.0 MAC and Upper Layer Protocols Interface
            Specification CM-SP-MULPIv3.0-I14-101008, IP Initialization
            Parameters TLV section.";
          smiv2:defval "0";
          smiv2:max-access "read-write";
          smiv2:oid "1.3.6.1.4.1.4491.2.1.20.1.31.1.3";
        }

        leaf docsIf3CmMdCfgIpProvModeStorageType {
          type snmpv2-tc:StorageType;
          description
           "This attribute determines if the CM persists the value of 
            IpProvMode across a single reset or across all resets.   The 
            default value of this attribute is 'nonVolatile' (3) which means
            that the CM persists the value of IpProvMode across all resets. 
            The CM persists the value of IpProveMode across only a single 
            reset when IpProvModeStorageType is set to volatile(2). Other 
            StorageType values are not applicable for this object; an attempt to
            set this object to a value of other(1), permanent(4), or readOnly(5)
            will be rejected with an error code of inconsistentValue.";
          reference
           "DOCSIS 3.0 MAC and Upper Layer Protocols Interface
            Specification CM-SP-MULPIv3.0-I14-101008, IP Initialization
            Parameters TLV section.";
          smiv2:defval "nonVolatile";
          smiv2:max-access "read-write";
          smiv2:oid "1.3.6.1.4.1.4491.2.1.20.1.31.1.4";
        }
      }
    }

    container docsIf3CmEnergyMgt1x1CfgTable {
      description
       "This object provides configuration state information 
        on the CM for the Energy Management 1x1 Mode feature.";
      reference
       "DOCSIS 3.0 MAC and Upper Layer Protocols Interface
        Specification CM-SP-MULPIv3.0-I20-121113, 
        Energy Management 1x1 Mode Encodings section.";
      smiv2:oid "1.3.6.1.4.1.4491.2.1.20.1.33";

      list docsIf3CmEnergyMgt1x1CfgEntry {
        key "docsIf3CmEnergyMgt1x1CfgDirection";
        description
         "The conceptual row of docsIf3CmEnergyMgt1x1CfgTable.";
        smiv2:oid "1.3.6.1.4.1.4491.2.1.20.1.33.1";

        leaf docsIf3CmEnergyMgt1x1CfgDirection {
          type DOCS-IF3-MIB:IfDirection;
          description
           "This index indicates whether the threshold applies to the 
            upstream or downstream.";
          smiv2:max-access "not-accessible";
          smiv2:oid "1.3.6.1.4.1.4491.2.1.20.1.33.1.1";
        }

        leaf docsIf3CmEnergyMgt1x1CfgEntryBitrateThrshld {
          type uint32;
          units "bps";
          description
           "This attribute specifies the upstream or downstream bitrate
            threshold (in bps) below which the CM will request to enter 
            Energy Management 1x1 Mode operation.";
          smiv2:max-access "read-write";
          smiv2:oid "1.3.6.1.4.1.4491.2.1.20.1.33.1.2";
        }

        leaf docsIf3CmEnergyMgt1x1CfgEntryTimeThrshld {
          type uint32 {
            range "1..65535";
          }
          units "seconds";
          description
           "This attribute specifies the number of consecutive seconds 
            that the upstream or downstream data rate needs to remain below
            the Upstream or Downstream Entry Bitrate Threshold in order to 
            determine that a transition to Energy Management 1x1 Mode is 
            required.";
          smiv2:max-access "read-write";
          smiv2:oid "1.3.6.1.4.1.4491.2.1.20.1.33.1.3";
        }

        leaf docsIf3CmEnergyMgt1x1CfgExitBitrateThrshld {
          type uint32;
          units "bps";
          description
           "This attribute specifies the upstream or downstream bitrate 
            threshold (in bps) above which the CM will request to leave 
            Energy Management 1x1 Mode operation.";
          smiv2:max-access "read-write";
          smiv2:oid "1.3.6.1.4.1.4491.2.1.20.1.33.1.4";
        }

        leaf docsIf3CmEnergyMgt1x1CfgExitTimeThrshld {
          type uint32 {
            range "1..65535";
          }
          units "seconds";
          description
           "This attribute specifies the number of consecutive seconds 
            that the upstream or downstream data rate needs to remain above
            the Upstream or Downstream Exit Bitrate Threshold in order to 
            determine that a transition out of Energy Management 1x1 Mode 
            is required.";
          smiv2:max-access "read-write";
          smiv2:oid "1.3.6.1.4.1.4491.2.1.20.1.33.1.5";
        }
      }
    }

    container docsIf3CmSpectrumAnalysisMeasTable {
      description
       "This table provides a list of spectral analysis measurements 
        as performed across a range of center frequencies. The table 
        is capable of representing a full scan of the spectrum.";
      smiv2:oid "1.3.6.1.4.1.4491.2.1.20.1.35";

      list docsIf3CmSpectrumAnalysisMeasEntry {
        key "docsIf3CmSpectrumAnalysisMeasFrequency";
        description
         "Each row in the docsIf3CmSpectrumAnalysisMeasTable 
          represents the spectral analysis around a single center 
          frequency point in the spectrum.";
        smiv2:oid "1.3.6.1.4.1.4491.2.1.20.1.35.1";

        leaf docsIf3CmSpectrumAnalysisMeasFrequency {
          type int32;
          description
           "This index indicates the center frequency of the spectral
            analysis span which is represented by this instance.";
          smiv2:max-access "not-accessible";
          smiv2:oid "1.3.6.1.4.1.4491.2.1.20.1.35.1.1";
        }

        leaf docsIf3CmSpectrumAnalysisMeasAmplitudeData {
          type DOCS-IF3-MIB:AmplitudeData;
          description
           "This attribute provides a list of the spectral amplitudes as 
            measured at the center frequency specified by the Frequency
            index.
            
            The frequency bins are ordered from lowest to highest 
            frequencies covering the frequency span. Information about the
            center frequency, frequency span, number of bins and resolution
            bandwidth are included to provide context to the measurement 
            point.";
          smiv2:max-access "read-only";
          smiv2:oid "1.3.6.1.4.1.4491.2.1.20.1.35.1.2";
        }

        leaf docsIf3CmSpectrumAnalysisMeasTotalSegmentPower {
          type docs-if:TenthdB;
          description
           "This attribute provides the total RF power present in the 
            segment with the center frequency equal to the Frequency index
            and the span equal to the SegmentFrequencySpan. The value 
            represents the sum of the spectrum power in all of the 
            associated bins. The value is computed by summing power (not 
            dB) values and converting the final sum to TenthdB.";
          smiv2:max-access "read-only";
          smiv2:oid "1.3.6.1.4.1.4491.2.1.20.1.35.1.3";
        }
      }
    }

    container docsIf3CmtsCmEmStatsTable {
      description
       "This table defines Energy Management mode statistics for the
        CM as reported by the CMTS.  For example, such metrics can
        provide insight into configuration of appropriate EM 1x1 Mode
        Activity Detection thresholds on the CM and/or to get feedback
        on how/if the current thresholds are working well or are 
        causing user experience issues.";
      smiv2:oid "1.3.6.1.4.1.4491.2.1.20.1.36";

      list docsIf3CmtsCmEmStatsEntry {
        key "docsIf3CmtsCmRegStatusId";
        description
         "The conceptual row of docsIf3CmtsCmEmStatsTable.";
        smiv2:oid "1.3.6.1.4.1.4491.2.1.20.1.36.1";

        leaf docsIf3CmtsCmRegStatusId {
          type leafref {
            path "/DOCS-IF3-MIB:DOCS-IF3-MIB/DOCS-IF3-MIB:docsIf3CmtsCmRegStatusTable/DOCS-IF3-MIB:docsIf3CmtsCmRegStatusEntry/DOCS-IF3-MIB:docsIf3CmtsCmRegStatusId";
          }
        }

        leaf docsIf3CmtsCmEmStatsEm1x1ModeTotalDuration {
          type uint32;
          units "seconds";
          description
           "This attribute indicates the total time duration, in seconds
            since registration, the CM identified by 
            docsIf3CmtsCmRegStatusId has been in Energy Management 1x1 
            mode, as controlled by the DBC-REQ Energy Management 1x1 
            Mode Indicator TLV.";
          smiv2:max-access "read-only";
          smiv2:oid "1.3.6.1.4.1.4491.2.1.20.1.36.1.1";
        }
      }
    }

    container docsIf3CmEm1x1StatsTable {
      description
       "This object defines Energy Management 1x1 mode statistics on
        the CM to provide insight into configuration of appropriate EM
        1x1 Mode Activity Detection thresholds and/or to get feedback
        on how/if the current thresholds are working well or are 
        causing user experience issues.
        These statistics are only applicable/valid when the Energy 
        Management 1x1 mode is enabled in the CM.";
      smiv2:oid "1.3.6.1.4.1.4491.2.1.20.1.37";

      list docsIf3CmEm1x1StatsEntry {
        key "ifIndex";
        description
         "The conceptual row of docsIf3CmEm1x1StatsTable.
          An instance exist for the CM MAC Domain Interface.";
        smiv2:oid "1.3.6.1.4.1.4491.2.1.20.1.37.1";

        leaf ifIndex {
          type leafref {
            path "/if-mib:IF-MIB/if-mib:ifTable/if-mib:ifEntry/if-mib:ifIndex";
          }
        }

        leaf docsIf3CmEm1x1StatsNumberTimesCrossedBelowUsEntryThrshlds {
          type uint32;
          description
           "This attribute indicates the number of times since 
            registration the CM crossed below the upstream entry bitrate
            threshold for a number of consecutive seconds equal to or 
            exceeding the upstream entry time threshold.";
          smiv2:max-access "read-only";
          smiv2:oid "1.3.6.1.4.1.4491.2.1.20.1.37.1.1";
        }

        leaf docsIf3CmEm1x1StatsNumberTimesCrossedBelowDsEntryThrshlds {
          type uint32;
          description
           "This attribute indicates the number of times since 
            registration the CM crossed below the downstream entry 
            bitrate threshold for a number of consecutive seconds equal
            to or exceeding the downstream entry time threshold.";
          smiv2:max-access "read-only";
          smiv2:oid "1.3.6.1.4.1.4491.2.1.20.1.37.1.2";
        }

        leaf docsIf3CmEm1x1StatsTotalDuration {
          type uint32;
          units "seconds";
          description
           "This attribute indicates the total time duration, in seconds
            since registration, the CM has been in Energy Management 1x1
            mode, as controlled by the DBC-REQ Energy Management 1x1 Mode
            Indicator TLV. This attribute differs from 
            docsIf3CmEm1x1StatsTotalDurationBelowUsDsThrshlds because it
            is dependent on effects of the Energy Management Cycle 
            Period, and processing of EM-REQ/EM-RSP messages and DBC 
            messages that specifically indicate entry into or exit from
            Energy Management 1x1 mode.";
          smiv2:max-access "read-only";
          smiv2:oid "1.3.6.1.4.1.4491.2.1.20.1.37.1.3";
        }

        leaf docsIf3CmEm1x1StatsTotalDurationBelowUsThrshlds {
          type uint32;
          units "seconds";
          description
           "This attribute indicates the total time duration, in seconds
            since registration, the CM satisfied upstream conditions for 
            entry into or remaining in Energy Management 1x1 mode.";
          smiv2:max-access "read-only";
          smiv2:oid "1.3.6.1.4.1.4491.2.1.20.1.37.1.4";
        }

        leaf docsIf3CmEm1x1StatsTotalDurationBelowDsThrshlds {
          type uint32;
          units "seconds";
          description
           "This attribute indicates the total time duration, in seconds
            since registration, the CM satisfied downstream conditions for 
            entry into or remaining in Energy Management 1x1 mode.";
          smiv2:max-access "read-only";
          smiv2:oid "1.3.6.1.4.1.4491.2.1.20.1.37.1.5";
        }

        leaf docsIf3CmEm1x1StatsTotalDurationBelowUsDsThrshlds {
          type uint32;
          units "seconds";
          description
           "This attribute indicates the total time duration, in seconds 
            since registration, the CM, with respect to both upstream and 
            downstream entry and exit thresholds, satisfied conditions for 
            entry into and remaining in Energy Management 1x1 mode.  This 
            attribute differs from docsIf3CmEm1x1StatsTotalDuration 
            because it is not dependent on effects of the Energy 
            Management Cycle Period or processing of EM-REQ/EM-RSP 
            messages and DBC messages that specifically indicate entry
            into or exit from Energy Management 1x1 mode.";
          smiv2:max-access "read-only";
          smiv2:oid "1.3.6.1.4.1.4491.2.1.20.1.37.1.6";
        }
      }
    }
  }

  notification docsIf3CmtsEventNotif {
    description
     "A notification to report a DOCSIS event detected on the 
      CMTS.
      
      This notification includes the following information:
      - docsDevEvLevel: the DOCSIS priority level associated with 
        the event.
      - docsDevEvId: the numeric identifier of the event.
      - docsDevEvText: The text description of the event.
      - docsDevEvLastTime: The local date and time when this event
        was generated.
      - sysName: the administratively-assigned name of the CMTS.
        e.g., The fully-qualified domain name as indicated in RFC 3418
        or in the absence the IP address of the CMTS administrative
        interface in dot '.' notation for IPv4 and colon ':' notation
        for and IPv6 Address as indicated in  RFC 3164";
    reference
     "DOCSIS 3.0 Operations Support System Interface
      Specification CM-SP-OSSIv3.0-I07-080522, Format and Content
      for Event, Syslog, and SNMP Notification Annex.
      RFC 3418, RFC 3164";
    smiv2:oid "1.3.6.1.4.1.4491.2.1.20.0.1";

    container object-1 {

      leaf docsDevEvIndex {
        type leafref {
          path "/docs-cable:DOCS-CABLE-DEVICE-MIB/docs-cable:docsDevEventTable/docs-cable:docsDevEventEntry/docs-cable:docsDevEvIndex";
        }
      }

      leaf docsDevEvLevel {
        type leafref {
          path "/docs-cable:DOCS-CABLE-DEVICE-MIB/docs-cable:docsDevEventTable/docs-cable:docsDevEventEntry/docs-cable:docsDevEvLevel";
        }
      }
    }

    container object-2 {

      leaf docsDevEvIndex {
        type leafref {
          path "/docs-cable:DOCS-CABLE-DEVICE-MIB/docs-cable:docsDevEventTable/docs-cable:docsDevEventEntry/docs-cable:docsDevEvIndex";
        }
      }

      leaf docsDevEvId {
        type leafref {
          path "/docs-cable:DOCS-CABLE-DEVICE-MIB/docs-cable:docsDevEventTable/docs-cable:docsDevEventEntry/docs-cable:docsDevEvId";
        }
      }
    }

    container object-3 {

      leaf docsDevEvIndex {
        type leafref {
          path "/docs-cable:DOCS-CABLE-DEVICE-MIB/docs-cable:docsDevEventTable/docs-cable:docsDevEventEntry/docs-cable:docsDevEvIndex";
        }
      }

      leaf docsDevEvText {
        type leafref {
          path "/docs-cable:DOCS-CABLE-DEVICE-MIB/docs-cable:docsDevEventTable/docs-cable:docsDevEventEntry/docs-cable:docsDevEvText";
        }
      }
    }

    container object-4 {

      leaf docsDevEvIndex {
        type leafref {
          path "/docs-cable:DOCS-CABLE-DEVICE-MIB/docs-cable:docsDevEventTable/docs-cable:docsDevEventEntry/docs-cable:docsDevEvIndex";
        }
      }

      leaf docsDevEvLastTime {
        type leafref {
          path "/docs-cable:DOCS-CABLE-DEVICE-MIB/docs-cable:docsDevEventTable/docs-cable:docsDevEventEntry/docs-cable:docsDevEvLastTime";
        }
      }
    }

    container object-5 {

      leaf sysName {
        type leafref {
          path "/snmpv2-mib:SNMPv2-MIB/snmpv2-mib:system/snmpv2-mib:sysName";
        }
      }
    }
  }

  notification docsIf3CmEventNotif {
    description
     "A notification to report a DOCSIS event detected on the  
      CM.
      
      This notification includes the following information:
      - docsDevEvLevel: the priority level associated with the
        event.
      - docsDevEvId: the unique identifier of the event that
        occurred.
      - docsDevEvText: a textual description of the event.
      - docsDevEvLastTime: The local date and time when this event
        was generated.";
    reference
     "DOCSIS 3.0 Operations Support System Interface
      Specification CM-SP-OSSIv3.0-I07-080522, Format and Content
      for Event, Syslog, and SNMP Notification Annex.";
    smiv2:oid "1.3.6.1.4.1.4491.2.1.20.0.2";

    container object-1 {

      leaf docsDevEvIndex {
        type leafref {
          path "/docs-cable:DOCS-CABLE-DEVICE-MIB/docs-cable:docsDevEventTable/docs-cable:docsDevEventEntry/docs-cable:docsDevEvIndex";
        }
      }

      leaf docsDevEvLevel {
        type leafref {
          path "/docs-cable:DOCS-CABLE-DEVICE-MIB/docs-cable:docsDevEventTable/docs-cable:docsDevEventEntry/docs-cable:docsDevEvLevel";
        }
      }
    }

    container object-2 {

      leaf docsDevEvIndex {
        type leafref {
          path "/docs-cable:DOCS-CABLE-DEVICE-MIB/docs-cable:docsDevEventTable/docs-cable:docsDevEventEntry/docs-cable:docsDevEvIndex";
        }
      }

      leaf docsDevEvId {
        type leafref {
          path "/docs-cable:DOCS-CABLE-DEVICE-MIB/docs-cable:docsDevEventTable/docs-cable:docsDevEventEntry/docs-cable:docsDevEvId";
        }
      }
    }

    container object-3 {

      leaf docsDevEvIndex {
        type leafref {
          path "/docs-cable:DOCS-CABLE-DEVICE-MIB/docs-cable:docsDevEventTable/docs-cable:docsDevEventEntry/docs-cable:docsDevEvIndex";
        }
      }

      leaf docsDevEvText {
        type leafref {
          path "/docs-cable:DOCS-CABLE-DEVICE-MIB/docs-cable:docsDevEventTable/docs-cable:docsDevEventEntry/docs-cable:docsDevEvText";
        }
      }
    }

    container object-4 {

      leaf docsDevEvIndex {
        type leafref {
          path "/docs-cable:DOCS-CABLE-DEVICE-MIB/docs-cable:docsDevEventTable/docs-cable:docsDevEventEntry/docs-cable:docsDevEvIndex";
        }
      }

      leaf docsDevEvLastTime {
        type leafref {
          path "/docs-cable:DOCS-CABLE-DEVICE-MIB/docs-cable:docsDevEventTable/docs-cable:docsDevEventEntry/docs-cable:docsDevEvLastTime";
        }
      }
    }
  }

  smiv2:alias "docsIf3Mib" {
    smiv2:oid "1.3.6.1.4.1.4491.2.1.20";
  }

  smiv2:alias "docsIf3Notifications" {
    smiv2:oid "1.3.6.1.4.1.4491.2.1.20.0";
  }

  smiv2:alias "docsIf3MibObjects" {
    smiv2:oid "1.3.6.1.4.1.4491.2.1.20.1";
  }

  smiv2:alias "docsIf3CmCapabilities" {
    smiv2:oid "1.3.6.1.4.1.4491.2.1.20.1.21";
  }

  smiv2:alias "docsIf3CmtsCmCtrl" {
    smiv2:oid "1.3.6.1.4.1.4491.2.1.20.1.27";
  }

  smiv2:alias "docsIf3CmEnergyMgtCfg" {
    smiv2:oid "1.3.6.1.4.1.4491.2.1.20.1.32";
  }

  smiv2:alias "docsIf3CmSpectrumAnalysisCtrlCmd" {
    smiv2:oid "1.3.6.1.4.1.4491.2.1.20.1.34";
  }

  smiv2:alias "docsIf3MibConformance" {
    smiv2:oid "1.3.6.1.4.1.4491.2.1.20.2";
  }

  smiv2:alias "docsIf3MibCompliances" {
    smiv2:oid "1.3.6.1.4.1.4491.2.1.20.2.1";
  }

  smiv2:alias "docsIf3MibGroups" {
    smiv2:oid "1.3.6.1.4.1.4491.2.1.20.2.2";
  }

}
