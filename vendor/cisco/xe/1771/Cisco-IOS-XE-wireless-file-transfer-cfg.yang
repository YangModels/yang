module Cisco-IOS-XE-wireless-file-transfer-cfg {
  yang-version 1;
  namespace "http://cisco.com/ns/yang/Cisco-IOS-XE-wireless-file-transfer-cfg";
  prefix wireless-file-transfer-cfg;

  import Cisco-IOS-XE-wireless-enum-types {
    prefix wireless-enum-types;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Model for managing file transfer configuration
     Copyright (c) 2018-2019 by Cisco Systems, Inc.
     All rights reserved.";

  revision 2019-06-03 {
    description
      "Added support for scheduled configuration download";
    reference
      "1.1.0";
    cisco-semver:module-version "1.1.0";
  }
  revision 2019-04-23 {
    description
      "Initial revision";
    reference
      "1.0.0";
    cisco-semver:module-version "1.0.0";
  }

  typedef transfer-mode {
    type enumeration {
      enum transfer-mode-unconfigured {
        value 0;
        description
          "Transfer mode none";
      }
      enum transfer-mode-tftp {
        value 1;
        description
          "Transfer mode TFTP";
      }
      enum transfer-mode-ftp {
        value 2;
        description
          "Transfer mode FTP";
      }
      enum transfer-mode-sftp {
        value 3;
        description
          "Transfer mode SFTP";
      }
    }
    description
      "Transfer Mode";
  }

  grouping file-xfer-params {
    description
      "Transfer parameters";
    choice transfer-mode-choice {
      default "transfer-mode-unconfigured";
      description
        "Choice of supported transfer modes";
      case transfer-mode-unconfigured {
        leaf xfer-disabled {
          type empty;
          description
            "Transfer mode disabled";
        }
      }
      case transfer-mode-tftp {
        leaf tftp-server {
          type inet:ip-address;
          default "0.0.0.0";
          description
            "TFTP server";
        }
        leaf tftp-path {
          type string;
          default "";
          description
            "TFTP path";
        }
      }
      case transfer-mode-ftp {
        leaf ftp-server {
          type inet:ip-address;
          default "0.0.0.0";
          description
            "FTP server";
        }
        leaf ftp-path {
          type string;
          default "";
          description
            "FTP path";
        }
        leaf ftp-username {
          type string;
          default "";
          description
            "FTP username";
        }
        leaf ftp-password {
          type string;
          default "";
          description
            "FTP password";
        }
        leaf ftp-password-type {
          type wireless-enum-types:crypt-type;
          must "((current() = 'clear') or (current() = 'aes'))" {
            error-message "Password type should be clear text";
            error-app-tag "must-violation";
          }
          default "clear-to-aes";
          description
            "FTP password type";
        }
      }
      case transfer-mode-sftp {
        leaf sftp-server {
          type inet:ip-address;
          default "0.0.0.0";
          description
            "SFTP server";
        }
        leaf sftp-path {
          type string;
          default "";
          description
            "SFTP path";
        }
        leaf sftp-username {
          type string;
          default "";
          description
            "SFTP username";
        }
        leaf sftp-password {
          type string;
          default "";
          description
            "SFTP password";
        }
        leaf sftp-password-type {
          type wireless-enum-types:crypt-type;
          must "((current() = 'clear') or (current() = 'aes'))" {
            error-message "Password type should be clear text";
            error-app-tag "must-violation";
          }
          default "clear-to-aes";
          description
            "SFTP password type";
        }
        leaf sftp-port {
          type uint32;
          default "22";
          description
            "SFTP port";
        }
      }
    }
  }

  grouping st-trace-export-profile-config {
    description
      "Details of the trace export profile";
    leaf trace-export-profile-name {
      type string;
      description
        "Trace export profile name";
    }
    leaf decoded-export {
      type boolean;
      default "false";
      description
        "Toggles decoded binary trace export";
    }
    leaf trace-export-enable {
      type boolean;
      default "false";
      description
        "Toggles trace export functionality";
    }
    leaf threshold {
      type uint32 {
        range "0 .. 100";
      }
      default "75";
      description
        "Threshold percent of total binary trace storage capacity at which logs are exported to the server";
    }
    container xfer-params {
      description
        "Transfer parameters for the profile";
      uses wireless-file-transfer-cfg:file-xfer-params;
    }
  }

  grouping st-config-download-profile-config {
    description
      "Details of the configuration download profile";
    leaf config-download-profile-name {
      type string;
      description
        "Configuration download profile name";
    }
    leaf calendar-profile-name {
      type string;
      default "";
      description
        "Calendar profile name";
    }
    leaf config-download-enable {
      type boolean;
      default "false";
      description
        "Toggles scheduled configuration download functionality";
    }
    container xfer-params {
      description
        "Transfer parameters for the profile";
      uses wireless-file-transfer-cfg:file-xfer-params;
    }
  }

  grouping st-wireless-management-transfer-config {
    description
      "Mapping of the active transfer profiles";
    leaf trace-export-profile-name {
      type string;
      default "";
      description
        "Active trace export profile name";
    }
    leaf config-download-profile-name {
      type string;
      default "";
      description
        "Active configuration download profile name";
    }
  }

  container file-transfer-cfg-data {
    description
      "File transfer configuration data";
    container trace-export-profiles {
      description
        "Trace export configuration";
      list trace-export-profile {
        key "trace-export-profile-name";
        description
          "List of Trace export profiles";
        uses wireless-file-transfer-cfg:st-trace-export-profile-config;
      }
    }
    container config-download-profiles {
      description
        "Scheduled configuration download configuration";
      list config-download-profile {
        key "config-download-profile-name";
        description
          "List of configuration download profiles";
        uses wireless-file-transfer-cfg:st-config-download-profile-config;
      }
    }
    container xfer-mgmt-config {
      presence "xfer-mgmt-config";
      description
        "Transfer management configuration to associate active file transfer profiles";
      uses wireless-file-transfer-cfg:st-wireless-management-transfer-config;
    }
  }
}
