module Cisco-IOS-XE-matm-oper {
  yang-version 1;
  namespace "http://cisco.com/ns/yang/Cisco-IOS-XE-matm-oper";
  prefix matm-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for MATM (MAC Address Translation Manager) information.
     Copyright (c) 2016-2019 by Cisco Systems, Inc.
     All rights reserved.";

  revision 2019-05-01 {
    description
      "Added semantic version";
    reference
      "1.1.0";
    cisco-semver:module-version "1.1.0";
  }
  revision 2019-01-09 {
    description
      "Initial revision";
    reference
      "1.0.0";
    cisco-semver:module-version "1.0.0";
  }

  typedef e-matm-table-type {
    type enumeration {
      enum mat-vlan {
        value 1;
        description
          "MAC address table type is VLAN";
      }
      enum mat-vlan-independent {
        value 4;
        description
          "MAC address table type is VLAN independent";
      }
      enum mat-l3if {
        value 5;
        description
          "MAC address table type is L3";
      }
      enum mat-vlan-table {
        value 6;
        description
          "Placeholder to identify the max for the MATM table type";
      }
    }
    description
      "MAC address table type";
  }

  typedef e-matm-addr-type {
    type enumeration {
      enum static {
        value 0;
        description
          "Static MAC address type";
      }
      enum dynamic {
        value 1;
        description
          "Dynamic MAC address type";
      }
      enum any {
        value 2;
        description
          "All other MAC address types";
      }
    }
    description
      "Type of MAC address";
  }

  grouping matm-table-key {
    description
      "Unique MATM entries identifier";
    leaf table-type {
      type matm-ios-xe-oper:e-matm-table-type;
      description
        "MATM table type";
    }
    leaf vlan-id-number {
      type uint32;
      description
        "MATM VLAN id";
    }
  }

  grouping matm-mac-key {
    description
      "Unique MAC entry identifier";
    leaf table-type {
      type matm-ios-xe-oper:e-matm-table-type;
      description
        "MATM table type";
    }
    leaf vlan-id-number {
      type uint32;
      description
        "VLAN id associated with MAC entry.
         When table type is vlan-independent the
         vlan id is not used and it is set to 1";
    }
    leaf mac {
      type yang:mac-address;
      description
        "MAC associated with the VLAN ";
    }
  }

  grouping matm-mac-param {
    description
      "MAC address parameters";
    leaf mat-addr-type {
      type matm-ios-xe-oper:e-matm-addr-type;
      description
        "MAC address type associated with this MAC entry";
    }
    leaf port {
      type string;
      description
        "Port associated with the MAC entry";
    }
    leaf vlan-all {
      type empty;
      description
        "Indicates all VLAN associated with this MAC entry";
    }
  }

  grouping matm-table-param {
    description
      "MATM operational entry details";
    leaf aging-time {
      type uint32;
      units "seconds";
      description
        "Aging time associated with the VLAN";
    }
    list matm-mac-entry {
      key "table-type vlan-id-number mac";
      description
        "Lists all MAC entries associated with this VLAN";
      uses matm-ios-xe-oper:matm-mac-param;
      uses matm-ios-xe-oper:matm-mac-key;
    }
  }

  container matm-oper-data {
    config false;
    description
      "Data nodes for MAC address table information";
    list matm-table {
      key "table-type vlan-id-number";
      description
        "MAC address table state information";
      uses matm-ios-xe-oper:matm-table-param;
      uses matm-ios-xe-oper:matm-table-key;
    }
  }
}
