submodule Cisco-IOS-XE-voice-dspfarm {
  belongs-to Cisco-IOS-XE-voice {
    prefix ios-voice;
  }

  import ietf-inet-types {
    prefix inet;
  }
  import Cisco-IOS-XE-interface-common {
    prefix ios-ifc;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Voice DSPFarm Yang model.
     Copyright (c) 2020 by Cisco Systems, Inc.
     All rights reserved.";

  revision 2021-11-01 {
    description
      "- Added opus codec under dspfarm profile
       - Added when condition in opus codec under dspfarm profile";
  }
  revision 2021-03-01 {
    description
      "- Added sccp ip precedence CLI
       - Added sccp bind CLI
       - Added keepalive [retries | timeout] CLIs";
  }
  revision 2020-11-01 {
    description
      "- Initial revision for 17.4.1";
  }
  revision 2020-07-01 {
    description
      "Initial version";
  }

  grouping config-dspfarm-profile-grouping {
    container dspfarm {
      description
        "dspfarm profile creation CLI";
      list profile {
        description
          "dspfarm profile creation CLI";
        key "id";
        leaf id {
          description
            "dspfarm profile ID";
          type uint16 {
            range "1..65535";
          }
        }
        leaf type {
          description
            "Configure the profile types";
          type enumeration {
            enum conference;
            enum mtp;
            enum transcode;
          }
          mandatory true;
        }
        leaf universal {
          when "../type = 'transcode'";
          description
            "Configure the transcode universal profile type";
          type empty;
        }
        container codec {
          description
            "Add the codec capability of this profile";
          leaf g711ulaw {
            description
              "Add the codec g711ulaw";
            type empty;
          }
          leaf g711alaw {
            description
              "Add the codec g711alaw";
            type empty;
          }
          leaf g722-64 {
            description
              "Add the codec g722-64";
            type empty;
          }
          leaf g729abr8 {
            description
              "Add the codec g729abr8";
            type empty;
          }
          leaf g729ar8 {
            description
              "Add the codec g729ar8";
            type empty;
          }
          leaf g729br8 {
            description
              "Add the codec g729br8";
            type empty;
          }
          leaf g729r8 {
            description
              "Add the codec g729r8";
            type empty;
          }
          leaf ilbc {
            description
              "Add the codec ilbc";
            type empty;
          }
          leaf opus {
            when "../../type = 'transcode'";
            description
              "Add the codec opus";
            type empty;
          }
          leaf isac {
            when "../../type = 'transcode' or ../../type = 'mtp'";
            description
              "Add the codec isac";
            type empty;
          }
          leaf pass-through {
            when "../../type = 'transcode' or ../../type = 'mtp'";
            description
              "Add the codec pass-through";
            type empty;
          }
        }
        container associate {
          description
            "To associate an application to this profile";
          leaf application {
            description
              "Configure the application to associate";
            type enumeration {
              enum sccp;
              enum cube;
            }
          }
        }
        leaf plc {
          when "../type = 'conference'";
          description
            "Enable/Disable packet loss concealment";
          type boolean;
          default "true";
        }
        leaf acoustic-shock-protection {
          when "../associate/application = 'cube' and ../type = 'transcode'";
          description
            "Enable the acoustic shock protection for transcode profiles";
          type boolean;
          default "false";
        }
        leaf noise-reduction {
          when "../associate/application = 'cube' and ../type = 'transcode'";
          description
            "Enable the noise reduction for transcode profiles";
          type boolean;
          default "false";
        }
        leaf call-progress-analysis {
          when "../associate/application = 'cube' and ../type = 'transcode'";
          description
            "Enable the call progress analysis for transcode profiles";
          type boolean;
          default "false";
        }
        leaf rsvp {
          description
            "Enable the reservation protocol for transcode profiles";
          type boolean;
          default "false";
        }
        leaf cng-fax-detect {
          when "../type = 'transcode'";
          description
            "Configure support cng fax detect feature";
          type boolean;
          default "false";
        }
        container maximum {
          description
            "Configure the maximum number for this profile";
          container sessions {
            description
              "Configure the maximum sessions of this profile";
            leaf max-sessions {
              when "../../../type = 'transcode' or ../../../type = 'conference'";
              description
                "Configure the maximum sessions of transcode or conference profile";
              type uint32 {
                range "1..4000";
              }
            }
            container max-mtp-sessions {
              when "../../../type = 'mtp'";
              description
                "Configure the maximum session of mtp profile";
              leaf hardware {
                description
                  "Configure the maximum hardware MTP sessions of this profile";
                type uint32 {
                  range "1..4000";
                }
              }
              leaf software {
                description
                  "Configure the maximum software MTP sessions of this profile";
                type uint32 {
                  range "1..6000";
                }
              }
            }
          }
          leaf conference-participants {
            when "../../type = 'conference'";
            description
              "Configure the maximum number of conferee per conference session";
            type enumeration {
              enum 8;
              enum 16;
              enum 32;
            }
            default "8";
          }
        }
        container conference-join {
          when "../type = 'conference'";
          description
            "Configure tone for joining a conference";
          leaf custom-cptone {
            description
              "Configure the cp tone for conference join";
            type string;
          }
        }
        container conference-leave {
          when "../type = 'conference'";
          description
            "Configure tone for leaving a conference";
          leaf custom-cptone {
            description
              "Configure the cp tone for conference leave";
            type string;
          }
        }
        container dtmf {
          when "../type = 'transcode'";
          leaf suppress {
            description
              "To suppress the DTMF packets for transcode profiles";
            type boolean;
            default "false";
          }
        }
        leaf shutdown {
          description
            "Shutdown or bring up the profile";
          type boolean;
          default "true";
        }
      }
    }
  }

  grouping config-sccp-grouping {
    container sccp-config {
      container sccp {
        description
          "Configure sccp protocol related parameters";
        container ip {
          description
            "Specify the IP related parameters values";
          leaf precedence {
            description
              "Specify the IP precedence parameter value";
            type uint8 {
              range "1..7";
            }
            default "5";
          }
        }
        leaf local {
          description
            "Specify the local gateway related parameters values";
          type string;
        }
        container sccp-ccm-list {
          list ccm {
            description
              "Configure a CCM into the sccp ccm list";
            key "host";
            leaf host {
              description
                "CCM IP address or domain name";
              type union {
                type inet:ipv4-address;
                type inet:ipv6-address;
                type inet:domain-name;
              }
            }
            leaf identifier {
              description
                "Set this CCM's identifier";
              type uint16 {
                range "1..65535";
              }
            }
            leaf version {
              description
                "Set the CCM's version";
              type enumeration {
                enum 3.0;
                enum 3.1;
                enum 3.2;
                enum 3.3;
                enum 4.0;
                enum 4.1;
                enum 5.0.1;
                enum 6.0;
                enum 7.0+;
              }
            }
          }
        }
        container sccp-ccm-group-list {
          container ccm {
            list group {
              key "id";
              leaf id {
                description
                  "Set a sccp ccm group with an ID number ID";
                type uint16 {
                  range "1..65535";
                }
              }
              leaf description {
                description
                  "The description of this ccm group";
                type string;
              }
              container bind {
                description
                  "Bind the specific interface to the CCM group";
                container interface {
                  description
                    "Select the interface to bind";
                  uses ios-ifc:interface-grouping;
                }
              }
              container keepalive {
                description
                  "Specify SCCP keepalive message related parameter values";
                leaf retries {
                  description
                    "Set the keepalive message retries parameter value";
                  type uint8 {
                    range "1..32";
                  }
                  default "3";
                }
                leaf timeout {
                  description
                    "Set the keepalive message timeout parameter value";
                  type uint8 {
                    range "0..180";
                  }
                  default "30";
                }
              }
              container associate {
                list ccm {
                  description
                    "Associate a CCM to this CCM group";
                  key "id";
                  leaf id {
                    description
                      "The CCM identifier to be associated";
                    type uint16 {
                      range "1..65535";
                    }
                  }
                  leaf priority {
                    description
                      "Set the CCM's priority in this CCM group";
                    type uint16 {
                      range "1..65535";
                    }
                  }
                }
                list profile {
                  description
                    "Associate a profile to this CCM group";
                  key "id";
                  leaf id {
                    description
                      "Set the profile ID to be associated with this CCM group";
                    type leafref {
                      path "../../../../../../../../ios-voice:dspfarm/ios-voice:profile/ios-voice:id";
                    }
                  }
                  leaf register {
                    description
                      "Configure the name of this profile to be registered";
                    type string {
                      length "6..15";
                    }
                  }
                }
              }
              container switchover {
                description
                  "Specify the Switchover related parameters values";
                container method {
                  description
                    "Configure switchover method related parameter";
                  choice switchover-choice {
                    leaf graceful {
                      description
                        "Select the graceful switchover method";
                      type empty;
                    }
                    leaf immediate {
                      description
                        "Select the immediate switchover method";
                      type empty;
                    }
                    default "graceful";
                  }
                }
              }
              container switchback {
                description
                  "Specify the Switchback related parameters values";
                leaf interval {
                  description
                    "Configure the switchback interval timer";
                  type uint16 {
                    range "1..3600";
                  }
                }
                container method {
                  description
                    "Configure the switchback method related parameter";
                  choice switchback-choice {
                    leaf graceful {
                      description
                        "Select the graceful switchback method";
                      type empty;
                    }
                    leaf immediate {
                      description
                        "Select the immediate switchback method";
                      type empty;
                    }
                    container guard {
                      description
                        "Select the graceful with guard switchback method";
                      presence "true";
                      leaf timeout {
                        description
                          "Specify the timeout value for the selected switchback method";
                        type uint32 {
                          range "60..172800";
                        }
                        default "7200";
                      }
                    }
                    container uptime {
                      description
                        "Select the uptime-delay switchback method";
                      presence "true";
                      leaf timeout {
                        description
                          "Select the timeout value in seconds";
                        type uint32 {
                          range "60..172800";
                        }
                      }
                    }
                    default "guard";
                  }
                }
              }
            }
          }
        }
      }
    }
    leaf sccp {
      description
        "To enable/disable sccp protocol";
      type empty;
    }
  }
}
