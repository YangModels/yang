module Cisco-IOS-XE-bridge-domain-asr900-deviation {
  namespace "http://cisco.com/ns/yang/Cisco-IOS-XE-bridge-domain-asr900-deviation";
  prefix ios-bd-asr900-d;

  import cisco-semver {
    prefix cisco-semver;
  }
  import Cisco-IOS-XE-native {
    prefix ios;
  }
  import Cisco-IOS-XE-bridge-domain {
    prefix ios-bd;
  }

  organization
    "Cisco Systems";
  description
    "Cisco XE Native Bridge Domain Deviation YANG module for IOS-XE ASR900 (RSP2 and RSP3)
     and ASR920 platforms
     Copyright (c) 2021 by Cisco Systems, Inc.
     All rights reserved.";

  revision 2021-11-01 {
    description
      "Added mac learning deviation";
  }

  deviation "/ios:native/ios:bridge-domain/ios-bd:brd-id/ios-bd:mac/ios-bd:learning-boolean" {
    deviate not-supported;
  }

  deviation "/ios:native/ios:bridge-domain/ios-bd:brd-id/ios-bd:mac/ios-bd:learning" {
    deviate not-supported;
  }
}
