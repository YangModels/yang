module Cisco-IOS-XE-geo-events {
  yang-version 1;
  namespace "http://cisco.com/ns/yang/Cisco-IOS-XE-geo-events";
  prefix geo-ios-xe-events;

  import Cisco-IOS-XE-ios-common-oper {
    prefix ios-common-ios-xe-oper;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for GEO database events operational data.
     Copyright (c) 2020 by Cisco Systems, Inc.
     All rights reserved.";

  revision 2021-03-01 {
    description
      "Initial revision";
    reference
      "1.0.0";
    cisco-semver:module-version "1.0.0";
  }

  typedef geo-db-update-result-type {
    type enumeration {
      enum geo-db-update-status-success {
        value 0;
        description
          "Geo-Location Database update successful.";
      }
      enum geo-db-update-status-failure {
        value 1;
        description
          "Geo-Location Database update failed.";
      }
      enum geo-db-update-status-fs-error {
        value 2;
        description
          "Geo-Location Database update filesystem error.";
      }
      enum geo-db-update-status-internal-error {
        value 3;
        description
          "Geo-Location Database update encountered internal error.";
      }
    }
    description
      "Geo-Location Database update status type";
  }

  grouping geo-db-update {
    description
      "Geo-Location Database Update";
    leaf severity-level {
      type ios-common-ios-xe-oper:notification-severity;
      description
        "Event severity";
    }
    leaf db-file {
      type string;
      description
        "Geo-Location Database update file";
    }
    leaf status {
      type geo-ios-xe-events:geo-db-update-result-type;
      description
        "Geo-Location Database update status";
    }
  }

  notification geo-db-update-event {
    description
      "Geo-Location Database Update Notification";
    uses geo-ios-xe-events:geo-db-update;
  }
}
