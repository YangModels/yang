module Cisco-IOS-XE-wireless-actions-rpc {
  yang-version 1;
  namespace "http://cisco.com/ns/yang/Cisco-IOS-XE-wireless-actions-rpc";
  prefix wireless-actions-rpc;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     conditional debug for wireless.
     Copyright (c) 2021 by Cisco Systems, Inc.
     All rights reserved.";

  revision 2021-07-01 {
    description
      "Initial revision";
    reference
      "1.0.0";
    cisco-semver:module-version "1.0.0";
  }

  typedef enm-wireless-debug-condition {
    type enumeration {
      enum ip-address {
        value 0;
        description
          "Debug based on IP address";
      }
      enum mac-address {
        value 1;
        description
          "Debug based on MAC address";
      }
    }
    description
      "Choice of wireless debug condition";
  }

  grouping wireless-cond-debug {
    description
      "Conditional debugging for wireless feature";
    leaf delete {
      type empty;
      description
        "Delete debug condition";
    }
    choice condition-choice {
      mandatory true;
      description
        "Select condition";
      case ip-address {
        leaf ip {
          type inet:ip-address;
          mandatory true;
          description
            "Debug based on IP address";
        }
      }
      case mac-address {
        leaf mac {
          type yang:mac-address;
          mandatory true;
          description
            "Debug based on MAC address";
        }
      }
    }
  }

  rpc wireless-cond-debug {
    description
      "Conditional debugging for wireless";
    input {
      uses wireless-actions-rpc:wireless-cond-debug;
    }
  }
}
