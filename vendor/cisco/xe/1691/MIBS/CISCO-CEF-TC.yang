/*
 * Generated by confdc --mib2yang-std
 * Source: mgmt/dmi/model/mib/src/CISCO-CEF-TC.mib
 */
/*
 * This YANG module has been generated by smidump 0.5.0:
 *
 *      smidump -f yang CISCO-CEF-TC
 *
 * Do not edit. Edit the source file instead!
 */

module CISCO-CEF-TC {

  namespace "urn:ietf:params:xml:ns:yang:smiv2:CISCO-CEF-TC";
  prefix CISCO-CEF-TC;

  import ietf-yang-smiv2 {
    prefix "smiv2";
  }

  organization
   "Cisco Systems, Inc.";

  contact
   "Postal: Cisco Systems, Inc.
    170 West Tasman Drive
    San Jose, CA 95134-1706
    USA
    
    Tel: +1 800 553-NETS
    
    E-mail: cs-cef@cisco.com";

  description
   "This MIB module defines Textual Conventions and
    OBJECT-IDENTITIES for use in documents defining
    management information base (MIBs) modules for 
    managing Cisco Express Forwarding (CEF).";

  revision 2005-09-30 {
    description
     "Initial version of this MIB module.";
  }

  typedef CefIpVersion {
    type enumeration {
      enum "ipv4" {
        value "1";
      }
      enum "ipv6" {
        value "2";
      }
    }
    description
     "The version of CEF IP forwarding.";
  }

  typedef CefAdjLinkType {
    type enumeration {
      enum "ipv4" {
        value "1";
      }
      enum "ipv6" {
        value "2";
      }
      enum "mpls" {
        value "3";
      }
      enum "raw" {
        value "4";
      }
      enum "unknown" {
        value "5";
      }
    }
    description
     "Link type for the adjacency. The adjacency link type 
      identifies protocol stack on neighbour device which will 
      process packets fed through adjacency.";
  }

  typedef CefAdjacencySource {
    type bits {
      bit atom {
        position "0";
      }
      bit linkRawAdj {
        position "1";
      }
      bit ipPseudowireAdj {
        position "2";
      }
      bit arp {
        position "3";
      }
      bit p2pAdj {
        position "4";
      }
      bit frMap {
        position "5";
      }
      bit atmPVC {
        position "6";
      }
      bit atmSVC {
        position "7";
      }
      bit atmTVC {
        position "8";
      }
      bit nbma {
        position "9";
      }
      bit mpoa {
        position "10";
      }
      bit atmBundle {
        position "11";
      }
      bit lec {
        position "12";
      }
      bit nhrp {
        position "13";
      }
      bit ipv6ND {
        position "14";
      }
      bit cmcc {
        position "15";
      }
      bit ipv6SixtoFourTunnel {
        position "16";
      }
      bit ipv6IsaTapTunnel {
        position "17";
      }
      bit ipv6AutoTunnel {
        position "18";
      }
      bit fibLc {
        position "19";
      }
      bit virtual {
        position "20";
      }
      bit multicast {
        position "21";
      }
      bit unknown {
        position "22";
      }
    }
    description
     "The mechanism by which the adjacency is learned.
      As the mechanism of learning the adjacency can be
      multiple (e.g. 'arp' and 'atmPVC'), hence the 
      value of this object represents the bit mask of
      adjacency sources.";
  }

  typedef CefPathType {
    type enumeration {
      enum "receive" {
        value "1";
      }
      enum "connectedPrefix" {
        value "2";
      }
      enum "attachedPrefix" {
        value "3";
      }
      enum "attachedHost" {
        value "4";
      }
      enum "attachedNexthop" {
        value "5";
      }
      enum "recursiveNexthop" {
        value "6";
      }
      enum "adjacencyPrefix" {
        value "7";
      }
      enum "specialPrefix" {
        value "8";
      }
      enum "unknown" {
        value "9";
      }
    }
    description
     "Type of the CEF Path.
      receive(1)          : path for the address
                            configured on any of the
                            interface in the device.
      
      connectedPrefix(2)  : connected prefix path
      
      attachedPrefix(3)   : attached prefix path
      
      attachedHost(4)     : attached host path 
      
      attachedNexthop(5)  : attached next hop path
      
      recursiveNexthop(6) : recursive next hop path
      
      adjacencyPrefix(7)  : adjacency prefix path
      
      specialPrefix(8)    : special prefix path
      
      unknown(9):         : unknown  path
      .";
  }

  typedef CefPrefixSearchState {
    type enumeration {
      enum "running" {
        value "1";
      }
      enum "matchFound" {
        value "2";
      }
      enum "noMatchFound" {
        value "3";
      }
    }
    description
     "The state of prefix search operation. 
      The description of each state is given below:
      
        running(1)      : this state signifies that a prefix 
                          search request is running.
      
        matchFound(2)   : this state signifies that a prefix 
                          search request is completed and a prefix
                          match has been found.
      
        noMatchFound(3) : this state signifies that a prefix 
                          search request is completed and a prefix
                          match has not been found.";
  }

  typedef CefForwardingElementSpecialType {
    type enumeration {
      enum "illegal" {
        value "1";
      }
      enum "punt" {
        value "2";
      }
      enum "drop" {
        value "3";
      }
      enum "discard" {
        value "4";
      }
      enum "null" {
        value "5";
      }
      enum "glean" {
        value "6";
      }
      enum "unresolved" {
        value "7";
      }
      enum "noRoute" {
        value "8";
      }
      enum "none" {
        value "9";
      }
    }
    description
     "Type of special forwarding element 
      
      illegal(1)   : illegal special forwarding element.
                     the packet will be dropped.
      
      punt(2)      : the packet will be punted to the
                     next switching path
      
      drop(3)      : not supported for Destination IP to next hop
                     interface and the packet will be dropped
      
      discard(4)   : the packet is for Destination IP through
                     next hop interface and it will be discarded
      
      null(5)      : the packet is for Destination IP to null0,
                     it will be dropped
      
      glean(6)     : an attempt will be made to complete the
                     encapsulation string through address 
                     resolution
      
      unResolved(7): unresolved forwarding element.
                     the packet will be dropped unconditionally. 
      
      noRoute(8)   : no route forwarding element.
                     This forwarding element will result
                     in rate limited punts to the next
                     switching path(to generate ICMP 
                     no route message) 
      
      none(9)      : not a special forwarding element and
                     the value of this object should be
                     ignored ";
  }

  typedef CefMplsLabelList {
    type binary {
      length "0..255";
    }
    description
     "This contains a list of MPLS Labels, 
      each separated by the ';' (semi-colon) character.  
      
      MPLS Label values are in accordance with the
      MplsLabel TEXTUAL-CONVENTION defined in the
      MPLS-TC-MIB.
      
      The following is en example containing two MPLS labels: 
        
         4294;100
      			
      An empty string value for this object indicates
      no MPLS Labels in this list. ";
  }

  typedef CefAdminStatus {
    type enumeration {
      enum "enabled" {
        value "1";
      }
      enum "disabled" {
        value "2";
      }
    }
    description
     "Admin status of CEF. The admin status of CEF
      may differ from the oper status of CEF depending
      upon the success of the admin operation.";
  }

  typedef CefOperStatus {
    type enumeration {
      enum "up" {
        value "1";
      }
      enum "down" {
        value "2";
      }
    }
    description
     "Operational status of CEF.";
  }

  typedef CefFailureReason {
    type enumeration {
      enum "none" {
        value "1";
      }
      enum "mallocFailure" {
        value "2";
      }
      enum "hwFailure" {
        value "3";
      }
      enum "keepaliveFailure" {
        value "4";
      }
      enum "noMsgBuffer" {
        value "5";
      }
      enum "invalidMsgSize" {
        value "6";
      }
      enum "internalError" {
        value "7";
      }
    }
    description
     "Reason of CEF Failure:
      
      none(1)                : no failure 
      
      mallocFailure(2)       : memory allocation failed for CEF
      
      hwFailure(3)           : hardware interface failure 
                               for CEF
      
      keepaliveFailure(4)    : keepalive was not received from 
                               the CEF peer entity
      
      noMsgBuffer(5)         : message buffers were exhausted 
                               while preparing IPC message to be 
                               sent to the CEF peer entity
      
      invalidMsgSize(6)      : IPC message was received with 
                               invalid size from the
                               CEF peer entity
      
      internalError(7)       : Some other internal error was 
                               detected for CEF";
  }

  typedef CefCCType {
    type enumeration {
      enum "lcDetect" {
        value "1";
      }
      enum "scanFibLcRp" {
        value "2";
      }
      enum "scanFibRpLc" {
        value "3";
      }
      enum "scanRibFib" {
        value "4";
      }
      enum "scanFibRib" {
        value "5";
      }
      enum "scanFibHwSw" {
        value "6";
      }
      enum "scanFibSwHw" {
        value "7";
      }
      enum "fullScanRibFib" {
        value "8";
      }
      enum "fullScanFibRib" {
        value "9";
      }
      enum "fullScanFibRpLc" {
        value "10";
      }
      enum "fullScanFibLcRp" {
        value "11";
      }
      enum "fullScanFibHwSw" {
        value "12";
      }
      enum "fullScanFibSwHw" {
        value "13";
      }
    }
    description
     "Type of the consistency checker.
      
      lcDetect         : This is an active consistency checker
                         which is triggered when a packet cannot 
                         be forwarded because the prefix is not
                         in the forwarding table. It Detects 
                         missing prefixes on the linecard CEF 
                         database by sending the missing prefixes 
                         to the RP.
                    
      scanFibLcRp      : This is an passive consistency checker
                         which performs a passive scan check of
                         the table on the line card.
      
                         This consistency checker operates on 
                         the line card by examining the FIB table 
                         for a configurable time period and sending 
                         the next n prefixes to the RP. 
      
      scanFibRpLc      : This is an passive consistency checker
                         which performs a passive scan check of
                         RP by examining the FIB table for 
                         a configurable period and
                         sending the next n prefixes to the 
                         line card. 
      
      scanRibFib       : This is an passive consistency checker
                         which compares routing information base 
                         (RIB) to the FIB table at a configurable
                         interval and provides the number of 
                         entries missing from the FIB table. 
      
      scanFibRib       : This is an passive consistency checker
                         which compares FIB Tables to the 
                         routing information base (RIB) 
                         at a configurable interval and provides 
                         the number of entries missing from the 
                         FIB table. 
      
      scanFibHwSw      : This is an passive consistency checker
                         which compares FIB Tables in hardware
                         to the FIB Tables in RP.
      
      scanFibSwHw      : This is an passive consistency checker
                         which compares FIB Tables in RP
                         to the FIB Tables in hardware.
      
      fullScanRibFib   : This is an active consistency checker
                         which is triggered by Management Station 
                         request. It compares the entire routing 
                         information base (RIB) to the FIB table
                         and provide the number of entries missing
                          from the FIB Table.
      
      fullScanFibRib   : This is an active consistency checker
                         which is triggered by Management Station 
                         request. It compares the FIB table to the 
                         routing information base (RIB)
                         and provide the number of entries missing
                         from the FIB Table.
      
      fullScanFibRpLc  : This is an active consistency checker
                         which is triggered by Management Station 
                         request. It compares the RP FIB Table 
                         with FIB Table on each LC and report 
                         inconsistencies.
                      
      fullScanFibLcRp  : This is an active consistency checker
                         which is triggered by Management Station 
                         request. It compares the Fib Table on LC 
                         with FIB table on RP and report 
                         inconsistencies.
      
      fullScanFibHwSw  : This is an active consistency checker
                         which is triggered by Management Station 
                         request. It compares the Fib Table in 
                         hardware with FIB table in RP and report 
                         inconsistencies.
      
      fullScanFibSwHw  : This is an active consistency checker
                         which is triggered by Management Station 
                         request. It compares the Fib Table in RP 
                         with FIB table in hardware and report 
                         inconsistencies.";
  }

  typedef CefCCAction {
    type enumeration {
      enum "ccActionStart" {
        value "1";
      }
      enum "ccActionAbort" {
        value "2";
      }
      enum "ccActionNone" {
        value "3";
      }
    }
    description
     "The action to be performed for the consistency
      checkers.
      
        ccActionStart(1)   :  start the Consistency checker
                              operation.
      
        ccActionAbort(2)   :  abort the Consistency checker 
                              operation. After aborting, the 
                              active process must recover. 
                              This can take some time, and 
                              during this period, the scan 
                              cannot be restarted.
      
        ccActionNone(3)    :  no operation is being performed 
                              on consistency checkers.";
  }

  typedef CefCCStatus {
    type enumeration {
      enum "ccStatusIdle" {
        value "1";
      }
      enum "ccStatusRunning" {
        value "2";
      }
      enum "ccStatusDone" {
        value "3";
      }
    }
    description
     "The status of consistency checker operation. 
      The description of each state is given below:
      
        ccStatusIdle(1)    :  this state signifies that
                              no consistency checker request
                              is being performed.
      
        ccStatusRunning(2) :  this state signifies that 
                              consistency checker request is 
                              in progress.
      
        ccStatusDone(3)     : this state signifies that 
                              consistency checker request is 
                              over. 
                            ";
  }

  smiv2:alias "ciscoCefTextualConventions" {
    smiv2:oid "1.3.6.1.4.1.9.9.493";
  }

}
