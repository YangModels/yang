module Cisco-IOS-XE-common-types {
  yang-version 1;
  namespace "http://cisco.com/ns/yang/Cisco-IOS-XE-common-types";
  prefix common-types-ios-xe;

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains type definitions common to all Cisco IOS XE native models
     
     Copyright (c) 2016-2017 by Cisco Systems, Inc.
     All rights reserved.";

  revision 2017-12-01 {
    description
      "- Properly indicate leaf-list ordering
       - Add addr-type to represent IP address types";
    reference "1.1.0";
  }
  revision 2017-05-05 {
    description
      "Initial revision";
    reference "1.0.0";
  }

  typedef addr-type {
    type enumeration {
      enum "address-none" {
        value 0;
      }
      enum "ipv4-address" {
        value 1;
      }
      enum "ipv6-address" {
        value 2;
      }
      enum "ipv4-address-mcast" {
        value 3;
      }
      enum "ipv6-address-mcast" {
        value 4;
      }
    }
    description
      "IP address type";
  }

  grouping mcp-bytestr {
    description
      "Type representing a byte array";
    leaf-list bytes {
      type uint8;
      ordered-by user;
      description
        "Byte array";
    }
  }
}
