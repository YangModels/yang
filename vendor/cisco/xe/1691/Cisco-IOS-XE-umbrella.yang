module Cisco-IOS-XE-umbrella {
  namespace "http://cisco.com/ns/yang/Cisco-IOS-XE-umbrella";
  prefix ios-umbrella;

  import ietf-inet-types {
    prefix inet;
  }

  import Cisco-IOS-XE-native {
    prefix ios;
  }

  import Cisco-IOS-XE-policy {
    prefix ios-policy;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Umbrella Yang model.
     Copyright (c) 2017-2018 by Cisco Systems, Inc.
     All rights reserved.";

  // =========================================================================
  // REVISION
  // =========================================================================
  revision 2018-05-14 {
    description
      "Limit string lengths for threat-defense features";
  }

  revision 2018-02-22 {
    description
      "Add threat-defense support for Ethernet interfaces";
  }

  revision 2018-02-06 {
    description
      "Refactor parameter-map";
  }

  revision 2017-11-27 {
    description
      "Added Change 25GE name";
  }

  revision 2017-11-14 {
    description
      "Added Two GE Interface";
  }

  revision 2017-08-30 {
    description
      "Initial revision";
  }

  grouping config-umbrella-grouping {
    container umbrella {
      description
        "Umbrella mode";
      container global {
        description
          "umbrella global parameter-map";
        presence true;
        leaf token {
          description  
            "Config umbrella token";
          type string {
            length "1..64";
          }
        }
        leaf local-domain {
          description
            "Local domain processing";
          type string {
            length "1..256";
          }
        }
        leaf dnscrypt {
          description
            "Enable DNSCrypt";
          type boolean;
          default true;
        }
        leaf public-key {
          description
            "DNSCrypt provider public key";
          type string {
            length "1..80";
          }
        }
        leaf udp-timeout {
          description
            "Config timeout value for UDP sessions";
          type uint8 {
            range "1..30";
          }
        }
        container resolver {
          description
            "Anycast address";
          list ipv4 {
            description
              "IPv4 anycast address";
            key address;
            leaf address {
              type inet:ipv4-address;
            }
          }
          list ipv6 {
            description
              "IPv6 anycast address";
            key address;
            leaf address {
              type inet:ipv6-address;
            }
          }
        }
      }
    }
  }

  grouping config-interface-umbrella-grouping {
    // interface * / umbrella
    container umbrella {
      description
        "Umbrella interface commands";
      leaf out {
        description
          "Umbrella Out direction";
        type empty;
      }
      leaf in {
        description
          "Umbrella In direction";
        type string {
          length "1..49";
        }
      }
    }
  }

  /////////////////////////////////////////////////////////
  // native / parameter-map type umbrella
  /////////////////////////////////////////////////////////
  augment "/ios:native/ios:parameter-map/ios:type" {
    uses config-umbrella-grouping;
  } //augment

  /////////////////////////////////////////////////////////
  // native / interface
  /////////////////////////////////////////////////////////
  augment "/ios:native/ios:interface/ios:Ethernet" {
    uses config-interface-umbrella-grouping;
  }

  augment "/ios:native/ios:interface/ios:FastEthernet" {
    uses config-interface-umbrella-grouping;
  }

  augment "/ios:native/ios:interface/ios:GigabitEthernet" {
    uses config-interface-umbrella-grouping;
  }

  augment "/ios:native/ios:interface/ios:TenGigabitEthernet" {
    uses config-interface-umbrella-grouping;
  }

  augment "/ios:native/ios:interface/ios:FiveGigabitEthernet" {
    uses config-interface-umbrella-grouping;
  }

  augment "/ios:native/ios:interface/ios:TwentyFiveGigE" {
    uses config-interface-umbrella-grouping;
  }

  augment "/ios:native/ios:interface/ios:FortyGigabitEthernet" {
    uses config-interface-umbrella-grouping;
  }

  augment "/ios:native/ios:interface/ios:HundredGigE" {
    uses config-interface-umbrella-grouping;
  }

  augment "/ios:native/ios:interface/ios:TwoGigabitEthernet" {
    uses config-interface-umbrella-grouping;
  }

  augment "/ios:native/ios:interface/ios:LISP" {
    uses config-interface-umbrella-grouping;
  }

  augment "/ios:native/ios:interface/ios:Loopback" {
    uses config-interface-umbrella-grouping;
  }

  augment "/ios:native/ios:interface/ios:Tunnel" {
    uses config-interface-umbrella-grouping;
  }

  augment "/ios:native/ios:interface/ios:Virtual-Template" {
    uses config-interface-umbrella-grouping;
  }

  augment "/ios:native/ios:interface/ios:Vlan" {
    uses config-interface-umbrella-grouping;
  }

  augment "/ios:native/ios:interface/ios:vasileft" {
    uses config-interface-umbrella-grouping;
  }

  augment "/ios:native/ios:interface/ios:vasiright" {
    uses config-interface-umbrella-grouping;
  }
} //module
