module Cisco-IOS-XE-lldp {
  namespace "http://cisco.com/ns/yang/Cisco-IOS-XE-lldp";
  prefix ios-lldp;


  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Link Layer Discovery Protocol (LLDP) Yang model.
     Copyright (c) 2016-2017 by Cisco Systems, Inc.
     All rights reserved.";

  // =========================================================================
  // REVISION
  // =========================================================================
  revision 2017-11-27 {
     description
       "Added Change 25GE name";
  }

  revision 2017-11-14 {
    description
      "This revision has changes for new 100GE interface addition";
  }

  revision 2017-09-15 {
    description
      "This revision has changes for new 2gig interface addition";
  }
  revision 2017-08-16 {
    description
      "This revision has changes for new 5gig and 25gig interfaces addition";
  }
  revision 2017-03-31 {
    description
      "Move interface LLDP configs from switch to common";
  }
  revision 2017-02-07 {
    description
      "Initial revision";
  }

  // Global configs
  grouping config-lldp-grouping {
    container lldp {
      description "Enables LLDP globally.";
      leaf run {
        description "Enable LLDP";
        type empty;
      }
    }
  }

  // Interface configs
  grouping config-interface-lldp-grouping {
    // interface * / lldp
    container lldp {
      description
        "LLDP interface subcommands";
      leaf receive {
        description
          "Enable LLDP reception on interface";
        type boolean;
      }
      leaf transmit {
        description
          "Enable LLDP transmission on interface";
        type boolean;
      }
    }
}


  /////////////////////////////////////////////////////////
  // native / lldp 
  /////////////////////////////////////////////////////////
  augment "/ios:native" {
    uses config-lldp-grouping;
  }

  /////////////////////////////////////////////////////////
  // native / interface * / lldp
  //
  //   The config is only allowed on generic "Ethernet" type of interfaces. 
  //   See config check in sys/lldp/cfg_int_lldp.h :
  //      LLDP_DEFAULT_ENABLE_INT(csb->interface)
  /////////////////////////////////////////////////////////
  augment "/ios:native/ios:interface/ios:FastEthernet" {
    uses config-interface-lldp-grouping;
  }

  augment "/ios:native/ios:interface/ios:GigabitEthernet" {
    uses config-interface-lldp-grouping;
  }

  augment "/ios:native/ios:interface/ios:TwoGigabitEthernet" {
    uses config-interface-lldp-grouping;
  }

  augment "/ios:native/ios:interface/ios:FiveGigabitEthernet" {
    uses config-interface-lldp-grouping;
  }

  augment "/ios:native/ios:interface/ios:TenGigabitEthernet" {
    uses config-interface-lldp-grouping;
  }

  augment "/ios:native/ios:interface/ios:TwentyFiveGigE" {
    uses config-interface-lldp-grouping;
  }

  augment "/ios:native/ios:interface/ios:FortyGigabitEthernet" {
    uses config-interface-lldp-grouping;
  }

  augment "/ios:native/ios:interface/ios:HundredGigE" {
    uses config-interface-lldp-grouping;
  }
}
