module Cisco-IOS-XE-igmp {
  namespace "http://cisco.com/ns/yang/Cisco-IOS-XE-igmp";
  prefix ios-igmp;

  import ietf-inet-types {
    prefix inet;
  }


  import Cisco-IOS-XE-native {
    prefix ios;
  }

  import Cisco-IOS-XE-policy {
    prefix policy;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Internet Group Management Protocol (IGMP) Yang model.
     Copyright (c) 2016-2017 by Cisco Systems, Inc.
     All rights reserved.";

  // =========================================================================
  // REVISION
  // =========================================================================
  revision 2017-11-27 {
     description
       "Added Change 25GE name";
  }

  revision 2017-11-14 {
    description
      "This revision has changes for new 40 and 100GE interface addition";
  }

  revision 2017-09-14 {
    description
      "This revison has changes for new 2gig interface addition";
  }
  revision 2017-08-28 {
    description
      "Extend modeling for multicast";
  }
  revision 2017-08-16 {
    description
      "This revision has changes for new 5gig and 25gig interfaces addition";
  }

  revision 2017-02-07 {
    description
      "Initial revision";
  }

  grouping config-ip-igmp-grouping {
    container igmp { //43480
      description
        "IGMP global configuration";
      container snooping-conf {
        leaf snooping {
          type boolean;
        }
      }
      container snooping {
        description
          "Global IGMP Snooping enable for Catalyst Vlans";
        container check {
          description
            "enforce TTL or Rtr-Alert Option checking";
          leaf rtr-alert-option {
            description
              "Only accept IGMP packets with router-alert option";
            type empty;
          }
          leaf ttl {
            description
              "Only accept IGMP packets with TTL=1";
            type empty;
          }
        }

        container explicit-tracking {
          description
            "Explicit tracking DB configuration";
          leaf limit {
            description
              "Explicit tracking DB limit";
            type uint32 {
              range "0..128000";
            }
          }
        }
        leaf l2-entry-limit {
          description
            "limit on the l2 entry that can be installed by IGMP snooping";
          type uint32 {
            range "1..100000";
          }
        }
        leaf last-member-query-count {
          description
            "Last member query count";
          type uint8 {
            range "1..7";
          }
        }
        leaf last-member-query-interval {
          description
            "Interval (milliseconds)";
          type uint16 {
            range "100..32767";
          }
        }
        container querier {
          description
            "IGMP querier configuration";
          presence "true";
          leaf address {
            description
              "IGMP querier source IP address";
            type inet:ipv4-address;
          }
          leaf max-response-time {
            description
              "IGMP querier maximum response time (sec)";
            type uint8 {
              range "1..25";
            }
          }
          leaf query-interval {
            description
              "IGMP querier query interval (sec)";
            type uint16 {
              range "1..18000";
            }
          }
          container tcn {
            description
              "IGMP querier TCN related parameters";
            container query {
              leaf count {
                description
                  "IGMP querier TCN query count";
                type uint8 {
                  range "1..10";
                }
              }
              leaf interval {
                description
                  "IGMP querier TCN query interval (sec)";
                type uint8 {
                  range "1..255";
                }
              }
            }
          }
          container timer {
            description
              "IGMP other querier timer";
            leaf expiry {
              description
                "IGMP querier other querier time out (sec)";
              type uint16 {
                range "60..300";
              }
            }
          }
          leaf version {
            description
              "IGMP version";
            type uint8 {
              range "1..2";
            }
          }
        }
        leaf report-suppression {
          description
            "Report suppression";
          type empty;
        }
        leaf robustness-variable {
          description
            "Robustness Variable number";
          type uint8 {
            range "1..3";
          }
        }
        container tcn {
          description
            "Topology change notification configuration";
          container flood {
            description
              "TCN flooding configuration";
            container query {
              description
                "TCN flooding query configuration";
              leaf count {
                description
                  "Count";
                type uint8 {
                  range "1..10";
                }
              }
            }
          }
          container query {
            description
              "TCN query configuration";
            leaf solicit {
              description
                "Solicit an IGMP general query";
              type empty;
            }
          }
        }
      }
      container ssm-map {
        description
          "SSM mapping commands";
        leaf enable {
          description
            "Enable SSM group to source mapping";
          type empty;
        }
        container query {
          description
            "Which database should we query for the source";
          leaf dns {
            description
              "Use DNS for source lookup";
            type empty;
          }
        }
        container static {
          description
            "SSM static group to source mapping";
          leaf acl {
            type union {
              type uint16 {
                range "1..99";
              }
              type string;
            }
          }
          leaf source-ip {
            type inet:ipv4-address;
          }
        }
      }
      list vrf {
        description "Select VPN Routing/Forwarding instance";
        key "name";
        leaf name {
          description "VPN Routing/Forwarding instance name";
          type string;
        }
        container ssm-map {
          description "SSM mapping commands";
          leaf enable {
            description "Enable SSM group to source mapping";
            type empty;
          }
          list static {
            description "SSM static group to source mapping";
            key "srcaddress";
            leaf srcaddress {
              description "SSM source address";
              type inet:ipv4-address;
            }
            leaf aclname {
              description "SSM group named access list";
              type string;
            }
          }
        }
      }
    }
  }

  grouping config-interface-ip-igmp-grouping {
    container igmp {
      description
        "IGMP interface commands";
      container static-group {
        description
          "IGMP static multicast group";
        list groups {
          key "name";
          leaf name {
            type union {
              type inet:ipv4-address;
              type enumeration {
                enum "*";
              }
            }
          }
          leaf-list source {
            type union {
              type inet:ipv4-address;
              type enumeration {
                enum "ssm-map";
              }
            }
          }
        }

        list class-map {
          description
            "Class map of type multicast-flows";
          key "id";
          leaf id {
            type leafref {
              path "/ios:native/ios:policy/policy:class-map/policy:name";
            }
          }
        }
      }

      list join-group {
        description
          "IGMP join multicast group";
        key "ip-group-address";
        leaf ip-group-address {
          description
            "IP group address";
          type inet:ipv4-address;
        }
        leaf source {
          description
            "IP source address";
          type inet:ipv4-address;
        }
      }
      leaf version {
        description
          "IGMP version";
        type uint8 {
          range "1..3";
        }
      }
    }
  }

  /////////////////////////////////////////////////////////
  // native / ip / igmp
  /////////////////////////////////////////////////////////
  augment "/ios:native/ios:ip" {
    uses config-ip-igmp-grouping;
  }

  /////////////////////////////////////////////////////////
  // native / interface * / ip / igmp
  /////////////////////////////////////////////////////////
  augment "/ios:native/ios:interface/ios:FastEthernet/ios:ip" {
    uses config-interface-ip-igmp-grouping;
  }

  augment "/ios:native/ios:interface/ios:GigabitEthernet/ios:ip" {
    uses config-interface-ip-igmp-grouping;
  }

  augment "/ios:native/ios:interface/ios:TenGigabitEthernet/ios:ip" {
    uses config-interface-ip-igmp-grouping;
  }

  augment "/ios:native/ios:interface/ios:FiveGigabitEthernet/ios:ip" {
    uses config-interface-ip-igmp-grouping;
  }

  augment "/ios:native/ios:interface/ios:TwentyFiveGigE/ios:ip" {
    uses config-interface-ip-igmp-grouping;
  }

  augment "/ios:native/ios:interface/ios:TwoGigabitEthernet/ios:ip" {
    uses config-interface-ip-igmp-grouping;
  }

  augment "/ios:native/ios:interface/ios:FortyGigabitEthernet/ios:ip" {
    uses config-interface-ip-igmp-grouping;
  }

  augment "/ios:native/ios:interface/ios:HundredGigE/ios:ip" {
    uses config-interface-ip-igmp-grouping;
  }

  augment "/ios:native/ios:interface/ios:Loopback/ios:ip" {
    uses config-interface-ip-igmp-grouping;
  }

  augment "/ios:native/ios:interface/ios:Port-channel/ios:ip" {
    uses config-interface-ip-igmp-grouping;
  }

  augment "/ios:native/ios:interface/ios:Tunnel/ios:ip" {
    uses config-interface-ip-igmp-grouping;
  }

  augment "/ios:native/ios:interface/ios:Virtual-Template/ios:ip" {
    uses config-interface-ip-igmp-grouping;
  }

  augment "/ios:native/ios:interface/ios:VirtualPortGroup/ios:ip" {
    uses config-interface-ip-igmp-grouping;
  }

  augment "/ios:native/ios:interface/ios:Vlan/ios:ip" {
    uses config-interface-ip-igmp-grouping;
  }
}
