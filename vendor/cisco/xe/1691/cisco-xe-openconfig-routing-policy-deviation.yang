module cisco-xe-openconfig-routing-policy-deviation {
  // namespace
  namespace "http://cisco.com/ns/yang/cisco-xe-routing-policy-deviation";

  prefix cisco-oc-rpol-dev;

  import openconfig-routing-policy {
    prefix oc-rpol;
  }

  organization
    "Cisco Systems, Inc.";

  contact
    " Cisco Systems, Inc.
    Customer Service

    Postal: 170 W Tasman Drive
    San Jose, CA 95134

    Tel: +1 1800 553-NETS

    E-mail: cs-yang@cisco.com";

  description
    "This module defines deviation statements for openconfig-routing-policy module.";

  revision 2017-03-30 {
    description
      "Initial Revision";

    reference
      "RFC 6020: YANG - A Data Modeling Language for the
       Network Configuration Protocol (NETCONF)";
  }

 

  deviation "/oc-rpol:routing-policy/oc-rpol:policy-definitions/oc-rpol:policy-definition/oc-rpol:statements/oc-rpol:statement/oc-rpol:conditions/oc-rpol:match-tag-set/oc-rpol:config/oc-rpol:tag-set" {
        description
            "Modifies the eigrp match tag condition so it can be referred by name rather than
             a reference to a predefined tag set since the predefined eigrp tag sets are not yet supported in Polaris 16.6.1.";

        deviate replace {
            type string;
        }

    }

   deviation "/oc-rpol:routing-policy/oc-rpol:policy-definitions/oc-rpol:policy-definition/oc-rpol:statements/oc-rpol:statement/oc-rpol:conditions/oc-rpol:match-tag-set/oc-rpol:state/oc-rpol:tag-set" {
        description
            "Modifies the eigrp match tag condition so it can be referred by name rather than
             a reference to a predefined tag set since the predefined eigrp tag sets are not yet supported in Polaris 16.6.1.";

        deviate replace {
            type string;
        }

    }


  deviation "/oc-rpol:routing-policy/oc-rpol:policy-definitions/oc-rpol:policy-definition/oc-rpol:statements/oc-rpol:statement/oc-rpol:conditions/oc-rpol:match-neighbor-set" {
        deviate not-supported;
        description  "Not supported on IOS-XE.";
      }


  deviation "/oc-rpol:routing-policy/oc-rpol:policy-definitions/oc-rpol:policy-definition/oc-rpol:statements/oc-rpol:statement/oc-rpol:conditions/oc-rpol:config" {
        deviate not-supported;
        description  "Not supported on IOS-XE.";
      }

  deviation "/oc-rpol:routing-policy/oc-rpol:policy-definitions/oc-rpol:policy-definition/oc-rpol:statements/oc-rpol:statement/oc-rpol:conditions/oc-rpol:state" {
        deviate not-supported;
        description  "Not supported on IOS-XE.";
      }

   deviation "/oc-rpol:routing-policy/oc-rpol:policy-definitions/oc-rpol:policy-definition/oc-rpol:statements/oc-rpol:statement/oc-rpol:conditions/oc-rpol:match-interface" {
        deviate not-supported;
        description  "Not supported in Polaris 16.6.1.";
      }

   deviation "/oc-rpol:routing-policy/oc-rpol:defined-sets/oc-rpol:tag-sets" {
        deviate not-supported;
        description  "Not supported in Polaris 16.6.1.";
      }

   deviation "/oc-rpol:routing-policy/oc-rpol:defined-sets/oc-rpol:prefix-sets/oc-rpol:prefix-set/oc-rpol:prefixes/oc-rpol:prefix/oc-rpol:config/oc-rpol:masklength-range" {
        deviate replace {
             type string {
              pattern '^([0-9]+\.\.[0-9]+)|exact';
             }
           }
      }

}
