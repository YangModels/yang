module Cisco-IOS-XE-l2vpn {
  namespace "http://cisco.com/ns/yang/Cisco-IOS-XE-l2vpn";
  prefix ios-l2vpn;

  import ietf-inet-types {
    prefix inet;
  }


  import Cisco-IOS-XE-native {
    prefix ios;
  }

  import Cisco-IOS-XE-interface-common {
    prefix ios-ifc;
  }

  import Cisco-IOS-XE-ethernet {
    prefix ios-eth;
  }

  import Cisco-IOS-XE-features {
    prefix ios-features;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Layer 2 Virtual Private Network (L2VPN) Yang model.
     Copyright (c) 2016-2017 by Cisco Systems, Inc.
     All rights reserved.";

  // =========================================================================
  // REVISION
  // =========================================================================
  revision 2018-02-13 {
    description
      "Added Evpn support";
  }
  revision 2017-11-27 {
     description
       "Added Change 25GE name";
  }

  revision 2017-11-14 {
    description
      "This revision has changes for new 40 and 100GE interface addition";
  }

  revision 2017-09-15 {
    description
      "This revision has changes for new 2gig interface addition";
  }
  revision 2017-08-16 {
    description
      "This revision has changes for new 5gig and 25gig interfaces addition";
  }
  revision 2017-08-10 {
    description
      "Add mtu for l2 vfi";
  }
  revision 2017-02-07 {
    description
      "Initial revision";
  }


  grouping config-interface-pseudowire-grouping {
    // pseudowire-class * / encapsulation
    leaf encapsulation {
      description
        "Data encapsulation method";
      type enumeration {
        enum "l2tpv2";
        enum "l2tpv3";
        enum "mpls";
        enum "udp";
      }
    }

    //pseudowire-class * / ip
    container ip {
      description
        "Specify IP parameters";
      when "../encapsulation = 'l2tpv2' or ../encapsulation = 'l2tpv3'";
      container dfbit {
        description
          "DF bit options for tunnel";
        leaf set {
          description
            "Set the DF bit in the tunnel header";
          type empty;
        }
      }
      container local {
        description
          "Specify local information";
        container interface {
          description
            "Source interface for pseudowire";
          uses ios-ifc:interface-grouping;
        }
      }
      container pmtu {
        description
          "Enable Path MTU for tunnel";
        presence "true";
        leaf max {
          description
            "Maximum Path MTU for session";
          type uint16 {
            range "68..65535";
          }
        }
      }
      leaf protocol {
        description
          "Specific IP protocol number to use";
        when "../../encapsulation = 'l2tpv3'";
        type enumeration {
          enum "l2tp";
          enum "uti";
        }
      }
      container tos {
        description
          "Specify ToS options for IP tunnel header";
        leaf reflect {
          description
            "Reflect IP payload ToS on tunnel";
          type empty;
        }
        leaf value {
          description
            "IP ToS value";
          type uint8;
        }
      }
      leaf ttl {
        description
          "Specify TTL value for IP tunnel header";
        type uint8;
      }
    }

    //pseudowire-class * / control-word
    leaf control-word {
      description
        "Include control-word in pseudowire packets";
      when "../encapsulation = 'mpls'";
      type empty;
    }

    //pseudowire-class * / interworking
    leaf interworking {
      description
        "Interworking options for pseudowire";
      type enumeration {
        enum "ethernet";
        enum "ip";
        enum "vlan";
      }
    }

    //pseudowire-class * / load-balance
    container load-balance {
      description
        "Loadbalancing for pseudowire";
      when "../encapsulation = 'mpls'";
      container flow {
        description
          "Enable flow based load balancing for pseudowire";
        presence "true";
        leaf ethernet {
          description
            "Ethernet pseudowire flow classification";
          type enumeration {
            enum "dst-mac";
            enum "src-dst-mac";
            enum "src-mac";
          }
        }
      }
    }

    //pseudowire-class * / monitor
    container monitor {
      description
        "Active monitoring of xconnect peer";
      when "../encapsulation = 'mpls'";
      container peer {
        description
          "Active monitoring of xconnect peer";
        container bfd {
          description
            "BFD active monitoring for the xconnect peer";
          presence "true";
          container local {
            description
              "Specify local endpoint information to map to a BFD session";
            container interface {
              description
                "Source interface for pseudowire";
              uses ios-ifc:interface-grouping;
            }
          }
        }
      }
    }

    //pseudowire-class * / preferred-path
    container preferred-path {
      description
        "Preferred path";
      container interface {
        description
          "Output Interface";
        choice Tunnel-Tunnel-tp {
          case Tunnel-case {
            leaf Tunnel {
              description
                "Tunnel interface";
              type uint64 {
                range "0..2147483647";
              }
            }
          }
          case Tunnel-tp-case {
            leaf Tunnel-tp {
              description
                "MPLS Transport Profile interface";
              type uint16;
            }
          }
        }
        leaf disable-fallback {
          description
            "disable fall back to alternative route";
          type empty;
        }
      }
      container peer-container {
        leaf peer {
          description
            "Peer Address";
          type union {
            type string;
            type inet:ipv4-address;
          }
        }
        leaf disable-fallback {
          description
            "disable fall back to alternative route";
          type empty;
        }
      }
    }

    //pseudowire-class * / protocol
    container protocol-mpls {
      when "../encapsulation = 'mpls'";
      leaf protocol {
        description
          "Signaling protocol to use";
        type enumeration {
          enum "ldp";
          enum "none";
        }
      }
    }

    container protocol-l2tpv2 {
      when "../encapsulation = 'l2tpv2'";
      leaf protocol {
        description
          "Signaling protocol to use";
        type enumeration {
          enum "l2tpv2";
          enum "none";
        }
      }
    }

    container protocol-l2tpv3 {
      when "../encapsulation = 'l2tpv3'";
      leaf protocol {
        description
          "Signaling protocol to use";
        type enumeration {
          enum "l2tpv3";
          enum "l2tpv3ietf";
          enum "none";
        }
      }
    }

    //pseudowire-class * / sequencing
    leaf sequencing {
      description
        "Sequencing options for pseudowire";
      when "../encapsulation = 'mpls' or ../encapsulation = 'l2tpv3'";
      type enumeration {
        enum "both";
        enum "receive";
        enum "resync";
        enum "transmit";
      }
    }

    //pseudowire-class * / status
    container status {
      description
        "Pseudowire status capabilities";
      presence "true";
      container admin-down {
        description
          "Admin down of Attachment Circuit";
        when "../../encapsulation = 'l2tpv2' or ../../encapsulation = 'l2tpv3'";
        leaf disconnect {
          description
            "Disconnect the session";
          type empty;
        }
      }
      container control-plane {
        description
          "control plane status events";
        leaf route-watch {
          description
            "listen on the control plane to route-watch events";
          type empty;
        }
      }
      leaf decoupled {
        description
          "Reflect standby status of the attachment circuit as up on the pseudowire";
        type empty;
      }
      container peer {
        description
          "peer status configuration";
        container topology {
          description
            "change status behaviour based on peer topology";
          leaf dual-homed {
            description
              "Our peer(s) are participating in a redundant solution with some form of redundancyprotocol running between the peer routers, Only one of the remote peers will advertise astatus of UP at a time. The other will advertise standby. Change our configuration so wecan send a status of UP on both active and redundant pseudowires";
            type empty;
          }
        }
      }
      container redundancy {
        description
          "Xconnect redundancy configuration";
        leaf master {
          description
            "Put the xconnect redundancy group on this node in master mode";
          type empty;
        }
      }
    }

    //pseudowire-class * / switching
    container switching {
      description
        "Switching TLV on/off for pseudowire";
      when "../encapsulation = 'mpls'";
      leaf tlv {
        description
          "Switching TLV on/off for pseudowire";
        type empty;
      }
    }
  }

  grouping config-interface-efp-xconnect-grouping {
    choice xconnect-choice {
      container xconnect {
        leaf address {
          type inet:ipv4-address;
        }
        leaf vcid {
          type uint32 {
            range "1..4294967295";
          }
        }
        leaf encapsulation {
          description
            "Data encapsulation method";
          type enumeration {
            enum "mpls";
            enum "l2tpv3";
          }
        }
        leaf manual {
          description
            "Manually configure L2TP session parameters";
          type empty;
        }
        leaf pw-class {
          description
            "Optional pseudowire-class to use for advanced configuration";
          type string;
        }
        leaf sequencing {
          description
            "Configure sequencing options for xconnect";
          when "../encapsulation = 'l2tpv3'";
          type enumeration {
            enum "both";
            enum "receive";
            enum "transmit";
          }
        }
        // interface * / xconnect encapsulation / backup peer
        container backup {
          description
            "Xconnect backup configuration commands";
          container peer {
            description
              "Backup pseudowire";
            leaf peer-router-ip-addr {
              type inet:ipv4-address;
            }
            leaf vcid {
              type uint32 {
                range "1..4294967295";
              }
            }
            leaf pw-class {
              type string;
            }
            leaf priority {
              description
                "Optional priority to use for backup pseudowire.";
              type uint8 {
                range "1..10";
              }
            }
          }
          container delay {
            description
              "backup delay time";
            leaf min {
              type uint32;
            }
            leaf max {
              type uint32;
            }
          }
        }
        leaf mtu {
          type uint32;
        }
      }

      //interface * / xconnect pw-class
      container xconnect-pw-class {
        container xconnect {
          description
            "Xconnect commands";
          leaf address {
            type inet:ipv4-address;
          }
          leaf vcid {
            type uint32 {
              range "1..4294967295";
            }
          }
          leaf pw-class {
            description
              "Pseudowire-class to use for encapsulation and protocol configuration";
            type string;
          }
          container udp {
            description
              "UDP";
            container port {
              description
                "UDP ports";
              leaf local {
                type uint32;
              }
              leaf remote {
                type uint32;
              }
            }
          }
        }
      }
    }
  }

  grouping config-interface-xconnect-grouping {
    // interface * / xconnect
    container xconnect {
      description
        "Xconnect commands";

      leaf address {
        type inet:ipv4-address;
      }
      leaf vcid {
        type uint32 {
          range "1..4294967295";
        }
      }
      leaf encapsulation {
        description
          "Data encapsulation method";
        type enumeration {
          enum "mpls" {
          }
          enum "l2tpv3";
        }
      }
      leaf manual {
        description
          "Manually configure L2TP session parameters";
        when "../encapsulation = 'l2tpv3'";
        type empty;
      }
      leaf sequence {
        description
          "Configure sequencing options for xconnect";
        when "../encapsulation = 'l2tpv3'";
        type enumeration {
          enum "both";
          enum "receive";
          enum "transmit";
        }
      }
      leaf pw-class {
        description
          "Pseudowire-class to use for encapsulation and protocol configuration";
        type string;
      }
    }
  }

  grouping config-l2-grouping {
    // l2 vfi *
    list vfi {
      if-feature ios-features:l2vpn;
      description
        "Configure a virtual forwarding instance";
      key "name";
      leaf name {
        type string;
      }
      leaf mode {
        type enumeration {
          enum "autodiscovery";
          enum "manual";
          enum "point-to-point";
        }
      }
      leaf evc {
        when "../mode = 'autodiscovery' or ../mode = 'manual'";
        type string;
      }
      container vpn {
        description
          "VPN configuration";
        when "../mode = 'autodiscovery' or ../mode = 'manual'";
        leaf id {
          description
            "VPN id";
          type uint64 {
            range "1..4294967295";
          }
        }
      }
      leaf bridge-domain {
        description
          "bridge-domain";
        type uint16 {
          range "1..16384";
        }
      }
      leaf mtu {
        description
          "MTU size in bytes";
        type uint32;
      }
      list neighbor {
        description
          "VFI neighbor configuration";
        key "router-id";
        leaf router-id {
          type inet:ipv4-address;
        }
        leaf vc-id {
          type uint64 {
            range "1..4294967295";
          }
        }
        leaf encapsulation {
          description
            "Connection encapsulation type";
          type enumeration {
            enum "l2tpv3";
            enum "mpls";
          }
        }
        leaf pw-class {
          description
            "Pseudowire-class configuration";
          type string;
        }
      }
    }
  }
  
  grouping config-l2vpn-evpn-main {
    container evpn {
      description
        "Ethernet Virtual Private Network (EVPN) configuration";
      container replication-type {
        description
          "Specify method for replicating BUM traffic";      
        choice replication-type-choice {
          leaf ingress {
            description
              "Ingress replication";      
            type empty;
          }
          leaf static {
            description
              "Static replication";      
            type empty;
          }
          leaf p2mp {
            description
              "p2mp replication";     
            type empty;
          }
          leaf mp2mp {
            description
              "mp2mp replication";      
            type empty;
          }
        }
      }
      container arp{
        description
          "arp parameters";
        container flooding-suppression{
          leaf disable{
            type empty;        
          }
        }
      }
      container mac {
        description
          "MAC parameters";   
        container duplication {
          description
            "MAC duplication detection";      
          leaf limit {
            description
             "Number of MAC moves within specified time interval";       
            type uint16{
              range 2..1000;
            }
          }
          leaf time{
            description
             "MAC duplication timer";     
            type uint32{
              range 10..36000;
           }
         }
       }
     }
     container ip {
       description
         "IP parameters";   
       container duplication {
         description
           "IP duplication detection";      
         leaf limit {
           description
             "Number of IP moves within specified time interval";       
           type uint16{
             range 2..1000;
           }
         }
         leaf time{
           description
             "IP duplication timer";      
           type uint32{
             range 10..36000;
           }
         }
       }
     }
     container mpls{
       description
                 "MPLS label config";     
       container label{
         container mode {
           choice mode-choice {
             leaf per-ce {
               description
                 "Allocate one MPLS label per Customer Edge device";     
               type empty;
             }
             leaf per-evi {
               description
                  "Allocate one MPLS label per EVPN Instance";   
               type empty;
             }
             leaf per-bd {
               type empty;
             }
           }
         }
       }
     }
     container multihoming {
       description
         "Evpn multihoming config";      
       container aliasing {
         leaf disable {
           type empty;
         }
       }
     }
     container router-id {
       description
         "Select interface to prefer for evpn router-id";
       container interface {
         uses ios-ifc:interface-grouping;
       }
     }
    }
  }


  grouping config-l2vpn-evpn-instance-sub-cmd {
    leaf encapsulation {
      description
        "Data encapsulation method";
      type enumeration {
        enum "vxlan";
        enum "mpls";
      }
    }
    container auto-route-target_cont {
      leaf auto-route-target {
        description 
          "Automatically set a route-target";
        type empty;
      }
    }
    container rd {
      description 
        "EVPN Route Distinguisher";
      leaf rd-value {
        description
          "ASN:nn or IP-address:nn";
        type string;
      }
    }
    container route-target {                                                   
      description
        "Route Target VPN Extended Communities";                      
      leaf rt-value {
        description
          "ASN:nn or IP-address:nn";
        type string;
      }
      container both {
        description 
          "Both import and export Target-VPN community";
        leaf rt-value {
          description
            "ASN:nn or IP-address:nn";   
          type string;
        }
      }
      container export {
        leaf rt-value {
          description
             "ASN:nn or IP-address:nn";
          type string;
        }
      }
      container import {
        description
          "Import Target-VPN community";
        leaf rt-value {
          description
             "ASN:nn or IP-address:nn";
          type string;
        }
      }
    }

  }

  grouping config-l2vpn-evpn-instance {
    container evpn-instance {
      container evpn {
        container instance{
          list instance {
            description
              "evpn instance";
            key "evpn-instance-num";
            leaf evpn-instance-num {
              description
                "evpn instance number";
              type string;
            }

            choice evpn-service-type {
              description
                "Evpn Service type.";
              container  point-to-point {
                presence "true";
                uses config-l2vpn-evpn-instance-sub-cmd;
              }
              container  vlan-aware {
                presence "true";
                uses config-l2vpn-evpn-instance-sub-cmd;
              }
              container  vlan-based {
                presence "true";
                uses config-l2vpn-evpn-instance-sub-cmd;
              }
              container  vlan-bundle {
                presence "true";
                uses config-l2vpn-evpn-instance-sub-cmd;
              }
            }
          }
        }
      }
    }
  }
  grouping config-l2vpn-grouping {
    container pseudowire {
      description
        "Global pseudowire parameters";
      container static-oam {
        description
          "Static PW OAM configuration";
        list class {
          description
            "Static PW OAM class configuration";
          key "pw-nm";
          leaf pw-nm {
            type string;
          }
          container timeout {
            description
              "timeout configurations";
            container refresh {
              description
                "refresh timeout configurations";
              container send {
                description
                  "refresh send timeout configuration";
                leaf interval {
                  type uint32 {
                    range "1..4095";
                  }
                }
              }
            }
          }
        }
      }
      container tlv {
        description
          "Global PW TLV configuration";
        list template {
          description
            "PW TLV Template Keyword";
          key "tlv-nm";
          leaf tlv-nm {
            type string;
          }
          container tlv {
            description
              "TLV config command";
            container tlv-type {
              leaf type {
                type uint8 {
                  range "1..40";
                }
              }
            }
            container tlv-description {
              leaf description {
                type string;
              }
            }
          }
        }
      }
      container group {
        description
          "Configure pseudowire group parameters";
        leaf status {
          description
            "Send pseudowire group status messages";
          type empty;
        }
      }
      leaf routing {
        description
          "Configure l2vpn pseudowire routing";
        type empty;
      }
    }
    container vfi {
      description
        "Configure a Virtual Forwarding Instance (VFI)";
      list context {
        description
          "Layer2 VPN Context";
        key "vfi-nm";
        leaf vfi-nm {
          description
            "Virtual Forwarding Instance (VFI) name";
          type string;
        }
        container autodiscovery {
          description
            "Auto Discovery mode";
          container bgp {
            description
              "Use BGP for neighbor discovery";
            container signaling {
              description
                "Signaling protocol to use";
              container bgp {
                description
                  "Use BGP signaling and discovery";
                presence "true";
                leaf template {
                  description
                    "Template to be used for autodiscovered pseudowires";
                  type string;
                }
              }
              container ldp {
                description
                  "Use LDP signaling";
                presence "true";
                leaf template {
                  description
                    "Template to be used for autodiscovered pseudowires";
                  type string;
                }
              }
            }
          }
        }
        container vpn {
          description
            "VPN configuration";
          leaf id {
            description
              "VPN id value";
            type uint32 {
              range "1..4294967295";
            }
          }
        }
      }
    }
    container xconnect {
      description
        "Configure a cross connect";
      list context {
        description
          "Layer2 VPN Context";
        key "xc-name";
        leaf xc-name {
          description
            "Configure the cross connect name";
          type string;
        }
        container xc-Mode-config-xconnect {
          leaf description {
            description
              "Description string";
            type string;
          }
          container interworking {
            description
              "Interworking options for the cross connect";
            leaf ethernet {
              description
                "Ethernet interworking";
              type empty;
            }
            leaf ip {
              description
                "IP interworking";
              type empty;
            }
            leaf vlan {
              description
                "VLAN interworking";
              type empty;
            }
          }
          container match {
            description
              "Set Xconnect packet matching criteria";
            container protocol {
              description
                "Protocol matching criterion";
              leaf ipv6 {
                description
                  "IPV6";
                type empty;
              }
            }
          }
          container member {
            description
              "Configure the cross connect member";
            list ipv4 {
              key "ipv4";
              leaf ipv4 {
                description
                  "IP address of the peer";
                type inet:ipv4-address;
              }
              leaf mem-vcid {
                description
                  "Enter VC ID value";
                type uint32 {
                  range "1..4294967295";
                }
              }
            }
            list interface {
              key "interface";
              leaf interface {
                description
                  "GigabitEthernet IEEE 802.3z";
                type string;
              }
              leaf group {
                description
                  "Configure the cross connect member redundancy group";
                type empty;
              }
              leaf service-instance {
                description
                  "Ethernet Service Instance";
                type empty;
              }
            }
            leaf Vlan {
              description
                "Vlan interface number";
              type uint16 {
                range "1..4094";
              }
            }
          }
          container redundancy {
            description
              "Xconnect redundancy information";
            leaf delay {
              description
                "Enable delay";
              type uint8 {
                range "0..180";
              }
            }
            container predictive {
              description
                "Switch over to backup member without waiting for UP status";
              leaf disabled {
                description
                  "Disable predictive switchover capability for this xconnect";
                type empty;
              }
              leaf enabled {
                description
                  "Enable predictive switchover capability for this xconnect";
                type empty;
              }
            }
          }
          container remote {
            description
              "L2VPN remote peer configuration commands";
            container circuit {
              description
                "Remote peer circuit configuration";
              leaf id {
                description
                  "Remote peer circuit ID";
                type empty;
              }
            }
            container link {
              description
                "Link information";
              leaf failure {
                description
                  "Failure information";
                type empty;
              }
            }
          }
          leaf shutdown {
            description
              "Shutdown Xconnect";
            type empty;
          }
        }
      }
    }
    container evpn_cont {
      uses config-l2vpn-evpn-main;
      uses config-l2vpn-evpn-instance;
    }
  }

  grouping config-l2vpn-config-grouping {
    container l2vpn {
      description
        "Layer2 VPN commands";
      presence "true";
      container logging {
        description
          "Configure logging flags";
        container pseudowire {
          description
            "pseudowire status transition logging";
          leaf status {
            description
              "pseudowire status up/down logging";
            type empty;
          }
        }
        leaf redundancy {
          description
            "xconnect redundancy events";
          type empty;
        }
      }
      container redundancy {
        description
          "Configure L2VPN redundancy parameters";
        container predictive {
          description
            "Switch over to backup member without waiting for UP status";
          leaf enabled {
            description
              "Enable predictive switchover capability for all xconnects";
            type empty;
          }
        }
      }
      leaf router-id {
        description
          "Layer2 router-id value";
        type inet:ipv4-address;
      }
      leaf shutdown {
        description
          "Shutdown Layer2 VPN";
        type empty;
      }
    }
  }

  grouping config-xconnect-grouping {
    container logging {
      // xconnect pseudowire
      container pseudowire {
        leaf status {
          type empty;
        }
      }
      // xconnect redundancy2
      leaf redundancy {
        type empty;
      }
    }
  }

  grouping pseudowire-grouping {
    // pseudowire-class * / encapsulation
    leaf encapsulation {
      description
        "Data encapsulation method";
      type enumeration {
        enum "l2tpv2";
        enum "l2tpv3";
        enum "mpls";
        enum "udp";
      }
    }
    //pseudowire-class * / ip
    container ip {
      description
        "Specify IP parameters";
      when "../encapsulation = 'l2tpv2' or ../encapsulation = 'l2tpv3'";
      container dfbit {
        description
          "DF bit options for tunnel";
        leaf set {
          description
            "Set the DF bit in the tunnel header";
          type empty;
        }
      }
      container local {
        description
          "Specify local information";
        container interface {
          description
            "Source interface for pseudowire";
          uses ios-ifc:interface-grouping;
        }
      }
      container pmtu {
        description
          "Enable Path MTU for tunnel";
        presence "true";
        leaf max {
          description
            "Maximum Path MTU for session";
          type uint16 {
            range "68..65535";
          }
        }
      }
      leaf protocol {
        description
          "Specific IP protocol number to use";
        when "../../encapsulation = 'l2tpv3'";
        type enumeration {
          enum "l2tp";
          enum "uti";
        }
      }
      container tos {
        description
          "Specify ToS options for IP tunnel header";
        leaf reflect {
          description
            "Reflect IP payload ToS on tunnel";
          type empty;
        }
        leaf value {
          description
            "IP ToS value";
          type uint8;
        }
      }
      leaf ttl {
        description
          "Specify TTL value for IP tunnel header";
        type uint8;
      }
    }
    //pseudowire-class * / control-word
    leaf control-word {
      description
        "Include control-word in pseudowire packets";
      when "../encapsulation = 'mpls'";
      type empty;
    }
    //pseudowire-class * / interworking
    leaf interworking {
      description
        "Interworking options for pseudowire";
      type enumeration {
        enum "ethernet";
        enum "ip";
        enum "vlan";
      }
    }
    //pseudowire-class * / load-balance
    container load-balance {
      description
        "Loadbalancing for pseudowire";
      when "../encapsulation = 'mpls'";
      container flow {
        description
          "Enable flow based load balancing for pseudowire";
        presence "true";
        leaf ethernet {
          description
            "Ethernet pseudowire flow classification";
          type enumeration {
            enum "dst-mac";
            enum "src-dst-mac";
            enum "src-mac";
          }
        }
      }
    }
    //pseudowire-class * / monitor
    container monitor {
      description
        "Active monitoring of xconnect peer";
      when "../encapsulation = 'mpls'";
      container peer {
        description
          "Active monitoring of xconnect peer";
        container bfd {
          description
            "BFD active monitoring for the xconnect peer";
          presence "true";
          container local {
            description
              "Specify local endpoint information to map to a BFD session";
            container interface {
              description
                "Source interface for pseudowire";
              uses ios-ifc:interface-grouping;
            }
          }
        }
      }
    }
    //pseudowire-class * / preferred-path
    container preferred-path {
      description
        "Preferred path";
      container interface {
        description
          "Output Interface";
        choice Tunnel-Tunnel-tp {
          case Tunnel-case {
            leaf Tunnel {
              description
                "Tunnel interface";
              type uint64 {
                range "0..2147483647";
              }
            }
          }
          case Tunnel-tp-case {
            leaf Tunnel-tp {
              description
                "MPLS Transport Profile interface";
              type uint16;
            }
          }
        }
        leaf disable-fallback {
          description
            "disable fall back to alternative route";
          type empty;
        }
      }
      container peer-container {
        leaf peer {
          description
            "Peer Address";
          type union {
            type string;
            type inet:ipv4-address;
          }
        }
        leaf disable-fallback {
          description
            "disable fall back to alternative route";
          type empty;
        }
      }
    }
    //pseudowire-class * / protocol
    container protocol-mpls {
      when "../encapsulation = 'mpls'";
      leaf protocol {
        description
          "Signaling protocol to use";
        type enumeration {
          enum "ldp";
          enum "none";
        }
      }
    }
    container protocol-l2tpv2 {
      when "../encapsulation = 'l2tpv2'";
      leaf protocol {
        description
          "Signaling protocol to use";
        type enumeration {
          enum "l2tpv2";
          enum "none";
        }
      }
    }
    container protocol-l2tpv3 {
      when "../encapsulation = 'l2tpv3'";
      leaf protocol {
        description
          "Signaling protocol to use";
        type enumeration {
          enum "l2tpv3";
          enum "l2tpv3ietf";
          enum "none";
        }
      }
    }
    //pseudowire-class * / sequencing
    leaf sequencing {
      description
        "Sequencing options for pseudowire";
      when "../encapsulation = 'mpls' or ../encapsulation = 'l2tpv3'";
      type enumeration {
        enum "both";
        enum "receive";
        enum "resync";
        enum "transmit";
      }
    }
    //pseudowire-class * / status
    container status {
      description
        "Pseudowire status capabilities";
      presence "true";
      container admin-down {
        description
          "Admin down of Attachment Circuit";
        when "../../encapsulation = 'l2tpv2' or ../../encapsulation = 'l2tpv3'";
        leaf disconnect {
          description
            "Disconnect the session";
          type empty;
        }
      }
      container control-plane {
        description
          "control plane status events";
        leaf route-watch {
          description
            "listen on the control plane to route-watch events";
          type empty;
        }
      }
      leaf decoupled {
        description
          "Reflect standby status of the attachment circuit as up on the pseudowire";
        type empty;
      }
      container peer {
        description
          "peer status configuration";
        container topology {
          description
            "change status behaviour based on peer topology";
          leaf dual-homed {
            description
              "Our peer(s) are participating in a redundant solution with some form of redundancyprotocol running between the peer routers, Only one of the remote peers will advertise astatus of UP at a time. The other will advertise standby. Change our configuration so wecan send a status of UP on both active and redundant pseudowires";
            type empty;
          }
        }
      }
      container redundancy {
        description
          "Xconnect redundancy configuration";
        leaf master {
          description
            "Put the xconnect redundancy group on this node in master mode";
          type empty;
        }
      }
    }

    //pseudowire-class * / switching
    container switching {
      description
        "Switching TLV on/off for pseudowire";
      when "../encapsulation = 'mpls'";
      leaf tlv {
        description
          "Switching TLV on/off for pseudowire";
        type empty;
      }
    }
  }

  grouping config-pseudowire-class-grouping {
    uses pseudowire-grouping;
  }

  grouping config-evpn-ethernet-segment {
    container evpn {        
      list ethernet-segment {
        description
          "Ethernet segment local discriminator value";  
        key "es-value";
        leaf es-value {
          description
            "Ethernet segment local discriminator value";      
          type uint16 {
            range "1..65535";
          }
        }
        container df-election{
          description
            "Designated forwarder election parameters";     
          leaf wait-time{
            type uint8 {
              range "1..10";
            }
          }
        }
        container redundancy {
          description
            "Multi-homing redundancy parameters";      
          choice redundancy-choice {
            leaf all-active {
              type empty;
            }
            leaf single-active {
              type empty;
            }
          }
        }
        leaf sytem-mac {
          description
            "System MAC address for generating the Ethernet Segment ID";      
          type string;
        }
      }
    }
  }


  /////////////////////////////////////////////////////////
  // native / interface / pseudowire
  /////////////////////////////////////////////////////////
  augment "/ios:native/ios:interface/ios:pseudowire" {
    uses config-interface-pseudowire-grouping {
      if-feature ios-features:l2vpn;   
    }
  }

  /////////////////////////////////////////////////////////
  // native / interface * / xconnect
  /////////////////////////////////////////////////////////
  augment "/ios:native/ios:interface/ios:FastEthernet" {
    uses config-interface-xconnect-grouping {
      if-feature ios-features:l2vpn;   
    }
  }

  augment "/ios:native/ios:interface/ios:GigabitEthernet" {
    uses config-interface-xconnect-grouping {
      if-feature ios-features:l2vpn;   
    }
  }

  augment "/ios:native/ios:interface/ios:TenGigabitEthernet" {
    uses config-interface-xconnect-grouping {
      if-feature ios-features:l2vpn;   
    }
  }

  augment "/ios:native/ios:interface/ios:FiveGigabitEthernet" {
    uses config-interface-xconnect-grouping {
      if-feature ios-features:l2vpn;
    }
  }

  augment "/ios:native/ios:interface/ios:TwentyFiveGigE" {
    uses config-interface-xconnect-grouping {
      if-feature ios-features:l2vpn;
    }
  }

  augment "/ios:native/ios:interface/ios:TwoGigabitEthernet" {
    uses config-interface-xconnect-grouping {
      if-feature ios-features:l2vpn;
    }
  }

  augment "/ios:native/ios:interface/ios:FortyGigabitEthernet" {
    uses config-interface-xconnect-grouping {
      if-feature ios-features:l2vpn;
    }
  }

  augment "/ios:native/ios:interface/ios:HundredGigE" {
    uses config-interface-xconnect-grouping {
      if-feature ios-features:l2vpn;
    }
  }

  augment "/ios:native/ios:interface/ios:Port-channel" {
    uses config-interface-xconnect-grouping  {
      if-feature ios-features:l2vpn;   
    }
  }

  ///////////////////////////////////////////////////////////////////
  // native / interface * / ethernet / servive / instance
  ///////////////////////////////////////////////////////////////////
  augment "/ios:native/ios:interface/ios:FastEthernet/ios-eth:service/ios-eth:instance" {
    uses config-interface-efp-xconnect-grouping {
      if-feature ios-features:efp;
    }    
  }

  augment "/ios:native/ios:interface/ios:GigabitEthernet/ios-eth:service/ios-eth:instance" {
    uses config-interface-efp-xconnect-grouping {
      if-feature ios-features:efp;
    } 
  }

  augment "/ios:native/ios:interface/ios:TenGigabitEthernet/ios-eth:service/ios-eth:instance" {
    uses config-interface-efp-xconnect-grouping {
      if-feature ios-features:efp;
    }
  }

  augment "/ios:native/ios:interface/ios:FiveGigabitEthernet/ios-eth:service/ios-eth:instance" {
    uses config-interface-efp-xconnect-grouping {
      if-feature ios-features:efp;
    }
  }

  augment "/ios:native/ios:interface/ios:TwentyFiveGigE/ios-eth:service/ios-eth:instance" {
    uses config-interface-efp-xconnect-grouping {
      if-feature ios-features:efp;
    }
  }

  augment "/ios:native/ios:interface/ios:TwoGigabitEthernet/ios-eth:service/ios-eth:instance" {
    uses config-interface-efp-xconnect-grouping {
      if-feature ios-features:efp;
    }
  }

  augment "/ios:native/ios:interface/ios:FortyGigabitEthernet/ios-eth:service/ios-eth:instance" {
    uses config-interface-efp-xconnect-grouping {
      if-feature ios-features:efp;
    }
  }

  augment "/ios:native/ios:interface/ios:HundredGigE/ios-eth:service/ios-eth:instance" {
    uses config-interface-efp-xconnect-grouping {
      if-feature ios-features:efp;
    }
  }

  augment "/ios:native/ios:interface/ios:Port-channel/ios-eth:service/ios-eth:instance" {
    uses config-interface-efp-xconnect-grouping {
      if-feature ios-features:efp;
    }    
  }

  ///////////////////////////////////////////////////////////////////
  // native / interface * / evpn
  ///////////////////////////////////////////////////////////////////
  augment "/ios:native/ios:interface/ios:FastEthernet" {
    uses config-evpn-ethernet-segment;
  }

  augment "/ios:native/ios:interface/ios:GigabitEthernet" {
    uses config-evpn-ethernet-segment;
  }

  augment "/ios:native/ios:interface/ios:TenGigabitEthernet" {
    uses config-evpn-ethernet-segment;
  }

  augment "/ios:native/ios:interface/ios:FiveGigabitEthernet" {
    uses config-evpn-ethernet-segment;
  }

  augment "/ios:native/ios:interface/ios:TwentyFiveGigE" {
    uses config-evpn-ethernet-segment;
  }

  augment "/ios:native/ios:interface/ios:TwoGigabitEthernet" {
    uses config-evpn-ethernet-segment;
  }

  augment "/ios:native/ios:interface/ios:FortyGigabitEthernet" {
    uses config-evpn-ethernet-segment;
  }

  augment "/ios:native/ios:interface/ios:HundredGigE" {
    uses config-evpn-ethernet-segment;
  }

  augment "/ios:native/ios:interface/ios:Port-channel" {
    uses config-evpn-ethernet-segment;
  }
  


  /////////////////////////////////////////////////////////
  // native / l2
  /////////////////////////////////////////////////////////
  augment "/ios:native/ios:l2" {
    uses config-l2-grouping {
      if-feature ios-features:l2;
    }      
  }

  /////////////////////////////////////////////////////////
  // native / l2vpn
  /////////////////////////////////////////////////////////
  augment "/ios:native/ios:l2vpn" {
    uses config-l2vpn-grouping {
      if-feature ios-features:l2vpn;
    }
  }

  /////////////////////////////////////////////////////////
  // native / l2vpn-config
  /////////////////////////////////////////////////////////
  augment "/ios:native/ios:l2vpn-config" {
    uses config-l2vpn-config-grouping {
      if-feature ios-features:l2vpn;
    }
  }

  /////////////////////////////////////////////////////////
  // native / xconnect
  /////////////////////////////////////////////////////////
  augment "/ios:native/ios:xconnect" {
    uses config-xconnect-grouping {
      if-feature ios-features:l2vpn;
    }
  }

  /////////////////////////////////////////////////////////
  // native / pseudowire-class
  /////////////////////////////////////////////////////////
  augment "/ios:native/ios:pseudowire-class" {
    uses config-pseudowire-class-grouping {
      if-feature ios-features:l2vpn;
    }   
  }
}
