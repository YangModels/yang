module Cisco-IOS-XE-native {
  namespace "http://cisco.com/ns/yang/Cisco-IOS-XE-native";
  prefix ios;

  import ietf-inet-types {
    prefix inet;
  }


  import Cisco-IOS-XE-types {
    prefix ios-types;
  }

  import Cisco-IOS-XE-features {
    prefix ios-features;
  }

  import Cisco-IOS-XE-interface-common {
    prefix ios-ifc;
  }

  include Cisco-IOS-XE-parser;
  include Cisco-IOS-XE-license;
  include Cisco-IOS-XE-line;
  include Cisco-IOS-XE-logging;
  include Cisco-IOS-XE-ip;
  include Cisco-IOS-XE-ipv6;
  include Cisco-IOS-XE-interfaces;

  organization
    "Cisco Systems, Inc.";

  contact
    "Cisco Systems, Inc.
     Customer Service

     Postal: 170 W Tasman Drive
     San Jose, CA 95134

     Tel: +1 1800 553-NETS

     E-mail: cs-yang@cisco.com";

  description
    "NED YANG module for IOS-XE
     Copyright (c) 2016-2018 by Cisco Systems, Inc.
     All rights reserved.";

  // =========================================================================
  // REVISION
  // =========================================================================
  revision 2018-05-22 {
    description
      "Remove wireless model";
  }

  revision 2018-03-27 {
    description
      "Move top level card to native before controller to keep the sequence.";
  }

  revision 2018-02-26 {
     description
       "Add model for username secret 9 SCRYPT";
  }
  revision 2018-02-06 {
     description
       "Refactor parameter-map";
  }
  revision 2018-02-01 {
    description
      "fix banner issue";
  }
  revision 2018-01-15 {
    description
      "Add monitor session type local and options";
  }
  revision 2018-01-07 {
    description
      "Add monitor session type erspan-dst and options under erspan-src";
  }
  revision 2017-10-24 {
    description
      "Add banner support back for login and motd";
  }
  revision 2017-10-23 {
    description
      "Support for AVB,PTP,MVRP";
  }
  revision 2017-10-16 {
    description
      "Add diff-dependency on VirtualPortGroup for virtual-service";
  }
  revision 2017-09-26 {
    description
      "Add username view";
  }
  revision 2017-08-30 {
    description
      "Add 'umbrella' to parameter-map enum";
  }
  revision 2017-08-14 {
    description
      "Model for monitor event-trace";
  }
  revision 2017-07-13 {
    description
      "Support for AVC";
  } 

  revision 2017-07-08 {
    description
      "Model for identity policy additional support";
  }

  revision 2017-06-26 {
    description
      "Model for identity policy";
  }

  revision 2017-06-23 {
    description
      "add options under monitor session type erspan-src";
  }  

  revision 2017-06-21 {
    description
      "add some model in domain";
  }

  revision 2017-06-15 {
    description
      "Removed native/access-list";
  }

  revision 2017-06-01 {
    description
      "add default crypto ikev2 policy and proposal";
  }

  revision 2017-03-24 {
    description
      "Removed banner";
  }

  revision 2017-02-07 {
    description
      "Initial revision";
  }


  /////////////////////////////////////////////////////////
  // TYPEDEF
  typedef monitor-event-type {
    type enumeration {
      enum "error";
      enum "detail";
      enum "major";
//    enum "bfd";
//    enum "event";
//    enum "exact-match";
//    enum "ffd";
//    enum "fsm";
//    enum "ha";
//    enum "ldp";
//    enum "pwoam";
//    enum "rf";
//    enum "status";
//    enum "switching-point";
//    enum "vccv";
    }
  }
  /////////////////////////////////////////////////////////


  /////////////////////////////////////////////////////////
  // Grouping
  /////////////////////////////////////////////////////////

  container native {

    /////////////////////////////////////////////////////////
    // native / default
    /////////////////////////////////////////////////////////
    container default {
      description
        "Set a command to its defaults";
      container crypto {
        description
          "Encryption module";
        container ikev2 {
          description
            "Configure IKEv2 Options";
          leaf proposal {
            description
              "Define IKEV2 proposals";
            type empty;
          }
          leaf policy {
            description
              "Define IKEV2 policies";
            type empty;
          }
        }
      }
    }

    /////////////////////////////////////////////////////////
    // native / bfd
    /////////////////////////////////////////////////////////
    container bfd { 
      description
        "BFD configuration commands";
      // @mount Cisco-IOS-XE-bfd
    }

    /////////////////////////////////////////////////////////
    // native / version
    /////////////////////////////////////////////////////////
    leaf version {
      description "Version";
      type string {
      }
    }

    /////////////////////////////////////////////////////////
    // native / stackwise-virtual
    /////////////////////////////////////////////////////////

    container stackwise-virtual{
      description
        "Enter stackwise-virtual configuration mode";
      presence true;
      // @mount Cisco-IOS-XE-stackwise-virtual.yang
    }

    /////////////////////////////////////////////////////////
    // native / boot
    /////////////////////////////////////////////////////////
    leaf boot-start-marker {
      type empty;
    }

    container boot {
      description
        "Modify boot system parameters";
      container system {
        description
          "System Image";
        leaf tftp-path {
          description
            "Example: 192.x.x.x/<path to image>";
          type string;
        }
        //@mount Cisco-IOS-XE-switch.yang
        //container switch
        leaf tftp {
          description
            "Example 192.168.x.x/<image-path>";
          type string;
        }
        container bootfile {
          description
            "WORD - boot filename";
          list filename-list {
            key "filename";
            leaf filename {
              description
                "WORD - TFTP filename or URL";
              type string;
            }
          }
        }
        container flash {
          description
            "flash - Boot from flash memory";
          list flash-list {
            key "flash-leaf";
            leaf flash-leaf {
              type string;
            }
          }
        }
      }
    }

    //@mount Cisco-IOS-XE-switch.yang
    //container enable-break and container manual

    leaf boot-end-marker {
      type empty;
    }

    /// ========================================================================
    /// banner
    /// ========================================================================
    grouping banner-grouping {
      leaf banner {
        description
          "Banner message format, c banner-text c, where 'c' is a delimiting character";
        type string;
      }
    }
    container banner {
      description
        "Define a login banner";
      container exec {
        description
          "Set EXEC process creation banner";
        uses banner-grouping;
      }
      container login {
        description
          "Set login banner";
        uses banner-grouping;
      }
      container prompt-timeout {
        description
          "Set Message for login authentication timeout";
        uses banner-grouping;
      }
      container motd {
        description
          "Set Message of the Day banner";
        uses banner-grouping;
      }
    }

    /////////////////////////////////////////////////////////
    // native / captive-portal-bypass
    /////////////////////////////////////////////////////////
    leaf captive-portal-bypass { 
      description
        "Enable Captive portal bypass for apple devices";
      type empty;
    }

    /////////////////////////////////////////////////////////
    // native / memory
    /////////////////////////////////////////////////////////
    container memory { 
      description "Configure memory management";
      container statistics {
        description "Configure statistics history table";
        container history {
          description "Configure statistics history table";
          leaf table {
            description "Configure statistics history table";
            type uint8 {
              range "12..72";
            }
          }
        }
      }
      container chunk {
        description "chunk related configuration";
        container siblings {
          description "chunk siblings related configuration";
          leaf threshold {
            description "Default is platform dependent";
            type uint32 {
              range "2..4294967295";
            }
          }
        }
      }
      container free {
        description "free memory low water mark";
        container low-watermark {
          description "low water mark for notifications";
          leaf IO {
            description "low water mark of memory in KB";
            type uint32 {
              range "1..3994575";
            }
          }
          leaf processor {
            description "low water mark of memory in KB";
            type uint32 {
              range "1..3994575";
            }
          }
        }
      }
      leaf lite {
        description "Enable/disable memory lite";
        type empty;
      }
      container reserve {
        description "reserve memory";
        container critical {
          description "Reserve Critical Memory";
          presence true;
          leaf memory-range {
            description "total amount of memory to be reserved in kilobytes";
              type uint32 {
                range "1..4294967295";
              }
          }
        }
      }
      container sanity {
        description "Enable memory sanity";
        presence true;
        leaf all {
          description "Enable memory sanity all";
          type empty;
        }
        leaf buffer {
          description "Enable memory sanity buffer";
          type empty;
        }
        leaf queue {
          type empty;
        }
      }
    }

    /////////////////////////////////////////////////////////
    // native / location
    /////////////////////////////////////////////////////////
    container location { 
      description
        "Global location configuration commands";
      container civic-location {
        description
          "Civic location information";
        list identifier {
          description
            "Set the identifier";
          key identifier;
          leaf identifier{
            type string;
          }
          leaf building {
            description
              "Building information";
            type string;
          }
          leaf floor {
            description
              "Floor number";
            type string;
          }
          leaf landmark {
            description
              "Landmark";
            type string;
          }
          leaf name {
            description
              "Resident name";
            type string;
          }
          leaf number {
            description
              "Street number";
            type string;
          }
        }
      }
    }

    /////////////////////////////////////////////////////////
    // native / call-home
    /////////////////////////////////////////////////////////
    container call-home { 
      description
        "Enter call-home configuration mode";
      presence true;
      // @mount Cisco-IOS-XE-call-home
    }

    /////////////////////////////////////////////////////////
    // native / hw-module
    /////////////////////////////////////////////////////////
    container hw-module { 
      description
        "Control of individual components in the system";
      container uplink {
        description
          "Uplink control";
        leaf select {
          description
            "Select uplink interface";
          type string;
        }
        leaf mode {
          description
            "Uplink mode";
          type enumeration {
            enum "shared-backplane";
          }
        }
      }
      list switch {
        description
           "Switch in the system";
          key "switch-number";
          leaf switch-number {
            description
              "Switch number in the Stack (Refer to show switch CLI)";
            type uint8 {
              range "1..8";
            }
          }
          container usbflash1 {
            description
              "USB SSD";
            container security {
              description
                "Security on usbflash1";
              container enable {
                description
                  "Enable security on usbflash1";
                presence true;
                leaf password {
                  description
                    "Enter password for enabling security on usbflash1";
                  type string;
                }
              }
            }
          }
        }

      list slot {
        description
          "Control a component in a slot";
          key "name";
          leaf name {
            description
              "Slot of LC";
            type string;
          }
          leaf shutdown {
            description
              "Shutdown a fru";
            type empty;
          }
      }

      leaf sm {
        type uint8;
      }
      leaf pvdm {
        type string;
      }
    }

    /////////////////////////////////////////////////////////
    // native / cisp
    /////////////////////////////////////////////////////////
    container cisp { 
      description "Set CISP parameters";
      leaf enable {
        description "Enable CISP";
        type empty;
      }
    }

    /////////////////////////////////////////////////////////
    // native / module
    /////////////////////////////////////////////////////////
    container module {
      description
        "Module";
      // @module Cisco-IOS-XE-switch
    }

    /////////////////////////////////////////////////////////
    // native / domain
    /////////////////////////////////////////////////////////
    list domain { 
      description
        "Domain Configuration Commands";
      key "name";
      leaf name {
        type string;
      }
      list vrf {
        description
          "Specify vrf for domain";
        key "name";
        leaf name {
          type string;
        }
        container border {
          description
            "Enter border router configuration submode";
          container advanced {
            description
              "Enter border router advanced configuration submode";
            leaf monitor-cache-percent {
              description
                "cache usage (%), border instance will AUTOMATICALLY go through" +
                " SHUT/NO SHUT any ACTIVE traffic on this border will be affected";
              type uint8 {
                range "1..100";
              }
            }
          }
          container source-interface {
            description
              "Source Interface for border";
            leaf Loopback {
              description
                "Loopback interface";
              type uint32;
            }
          }
          leaf master {
            description
              "Specify IP address of Domain master controller";
            type union {
              type inet:ipv4-address;
              type enumeration {
                enum "local";
              }
            }
          }
          container password {
            description
              "MD5 password to be used with MC";
            leaf encryption {
              type enumeration {
                enum "0";
                enum "7";
              }
            }
            leaf clear-key {
              type string;
            }
          }
        }
        container master {
          description
            "Enter master controller configuration submode";
          choice master-type {
            case branch {
              leaf branch {
                description
                  "Set master type as branch hub";
                type empty;
              }
            }
            case hub {
              leaf hub {
                description
                  "Set master type as hub";
                type empty;
              }
            }
            case transit {
              leaf transit {
                description
                  "Set master type as transit";
                type uint8 {
                  range "1..64";
                }
              }
            }
          }
          container advanced {
            description
              "Advanced configuration submode";
            leaf byte-loss-threshold {
              description
                "Specify minimum byte loss calculation threshold";
              type uint16 {
                range "0..5600";
              }
            }
            leaf channel-unreachable-timer {
              description
                "Unreach interval detection";
              type uint16 {
                range "1..65535";
              }
            }
            leaf load-sharing {
              description
                "Enable load-sharing";
              type empty;
            }
            leaf minimum-mask-length {
              description
                "Specify minimum mask length";
              type uint8 {
                range "1..32";
              }
            }
            leaf mitigation-mode {
              description
                "Enable brownout detection in domain";
              type enumeration {
                enum "aggressive";
              }
            }
            leaf packet-loss-threshold {
              description
                "Specify minimum packet loss calculation threshold";
              type uint8 {
                range "1..100";
              }
            }
            container smart-probes {
              description
                "Smart probes configuration";
              leaf destination-port {
                description
                  "Specify smart probes destination port number";
                type uint16 {
                  range "1..65535";
                }
              }
              leaf source-port {
                description
                  "Specify smart probes source port number";
                type uint16 {
                  range "1..65535";
                }
              }
            }
            container syslog {
              description
                "Specify syslog minimim time between tca";
              leaf tca-time-min {
                description
                  "Specify time between syslog tcas in seconds";
                type uint32 {
                  range "30..36000";
                }
              }
            }
            container tcp {
              description
                "Specify tcp port numbers for mc-br communication";
              leaf mc-port {
                description
                  "Specify tcp MC self port for mc-br communication";
                type uint16 {
                  range "1..65535";
                }
              }
            }
            leaf threshold-variance {
              description
                "Policy decision Threshold variance";
              type uint8 {
                range "0..100";
              }
            }
            container traffic-class-ageout-timer {
              description
                "Traffic-class DB age timer";
              leaf interval {
                description
                  "Specify new timer interval value mins/hours";
                type uint16 {
                  range "5..65535";
                }
              }
              leaf interval-unit {
                type enumeration {
                  enum "hours";
                  enum "minutes";
                }
              }
            }
            leaf transit-site-affinity {
              description
                "Enable Transit Site Affinity";
              type empty;
            }
          }
          container collector {
            description
              "NMS/v9 collector configuration";
            leaf ip {
              type inet:ipv4-address;
            }
            leaf port {
              description
                "Specify collector port number";
              type uint16;
            }
          }
          container enterprise-prefix {
            description
              "Enterprise prefix configuration";
            leaf prefix-list {
              description
                "Specify prefix-list with static site targets";
              type string;
            }
          }
          container load-balance {
            description
              "load balance non-policy traffic";
            presence "true";
            container advanced {
              description
                "Load balancing configuration mode";
              uses domain-vrf-master-hub-class-grouping;
            }
          }
          container password {
            description
              "MD5 password to be used with BRs";
            leaf encryption {
              type enumeration {
                enum "0";
                enum "7";
              }
            }
            leaf clear-key {
              type string;
            }
          }
          container site-prefixes {
            description
              "site-prefixes configuration";
            leaf prefix-list {
              description
                "Specify prefix-list with static site targets";
              type string;
            }
          }
          container source-interface {
            description
              "Source Interface for master controller";
            leaf Loopback {
              description
                "Loopback interface";
              type uint32;
            }
          }
          list class {
            description
              "Create domain class and enter domain class command mode";
            key "name sequence";
            leaf name {
              type string;
            }
            leaf sequence {
              description
                "Set the Sequence for the class";
              type uint16;
            }
            uses domain-vrf-master-hub-class-grouping;
          }
          leaf hub-ip {
            type inet:ipv4-address;
          }
        }
      }
    }

    grouping domain-vrf-master-hub-class-grouping { 
      container match {
        description
          "Specify the applications the policy applies to";
        list dscp {
          description
            "specify DSCP";
          key "value";
          leaf value {
            type ios-types:dscp-type;
          }
          leaf policy {
            description
              "Specify the policy (user defined/predefined)";
            type enumeration {
              enum "best-effort";
              enum "bulk-data";
              enum "custom";
              enum "low-latency-data";
              enum "real-time-video";
              enum "scavenger";
              enum "voice";
            }
          }
        }
      }
      container path-preference {
        description
          "Specify the preferred provider";
        leaf primary {
          description
            "Primary service provider";
          type string;
        }
        leaf primary2 {
          description
            "Primary service provider";
          type string;
        }
        leaf primary3 {
          description
            "Primary service provider";
          type string;
        }
        leaf fallback {
          description
            "Specify the fallback provider";
          type union {
            type enumeration {
              enum "routing";
              enum "blackhole";
            }
            type string;
          }
        }
        leaf fallback2 {
          description
            "Fallback service provider";
          type string;
        }
        leaf fallback3 {
          description
            "Fallback service provider";
          type string;
        }
      }
      leaf path-last-resort {
        description
          "Specify path of last resort provider";
        type string;
      }
    }

    grouping identity-policy-grouping {
      leaf absolute-timer {
        description
          "Absolute timeout value in seconds";
        type uint16 {
          range "1..65535";
        }
      }
      leaf access-group {
        description
          "Access list to be applied";
        type string;
      }
      leaf description {
        description
          "Enter a description";
        type string;

      }
      leaf inactivity-timer {
        description
          "Inactivity timeout value in seconds";
        type uint16 {
          range "0..65535";
        }
      }
      leaf interface-template {
        description
          "Interface template to be applied";
        type string;
      }
      container linksec {
        description
          "Configure link security parameters";
        leaf policy {
          description
            "Set the link security policy";
          type enumeration {
            enum "must-not-secure";
            enum "must-secure";
            enum "should-secure";
          }
        }
      }
      container redirect {
        description
          "Redirect clients to a particular location";
        leaf url {
          description
            "URL where clients should be redirected";
          type string;
        }
      }
      container service-policy {
        description
          "Configure service policy";
        list qos {
          description
            "Configure qos policies for client";
          key "direction";
          leaf direction {
            type enumeration {
              enum "input";
              enum "output";
            } 
          }
          leaf name {
            type string;
          }
        }
      }
      leaf sgt {
        description
          "SGT tag";
        type uint16 {
          range "2..65519";
        }
      }
      leaf tag {
        description
          "tag name";
        type string;
      }
      container tunnel {
        description
          "tunnel for wired client access";
        container type {
          description
            "tunnel type";
          container capwap {
            description
              "capwap tunnel type";
            leaf name {
              description
                "tunnel profile name";
              type string;
            }
          }
        }
      }
      leaf vlan {
        description
          "Enter a VlanId";
        type uint16 {
          range "1..4094";
        }
      }
      container voice {
        description
          "Voice feature";
        leaf vlan {
          description
            "Critical voice vlan";
          type empty;
        }
      }
    }

    /////////////////////////////////////////////////////////
    // native / parser
    /////////////////////////////////////////////////////////
    uses config-parser-grouping;


    /////////////////////////////////////////////////////////
    // native / service
    /////////////////////////////////////////////////////////
    container service { 
      description
        "Modify use of network based services";
      // service internal
      leaf internal {
        // Note: allow additional control of the LTE modem
        description
          "Enable/Disable Internal commands";
        type empty;
      }
      // service pad
      container pad-conf {
        leaf pad {
          description
            "Enable PAD commands";
          type boolean;
        }
      }
      container pad {
        description
          "Enable PAD commands";
        presence "true";
        leaf cmns {
          description
            "Enable PAD over CMNS connections";
          type empty;
        }
        leaf from-xot {
          description
            "Accept XOT to PAD connections";
          type empty;
        }
        leaf to-xot {
          description
            "Allow outgoing PAD over XOT connections";
          type empty;
        }
      }
      // service password-encryption
      leaf password-encryption {
        description
          "Encrypt system passwords";
        type empty;
      }
          // service password-recovery
      leaf password-recovery {
        description "Enable password recovery";
        type boolean;
      }

      // service timestamps
      container timestamps {
        description
          "Timestamp debug/log messages";
        presence "true";
        // service timestamps debug
        container debug {
          description
            "Timestamp debug messages";
          // service timestamps debug datetime
          container datetime {
            description
              "Timestamp with date and time";
            presence "true";
            // service timestamps debug datetime localtime
            container localtime {
              description
                "Use local time zone for timestamps";
              presence "true";
              // service timestamps debug datetime localtime msec
              container msec {
                description
                  "Include milliseconds in timestamp";
                presence "true";
                uses service-timestamp-show-timezone-and-year;
              }  
              // service timestamps debug datetime localtime show-timezone 
              container show-timezone {
                description
                  "Add time zone information to timestamp";
                presence "true";
                uses service-timestamp-msec-and-year;
              }  
              // service timestamps debug datetime localtime year 
              container year {
                description
                  "Include year in timestamp";
                presence "true";
                uses service-timestamp-msec-and-show-timezone;				
              }  
            }
            // service timestamps debug datetime msec 
            container msec {
              description
                "Include milliseconds in timestamp";
              presence "true";
              // service timestamps debug datetime msec localtime
              container localtime {
                description
                  "Use local time zone for timestamps";
                presence "true";
                uses service-timestamp-show-timezone-and-year;				
              }  
              // service timestamps debug datetime msec show-timezone 
              container show-timezone {
                description
                  "Add time zone information to timestamp";
                presence "true";
                uses service-timestamp-local-time-and-year;				
              }  
              // service timestamps debug datetime msec year 
              container year {
                description
                  "Include year in timestamp";
                presence "true";
                uses service-timestamp-local-time-and-show-timezone;				
              }
            }
            // service timestamps debug datetime show-timezone 
            container show-timezone {
              description
                "Add time zone information to timestamp";
              presence "true";
              // service timestamps debug datetime show-timezone localtime
              container localtime {
                description
                  "Use local time zone for timestamps";
                presence "true";
                uses service-timestamp-msec-and-year;				
              }  
              // service timestamps debug datetime show-timezone msec 
              container msec {
                description
                  "Include milliseconds in timestamp";
                presence "true";
                uses service-timestamp-local-time-and-year;				
              }  
              // service timestamps debug datetime show-timezone year 
              container year {
                description
                  "Include year in timestamp";
                presence "true";
                uses service-timestamp-local-time-and-msec;				
              }
            }
            // service timestamps debug datetime year 
            container year {
              description
                "Include year in timestamp";
              presence "true";
              // service timestamps debug datetime year localtime
              container localtime {
                description
                  "Use local time zone for timestamps";
                presence "true";
                uses service-timestamp-msec-and-show-timezone;   				
              }
              // service timestamps debug datetime year msec 
              container msec {
                description
                  "Include milliseconds in timestamp";
                presence "true";
                uses service-timestamp-local-time-and-show-timezone;				
              }
              // debug service timestamps debug datetime year show-timezone 
              container show-timezone {
                description
                  "Add time zone information to timestamp";
                presence "true";
                uses service-timestamp-local-time-and-msec;				
              }
            }
          }                        
          leaf uptime {
            description
              "Timestamp with system uptime";
            type empty;
          }
        }
        // service timestamps log
        container log {
          description
            "Timestamp log messages";
          container datetime {
            description
              "Timestamp with date and time";
            presence "true";
            leaf msec {
              description
                "Include milliseconds in timestamp";
              type empty;
            }
            leaf localtime {
              description
                "Use local time zone for timestamps";
              type empty;
            }
            leaf show-timezone {
              description
                "Add time zone information to timestamp";
              type empty;
            }
            leaf year {
              description
                "Include year in timestamp";
              type empty;
            }
          }
          leaf uptime {
            description
              "Timestamp with system uptime";
            type empty;
          }
        }
      }
      // service alignment
      container alignment {
        description
          "Control alignment correction and logging";
        leaf detection {
          description
            "Enable detection of alignment issues";
          type empty;
        }
        leaf logging {
          description
            "Enable logging of alignment issues";
          type empty;
        }
      }
      // service call-home
      leaf call-home {
        description
          "Enable call-home service";
        type empty;
      }
      // service compress-config
      leaf compress-config {
        description
          "Compress the configuration file";
        type empty;
      }
      leaf config {
        description
          "TFTP load config files";
        type empty;
      }
      // service counters
      container counters {
        description
          "Control aging of interface counters";
        container max {
          description
            "Maximum counter aging threshold";
          leaf age {
            description
              "Aging threshold";
            type uint8 {
              range "0..60";
            }
          }
        }
      }

      // service dhcp
      leaf dhcp {
        description
          "Enable DHCP server and relay agent";
        type empty;
      }

      // service disable-ip-fast-frag
      leaf disable-ip-fast-frag {
        description
          "Disable IP particle-based fast fragmentation";
        type empty;
      }

      // service exec-callback
      leaf exec-callback {
        description
          "Enable exec callback";
        type empty;
      }

      // service exec-wait
      leaf exec-wait {
        description
          "Delay EXEC startup on noisy lines";
        type empty;
      }

      // service finger
      leaf finger {
        description
          "Allow responses to finger requests";
        type empty;
      }

      // service heartbeat
      container heartbeat {
        description
          "Enable heartbeat processing";
        leaf fatal-count {
          description
            "Set heartbeat fatal count";
          type uint8 {
            range "1..60";
          }
        }
        leaf interrupt-interval {
          description
            "Set heartbeat interrupt test interval";
          type uint8 {
            range "0..60";
          }
        }
        leaf interrupt-max {
          description
            "Set maximum message count from interrupt test";
          type uint8 {
            range "0..60";
          }
        }
        leaf transmit-interval {
          description
            "Set heartbeat transmit interval";
          type uint8 {
            range "1..30";
          }
        }
        leaf warning-timeout {
          description
            "Set heartbeat warning timeout interval";
          type uint8 {
            range "5..60";
          }
        }
      }
      // service hide-telnet-addresses
      leaf hide-telnet-addresses {
        description
          "Hide destination addresses in telnet command";
        type empty;
      }
      //  image-version          image-version
      // service linenumber
      leaf linenumber {
        description
          "enable line number banner for each exec";
        type empty;
      }
      // log-hidden
      leaf log-hidden {
          description
            "Enable syslog msgs for hidden/internal commands";
          type empty;
      }
      // service nagle
      leaf nagle {
        description
          "Enable Nagle's congestion control algorithm";
        type empty;
      }
      // service old-slip-prompts
      leaf old-slip-prompts {
        description
          "Allow old scripts to operate with slip/ppp";
        type empty;
      }
      //  prompt                 Enable mode specific prompt
      container prompt {
          description
            "Enable mode specific prompt";
          leaf config {
              description
                "Enable configuration mode prompt";
              type empty;
          }
      }
      // service pt-vty-logging
      leaf pt-vty-logging {
        description
          "Log significant VTY-Async events";
        type empty;
      }
      // service sequence-numbers
      leaf sequence-numbers {
        description
          "Stamp logger messages with a sequence number";
        type empty;
      }
      // service slave-log
      leaf slave-log {
        description
          "Enable log capability of slave IPs";
        type empty;
      }
      // service tcp-keepalives-in
      leaf tcp-keepalives-in {
        description
          "Generate keepalives on idle incoming network connections";
        type empty;
      }
      // service tcp-keepalives-out
      leaf tcp-keepalives-out {
        description
          "Generate keepalives on idle outgoing network connections";
        type empty;
      }
      //  telnet-zeroidle        Set TCP window 0 when connection is idle
      leaf telnet-zeroidle {
          description
            "Set TCP window 0 when connection is idle";
          type empty;
      }
      //  timestamps             Timestamp debug/log messages
      //  service tcp-small-servers
      leaf tcp-small-servers {
        description
          "Enable small TCP servers (e.g., ECHO)";
        type empty;
      }
      //  service udp-small-servers      Enable small UDP servers (e.g., ECHO)
      leaf udp-small-servers {
        description
          "Enable small UDP servers (e.g., ECHO)";
        type empty;
      }
      // service unsupported-transceiver
      leaf unsupported-transceiver {
        description
          "Enable support for third-party transceivers";
        type empty;
      }
    }

    /////////////////////////////////////////////////////////
    // native / platform
    /////////////////////////////////////////////////////////
    container platform {
      description
        "platform specific configuration";
      //@mount Cisco-IOS-XE-platform
    }

    /////////////////////////////////////////////////////////
    // native / hostname
    /////////////////////////////////////////////////////////
    leaf hostname {
      description "Set system's network name";
      type string {
      }
    }

    /////////////////////////////////////////////////////////
    // native / enable
    /////////////////////////////////////////////////////////
    container enable {
      description
        "Modify enable password parameters";
      container password {
        description
          "Assign the privileged level password (MAX of 25 characters)";
        uses password-07-grouping;
      }
      leaf last-resort {
        description
          "Define enable action if no TACACS servers respond";
        type enumeration {
          enum "password";
          enum "succeed";
        }
      }
      container secret {
        description
          "Assign the privileged level secret";
        leaf level {
          description
            "Set exec level password";
          type uint8;
        }
        leaf type {
          type enumeration {
            enum "0";
            enum "4";
            enum "5";
          }
        }
        leaf secret {
          type string;
        }
      }
      leaf use-tacacs {
        description
          "Use TACACS to check enable passwords";
        type empty;
      }
    }

    /////////////////////////////////////////////////////////
    // native / password
    /////////////////////////////////////////////////////////
    container password { 
      description "Configure encryption password (key)";
      container encryption {
        description "Encrypt system passwords";
        leaf aes {
          description "Enable stronger (AES) password encryption";
          type empty;
        }
      }
    }

    /////////////////////////////////////////////////////////
    // native / eap
    /////////////////////////////////////////////////////////
    container eap { 
      description "Configure EAP authenticator parameters";
      list profile {
        description "EAP authenticator profile configuration";
        key "name";
        leaf name {
          description "WORD;;EAP authenticator profile name";
          type string;
        }
        container method {
          description "Add an allowed method";
          leaf fast {
            description
              "EAP-FAST method allowed";
            type empty;
          }
          leaf gtc {
            description
              "EAP-GTC method allowed";
            type empty;
          }
          leaf leap {
            description
              "EAP-LEAP method allowed";
            type empty;
          }
          leaf mschapv2 {
            description
              "EAP-MSCHAPV2 method allowed";
            type empty;
          }
          leaf peap {
            description
              "EAP-PEAP method allowed";
            type empty;
          }
          leaf md5 {
            description "EAP-MD5 method allowed";
            type empty;
          }
          leaf tls {
            description "EAP-TLS method allowed";
            type empty;
          }
        }
        leaf pki-trustpoint {
          description "Set the default pki trustpoint";
          type string;
        }
      }
    }

    /////////////////////////////////////////////////////////
    // native / archive
    /////////////////////////////////////////////////////////
    container archive { 
      description
        "Archive the configuration";
      // archive log
      container log {
        description
          "Logging commands";
        container config {
          description
            "Logging changes to the running configuration";
          leaf hidekeys {
            description
              "suppress output (e.g. passwords) when displaying logged commands";
            type empty;
          }
          //archive log config / logging
          container logging {
            description
              "Modify config logging parameters";
            leaf enable {
              description
                "Enable the config logger";
              type empty;
            }
            leaf size {
              description
                "Maximum number of logged commands that will be kept by the config log";
              type uint16 {
                range "1..1000";
              }
            }
            container persistent {
              description
                "Log configuration persistent";
              presence "true";
              leaf auto {
                description
                  "Log configuration commands automatically";
                type empty;
              }
              leaf reload {
                description
                  "Apply persisted commands on reload";
                type empty;
              }
            }
          }
          //archive log config /notify
          container notify {
            description
              "Send logged commands to target applications";
            container syslog {
              description
                "Send logged commands as syslog messages";
              presence "true";
              leaf contenttype {
                description
                  "Type of the syslog message content";
                type enumeration {
                  enum "plaintext";
                  enum "xml";
                }
              }
            }
          }
        }
      }
      //archive path
      leaf path {
        description
          "path for backups";
        type union {
          type enumeration {
            enum "bootflash:";
            enum "flash:";
            enum "ftp:";
            enum "harddisk:";
            enum "http:";
            enum "https:";
            enum "pram:";
            enum "rcp:";
            enum "scp:";
            enum "tftp:";
          }
          type string;
        }
      }
      //archive maximum
      leaf maximum {
        description
          "maximum number of backup copies";
        type uint8 {
          range "1..14";
        }
      }
      //archive write-memory
      leaf write-memory {
        description
          "Enable automatic backup generation during write memory";
          type empty;
      }
      //archive time-period
      leaf time-period {
        description
          "Period of time in minutes to automatically archive the running-config";
        type uint32 {
          range "1..525600";
        }
      }
    }

    /////////////////////////////////////////////////////////
    // native / username
    /////////////////////////////////////////////////////////
    list username {
      description
        "Establish User Name Authentication";
      key "name";
      leaf name {
        type string;
      }
      // username * privilege
      leaf privilege {
        description
          "Set user privilege level";
        type uint8 {
          range "0..15";
        }
      }
      // username * view
      leaf view {
        description
          "Set view name";
        type string;
      }
      leaf one-time {
        description
          "Specify that the username/password is valid for only one time";
        type empty;
      }
      // username * password
      container password {
        description
          "Specify the password for the user";
        leaf encryption {
          type enumeration {
            enum "0";
            enum "7";
          }
        }
        leaf password {
          type string;
        }
      }
      // username * secret
      container secret {
        description
          "Specify the secret for the user";
        leaf encryption {
          type enumeration {
            enum "0";
            enum "5";
            enum "9";
          }
        }
        leaf secret {
          type string;
        }
      }
    }

    /////////////////////////////////////////////////////////
    // native / card
    /////////////////////////////////////////////////////////
    container card {
      description
        "Configure T1/E1 SPA";
      // @mount Cisco-IOS-XE-card
    }

    /////////////////////////////////////////////////////////
    // native / controller
    /////////////////////////////////////////////////////////
    container controller { 
      description
        "Configure controller";
      // @mount Cisco-IOS-XE-controller
    }

    /////////////////////////////////////////////////////////
    // native / aqm-register-fnf
    /////////////////////////////////////////////////////////
    leaf aqm-register-fnf {
      description
        "Export audio/video stats to flow record";
      type empty;
    }

    /////////////////////////////////////////////////////////
    // native / vrf
    /////////////////////////////////////////////////////////
    // Note: /vrf must be before /ip and /ipv6 and /interface
    uses config-vrf-definition-grouping;


    /////////////////////////////////////////////////////////
    // native / rmon
    /////////////////////////////////////////////////////////
    container rmon { 
      description
        "Remote Monitoring";
      list alarm {
        description
          "Configure an RMON alarm";
        key "number";
        leaf number {
          type uint16;
        }
        leaf mib-object {
          type string;
        }
        leaf sample-interval {
          type uint32;
        }
        leaf test-mode {
          type enumeration {
            enum "absolute";
            enum "delta";
          }
        }
        leaf rising-threshold {
          description
            "Configure the rising threshold";
          type int32;
        }
        leaf rising-event {
          type uint16;
        }
        leaf falling-threshold {
          description
            "Configure the falling threshold";
          type int32;
        }
        leaf falling-event {
          type uint16;
        }
        leaf owner {
          description
            "Specify an owner for the alarm";
          type string;
        }
      }
      list event {
        description
          "Configure an RMON event";
        key "number";
        leaf number {
          type uint16;
        }
        container log {
          description
            "Generate RMON log when the event fires";
          presence "true";
          leaf trap {
            description
              "Generate SNMP trap when the event fires";
            type string;
          }
          leaf description {
            description
              "Specify a description of the event";
            type string;
          }
          leaf owner {
            description
              "Specify an owner for the event";
            type string;
          }
        }
      }
    }

    /////////////////////////////////////////////////////////
    // native / sampler
    /////////////////////////////////////////////////////////
    list sampler { 
      description
        "Define a Sampler";
      key "name";
      leaf name {
        type string;
      }
      // @mount Cisco-IOS-XE-flow
    }

    /////////////////////////////////////////////////////////
    // native / flow
    /////////////////////////////////////////////////////////
    container flow { 
      description
        "Global Flow configuration subcommands";
      // @mount Cisco-IOS-XE-flow
    }

    /////////////////////////////////////////////////////////
    // native / ip
    /////////////////////////////////////////////////////////
    uses config-ip-grouping;


    /////////////////////////////////////////////////////////
    // native / mka
    /////////////////////////////////////////////////////////
    container mka { 
      description "MACsec Key Agreement (MKA) configuration";
      //@mount Cisco-IOS-XE-mka
    }

    /////////////////////////////////////////////////////////
    // native / macro
    /////////////////////////////////////////////////////////
    container macro { 
      description
        "Macro configuration";
      container global {
        description
          "Enter global macro configuration";
        leaf description {
          description
            "Macro description of this device";
          type string;
        }
      }
      container auto {
        description "Macro autoexecution settings";
        //@mount Cisco-IOS-XE-switch.yang
      }
    }

    /////////////////////////////////////////////////////////
    // native / ipv6
    /////////////////////////////////////////////////////////
    uses config-ipv6-grouping;

    /////////////////////////////////////////////////////////
    // native / vlan
    // Note: /vlan must be before /interface
    /////////////////////////////////////////////////////////
    container vlan { 
      description
        "Global vlan configuration";
      // @mount Cisco-IOS-XE-vlan
    }

     /////////////////////////////////////////////////////////
     // native / mvrp
     /////////////////////////////////////////////////////////
     container mvrp { 
       description
         "Global MVRP";
       //@mount Cisco-IOS-XE-mvrp
     }   
 
     /////////////////////////////////////////////////////////
     // native / avb 
     /////////////////////////////////////////////////////////
     container avb { 
       description
         "Global AVB";
          presence "true";
       //@mount Cisco-IOS-XE-avb
     }   
 
     /////////////////////////////////////////////////////////
     // native / ptp 
     /////////////////////////////////////////////////////////
     container ptp { 
       description
         "Global PTP";
       //@mount Cisco-IOS-XE-ptp
     }   

    /////////////////////////////////////////////////////////
    // native / cdp
    /////////////////////////////////////////////////////////
    container cdp { 
      description
        "Global CDP configuration subcommands";
      // @mount Cisco-IOS-XE-cdp
    }

    /////////////////////////////////////////////////////////
    // native / avc
    /////////////////////////////////////////////////////////
    container avc {
      description "Application visibility and control";
      // @mount Cisco-IOS-XE-nbar
    }

    /////////////////////////////////////////////////////////
    // native / policy *
    // Note: /policy must be before /interface
    /////////////////////////////////////////////////////////
    container policy {
      // Note: A top level container has been added for class map
      // and policy map. Mandatory leaf in list class-map has to reside
      // in a container to be compiled in the augmented file. All test
      // cases related to class-map have to be updated

      // @mount Cisco-IOS-XE-policy
    }

    /////////////////////////////////////////////////////////
    // native / interface
    /////////////////////////////////////////////////////////
    uses config-interface-grouping;

    /////////////////////////////////////////////////////////
    // native / route-map *
    /////////////////////////////////////////////////////////
    list route-map {
      description
        "Route map tag";
      key "name";
      leaf name {
        description
          "WORD;;Route map tag";
        type string;
      }
      // @mount Cisco-IOS-XE-route-map
    }

    /////////////////////////////////////////////////////////
    // native / route-tag *
    /////////////////////////////////////////////////////////
    container route-tag { 
      // @mount Cisco-IOS-XE-eigrp
    }

    /////////////////////////////////////////////////////////
    // native / authentication *
    /////////////////////////////////////////////////////////
    // @mount Cisco-IOS-XE-sanet

    /////////////////////////////////////////////////////////
    // native / table-map
    /////////////////////////////////////////////////////////
    // Note: Must come before policer aggregate
    list table-map { 
      description
        "Configure Table Map";
      key "name";
      leaf name {
        type string;
      }
      // @mount Cisco-IOS-XE-qos
    } //table-map

    /////////////////////////////////////////////////////////
    // native / sdm
    /////////////////////////////////////////////////////////
    container sdm {
      description
        "Switch database management";
      //@mount Cisco-IOS-XE-switch
    }

    /////////////////////////////////////////////////////////
    // native / mls
    /////////////////////////////////////////////////////////
    // Note: must come before class-map and policy-map.
    container mls { 
      description
        "mls global commands";
      // @mount Cisco-IOS-XE-mls
    }

    /////////////////////////////////////////////////////////
    // native / object-group
    /////////////////////////////////////////////////////////
    container object-group { 
      description
        "Configure Object group";
      // @mount Cisco-IOS-XE-object-group
    }

    /////////////////////////////////////////////////////////
    // native / policer
    /////////////////////////////////////////////////////////
    // Note: must come before class-map and policy-map.
    // TBD : removed for now since there is no use cases
    // @mount Cisco-IOS-XE-policer

    list pseudowire-class { 
      description
        "Pseudowire-class configuration";
      key "name";
      leaf name {
        type string;
      }
      // @mount Cisco-IOS-XE-pseudowire-class
    }

    /////////////////////////////////////////////////////////
    // native / control-plane *
    /////////////////////////////////////////////////////////
    container control-plane {
      description
        "Configure control plane services";
      presence "true";
    }
 
    /////////////////////////////////////////////////////////
    // native / control-plane *
    /////////////////////////////////////////////////////////
    container control-plane-host {
      container control-plane {
        description
          "Configure control plane services";

        container host {
          presence "true";
          list management-interface {
            description "Configure interface for receiving network management traffic";
            key "interface-name";
            leaf interface-name {
              type string;
            }
            container allow {
              description "Allowed network management protocols on selected interface";
              leaf beep {
                description "Beep Protocol";
                type empty;
              }
              leaf ftp {
                description "File Transfer Protocol";
                type empty;
              }
              leaf http {
                description "HTTP Protocol";
                type empty;
              }
              leaf https {
                description "HTTPS Protocol";
                type empty;
              }
              leaf snmp {
                description "Simple Network Management Protocol";
                type empty;
              }
              leaf ssh {
                description "Secure Shell Protocol";
                type empty;
              }
              leaf telnet {
                description "Telnet Protocol";
                type empty;
              }
              leaf tftp {
                description "Trivial File Transfer Protocol";
                type empty;
              }
              leaf tl1 {
                description "Transaction Language Session Protocol";
                type empty;
              }
            }
          }
        }
      }
    }

    /////////////////////////////////////////////////////////
    // native / config-register *
    /////////////////////////////////////////////////////////
    leaf config-register { 
      description "Define the configuration register";
      type string {
        pattern "[0-9xXa-fA-F].*";
      }
    }

    /////////////////////////////////////////////////////////
    // native / clock *
    /////////////////////////////////////////////////////////
    container clock { 
      description
        "Configure time-of-day clock";
      container calendar-valid {
        description
          "Calendar time is authoritative";
        presence "true";
      }
      container summer-time {
        description
          "Configure summer (daylight savings) time";
        leaf zone {
          type string;
        }
        choice summer-choice {
          case date-case {
            leaf date {
              description
                "Configure absolute summer time";
              type empty;
            }
            leaf start-day {
              type uint8 {
                range "1..31";
              }
            }
            leaf start-month {
              type ios-types:month-type;
            }
            leaf start-year {
              type uint32 {
                range "1993..2035";
              }
            }
            leaf start-time {
              type ios-types:hhmm-type;
            }
            leaf date-end-day {
              type uint8 {
                range "1..31";
              }
            }
            leaf date-end-month {
              type ios-types:month-type;
            }
            leaf date-end-year {
              type uint32 {
                range "1993..2035";
              }
            }
            leaf date-end-time {
              type ios-types:hhmm-type;
            }
            leaf offset {
              type uint16 {
                range "1..1440";
              }
            }
          }
          case recurring-case {
            leaf recurring {
              description
                "Configure recurring summer time";
              type empty;
            }
            leaf recurring-start {
              type union {
                type uint8 {
                  range "1..4";
                }
                type enumeration {
                  enum "first";
                  enum "last";
                }
              }
            }
            leaf recurring-start-day {
              type ios-types:weekday-type;
            }
            leaf recurring-start-month {
              type ios-types:month-type;
            }
            leaf recurring-start-time {
              type ios-types:hhmm-type;
            }
            leaf recurring-end {
              type union {
                type uint8 {
                  range "1..4";
                }
                type enumeration {
                  enum "first";
                  enum "last";
                }
              }
            }
            leaf recurring-end-day {
              type ios-types:weekday-type;
            }
            leaf recurring-end-month {
              type ios-types:month-type;
            }
            leaf recurring-end-time {
              type ios-types:hhmm-type;
            }
            leaf recurring-offset {
              type uint16 {
                range "1..1440";
              }
            }
          }
        }
      }
      container timezone {
        description
          "Configure time zone";
        leaf zone {
          type string;
        }
        leaf offset {
          type enumeration {
            enum "+";
            enum "-";
          }
        }
        leaf hours {
          type int8 {
            range "-23..23";
          }
        }
        leaf minutes {
          type int8 {
            range "0..59";
          }
        }
      }
    }

    /////////////////////////////////////////////////////////
    // native / hw-switch *
    /////////////////////////////////////////////////////////
    // @mount Cisco-IOS-XE-switch

    /////////////////////////////////////////////////////////
    // native / logging *
    /////////////////////////////////////////////////////////
    uses config-logging-grouping; 

    /////////////////////////////////////////////////////////
    // native / aaa
    /////////////////////////////////////////////////////////
    container aaa { 
      description
        "Authentication, Authorization and Accounting.";
      // @mount Cisco-IOS-XE-aaa
    }

    /////////////////////////////////////////////////////////
    // native / privilege
    /////////////////////////////////////////////////////////
    uses config-privilege-grouping;

    /////////////////////////////////////////////////////////
    // native / login *
    /////////////////////////////////////////////////////////
    container login { 
      description
        "Enable secure login checking";
      leaf delay {
        description
          "Set delay between successive fail login";
        type uint8 {
          range "1..10";
        }
      }
      container on-failure {
        description
          "Set options for failed login attempt";
        presence "true";
        container log {
          description
            "Generate syslogs on failure logins";
          presence "true";
          leaf every {
            description
              "Periodicity for logs generated";
            type uint16 {
              range "1..65535";
            }
          }
        }
      }
      container on-success {
        description
          "Set options for successful login attempt";
        presence "true";
        container log {
          description
            "Generate syslogs on successful logins";
          presence "true";
          leaf every {
            description
              "Periodicity for logs generated";
            type uint16 {
              range "1..65535";
            }
          }
        }
      }
    }

    /////////////////////////////////////////////////////////
    // native / multilink *
    /////////////////////////////////////////////////////////
    container multilink {
      description
        "PPP multilink global configuration";
      //@mount Cisco-IOS-XE-ppp
    }

    /////////////////////////////////////////////////////////
    // native / mac-address-table *
    /////////////////////////////////////////////////////////
    // TODO remove candidate
    container mac-address-table { 
      description
        "Configure the MAC address table";
      container evc-xconnect {
        description
          "All ethernet virtual connections xconnect";
        leaf l2pt-forward-all {
          description
            "Layer 2 Protocol Forward All";
          type empty;
        }
      }
      container limit {
        description
          "Enter parameters for mac limit feature";
        list bdomain {
          description
            "bdomain number for  mac limit feature";
          key "number";
          leaf number {
            type uint16 {
              range "1..4095";
            }
          }
          leaf action {
            description
              "Enter action";
            type enumeration {
              enum "warning";
              enum "limit";
              enum "shutdown";
            }
          }
          leaf maximum {
            description
              "Enter max allowed entries";
            type uint32 {
              range "0..16000";
            }
          }
        }
      }
      container learning {
        description
          "Enable a MAC table learning feature";
        list vlan {
          description
            "Layer 2 table learning per VLAN";
          key "id";
          leaf id {
            type uint16 {
              range "1..4094";
            }
          }
          leaf module {
            description
              "Layer 2 table learning per VLAN per module";
            type uint8 {
              range "1..9";
            }
          }
        }
      }
    }

    /////////////////////////////////////////////////////////
    // native / redundancy *
    /////////////////////////////////////////////////////////
    container redundancy { 
      description
        "Enter redundancy mode";
      presence true;
      // redundancy maintenance-mode
      leaf maintenance-mode {
        description
          "Enable/Disable maintenance mode ";
        type empty;
      }
      // redundancy main-cpu
      container main-cpu {
        description
          "Enter main-cpu mode";
        presence true;
        container auto-sync {
          leaf running-config {
            type empty;
          }
          leaf config-register {
            type empty;
          }
          leaf bootvar {
            type empty;
          }
          leaf standard {
            type empty;
          }
        }
        container standby {
           description
             "Standby";
           container console {
              description
                "Console";
              leaf enable {
                 description
                   "Enable";
                 type empty;
              }
           }
           container initialization {
              description
                "Initialization";
              container delay {
                 description
                   "Delay";
                 leaf second {
                    description
                      "Delay value in seconds";
                    type uint16 {
                        range "30..1800";
                    }
                 }
                 leaf boot-only {
                    description
                      "Delay effective only on system boot";
                    type empty;
                 }
              }
           }
        }
      }
       // redundancy mode
      leaf mode {
        description
          "redundancy mode for this chassis";
        type enumeration {
          enum "rpr";
          enum "rpr-plus";
          enum "sso";
          enum "none";
        }
      }
      container policy {
         description
           "redundancy policy enforcement";
         container config-sync {
            description
              "config sync parameters";
            container bulk {
               description
                 "bulk configuration mode";
               container prc {
                  description
                    "prc policy enforcement";
                  leaf reload {
                     description
                       "reload standby";
                     type boolean;
                  }
               }
            }
            container lbl {
               description
                 "line-by-line configuration mode";
               container prc {
                  description
                    "prc policy enforcement";
                  leaf reload {
                     description
                       "reload standby";
                     type boolean;
                  }
               }
            }
         }
      }
      container timer {
         description
           "Select a timer to configure";
         leaf rpso {
            description
              "Delay value in seconds";
            type uint16 {
               range "120..1200";
            }
         }
      }
      container interchassis {
        description
          "Enter interchassis mode";
        list group {
          description
            "Enter the redundancy group number";
          key "group-number";
          leaf group-number {
            type uint64 {
              range "1..4294967295";
            }
          }
          container monitor {
            description
              "define the peer monitoring method";
            leaf peer {
              description
                "the peer method";
              type empty;
            }
            leaf bfd {
              description
                "set peer monitoring method to bfd";
              type empty;
            }
          }
          container member {
            description
              "specify a redundancy group member";
            leaf ip {
              description
                "specify the redundancy group member using an ip address";
              type inet:ipv4-address;
            }
          }
          container backbone {
            description
              "specify a redundancy group member";
            container interface {
              uses ios-ifc:interface-grouping;
            }
          }
        }
      }
    }

    /////////////////////////////////////////////////////////
    // native / scheduler *
    /////////////////////////////////////////////////////////
    container scheduler { 
      description
        "Scheduler parameters";
      container runtime {
        description "Process runtime controls";
        leaf netinput {
          description "Process-switching run time (in milliseconds)";
          type uint16 {
            range "100..40000";
          }
        }
      }
      container allocate {
        description
          "Guarantee CPU time for processes";
        leaf interrupt-time {
          type uint16 {
            range "400..60000";
          }
        }
        leaf process-time {
          type uint16 {
            range "100..4000";
          }
        }
      }
    }

    /////////////////////////////////////////////////////////
    // native / epm *
    /////////////////////////////////////////////////////////
    container epm { 
      description "EPM Global Configuration Commands";
      leaf logging {
        description "Enable EPM logging";
        type empty;
        }
    }

    /////////////////////////////////////////////////////////
    // native / spanning-tree *
    /////////////////////////////////////////////////////////
    container spanning-tree { 
      description
        "Spanning Tree Subsystem";
      // @mount Cisco-IOS-XE-spanning-tree
    }

    /////////////////////////////////////////////////////////
    // native / subscriber *
    /////////////////////////////////////////////////////////
    container subscriber { 
      description
        "Subscriber configuration";
      leaf templating {
        description
          "Configure subscriber templating";
        type empty;
      }
    }

    /////////////////////////////////////////////////////////
    // native / track *
    /////////////////////////////////////////////////////////
    container track { 
      description
        "Object tracking configuration commands";
      // @mount Cisco-IOS-XE-track
    }

    /////////////////////////////////////////////////////////
    // native / dot1x
    /////////////////////////////////////////////////////////
    container dot1x { 
      description
        "IEEE 802.1X Global Configuration Commands";
      // @mount Cisco-IOS-XE-dot1x
    }

    /////////////////////////////////////////////////////////
    // native / mab
    /////////////////////////////////////////////////////////
    container mab { 
      description
        "mab Configuration Commands";
      container logging {
        description
          "Set logging parameters";
        leaf verbose {
          description
            "Show verbose messages in system logs";
          type empty;
        }
      }
    }

    /////////////////////////////////////////////////////////
    // native / fallback
    /////////////////////////////////////////////////////////
    container fallback { 
      description "Fallback configuration commands";
      // @mount Cisco-IOS-XE-dot1x
    }

    /////////////////////////////////////////////////////////
    // native / parameter-map *
    /////////////////////////////////////////////////////////
    container parameter-map { 
      //Note: put the top level nodes in the base file. Nodes in
      //augmented file will show up in the submode (config-profile)#
      description
        "parameter map";
      container type {
        description
          "parameter map type";
        // Each parameter-map type should augment from this point
        // @mount Cisco-IOS-XE-policy
      }
    }

    /////////////////////////////////////////////////////////
    // native / ppp *
    /////////////////////////////////////////////////////////
    container ppp { 
      description
        "PPP global configuration";
      // @mount Cisco-IOS-XE-ppp
    }

    /////////////////////////////////////////////////////////
    // native / mac *
    /////////////////////////////////////////////////////////
    container mac { 
      description
        "Global MAC configuration subcommands";
      container address-table {
        description
          "Configure the MAC address table";
        container aging-time {
          description
            "Set MAC address table entry maximum age";
          leaf val {
            type uint32 {
              range "0 | 10..1000000";
            }
          }
          leaf routed-mac {
            description
              "Set RM Aging interval";
            type empty;
          }
          leaf vlan {
            description
              "VLAN Keyword";
            type uint16 {
              range "1..4094";
            }
          }
        }
        leaf control-packet-learn {
          description
            "Enable/Disable learning from Control Packets";
          type empty;
        }
        container learning {
          description
            "Enable MAC table learning feature";
          leaf vlan {
            description
              "<1-4094>;;VLAN id to enable MAC Address learning";
            type uint16 {
              range "1..4094";
            }
          }
        }
        container notification {
          description
            "Enable/Disable MAC Notification on the switch";
          container change {
            description
              "Enable/Disable MAC Notification feature on the switch";
            presence "true";
            leaf history-size {
              description
                "Number of entries in history table (0-500)";
              type uint16 {
                range "0..500";
              }
            }
            leaf interval {
              description
                "Notification interval in seconds (0-2147483647)";
              type uint32 {
                range "0..2147483647";
              }
            }
          }
          leaf mac-move {
            description
              "Enable Mac Move Notification";
            type empty;
          }
          container threshold {
            description
              "Configure L2 Table monitoring";
            presence "true";
            leaf interval {
              description
                "<120-1000000> Interval time in seconds";
              type uint32 {
                range "120..1000000";
              }
            }
            container limit {
              description
                "Limit percentage";
              leaf percentage {
                description
                  "Percentage (0-100)";
                type uint8 {
                  range "0..100";
                }
              }
              leaf interval {
                description
                  "<120-1000000> Interval time in seconds";
                type uint32 {
                  range "120..1000000";
                }
              }
            }
          }
        }
        container static {
          description
            "Static MAC entry";
          leaf mac-address {
            description
              "xxxx.xxxx.xxxx 48 bit mac address";
            type ios-types:cisco-mac-address-type;
          }
          leaf vlan {
            description
              "<1-4094> VLAN id of mac address table (1-4094)";
            type uint16 {
              range "1..4094";
            }
          }
          leaf drop {
            description
              "drop frames";
            type empty;
          }
          leaf interface {
            description
              "Output interface exact long name";
            type string;
          }
        }
      }
      // @mount Cisco-IOS-XE-acl for access-list
    }

    /////////////////////////////////////////////////////////
    // native / tacacs
    /////////////////////////////////////////////////////////
    container tacacs { 
      description
        "TACACS server configuration command";
      // @mount Cisco-IOS-XE-tacacs
    }

    /////////////////////////////////////////////////////////
    // native / tacacs-server
    /////////////////////////////////////////////////////////
    container tacacs-server { 
      description
        "Modify TACACS query parameters";
      // @mount Cisco-IOS-XE-tacacs-server
    }

    /////////////////////////////////////////////////////////
    // native / software 
    /////////////////////////////////////////////////////////
    container software { 
      description
        "Configure software installation parameters";
      container auto-upgrade {
        description
          "Configure software auto upgrade parameters";
        leaf enable {
          description
            "Enable the auto upgrade installation feature";
          type empty;
        }
      }
    }

    /////////////////////////////////////////////////////////
    // native / upgrade
    /////////////////////////////////////////////////////////
    container upgrade { 
      description
        "Global upgrade configuration subcommands";
      container fpd {
        description
          "Configure field programmable devices upgrade options";
        leaf auto {
          description
            "Auto upgrade all FPD images";
          type empty;
        }
        leaf path {
          description
            "Set path to locate the FPD image package file for auto upgrade";
          type string;
        }
      }
    }

    /////////////////////////////////////////////////////////
    // native / vtp
    /////////////////////////////////////////////////////////
    container vtp { 
      description
        "Configure global VTP state";
    }

    /////////////////////////////////////////////////////////
    // native / xconnect
    /////////////////////////////////////////////////////////
    container xconnect { 
      // @mount Cisco-IOS-XE-l2vpn
    }

    /////////////////////////////////////////////////////////
    // native / fabric *
    /////////////////////////////////////////////////////////
    //TODO: Should fabric be moved out of the main model?
    // Remove candidate
    container fabric {
      description
        "Catalyst 6000 crossbar fabric configuration commands";
      container switching-mode {
        description
          "Switching mode settings";
        container allow {
          description
            "Allow settings";
          choice allow-choice {
            leaf bus-mode {
              description
                "Allow switching in bus mode for modules";
              type empty;
            }
            container truncated {
              description
                "Truncated switching mode";
              presence "true";
              leaf threshold {
                description
                  "Number of SFM-capable modules for truncated switching mode. Switch applies the threshold only when the mode is disallowed. Switch ignores the threshold when the truncated mode is allowed";
                type uint8 {
                  range "1..9";
                }
              }
            }
          }
        }
        container force {
          description
            "Force modules to different switching modes";
          leaf bus-mode {
            description
              "Switching mode of service modules will be forced to bus-mode by powercycling it.";
            type empty;
          }
        }
      }
    }

    /////////////////////////////////////////////////////////
    // native / port-channel *
    /////////////////////////////////////////////////////////
    container port-channel {
      description
        "EtherChannel configuration";
      //@mount Cisco-IOS-XE-ethernet
    }

    /////////////////////////////////////////////////////////
    // native / key *
    /////////////////////////////////////////////////////////
    container key { 
      description
        "Key management";
      //@mount Cisco-IOS-XE-crypto
    }

    /////////////////////////////////////////////////////////
    // native / l2
    /////////////////////////////////////////////////////////
    container l2 { 
      description
        "Layer 2 configuration";
      leaf router-id {
        description
          "Configure a layer 2 identifier";
        type inet:ipv4-address;
      }
      //@mount Cisco-IOS-XE-l2vpn
    }

    /////////////////////////////////////////////////////////
    // native / system
    /////////////////////////////////////////////////////////
    container system {
      description
        "Set the system configuration";
      //@mount Cisco-IOS-XE-system
    }

    /////////////////////////////////////////////////////////
    // native / errdisable
    /////////////////////////////////////////////////////////
    container errdisable { 
      description
        "Error disable";
      // errdisable detect
      container detect {
        description
          "Error disable detection";
        container cause {
          description
            "Enable error disable detection for application";
          leaf all {
            description
              "Enable error detection on all cases";
            type empty;
          }
          leaf arp-inspection {
            description
              "Enable error detection for arp inspection";
            type empty;
          }
          leaf bpduguard {
            description
              "Enable error detection on bpdu-guard";
            type empty;
          }
          leaf dhcp-rate-limit {
            description
              "Enable error detection on dhcp-rate-limit";
            type empty;
          }
          leaf dtp-flap {
            description
              "Enable error detection on dtp-flapping";
            type empty;
          }
          leaf gbic-invalid {
            description
              "Enable error detection on gbic-invalid";
            type empty;
          }
          leaf inline-power {
            description
              "Enable error detection for inline-power";
            type empty;
          }
          leaf l2ptguard {
            description
              "Enable timer to recover from l2protocol-tunnel error disable state";
            type empty;
          }
          leaf link-flap {
            description
              "Enable error detection on linkstate-flapping";
            type empty;
          }
          leaf loopback {
            description
              "Enable error detection on loopback";
            type empty;
          }
          leaf mlacp-minlink {
            type empty;
          }
          leaf pagp-flap {
            description
              "Enable error detection on pagp-flapping";
            type empty;
          }
          leaf pppoe-ia-rate-limit {
            description
              "Enable error detection on PPPoE IA rate-limit";
            type empty;
          }
          container security-violation {
            description "Enable error detection on 802.1x-guard";
            container shutdown {
              description "Specify error disable shutdown mode for 802.1x-guard";
              leaf vlan {
                description "Shutdown vlan on 802.1x-guard violation";
                type empty;
              }
            }
          }
          leaf sfp-config-mismatch {
            description
              "Enable error detection on SFP config mismatch";
            type empty;
          }
          leaf small-frame {
            description
              "Enable error detection on small_frame";
            type empty;
          }
        }
      }
      // errdisable flap-setting
      container flap-setting {
        description
          "Error disable flap detection setting";
        container cause {
          description
            "Set error disable flap parameters for application";
          container dtp-flap {
            description
              "Set the variables related to detection of dtp flaps";
            leaf max-flaps {
              description
                "maximum flaps allowed before setting to errdisable";
              type uint8 {
                range "1..100";
              }
            }
            leaf time {
              description
                "time period the flaps are counted";
              type uint8 {
                range "1..120";
              }
            }
          }
          container link-flap {
            description
              "Set the variables related to detection of link flaps";
            leaf max-flaps {
              description
                "maximum flaps allowed before setting to errdisable";
              type uint8 {
                range "1..100";
              }
            }
            leaf time {
              description
                "time period the flaps are counted";
              type uint8 {
                range "1..120";
              }
            }
          }
          container pagp-flap {
            description
              "Set the variables related to detection of pagp flaps";
            leaf max-flaps {
              description
                "maximum flaps allowed before setting to errdisable";
              type uint8 {
                range "1..100";
              }
            }
            leaf time {
              description
                "time period the flaps are counted";
              type uint8 {
                range "1..120";
              }
            }
          }
        }
      }
      // errdisable recovery
      container recovery {
        description
          "Error disable recovery";
        // errdisable recovery cause
        container cause {
          description
            "Enable error disable recovery for application";
          leaf all {
            description
              "Enable timer to recover from all error causes";
            type empty;
          }
          leaf arp-inspection {
            description
              "Enable timer to recover from arp inspection error disable state";
            type empty;
          }
          leaf bpduguard {
            description
              "Enable timer to recover from BPDU Guard error";
            type empty;
          }
          leaf channel-misconfig {
            description
              "(STP)  Enable timer to recover from channel misconfig error";
            type empty;
          }
          leaf dhcp-rate-limit {
            description
              "Enable timer to recover from dhcp-rate-limit error";
            type empty;
          }
          leaf dtp-flap {
            description
              "Enable timer to recover from dtp-flap error";
            type empty;
          }
          leaf gbic-invalid {
            description
              "Enable timer to recover from invalid GBIC error";
            type empty;
          }
          leaf inline-power {
            description
              "Enable timer to recover from inline-power error";
            type empty;
          }
          leaf l2ptguard {
            description
              "Enable timer to recover from l2protocol-tunnel error disable state";
            type empty;
          }
          leaf link-flap {
            description
              "Enable timer to recover from link-flap error";
            type empty;
          }
          leaf link-monitor-failure {
            type empty;
          }
          leaf loopback {
            description
              "Enable timer to recover from loopback error";
            type empty;
          }
          leaf mac-limit {
            description
              "Enable timer to recover from mac limit disable state";
            type empty;
          }
          leaf mlacp-minlink {
            type empty;
          }
          container oam-remote-failure {
            presence "true";
            leaf critical-event {
              type empty;
            }
            leaf dying-gasp {
              type empty;
            }
            leaf link-fault {
              type empty;
            }
          }
          leaf pagp-flap {
            description
              "Enable timer to recover from pagp-flap error";
            type empty;
          }
          leaf port-mode-failure {
            description
              "Enable timer to recover from port mode change failure";
            type empty;
          }
          leaf pppoe-ia-rate-limit {
            description
              "Enable timer to recover from PPPoE IA rate-limit error";
            type empty;
          }
          leaf psp {
            type empty;
          }
          leaf psecure-violation {
            description
              "Enable timer to recover from psecure violation error";
            type empty;
          }
          leaf security-violation {
            description
              "Enable timer to recover from 802.1x violation error";
            type empty;
          }
          leaf sfp-config-mismatch {
            description
              "Enable timer to recover from SFP config mismatch error";
            type empty;
          }
          leaf small-frame {
            description
              "Enable timer to recover from small frame error";
            type empty;
          }
          leaf storm-control {
            description
              "Enable timer to recover from storm-control error";
            type empty;
          }
          leaf udld {
            description
              "Enable timer to recover from udld error";
            type empty;
          }
          leaf unicast-flood {
            type empty;
          }
          leaf vmps {
            description
              "Enable timer to recover from vmps shutdown error";
            type empty;
          }
        }
        leaf interval {
          description
            "Error disable recovery timer value";
          type uint32 {
            range "30..86400";
          }
        }
      }
    }

    /////////////////////////////////////////////////////////
    // native / identity
    /////////////////////////////////////////////////////////
    container identity { 
      description "Identity Configuration Commands";
      list policy {
        description
          "Create an Identity policy";
        key "name";
        leaf name {
          description "Specify a policy name";
          type string;
        }
        container no {
          description
            "Negate a command or set its defaults";
          uses identity-policy-grouping;
        }
        uses identity-policy-grouping;
      }
      container profile {
        description "Create an Identity profile";
        leaf dot1x {
          description "Service type for 802.1x";
          type empty;
        }
        leaf default {
          description "Service type default";
          type empty;
        }
      }
    }

    /////////////////////////////////////////////////////////
    // native / monitor
    /////////////////////////////////////////////////////////
    grouping monitor-event-trace-enable-disable-grouping {
      leaf enable {
        type empty;
      }
      leaf disable {
        type empty;
      }
    }

    container monitor { 
      description
        "Monitoring different system events";
      container event-trace {
        description
          "Tracing of system events";
        container timestamps {
          presence "true"; 
          description
           "Format of event trace timestamps";
          leaf uptime {
            description
              "Timestamp with system uptime";
            type empty;
          }			
        }
        container atom {
          description
            "AToM traces";
          container error {
            description
              "This buffer stores only error logs by default.";
            uses monitor-event-trace-enable-disable-grouping;
            leaf-list include {
              description
                "Include a subset of debug types";
              type monitor-event-type;
            }
          }
          container event {
            description
              "This buffer stores all logs by default.";
            uses monitor-event-trace-enable-disable-grouping;
            leaf size {
               type uint32;
            }
            leaf-list exclude {
              description
                "Include a subset of debug types";
              type monitor-event-type;
            }
          }
          container major {
            description
              "This buffer stores only major logs and error logs by default.";
            uses monitor-event-trace-enable-disable-grouping;
            leaf-list include {
              description
                "Include a subset of debug types";
              type monitor-event-type;
            }
          }
        }
        leaf sequence-number {
          description
           "Display event trace entries with sequence number";
          type empty;
        }
      }
      // monitor session *
      list session {
        description
          "Configure a SPAN session";
        key "id";
        leaf id {
          type uint8 {
            range "1..66";
          }
        }
        // monitor session * destination
        container destination {
          description
            "SPAN destination interface or VLAN";
          list interface {
            description
              "SPAN destination interface";
            key "name";
            leaf name {
              description
                "Interface Name";
              type string;
            }
            leaf encapsulation {
              description
                "Set encapsulation for destination interface";
              type enumeration {
                enum "dot1q";
                enum "isl";
                enum "replicate";
              }
            }
            leaf ingress {
              description
                "Enable ingress traffic forwarding";
              type empty;
            }
            leaf ingress-encap {
              when "../ingress" {
              }
              type enumeration {
                enum "dot1q";
                enum "isl";
                enum "untagged";
              }
            }
            leaf vlan {
              description
                "Set default VLAN for untagged ingress traffic";
              when "../ingress" {
              }
              type uint16 {
                range "1..4094";
              }
            }
	        }
          //  remote     SPAN destination Remote
          container remote {
            description "SPAN destination Remote";
            leaf vlan {
              description "Remote SPAN destination RSPAN VLAN";
              type uint16 {
                range "1006..4094";
              }
            }
          }
        }
        //  filter       SPAN filter VLAN
        // monitor session * filter       SPAN filter VLAN
        container filter {
          description
            "SPAN filter VLAN";
          container packet-type {
            leaf status {
              type enumeration {
                enum "good";
                enum "bad";
              }
            }
            leaf direction {
              type enumeration {
                enum "rx";
                enum "tx";
              }
            }
          }
          container ip {
            description "Specify IP Access control rules";
            container access-group {
              description "Specify access control group";
              leaf acl-name {
                description "Access-list name";
                type string;
              }
            }
          }
        }
        // monitor session * source
        container source {
          description
            "SPAN source interface, VLAN ";
          list interface {
            description
              "SPAN source interface";
            key "name";
            leaf name {
              description
                "Interface Name";
              type string;
            }
            leaf direction {
              type enumeration {
                enum "both";
                enum "rx";
                enum "tx";
              }
            }
          }
          container vlan {
            description
              "SPAN source VLAN";
            leaf vlan {
              type uint16 {
                range "1..4094";
              }
            }
            // ,     Specify another range of VLANs
            // -     Specify a range of VLANs
            leaf direction {
              type enumeration {
                enum "both";
                enum "rx";
                enum "tx";
              }
            }
          }
          //  remote     SPAN source Remote
          container remote {
            description
              "SPAN source Remote";
            leaf vlan {
              description
                "Remote SPAN source RSPAN VLAN <1-1001>|<1006-4094>";
              type uint16 {
                range "1..1001 | 1006..4094";
              }
            }
          } // remote
        }
        container type {
          description
            "Type of monitor session";
          container erspan-source {
            description
              "Encapsulated RSPAN Source Session";				
            presence "true";
            leaf description {
              description
                "Description for this session";
              type string;
            }
            container source {
              description
                "SPAN source interface, VLAN ";
              list interface {
                description
                  "SPAN source interface";
                key "name";
                leaf name {
                  description
                    "Interface Name";
                  type string;
                }
                leaf direction {
                  type enumeration {
                    enum "both";
                    enum "rx";
                    enum "tx";
                  }
                }
              }
              list vlan {
                description
                  "SPAN source VLAN";
                key "vlan1";
                leaf vlan1 {
                  type uint16 {
                    range "1..4094";
                  }
                }
                leaf direction {
                  type enumeration {
                    enum "both";
                    enum "rx";
                    enum "tx";
                  }
                }
              }
            }
            container filter {
              description
                "SPAN filter VLAN";
              list vlan {
                key "vlan1";
                leaf vlan1 {
                  type uint16 {
                    range "1..4094";
                  }
                }
              }
              container ip {
                description "Specify IP Access control rules";
                container access-group {
                  description "Specify access control group";
                  leaf acl-name {
                    description "Access-list name";
                    type string;
                  }
                }
              }
              leaf sgt {
                description "SPAN source SGT";
                type uint16 {
                  range "0..65535";
                }
              }
            }
            leaf header-type {
                description
                  "ERSPAN header-type for encapsulation. Default is type 2";
                type uint8 {
                  range "2..3";
                }
            }
            leaf shutdown {
              description
                "Take the Service Instance out of Service";
              type empty;
            }
            container destination {
              description
                "Specify Destination and their properties";				  
              presence "true";
              container ip {
                description
                  "IP Properties";
                leaf address {
                  description
                    "Enter IP Address";
                  type inet:ipv4-address;
                }				  
                leaf ttl {
                  description
                    "IP TTL";
                  type uint16 {
                    range "2..255";
                  }
                }
              }  				
              leaf erspan-id {
                description
                  "Enter ERSPAN Identifier";
                type uint16 {
                  range "1..1023";
                }
              }  				
              container origin {
                description
                  "Origin IP Properties";
                container ip {
                  description
                    "origin IP Properties";
                  leaf address {
                    description
                      "Enter IP Address";
                    type inet:ipv4-address;
                  }
                }
              }
            }
          }
          container erspan-destination {
            description
              "Encapsulated RSPAN Destination Session";				
            presence "true";
            leaf description {
              description
                "Properties for this session";
              type string;
            }
            container destination {
              description
                "SPAN destination interface, VLAN ";
              list interface {
                description
                  "SPAN destination interface";
                key "name";
                leaf name {
                  description
                    "Interface Name";
                  type string;
                }
              }
              leaf vlan {
                description
                  "Remote SPAN destination RSPAN VLAN <1-1001>|<1006-4094>";
                type uint16 {
                  range "1..1001 | 1006..4094";
                }
              }
            }
            leaf shutdown {
              description
                "Shutdown this session";
              type empty;
            }
            container source {
              description
                "Specify Source and their properties";				  
              presence "true";
              container ip {
                description
                  "IP Address";
                leaf address {
                  description
                    "Enter IP Address";
                  type inet:ipv4-address;
                }				  
              }
              leaf vrf {
                description
                  "Enter VRF number";
                type string;
              }
              leaf erspan-id {
                description
                  "Enter ERSPAN Identifier";
                type uint16 {
                  range "1..1023";
                }
              }  				
            }
          }//erspan

          container local {
            description
              "Local SPAN Session";
            presence "true";
            leaf description {
              description
                "Description for this session";
              type string;
            }
            container source {
              description
                "SPAN source Interface/VLAN/CPU";
              list interface {
                description
                  "SPAN source interface";
                key "name";
                leaf name {
                  description
                    "Interface Name";
                  type string;
                }
                leaf direction {
                  type enumeration {
                    enum "both";
                    enum "rx";
                    enum "tx";
                  }
                }
              }//list interface

              list vlan {
                description
                  "SPAN source VLAN";
                key "vlan1";
                leaf vlan1 {
                  type uint16 {
                    range "1..4094";
                  }
                }
                leaf direction {
                  type enumeration {
                    enum "both";
                    enum "rx";
                    enum "tx";
                  }
                }
              }//list vlan
            }//source

            // monitor session * destination
            container destination {
              description
                "SPAN destination interface or VLAN";
              list interface {
                description
                  "SPAN destination interface";
                key "name";
                leaf name {
                  description
                    "Interface Name";
                  type string;
                }
              }//interface
            }//destination

            container filter {
              description
                "SPAN filter VLAN";
              list vlan {
                key "vlan1";
                leaf vlan1 {
                  type uint16 {
                    range "1..4094";
                  }
                }
              }
            }//filter
            leaf shutdown {
              description
                "Take the Service Instance out of Service";
              type empty;
            }
          }//local

        }
      }
    }

    /////////////////////////////////////////////////////////
    // native / tftp-server
    /////////////////////////////////////////////////////////
    list tftp-server { 
      description
        "Provide TFTP service for netload requests";
      key "name";
      leaf name {
        type string;
      }
    }

    /////////////////////////////////////////////////////////
    // native / radius-server
    /////////////////////////////////////////////////////////
    container radius-server { 
      description
        "Modify RADIUS query parameters";
      // @mount Cisco-IOS-XE-radius-server
    }

    /////////////////////////////////////////////////////////
    // native / radius
    /////////////////////////////////////////////////////////
    container radius { 
      description
        "RADIUS server configuration command";
      // @mount Cisco-IOS-XE-radius
    }

    /////////////////////////////////////////////////////////
    // native / zone
    /////////////////////////////////////////////////////////
    container zone { 
      description
        "FW with zoning";
      // @mount Cisco-IOS-XE-zone
    }

    /////////////////////////////////////////////////////////
    // native / zone-pair
    /////////////////////////////////////////////////////////
    container zone-pair { 
      description
        "Zone pair command";
       // @mount Cisco-IOS-XE-zone
    }

    /////////////////////////////////////////////////////////
    // native / alarm-contact *
    /////////////////////////////////////////////////////////
    list alarm-contact {
      key "name";
      leaf name {
        type uint8 {
          range "1..4";
        }
      }
      leaf description {
        type string {
          length "1..80";
        }
      }
      leaf severity {
        type enumeration {
          enum "critical";
          enum "major";
          enum "minor";
        }
      }
      leaf trigger {
        type enumeration {
          enum "open";
          enum "closed";
        }
      }
    }

    /////////////////////////////////////////////////////////
    // native / ethenet *
    /////////////////////////////////////////////////////////
    container ethernet { 
      description
        "Ethernet configuration";
      // @mount Cisco-IOS-XE-ethernet
    }

    /////////////////////////////////////////////////////////
    // native / bridge-domain
    /////////////////////////////////////////////////////////
    container bridge-domain { 
      description
        "Bridge-domain global configuration commands";
    }

    /////////////////////////////////////////////////////////
    // native / crypto
    /////////////////////////////////////////////////////////
    container crypto { 
      description
        "Encryption module";
      // @mount Cisco-IOS-XE-crypto
    }

    /////////////////////////////////////////////////////////
    // native / cts
    /////////////////////////////////////////////////////////
    container cts { 
      description
        "Configures Cisco TrustSec";
      // @mount Cisco-IOS-XE-cts
    }

    /////////////////////////////////////////////////////////
    // native / bfd-template
    /////////////////////////////////////////////////////////
    container bfd-template {
      description
        "BFD-template";
      // @mount Cisco-IOS-XE-bfd-template
    }

    /////////////////////////////////////////////////////////
    // native / pfr
    /////////////////////////////////////////////////////////
    container pfr { 
      description
        "Performance Routing configuration submodes";
      // @mount Cisco-IOS-XE-pfr
    }

    /////////////////////////////////////////////////////////
    // native / pfr-map
    /////////////////////////////////////////////////////////
    list pfr-map { 
      description
        "Create pfr-map and enter pfr-map command mode";
      key "pfr-tg";
      leaf pfr-tg {
        description
          "pfr-map tag";
        type string;
      }
      // @mount Cisco-IOS-XE-pfr-map
    }

    /////////////////////////////////////////////////////////
    // native / facility-alarm *
    /////////////////////////////////////////////////////////
    container facility-alarm { 
      description
        "Configure facility alarms";
      leaf severity {
        type enumeration {
          enum "critical";
        }
      }
      leaf exceed-action {
        description
          "Behavior on critical threshold exceed";
        type enumeration {
          enum "shutdown";
        }
      }
    }

    /////////////////////////////////////////////////////////
    // native / setup *
    /////////////////////////////////////////////////////////
    container setup {
      description
        "Configure setup options";
      //@mount Cisco-IOS-XE-switch
    }

    /////////////////////////////////////////////////////////
    // native / tod-clock *
    /////////////////////////////////////////////////////////
    container tod-clock { 
      if-feature ios-features:tod-clock;
      description
        "Tod clock config commands";
      container input-source {
        description
          "Synchronization Input Source";
        leaf priority {
          type uint8 {
            range "1..250";
          }
        }
        container ptp {
          leaf domain {
            type uint8;
          }
        }
      }
    }

    /////////////////////////////////////////////////////////
    // native / network-clock *
    /////////////////////////////////////////////////////////
    container network-clock { 
      description
        "Network clock config commands";
      container synchronization {
        description
          "Network clock synchronization selection process";
        leaf automatic {
          description
            "ITU-T G.781/Telcordia standard based";
          type empty;
        }
        leaf mode {
          description
            "synchronization networking mode";
          type enumeration {
            enum "QL-enabled";
          }
        }
      }
      container wait-to-restore {
        description
          "Wait-to-Restore timer";
        leaf time {
          description
            "Wait-to-Restore time";
          type uint32 {
            range "0..86400";
          }
        }
        leaf global {
          description
            "Global";
          type empty;
        }
      }
      container input-source {
        description
          "Synchronization Input Source";
        leaf priority {
          type uint8 {
            range "1..250";
          }
        }
        container interface {
          uses ios-ifc:interface-grouping;
        }
        container ptp {
          leaf domain {
            type uint8;
          }
        }
      }
    }

    /////////////////////////////////////////////////////////
    // native / l2vpn *
    /////////////////////////////////////////////////////////
    container l2vpn { 
      description
        "Layer2 VPN commands";
      // @mount Cisco-IOS-XE-l2vpn
    }

    /////////////////////////////////////////////////////////
    // native / l2vpn-config *
    /////////////////////////////////////////////////////////
    container l2vpn-config { 
      // @mount Cisco-IOS-XE-l2vpn
    }

    /////////////////////////////////////////////////////////
    // native / l3vpn *
    /////////////////////////////////////////////////////////
    container l3vpn {
      description
        "l3vpn encapsulation ip commands";
      // @mount Cisco-IOS-XE-l3vpn
    }


    /////////////////////////////////////////////////////////
    // native / mpls
    /////////////////////////////////////////////////////////
    container mpls { 
      description
        "Configure MPLS parameters";
      // @mount Cisco-IOS-XE-mpls
    }

    /////////////////////////////////////////////////////////
    // native / router
    /////////////////////////////////////////////////////////
    container router { //68643
      // @mount Cisco-IOS-XE-bgp

      // @mount Cisco-IOS-XE-ospfv3

      // @mount Cisco-IOS-XE-ospf

      // @mount Cisco-IOS-XE-isis

      // @mount Cisco-IOS-XE-rip

      // @mount Cisco-IOS-XE-lisp
    }

    /////////////////////////////////////////////////////////
    // native / service-chain *
    /////////////////////////////////////////////////////////
    container service-chain { 
      description
        "Service Chain mode";
      // @mount Cisco-IOS-XE-service-chain
    }

    /////////////////////////////////////////////////////////
    // native / performance / monitor (ezPM)
    /////////////////////////////////////////////////////////
    container performance { 
      description
        "Global Performance monitor configuration";
      //@mount Cisco-IOS-XE-ezpm
    }

    /////////////////////////////////////////////////////////
    // native / otv *
    /////////////////////////////////////////////////////////
    container otv { 
      description
        "Configure OTV information";
    }

    /////////////////////////////////////////////////////////
    // native / remote-management *
    /////////////////////////////////////////////////////////
    container remote-management {
      description
        "Enable the remote managment";
      leaf dmi {
        description
          "data-model-interface";
        type empty;
      }
      leaf restful-api {
        description
          "RESTful API";
        type boolean;
      }
    }

    /////////////////////////////////////////////////////////
    // native / virtual-service
    /////////////////////////////////////////////////////////
    list virtual-service {
      description
        "Configure virtual service";
      key "name";
      leaf name {
        type string {
          length "1..63";
        }
      }
    }

    /////////////////////////////////////////////////////////
    // native / snmp
    /////////////////////////////////////////////////////////
    container snmp { 
      description
        "Modify SNMP interface parameters";
    }

    /////////////////////////////////////////////////////////
    // native / snmp-server
    /////////////////////////////////////////////////////////
    container snmp-server { 
      description
        "Modify SNMP engine parameters";
    }

    /////////////////////////////////////////////////////////
    // native / segment-routing *
    /////////////////////////////////////////////////////////
    container segment-routing { 
      description
        "Enter Segment Routing Mode";
      // @mount Cisco-IOS-XE-segment-routing
    }

    /////////////////////////////////////////////////////////
    // native / license
    /////////////////////////////////////////////////////////
    uses config-license-grouping;
    
    /////////////////////////////////////////////////////////
    // native / disable-eadi
    /////////////////////////////////////////////////////////
    leaf disable-eadi { 
      type empty;
    }

    /////////////////////////////////////////////////////////
    // native / memory-size
    /////////////////////////////////////////////////////////
    container memory-size { 
      if-feature ios-features:mem-size;
      description
        "Adjust memory size by percentage";
      leaf iomem {
        description
          "I/O memory";
        type uint8 {
          range "5..25" {
          }
        }
      }
    }

    /////////////////////////////////////////////////////////
    // native / transceiver
    /////////////////////////////////////////////////////////
    //TODO remove candidate
    container transceiver { 
      if-feature ios-features:transceiver;
      description
        "Select from transceiver configuration commands";
      container type {
        description
          "type keyword";
        container all {
          container monitoring {
            description
              "Enable/disable monitoring";
            presence "true";
            leaf interval {
              description
                "Set interval for monitoring";
              type uint16 {
                range "300..3600";
              }
            }
          }
        }
      }
    }

    /////////////////////////////////////////////////////////
    // native / service-insertion *
    /////////////////////////////////////////////////////////
    container service-insertion { 
      description
        "Service Insertion mode";
      // @mount Cisco-IOS-XE-service-insertion
    }
    
    /////////////////////////////////////////////////////////
    // native / udld
    /////////////////////////////////////////////////////////
    container udld { 
      description
        "Configure global UDLD setting";
      // @mount Cisco-IOS-XE-udld
    }

    /////////////////////////////////////////////////////////
    // native / qos
    /////////////////////////////////////////////////////////
    container qos { 
      description
        "Global QoS configuration commands";
      presence true;
      // @mount Cisco-IOS-XE-qos
    }

    /////////////////////////////////////////////////////////
    // native / time-range
    /////////////////////////////////////////////////////////
    list time-range { 
      description
        "Define time range entries";
      key "word";
      leaf word {
        type string;
      }
      container absolute {
        description
          "absolute time and date";
        container start {
          description
            "starting time and date";
          leaf start-time{
            description
              "Starting time";
            type string;
          }
          leaf day-of-month{
            description
              "<1-31>  Day of the month";
            type uint8;
          }
          leaf month {
            description
              "Month of the year [eg: Jan for January, Jun for June]";
            type string;
          }
          leaf year {
            description
              "Year";
            type uint16 {
              range "1993..2035";
            }
          }
        }
      }
    }

    /////////////////////////////////////////////////////////
    // native / device-tracking
    /////////////////////////////////////////////////////////
    container device-tracking {
      description
        "Device tracking configuration commands";
      // @mount Cisco-IOS-XE-device-tracking
    }

    /////////////////////////////////////////////////////////
    // native / fhrp
    /////////////////////////////////////////////////////////
    container fhrp { 
      description
        "Configure First Hop Redundancy Protocols";
      container version {
        description
          "Configure which FHRP version is allowed to run";
        leaf vrrp {
          description
            "Configure Virtual Router Rendundancy Protocol";
          type enumeration {
            enum "v2";
            enum "v3";
          }
        }
      }
    }

    /////////////////////////////////////////////////////////
    // native / metadata
    /////////////////////////////////////////////////////////
    container metadata { 
      description
        "Metadata Application";
      container flow {
        description
          "Enable Metadata Flow Handling";
        presence true;
        leaf transmit {
          description
            "Enable Metadata Flow Transmit ";
          type empty;
        }
      }
    }

    /////////////////////////////////////////////////////////
    // native / profile
    /////////////////////////////////////////////////////////
    // TODO remove candidate
    container profile { 
      description
        "MSP Profile";
      leaf flow {
        description
          "MSP Profile Flow";
        type empty;
      }
    }

    /////////////////////////////////////////////////////////
    // native / alias
    /////////////////////////////////////////////////////////
    container alias { 
      description
        "Create command alias";
      container exec {
        description
          "Exec mode";
        leaf alias-name {
          type string;
        }
        leaf new-alias-name {
          type string;
        }
      }
    }
    /////////////////////////////////////////////////////////
    // native / line *
    /////////////////////////////////////////////////////////
    uses config-line-grouping; 

    /////////////////////////////////////////////////////////
    // native / ntp *
    /////////////////////////////////////////////////////////
    container ntp { 
      description
        "Configure NTP";
    }

    /////////////////////////////////////////////////////////
    // native / wsma *
    /////////////////////////////////////////////////////////
    container wsma { 
      description
        "Configure Web Services Management Agents";
      // @mount Cisco-IOS-XE-wsma
    }

    /////////////////////////////////////////////////////////
    // native / event
    /////////////////////////////////////////////////////////
    container event { 
      description
        "Event related configuration commands";
      // @mount Cisco-IOS-XE-event
    }
    
    container template {
      description "template";
      // @mount Cisco-IOS-XE-template
    }

    grouping service-timestamp-show-timezone-and-year {				
      leaf show-timezone {
        description
          "Add time zone information to timestamp";
        type empty;
      }
      leaf year {
        description
          "Include year in timestamp";
        type empty;
      }
    }
    grouping service-timestamp-msec-and-year {
      leaf msec {
        description
          "Include milliseconds in timestamp";
        type empty;
      }
      leaf year {
        description
          "Include year in timestamp";
        type empty;
      }
    }
    grouping service-timestamp-msec-and-show-timezone {				
      leaf msec {
        description
          "Include milliseconds in timestamp";
        type empty;
      }
      leaf show-timezone {
        description
          "Add time zone information to timestamp";
        type empty;
      }
    }
    grouping service-timestamp-local-time-and-year {				
      leaf localtime {
        description
          "Use local time zone for timestamps";
        type empty;
      }
      leaf year {
        description
          "Include year in timestamp";
        type empty;
      }
    }
    grouping service-timestamp-local-time-and-show-timezone {				
      leaf localtime {
        description
          "Use local time zone for timestamps";
        type empty;
      }
      leaf show-timezone {
        description
          "Add time zone information to timestamp";
        type empty;
      }
    }
    grouping service-timestamp-local-time-and-msec {				
      leaf localtime {
        description
          "Use local time zone for timestamps";
        type empty;
      }
      leaf msec {
        description
          "Include milliseconds in timestamp";
        type empty;
      }
    }
    grouping process-rising-grouping {
      container rising {
        description "rising threshold";
        list cpu-range {
          key "cpu-range";
          leaf cpu-range {
            type uint8 {
              range "1..100";
            }
          }
          container interval {
            description "observation interval";
            list cpu-range {
              key "cpu-range";
              leaf cpu-range {
                type uint32 {
                  range "5..86400";
                }
              }
              container falling {
                description "falling threshold";
                list cpu-range {
                  key "cpu-range";
                  leaf cpu-range {
                    type uint8 {
                      range "1..100";
                    }
                  }
                  leaf interval {
                    description "observation interval";
                    type uint32 {
                      range "5..86400";
                    }
                  }
                }
              }
            }
          }
        }
      }
    }
    container process {
      description "Configure process";
      container cpu {
        description "Configure cpu parameters";
        container threshold {
          description "cpu threshold parameters";
          container type {
            description "cpu threshold type";
            container interrupt {
              description "interrupt level utilization";
              uses process-rising-grouping;
            }
            container process {
              description "process level utilization";
              uses process-rising-grouping;
            }
            container total {
              description "total cpu utilization";
              uses process-rising-grouping;
            }
          }
        }
      }
    }
    ///=================================
    /// exception
    ///=================================
    container exception {
      description "help";
      container crashinfo {
        description "Crashinfo collection";
        presence true;
        leaf buffersize {
          description "buffer size in Kbytes 256K or less (default is 32K)";
          type uint16 {
            range "32..256";
          }
        }
      }
    }
    /////////////////////////////////////////////////////////
    // native / iox *
    /////////////////////////////////////////////////////////
    container iox {
      description
        "Configure IOx services";
      presence true;
    }
  } // native
}
