module Cisco-IOS-XE-ethernet-radium-deviation {
  yang-version 1.1;
  namespace "http://cisco.com/ns/yang/Cisco-IOS-XE-ethernet-radium-deviation";
  prefix ios-ethernet-radium-d;

  import Cisco-IOS-XE-native {
    prefix ios;
  }
  import Cisco-IOS-XE-ethernet {
    prefix ios-eth;
  }

  organization
    "Cisco Systems";
  description
    "Cisco XE Native Deviation YANG module for radium platforms
     Restricts LACP min-bundle range to 1-4 due to hardware limitations
     Copyright (c) 2025 by Cisco Systems, Inc.
     All rights reserved.";

  revision 2024-07-01 {
    description
      "- Add deviation file to restrict LACP min-bundle range for radium platforms (4-port limit)";
  }

  deviation "/ios:native/ios:interface/ios:Port-channel/ios-eth:lacp/ios-eth:min-bundle" {
    deviate replace {
      type uint8 {
        range "1..4";
      }
    }
  }
}
