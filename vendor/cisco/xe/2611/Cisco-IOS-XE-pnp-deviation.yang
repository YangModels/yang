module Cisco-IOS-XE-pnp-deviation {
  yang-version 1.1;
  namespace "http://cisco.com/ns/yang/Cisco-IOS-XE-pnp-deviation";
  prefix ios-pnp-d;

  import Cisco-IOS-XE-native {
    prefix ios;
  }
  import Cisco-IOS-XE-pnp {
    prefix ios-pnp;
  }

  organization
    "Cisco Systems";
  description
    "Cisco XE Native PNP Deviation YANG module for IOS
     Copyright (c) 2023 by Cisco Systems, Inc.
     All rights reserved.";

  deviation "/ios:native/ios-pnp:pnp/ios-pnp:profile/ios-pnp:transport/ios-pnp:https/ios-pnp:ipv4/ios-pnp:port" {
    deviate add {
      default "443";
    }
  }

  deviation "/ios:native/ios-pnp:pnp/ios-pnp:profile/ios-pnp:transport/ios-pnp:http/ios-pnp:ipv4/ios-pnp:port" {
    deviate add {
      default "80";
    }
  }
}
