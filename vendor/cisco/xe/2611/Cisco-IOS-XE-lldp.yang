module Cisco-IOS-XE-lldp {
  yang-version 1.1;
  namespace "http://cisco.com/ns/yang/Cisco-IOS-XE-lldp";
  prefix ios-lldp;

  import cisco-semver {
    prefix cisco-semver;
  }
  import Cisco-IOS-XE-native {
    prefix ios;
  }
  import Cisco-IOS-XE-features {
    prefix ios-features;
  }
  import ietf-inet-types {
    prefix inet;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Link Layer Discovery Protocol (LLDP) Yang model.
     Copyright (c) 2016-2017 by Cisco Systems, Inc.
     All rights reserved.";

  revision 2025-07-01 {
    description
      "- Added FiftyGigabitEthernet interface support";
    cisco-semver:module-version "1.4.0";
  }
  revision 2025-03-01 {
    description
      "- Remove feature condition for Management VLAN,
         Management Address, System name, Network hash
         configuration";
    cisco-semver:module-version "1.3.0";
  }
  revision 2023-07-01 {
    description
      "-Added custom configurations for Management VLAN,
        Management Address, System name, Network Hash
       -Included feature check lldp-custom-config for
        the custom configurations added";
    cisco-semver:module-version "1.2.0";
  }
  revision 2022-11-01 {
    description
      "- Update yang-version to 1.1";
    cisco-semver:module-version "1.1.0";
  }
  revision 2019-07-01 {
    description
      "Establish semantic version baseline
       -TLV types have been changed";
    cisco-semver:module-version "1.0.0";
  }
  revision 2019-01-22 {
    description
      "Added leaf for App-hosting Gigabit Ethernet interface";
  }
  revision 2018-11-07 {
    description
      "Cleanup spelling errors in description statements";
  }
  revision 2018-07-25 {
    description
      "Changed the type of tlv-select leafs to boolean to better represent CLI state";
  }
  revision 2018-07-17 {
    description
      "Changed the range of the timer leaf to match CLI";
  }
  revision 2017-11-27 {
    description
      "Added Change 25GE name";
  }
  revision 2017-11-14 {
    description
      "This revision has changes for new 100GE interface addition";
  }
  revision 2017-09-15 {
    description
      "This revision has changes for new 2gig interface addition";
  }
  revision 2017-08-16 {
    description
      "This revision has changes for new 5gig and 25gig interfaces addition";
  }
  revision 2017-03-31 {
    description
      "Move interface LLDP configuration from switch to common";
  }
  revision 2017-02-07 {
    description
      "Initial revision";
  }

  grouping config-lldp-grouping {
    container lldp {
      description
        "Enables LLDP globally.";
      leaf holdtime {
        description
          "Specify the holdtime (in sec) to be sent in packets";
        type uint32 {
          range "0..65535";
        }
        default "120";
      }
      leaf reinit {
        description
          "Specify the delay (in secs) for LLDP to initialize";
        type uint8 {
          range "2..5";
        }
        default "2";
      }
      leaf run {
        description
          "Enable LLDP";
        type empty;
      }
      leaf timer {
        description
          "Rate at which LLDP packets are sent (in sec)";
        type uint16 {
          range "5..65534";
        }
        default "30";
      }
      leaf management-vlan {
        description
          "Custom Management VLAN";
        type uint16 {
          range "1..4095";
        }
      }
      leaf custom-network-hash {
        description
          "Custom Network hash";
        type string;
      }
      container management-address {
        description
          "Management address configuration";
        leaf-list ipv4 {
          description
            "IPV4 address List";
          type inet:ipv4-address;
        }
        leaf-list ipv6 {
          description
            "IPV6 address List";
          type inet:ipv6-address;
        }
      }
      list system-name {
        description
          "System name";
        key "switch-id";
        leaf name {
          description
            "System name";
          type string;
        }
        leaf switch-id {
          description
            "Switch identifier";
          type uint8 {
            range "0..17";
          }
        }
      }
      container tlv-select {
        description
          "Selection of LLDP TLVs to send";
        leaf four-wire-power-management {
          description
            "Cisco 4-wire Power via MDI TLV";
          default "true";
          type boolean;
        }
        leaf mac-phy-cfg {
          description
            "IEEE 802.3 MAC/Phy Configuration/status TLV";
          default "true";
          type boolean;
        }
        leaf management-address {
          description
            "Management Address TLV";
          default "true";
          type boolean;
        }
        leaf port-description {
          description
            "Port Description TLV";
          default "true";
          type boolean;
        }
        leaf port-vlan {
          description
            "Port VLAN ID TLV";
          default "true";
          type boolean;
        }
        leaf power-management {
          description
            "IEEE 802.3 DTE Power via MDI TLV";
          default "true";
          type boolean;
        }
        leaf system-capabilities {
          description
            "System Capabilities TLV";
          default "true";
          type boolean;
        }
        leaf system-description {
          description
            "System Description TLV";
          default "true";
          type boolean;
        }
        leaf system-name {
          description
            "System Name TLV";
          default "true";
          type boolean;
        }
      }
    }
  }

  grouping config-interface-lldp-grouping {
    container lldp {
      description
        "LLDP interface subcommands";
      leaf receive {
        description
          "Enable LLDP reception on interface";
        default "true";
        type boolean;
      }
      container tlv-select {
        description
          "Selection of LLDP TLVs to send";
        leaf four-wire-power-management {
          description
            "Cisco 4-wire Power via MDI TLV";
          default "true";
          type boolean;
        }
        leaf power-management {
          description
            "IEEE 802.3 DTE Power via MDI TLV";
          default "true";
          type boolean;
        }
      }
      container med-tlv-select {
        description
          "Selection of LLDP MED TLVs to send";
        if-feature "ios-features:med";
        leaf inventory-management {
          description
            "LLDP MED Inventory Management TLV";
          type boolean;
          default "true";
        }
        leaf power-management {
          description
            "LLDP MED power Management TLV";
          type boolean;
          default "true";
        }
        leaf location {
          description
            "LLDP MED Location TLV";
          type boolean;
          default "true";
        }
        leaf network-policy {
          description
            "LLDP MED Network Policy TLV";
          type boolean;
          default "true";
        }
      }
      leaf transmit {
        description
          "Enable LLDP transmission on interface";
        default "true";
        type boolean;
      }
    }
  }

  augment "/ios:native" {
    uses config-lldp-grouping;
  }

  augment "/ios:native/ios:interface/ios:FastEthernet" {
    uses config-interface-lldp-grouping;
  }

  augment "/ios:native/ios:interface/ios:GigabitEthernet" {
    uses config-interface-lldp-grouping;
  }

  augment "/ios:native/ios:interface/ios:TwoGigabitEthernet" {
    uses config-interface-lldp-grouping;
  }

  augment "/ios:native/ios:interface/ios:FiveGigabitEthernet" {
    uses config-interface-lldp-grouping;
  }

  augment "/ios:native/ios:interface/ios:AppGigabitEthernet" {
    uses config-interface-lldp-grouping;
  }

  augment "/ios:native/ios:interface/ios:TenGigabitEthernet" {
    uses config-interface-lldp-grouping;
  }

  augment "/ios:native/ios:interface/ios:TwentyFiveGigE" {
    uses config-interface-lldp-grouping;
  }

  augment "/ios:native/ios:interface/ios:FortyGigabitEthernet" {
    uses config-interface-lldp-grouping;
  }

  augment "/ios:native/ios:interface/ios:FiftyGigabitEthernet" {
    uses config-interface-lldp-grouping;
  }

  augment "/ios:native/ios:interface/ios:HundredGigE" {
    uses config-interface-lldp-grouping;
  }
}
