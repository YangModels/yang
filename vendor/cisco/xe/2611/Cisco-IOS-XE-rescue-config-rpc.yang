module Cisco-IOS-XE-rescue-config-rpc {
  yang-version 1.1;
  namespace "http://cisco.com/ns/yang/Cisco-IOS-XE-rescue-config-rpc";
  prefix ios-xe-rescue-config-rpc;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for RPCs related to the rescue configuration.
     Copyright (c) 2024 by Cisco Systems, Inc.
     All rights reserved.";

  revision 2026-02-01 {
    description
      "Added new leaf to rescue-config-rpc";
    cisco-semver:module-version "1.1.0";
  }
  revision 2025-07-01 {
    description
      "Initial revision";
    reference
      "1.0.0";
    cisco-semver:module-version "1.0.0";
  }

  grouping rescue-config-rpc-output {
    description
      "Output data";
    leaf result {
      type string;
      description
        "Output returned by the network element";
    }
    leaf error-message {
      type string;
      description
        "Error returned by the network element";
    }
  }

  grouping rescue-config-save {
    description
      "Save the rescue configuration, which serves as a golden configuration.";
    leaf comment {
      type string;
      description
        "Rescue configuration comment.";
    }
  }

  grouping rescue-config-apply {
    leaf force {
      description
        "Forcefully attempt to apply rescue configuration.";
      type empty;
    }
    leaf comment {
      type string;
      description
        "Set rollback comment.";
    }
  }

  grouping rescue-config-get-resp {
    description
      "Rescue configuration output.";
    leaf rescue-config {
      type string;
      description
        "Rescue configuration output data.";
    }
  }

  grouping rescue-config-info-resp {
    description
      "Rescue information output.";
    leaf comment {
      type string;
      description
        "Rescue configuration comment.";
    }
    leaf username {
      type string;
      description
        "The user who performed rescue config save operation.";
    }
    leaf deprecated-disabled {
      type boolean;
      description
        "Flag indicating if deprecated model elements are disabled.";
    }
    leaf timestamp {
      type yang:date-and-time;
      description
        "The time when rescue configuration was created.";
    }
    leaf image-version {
      type string;
      description
        "System image version.";
    }
  }

  rpc rescue-config-get {
    description
      "Get rescue configuration.";
    output {
      uses ios-xe-rescue-config-rpc:rescue-config-get-resp;
    }
  }

  rpc rescue-config-apply {
    description
      "Apply the rescue configuration, which essentially replaces the current configuration with the saved rescue configuration.";
    input {
      uses ios-xe-rescue-config-rpc:rescue-config-apply;
    }
    output {
      uses ios-xe-rescue-config-rpc:rescue-config-rpc-output;
    }
  }

  rpc rescue-config-save {
    description
      "Save rescue configuration.";
    input {
      uses ios-xe-rescue-config-rpc:rescue-config-save;
    }
    output {
      uses ios-xe-rescue-config-rpc:rescue-config-rpc-output;
    }
  }

  rpc rescue-config-delete {
    description
      "Delete rescue configuration.";
    output {
      uses ios-xe-rescue-config-rpc:rescue-config-rpc-output;
    }
  }

  rpc rescue-config-info {
    description
      "Information of rescue configuration.";
    output {
      uses ios-xe-rescue-config-rpc:rescue-config-info-resp;
    }
  }
}
