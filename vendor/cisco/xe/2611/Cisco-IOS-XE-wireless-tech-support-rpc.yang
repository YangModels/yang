module Cisco-IOS-XE-wireless-tech-support-rpc {
  yang-version 1.1;
  namespace "http://cisco.com/ns/yang/Cisco-IOS-XE-wireless-tech-support-rpc";
  prefix wireless-tech-support-actions-rpc;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This YANG model has options to retrieve show tech-support wireless command output
     into a text file and option to retrieve system reports along with output of command
     'show tech-support wireless', into a tar file
     Copyright (c) 2024-2025 by Cisco Systems, Inc.
     All rights reserved.";

  revision 2026-02-01 {
    description
      "Added support for wireless client MAC address filtering in tech-support file generation";
    reference
      "1.1.0";
    cisco-semver:module-version "1.1.0";
  }
  revision 2024-07-01 {
    description
      "Initial revision";
    reference
      "1.0.0";
    cisco-semver:module-version "1.0.0";
  }

  typedef wireless-file-info-list {
    type enumeration {
      enum wireless {
        value 0;
        status deprecated;
        description
          "This option is to retrieve output of command 'show tech-support wireless' into a file (deprecated).
           Use wireless-v2 instead.";
      }
      enum wireless-v2 {
        value 1;
        description
          "This option is to retrieve output of command 'show tech-support wireless' into a file";
      }
    }
    description
      "Options for tech-support file.";
  }

  grouping wireless-archive-options {
    description
      "Options for tech-support wireless archive generation. Tech-support
       archive is an archive of the 'show tech-support wireless' file and system
       report";
    leaf archive {
      type boolean;
      default "true";
      description
        "Tech-support wireless archive generate option
         if this option is marked as 'true' tech-support wireless archive will be generated
         The tech support wireless file included in the archive will be equivalent
         to the output of command 'show tech-support wireless'";
    }
  }

  grouping wireless-file-options {
    description
      "This option is to retrieve output of command 'show tech-support wireless'";
    choice info-type-choice {
      mandatory true;
      description
        "Options for technical support";
      case wireless {
        leaf wireless-info {
          type boolean;
          default "true";
          status deprecated;
          description
            "This option will collect output of 'show tech-support wireless' command into a file (deprecated).
             Use wireless-info-v2 instead.";
        }
      }
      case wireless-v2 {
        leaf wireless-info-v2 {
          type boolean;
          default "true";
          description
            "This option will collect output of 'show tech-support wireless' command into a file";
        }
        leaf client-mac {
          type yang:mac-address;
          must "(../wireless-info-v2 = 'true') or (../client-mac = '00:00:00:00:00:00')" {
            error-message "Option 'wireless-info-v2' needs to be set as 'true' to collect client information";
            error-app-tag "must-violation";
          }
          default "00:00:00:00:00:00";
          description
            "This option will collect output of 'show tech-support wireless client mac <mac-address>' command into a file.
             Make sure it is in 'aa:aa:aa:aa:aa:aa' format";
        }
      }
    }
  }

  grouping tech-support-wireless-response {
    description
      "Response to tech-support wireless actions";
    leaf file-name {
      type string {
        pattern '(flash:|bootflash:|crashinfo:|harddisk:)[A-Za-z_0-9]*';
      }
      description
        "File name of the tech-support wireless archive/file that will be generated. If
         the file-name is empty, it indicates that there was failure in the
         operation, possibly an internal error or another operation was being
         processed. In such cases, the reason for failure will also be
         attached to the response message. The arrival of response does not
         indicate that the operation is complete because the tech-support wireless
         operation takes a huge amount of time to complete and notifications
         related to the execution can be consumed by subscribing to the tech-support
         event notification model which will contain the same file-name found in this
         response message.";
    }
  }

  rpc tech-support-wireless-archive {
    description
      "RPC message for tech-support wireless archive generation";
    input {
      uses wireless-tech-support-actions-rpc:wireless-archive-options;
    }
    output {
      uses wireless-tech-support-actions-rpc:tech-support-wireless-response;
    }
  }

  rpc tech-support-wireless-file {
    description
      "RPC message for tech-support wireless file generation";
    input {
      uses wireless-tech-support-actions-rpc:wireless-file-options;
    }
    output {
      uses wireless-tech-support-actions-rpc:tech-support-wireless-response;
    }
  }
}
