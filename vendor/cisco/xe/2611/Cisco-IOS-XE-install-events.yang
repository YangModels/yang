module Cisco-IOS-XE-install-events {
  yang-version 1.1;
  namespace "http://cisco.com/ns/yang/Cisco-IOS-XE-install-events";
  prefix install-ios-xe-events;

  import Cisco-IOS-XE-install-event-types {
    prefix install-event-types-ios-xe;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for install status notification for image install events.
     Copyright (c) 2019-2022 by Cisco Systems, Inc.
     All rights reserved.";

  revision 2022-11-01 {
    description
      "Update yang-version to 1.1";
    reference
      "2.6.0";
    cisco-semver:module-version "2.6.0";
  }
  revision 2022-03-01 {
    description
      "- Added install status for package in use
       - Added install status for install operation cancellations
       - Added install status for rollback operations
       - Added install status indicating user confirmation activity
       - Added install status for auto upgrade start, fail, complete
       - Type definitions are moved to install-event-types-ios-xe";
    reference
      "2.5.0";
    cisco-semver:module-version "2.5.0";
  }
  revision 2021-11-01 {
    description
      "- Added install sub-state enums for smu add fail cleanup
       - Added install status for add fail cleanup and add pre and post checks
       - Added install status for ISSU compatibility check
       - Added install status for activate pre checks, post checks, smu, sub-package, and fail cleanup
       - Added install sub-state enums to report additional failure conditions related to SMU and install";
    reference
      "2.4.0";
    cisco-semver:module-version "2.4.0";
  }
  revision 2021-07-01 {
    description
      "- Install notification sub-state enumeration has been extended to include additional install progress states";
    reference
      "2.3.0";
    cisco-semver:module-version "2.3.0";
  }
  revision 2021-03-01 {
    description
      "- Added a new error message enum in install status notification to report
         a no-disk-space-left-on-device error.
       - Added ISSU data model changes
       - Install notification sub-state enumeration has been extended to include staggered AP upgrade progress states";
    reference
      "2.2.0";
    cisco-semver:module-version "2.2.0";
  }
  revision 2020-11-01 {
    description
      "Added AP image predownload sub-states notification";
    reference
      "2.1.0";
    cisco-semver:module-version "2.1.0";
  }
  revision 2020-07-01 {
    description
      "- Added enum values for installation sub-states
       - Remove unused empty container install-events";
    reference
      "2.0.0";
    cisco-semver:module-version "2.0.0";
  }
  revision 2020-03-01 {
    description
      "Initial revision";
    reference
      "1.0.0";
    cisco-semver:module-version "1.0.0";
  }

  notification install-status {
    description
      "install status notification";
    uses install-event-types-ios-xe:common-notification-header;
    uses install-event-types-ios-xe:install-notification-fields;
  }
}
