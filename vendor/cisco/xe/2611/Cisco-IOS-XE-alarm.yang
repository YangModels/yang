module Cisco-IOS-XE-alarm {
  yang-version 1.1;
  namespace "http://cisco.com/ns/yang/Cisco-IOS-XE-alarm";
  prefix ios-alarm;

  import Cisco-IOS-XE-features {
    prefix ios-features;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Alarm Yang model.
     Copyright (c) 2023 by Cisco Systems, Inc.
     All rights reserved.";

  revision 2026-02-01 {
    description
      "- Added additional commands for alarm
       - Added if-feature check for ptp and hsr
       - Modified some leaf types to boolean for setting default values";
  }
  revision 2023-07-01 {
    description
      "Initial revision";
  }

  typedef severity-type {
    type enumeration {
      enum major;
      enum minor;
      enum none;
    }
    description
      "Severity level for alarm contacts";
  }

  typedef contact-identifier {
    type union {
      type uint8 {
        range "1..4";
      }
      type enumeration {
        enum all;
      }
    }
  }

  grouping alarm-grouping {
    container alarm {
      container contact {
        description
          "List of alarm contacts";
        list contact-id {
          key "contact-number";
          leaf contact-number {
            description
              "Alarm contact number";
            type contact-identifier;
          }
          leaf description {
            description
              "Description only valid for individual contacts";
            type string {
              length "1..80";
            }
          }
          leaf severity {
            type severity-type;
            description
              "Contact severity level";
            default "minor";
          }
          leaf trigger {
            type enumeration {
              enum open {
                description
                  "Set contact state to open";
              }
              enum closed {
                description
                  "Set contact state to closed";
              }
            }
            description
              "Trigger the contact with specified state";
            default "closed";
          }
        }
      }
      container facility {
        description
          "Alarm Facility Configuration data";
        container power-supply {
          description
            "Power supply settings";
          leaf disable {
            description
              "Disables the power supply alarm";
            type empty;
          }
          leaf notifies {
            description
              "Sends power supply alarm traps to an SNMP server.";
            type empty;
          }
          leaf syslog {
            description
              "Enable/disable syslog messages";
            type boolean;
            default "true";
          }
          container relay {
            description
              "Power Supply information details";
            leaf major {
              description
                "Associates the power supply alarm to the relay.";
              type empty;
            }
          }
        }
        container ptp {
          if-feature "ios-features:ptp";
          description
            "PTP settings";
          leaf enable {
            description
              "Enable PTP alarms";
            type empty;
          }
          leaf notifies {
            description
              "Enable notifications to be sent to an SNMP server";
            type empty;
          }
          leaf syslog {
            description
              "Send PTP alarm traps to a syslog server";
            type empty;
          }
          container relay {
            description
              "PTP information details";
            leaf major {
              description
                "Associates the PTP alarm to the relay.";
              type empty;
            }
          }
        }
        container hsr {
          if-feature "ios-features:hsr";
          description
            "HSR settings";
          leaf enable {
            description
              "Enable HSR alarms";
            type empty;
          }
          leaf notifies {
            description
              "Enable notifications to be sent to an SNMP server";
            type empty;
          }
          leaf syslog {
            description
              "Send HSR  alarm traps to a syslog server";
            type empty;
          }
          container relay {
            description
              "HSR information details";
            leaf major {
              description
                "Associates the HSR alarm to the relay.";
              type empty;
            }
          }
        }
        container dlr {
          if-feature "ios-features:dlr";
          description
            "DLR settings";
          leaf enable {
            description
              "Enable DLR alarms";
            type empty;
          }
          leaf notifies {
            description
              "Enable notifications to be sent to an SNMP server";
            type empty;
          }
          leaf syslog {
            description
              "Send DLR alarm traps to a syslog server";
            type empty;
          }
          container relay {
            description
              "DLR information details";
            leaf major {
              description
                "Associates the DLR alarm to the relay.";
              type empty;
            }
          }
        }
        container sd-card {
          description
            "SD card settings";
          leaf enable {
            description
              "Enable alarm";
            type empty;
          }
          leaf notifies {
            description
              "Enable notification sent to server";
            type empty;
          }
          leaf syslog {
            description
              "Enable system logger";
            type empty;
          }
          container relay {
            description
              "SD card information details";
            leaf major {
              description
                "Associates the SD card alarm to the relay.";
              type empty;
            }
          }
        }
        container temperature {
          description
            "Temperature settings";
          container primary {
            description
              "Primary temperature alarm settings";
            leaf high {
              description
                "Higher threshold range in degree C
                 Device-specific range  and default values:
                 - ie35xx    : <-40 - 96>     80
                 - ie3x00    : <-55 - 125>    90
                 - ie31xx    : <-55 - 125>    90
                 - ie9k      : <-40 - 96>     80
                 - s5200     : <-55 - 125>    90
                 - s5800     : <-55 - 125>    90
                 - s58x0     : <-40 - 96>     80
                 - s78x0     : <-40 - 96>     80";
              type int32 {
                range "-55..125";
              }
            }
            leaf low {
              description
                "Lower threshold range in degree C
                 Device-specific range and default values:
                 - ie35xx    : <-40 - 96>      0
                 - ie3x00    : <-55 - 125>    -40
                 - ie31xx    : <-55 - 125>    -40
                 - ie9k      : <-40 - 96>      0
                 - s5200     : <-55 - 125>    -40
                 - s5800     : <-55 - 125>    -40
                 - s58x0     : <-40 - 96>      0
                 - s78x0     : <-40 - 96>      0";
              type int32 {
                range "-55..125";
              }
            }
            leaf notifies {
              description
                "Enable notification sent to server";
              type boolean;
              default "true";
            }
            leaf syslog {
              description
                "Enable system logger";
              type boolean;
              default "true";
            }
            container relay {
              description
                "Primary temperature information details";
              leaf major {
                description
                  "Associates the Primary temperature alarm to the relay.";
                type boolean;
                default "true";
              }
            }
          }
          container secondary {
            description
              "Secondary temperature alarm settings";
            leaf high {
              description
                "Higher threshold range in degree C
                 Device-specific range values:
                 - ie35xx    : <-40 - 96>
                 - ie3x00    : <-55 - 125>
                 - ie31xx    : <-55 - 125>
                 - ie9k      : <-40 - 96>
                 - s5200     : <-55 - 125>
                 - s5800     : <-55 - 125>
                 - s58x0     : <-40 - 96>
                 - s78x0     : <-40 - 96>";
              type int32 {
                range "-55..125";
              }
            }
            leaf low {
              description
                "Lower threshold range in degree C
                 Device-specific range values:
                 - ie35xx    : <-40 - 96>
                 - ie3x00    : <-55 - 125>
                 - ie31xx    : <-55 - 125>
                 - ie9k      : <-40 - 96>
                 - s5200     : <-55 - 125>
                 - s5800     : <-55 - 125>
                 - s58x0     : <-40 - 96>
                 - s78x0     : <-40 - 96>";
              type int32 {
                range "-55..125";
              }
            }
            leaf notifies {
              description
                "Enable notification sent to server";
              type empty;
            }
            leaf syslog {
              description
                "Enable system logger";
              type empty;
            }
            container relay {
              description
                "Secondary temperature information details";
              leaf major {
                description
                  "Associates the Secondary temperature alarm to the relay.";
                type empty;
              }
            }
          }
        }
        container input-alarm {
          description
            "Input alarm configuration";
          list alarm-id {
            key "input-alarm-id";
            leaf input-alarm-id {
              description
                "Alarm input-alarm number";
              type uint8 {
                range "1..4";
              }
            }
            leaf notifies {
              description
                "Enable notification sent to server";
              type empty;
            }
            leaf syslog {
              description
                "Enable system logger";
              type boolean;
              default "true";
            }
            container relay {
              description
                "Input alarm information details";
              leaf major {
                description
                  "Associates the Input alarm to the relay.";
                type empty;
              }
            }
          }
        }
        leaf fcs-hysteresis {
          description
            "FCS error threshold hysteresis";
          type uint8 {
            range "1..10";
          }
          default "10";
        }
      }
      container relay-mode {
        description
          "Configuration for alarm relay operation mode";
        leaf negative {
          description
            "When configured, relay is energized during normal operation
             and de-energized on alarm. When not configured (default),
             relay is de-energized during normal operation and
             energized on alarm.";
          type empty;
        }
      }
    }
  }

  augment "/ios:native" {
    uses alarm-grouping;
  }
}
