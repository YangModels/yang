module Cisco-IOS-XE-device-sensor-deviation {
  yang-version 1.1;
  namespace "http://cisco.com/ns/yang/Cisco-IOS-XE-device-sensor-deviation";
  prefix ios-ds-d;

  import Cisco-IOS-XE-device-sensor {
    prefix ios-ds;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Device Sensor Yang model.
     Copyright (c) 2016 by Cisco Systems, Inc.
     All rights reserved.";

  revision 2026-02-01 {
    description
      "- Adding device sensor ";
  }

  deviation "/ios:native/ios-ds:device-sensor/ios-ds:filter-list/ios-ds:lldp/ios-ds:list/ios-ds:tlv/ios-ds:number/ios-ds:tlv-nnumber/ios-ds:tlv-number" {
    deviate replace {
      type uint8 {
        range "1..126";
      }
    }
  }

  deviation "/ios:native/ios-ds:device-sensor/ios-ds:filter-list/ios-ds:mdns/ios-ds:list/ios-ds:tlv/ios-ds:name" {
    deviate add {
      must "not(((current() = 'pointer-records') and (1 = ../number)) or
                ((current() = 'text-records') and (2 = ../number)) or
                ((current() = 'srv-records') and (3 = ../number)) or
                ((current() = 'device-version') and (4 = ../number)))" {
        error-message "Element is already part of number leaf-list";
      }
    }
  }

  deviation "/ios:native/ios-ds:device-sensor/ios-ds:filter-list/ios-ds:mdns/ios-ds:list/ios-ds:tlv/ios-ds:number" {
    deviate add {
      must "not(((../name = 'pointer-records') and (1 = current())) or
                ((../name = 'text-records') and (2 = current())) or
                ((../name = 'srv-records') and (3 = current())) or
                ((../name = 'device-version') and (4 = current())))" {
        error-message "Element is already part of name leaf-list";
      }
    }
  }
}
