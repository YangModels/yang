module Cisco-IOS-XE-aws-common-cfg {
  yang-version 1.1;
  namespace "http://cisco.com/ns/yang/Cisco-IOS-XE-aws-common-cfg";
  prefix aws-common-cfg;

  import Cisco-IOS-XE-common-types {
    prefix common-types-ios-xe;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for AWS common configurational data.
     Copyright (c) 2023-2025 by Cisco Systems, Inc.
     All rights reserved.";

  revision 2026-02-01 {
    description
      "Amend secret key pattern to handle
       AES-encrypted values.";
    reference
      "1.1.0";
    cisco-semver:module-version "1.1.0";
  }
  revision 2025-07-01 {
    description
      "Initial revision";
    reference
      "1.0.0";
    cisco-semver:module-version "1.0.0";
  }

  typedef aws-vrf-name {
    type enumeration {
      enum aws-mgmt-vrf {
        value 0;
        description
          "Management VRF";
      }
      enum aws-global-vrf {
        value 1;
        description
          "Global VRF";
      }
    }
    description
      "AWS VRF type";
  }

  grouping aws-access-config {
    description
      "AWS access config data";
    leaf access-key-id {
      type string {
        length "0|16..128";
        pattern '[A-Z0-9]*';
      }
      must "string-length(current()) + string-length(../secret-access-key | '') <= 200" {
        error-message "sum of characters in access-key-id & secret-access-key must be equal to or less than 200";
      }
      default "";
      description
        "AWS access key ID";
    }
    leaf secret-access-key {
      type string {
        length "0|16..128";
        pattern "[\\] A-Za-z0-9!\"#%&()*+,\\-./:;<=>^?@\\\\$_`{|}\\[']*";
      }
      must "string-length(current()) + string-length(../access-key-id | '') <= 200" {
        error-message "sum of characters in access-key-id & secret-access-key must be equal to or less than 200";
      }
      default "";
      description
        "AWS secret access key. May be plaintext or encrypted.
         If plaintext, only alphanumeric characters, forward
         slash, plus and equals characters are allowed.";
    }
    leaf secret-access-key-type {
      type common-types-ios-xe:password-encryption-type;
      default "pw-encryption-clear";
      description
        "secret access key encryption type";
    }
  }

  grouping st-aws-proxy-config {
    description
      "AWS proxy config data";
    leaf http-url {
      type string {
        length "0..200";
        pattern '(((http)://[A-Za-z0-9@.:/?=%,&-]+)|(((([0-1]?[0-9]{1,2})|([2]?[0-5]{1,2})|([2]?[0-4][0-9]))[.]){3}(([0-1]?[0-9]{1,2})|([2]?[0-5]{1,2})|([2]?[0-4][1-9]))))*';
      }
      default "";
      description
        "HTTP URL";
    }
    leaf http-port {
      type uint16;
      default "0";
      description
        "HTTP Port";
    }
    leaf https-url {
      type string {
        length "0..200";
        pattern '(((https)://[A-Za-z0-9@.:/?=%,&-]+)|(((([0-1]?[0-9]{1,2})|([2]?[0-5]{1,2})|([2]?[0-4][0-9]))[.]){3}(([0-1]?[0-9]{1,2})|([2]?[0-5]{1,2})|([2]?[0-4][1-9]))))*';
      }
      default "";
      description
        "HTTPS URL";
    }
    leaf https-port {
      type uint16;
      default "0";
      description
        "HTTPS Port";
    }
  }
}
