submodule Cisco-IOS-XE-bgp-rpc {
  yang-version 1.1;
  belongs-to Cisco-IOS-XE-rpc {
    prefix ios-xe-rpc;
  }

  import cisco-semver {
    prefix cisco-semver;
  }
  import ietf-inet-types {
    prefix inet;
  }

  organization
    "Cisco Systems";
  contact
    "<mailto:cs-yang@cisco.com>";
  description
    "NED BGP RPC YANG module for IOS
     Copyright (c) 2016-2025 by Cisco Systems, Inc.
     All rights reserved.";

  revision 2026-02-01 {
    description
      "- Added support for clear ip bgp * soft";
    cisco-semver:module-version "1.2.0";
  }
  revision 2022-11-01 {
    description
      "- Update yang-version to 1.1";
    cisco-semver:module-version "1.1.0";
  }
  revision 2019-07-01 {
    description
      "Establish semantic version baseline";
    cisco-semver:module-version "1.0.0";
  }
  revision 2018-12-06 {
    description
      "created for NED RPC modularisation";
  }

  grouping clear-choice-ip-case-ip-protocol-bgp-case-grouping {
    container bgp {
      description
        "Clear BGP connections";
      status deprecated;
      leaf peer-address-drop-node-name {
        description
          "BGP neighbor address to clear";
        status deprecated;
        type union {
          type inet:ipv4-address;
          type inet:ipv6-address;
        }
      }
      leaf vrf {
        description
          "Select a VPN Routing/Forwarding instance";
        status deprecated;
        type string;
      }
      container bgp-peer-drop-node-name {
        description
          "BGP peer to clear";
        leaf neighbor-address-drop-node-name {
          description
            "BGP neighbor address to clear";
          type union {
            type inet:ipv4-address;
            type inet:ipv6-address;
            type string {
              pattern '\*';
            }
          }
        }
        container soft {
          description
            "Soft clear BGP peer";
          presence "Indicates that the soft leaf is present";
          container in {
            description
              "Soft clear inbound BGP peer";
            presence "Indicates that the in leaf is present";
            leaf prefix-filter {
              description
                "Soft clear inbound BGP peer with prefix filter";
              type empty;
            }
          }
          leaf out {
            description
              "Soft clear outbound BGP peer";
            type empty;
          }
          leaf slow {
            description
              "Soft clear BGP peer with slow mode";
            type empty;
          }
        }
      }
    }
  }
}
