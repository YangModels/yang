module Cisco-IOS-XE-isis-intf-oper {
  yang-version 1.1;
  namespace "http://cisco.com/ns/yang/Cisco-IOS-XE-isis-intf-oper";
  prefix isis-intf-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for ISIS intf operational data.
     Copyright (c) 2024-2025 by Cisco Systems, Inc.
     All rights reserved.";

  revision 2025-07-01 {
    description
      "Initial revision";
    reference
      "1.0.0";
    cisco-semver:module-version "1.0.0";
  }

  typedef isis-if-level-type {
    type enumeration {
      enum level-1 {
        value 0;
        description
          "Level 1 adjacency";
      }
      enum level-2 {
        value 1;
        description
          "Level 2 adjacency";
      }
    }
    description
      "Level of ISIS adjacency";
  }

  typedef isis-if-ckt-level-type {
    type enumeration {
      enum ckt-level-1 {
        value 0;
        description
          "Level 1 adjacency";
      }
      enum ckt-level-2 {
        value 1;
        description
          "Level 2 adjacency";
      }
      enum ckt-level-12 {
        value 2;
        description
          "Level 12 adjacency";
      }
    }
    description
      "Circuit type of ISIS adjacency";
  }

  typedef isis-if-nbr-state {
    type enumeration {
      enum adj-up {
        value 0;
        description
          "Adjacency is in UP state";
      }
      enum adj-down {
        value 1;
        description
          "Adjacency is in DOWN state";
      }
      enum adj-init {
        value 2;
        description
          "Adjacency is in INIT state";
      }
      enum adj-stdby {
        value 3;
        description
          "Adjacency is in STANDBY state";
      }
    }
    description
      "Current state of ISIS adjacency";
  }

  typedef isis-if-padding-state {
    type enumeration {
      enum padding-strict {
        value 0;
        description
          "Describes strict padding";
      }
      enum padding-loose {
        value 1;
        description
          "Describes loose padding";
      }
      enum padding-adaptive {
        value 2;
        description
          "Describes adaptive padding";
      }
      enum padding-disable {
        value 3;
        description
          "Hello padding disabled on the interface";
      }
    }
    description
      "Padding type on the interface";
  }

  typedef isis-if-circuit-type {
    type enumeration {
      enum ckt-p2p {
        value 0;
        description
          "Describes Point-to-point interface";
      }
      enum ckt-bcast {
        value 1;
        description
          "Describes Broadcast interface";
      }
    }
    description
      "Circuit type on the interface";
  }

  grouping isis-if-nbr-key {
    description
      "Compound key that identifies a unique neighbor within an ISIS tag";
    leaf system-id {
      type yang:phys-address;
      description
        "System ID of the neighbor";
    }
    leaf level {
      type isis-intf-ios-xe-oper:isis-if-level-type;
      description
        "Level of the adjacency formed";
    }
    leaf if-name {
      type string;
      description
        "Interface name on which adjacency is formed";
    }
  }

  grouping isis-if-nbr-rec {
    description
      "Details of the adjacency formed";
    leaf nbr-ipv4-addr {
      type inet:ip-address;
      description
        "IPv4 Address of the neighbor";
    }
    leaf nbr-ipv6-addr {
      type inet:ipv6-address;
      description
        "IPv6 Address of the neighbor";
    }
    leaf adj-state {
      type isis-intf-ios-xe-oper:isis-if-nbr-state;
      description
        "Current state of the adjacency";
    }
    leaf nbr-snpa {
      type yang:mac-address;
      description
        "ISIS Neighbor sub-network point of attachment";
    }
    leaf local-ext-ckt-id {
      type uint32;
      description
        "Local extended circuit ID";
    }
    leaf nbr-ext-ckt-id {
      type uint32;
      description
        "Neighbor extended circuit ID";
    }
    leaf pri {
      type uint8;
      description
        "Priority of the neighboring IS";
    }
    leaf dis-system-id {
      type string;
      description
        "Designated intermediate system id";
    }
    leaf nbr-ckt-type {
      type isis-intf-ios-xe-oper:isis-if-ckt-level-type;
      description
        "Received ISIS circuit type";
    }
    leaf adj-type {
      type isis-intf-ios-xe-oper:isis-if-ckt-level-type;
      description
        "Formed ISIS adjacency type";
    }
    leaf up-time {
      type yang:date-and-time;
      description
        "Time at which adjacency transitioned into UP state";
    }
    leaf restart-support {
      type boolean;
      description
        "When set to true, ISIS graceful restart is supported";
    }
    leaf restart-status {
      type boolean;
      description
        "When set to true, neighbor is being helped";
    }
    leaf-list nlpid {
      type uint8;
      ordered-by user;
      description
        "Supported protocol, as per TLV 129";
    }
    leaf multi-topo {
      type boolean;
      description
        "When set to true, ISIS multi-topology is supported";
    }
    leaf-list topo {
      type uint32;
      ordered-by user;
      description
        "List of ISIS multi-topology IDs supported
             MT ID 0: Equivalent to the standard topology
             MT ID 1: IPv4 in-band management purposes
             MT ID 2: IPv6 routing topology
             MT ID 3: IPv4 multicast routing topology
             MT ID 4: IPv6 multicast routing topology
             MT ID 5: IPv6 in-band management purposes
             MT ID 6-3995: Reserved for IETF consensus";
    }
    leaf-list area-addr {
      type yang:phys-address;
      ordered-by user;
      description
        "List of ISIS area addresses";
    }
  }

  grouping isis-if-state {
    description
      "List of interfaces for a specific tag";
    leaf if-name {
      type string;
      description
        "Interface name";
    }
    leaf is-enabled {
      type boolean;
      description
        "Is the interface enabled for ISIS";
    }
    leaf is-passive {
      type boolean;
      description
        "Is the interface passive";
    }
    leaf hello-padding {
      type isis-intf-ios-xe-oper:isis-if-padding-state;
      description
        "Defines hello-padding type on this interface";
    }
    leaf circuit-type {
      type isis-intf-ios-xe-oper:isis-if-circuit-type;
      description
        "Defines ISIS interface type";
    }
  }

  grouping isis-if-tag-type {
    description
      "Each entry contains tag information of single IS-IS instance";
    leaf tag {
      type string;
      description
        "IS-IS router tag";
    }
    list isis-if {
      key "if-name";
      description
        "List of interfaces for a specific tag";
      uses isis-intf-ios-xe-oper:isis-if-state;
    }
    list isis-if-nbr {
      key "system-id level if-name";
      description
        "List of neighbors for a specific tag";
      uses isis-intf-ios-xe-oper:isis-if-nbr-rec;
      uses isis-intf-ios-xe-oper:isis-if-nbr-key;
    }
  }

  container isis-intf-oper-data {
    config false;
    description
      "Operational state of the IS-IS interface subsystem";
    list isis-if-tag-type {
      key "tag";
      description
        "List of ISIS routers";
      uses isis-intf-ios-xe-oper:isis-if-tag-type;
    }
  }
}
