module Cisco-IOS-XE-isdn {
  yang-version 1.1;
  namespace "http://cisco.com/ns/yang/Cisco-IOS-XE-isdn";
  prefix ios-isdn;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native ISDN Yang model.
     Copyright (c) 2019-2020 by Cisco Systems, Inc.
     All rights reserved.";

  revision 2022-11-01 {
    description
      "- Update yang-version to 1.1";
    cisco-semver:module-version "1.2.0";
  }
  revision 2021-03-01 {
    description
      "- Added isdn map address CLI
       - Added isdn outgoing ie CLI";
    cisco-semver:module-version "1.1.0";
  }
  revision 2020-07-01 {
    description
      "Initial revision";
    cisco-semver:module-version "1.0.0";
  }

  grouping config-isdn-global-cli-grouping {
    container isdn {
      description
        "ISDN configuration commands";
      leaf logging {
        description
          "Enable logging for some isdn events";
        type empty;
      }
      leaf switch-type {
        description
          "Select the ISDN switch type";
        type enumeration {
          enum none;
          enum primary-4ess;
          enum primary-5ess;
          enum primary-dms100;
          enum primary-net5;
          enum primary-ni;
          enum primary-ntt;
          enum primary-qsig;
        }
      }
    }
  }

  grouping config-isdn-interface-cli-grouping {
    container trunk-group {
      description
        "Configure interface to be in a trunk group";
      leaf trunk-group-label {
        description
          "Trunk group label";
        type string {
          length "1..64";
        }
      }
      leaf trunk-group-preference {
        description
          "trunk group preference value";
        type uint8 {
          range "1..64";
        }
      }
    }
    container isdn {
      description
        "ISDN Interface configuration commands";
      container switch-type {
        description
          "Select the Interface ISDN switch type";
        leaf switch-type-pri {
          when '/ios:native/ios:interface/ios:Serial';
          type enumeration {
            enum primary-4ess;
            enum primary-5ess;
            enum primary-dms100;
            enum primary-net5;
            enum primary-ni;
            enum primary-ntt;
            enum primary-qsig;
          }
        }
      }
      container incoming-voice {
        description
          "Specify options for incoming calls";
        choice call-type {
          leaf data {
            description
              "Incoming voice calls will be handled as modem data";
            type empty;
          }
          leaf modem {
            description
              "Incoming voice calls will be handled as modem";
            type empty;
          }
          leaf voice {
            description
              "Incoming voice calls will be handled as voice";
            type empty;
          }
        }
        leaf b-channel-bw {
          description
            "B channel bandwidth";
          when '../data or ../modem';
          type enumeration {
            enum 56;
            enum 64;
          }
        }
      }
      leaf protocol-emulate {
        description
          "Protocol (L2/L3) emulation network/user side";
        type enumeration {
          enum network;
          enum user;
        }
        default "user";
      }
      container timer {
        description
          "Specify ISDN Timer values to be changed";
        leaf T200 {
          description
            "Specify Timer T200 in milliseconds";
          type uint32 {
            range "400..400000";
          }
          default "1000";
        }
        leaf T203 {
          description
            "Specify Timer T203 in milliseconds";
          type uint32 {
            range "400..400000";
          }
        }
        leaf T301 {
          description
            "Specify Timer T301 in milliseconds";
          type uint32 {
            range "180000..86400000";
          }
        }
        leaf T303 {
          description
            "Specify Timer T303 in milliseconds";
          type uint32 {
            range "400..86400000";
          }
        }
        leaf T306 {
          description
            "Specify Timer T306 in milliseconds";
          type uint32 {
            range "400..86400000";
          }
          default "30000";
        }
        leaf T309 {
          description
            "Specify Timer T309 in milliseconds";
          type uint32 {
            range "0..86400000";
          }
        }
        leaf T310 {
          description
            "Specify Timer T310 in milliseconds";
          type uint32 {
            range "400..400000";
          }
        }
        leaf T321 {
          description
            "Specify Timer T321 in milliseconds";
          type uint32 {
            range "0..86400000";
          }
        }
      }
      container map {
        description
          "Specify E.164 address to numbering plan and type mapping";
        container address {
          description
            "Map an ISDN address";
          list plan-type {
            description
              "ISDN map address plan and type";
            max-elements 30;
            key "id";
            leaf id {
              description
                "ISDN map string";
              type string {
                pattern '.*';
                length "1..20";
              }
            }
            leaf plan {
              description
                "Set address numbering plan";
              type enumeration {
                enum data;
                enum isdn;
                enum national;
                enum privacy;
                enum reserved/10;
                enum reserved/11;
                enum reserved/12;
                enum reserved/13;
                enum reserved/14;
                enum reserved/2;
                enum reserved/5;
                enum reserved/6;
                enum reserved/7;
                enum telex;
                enum unknown;
              }
            }
            leaf type {
              description
                "Set address number type";
              type enumeration {
                enum abbreviated;
                enum international;
                enum national;
                enum network;
                enum reserved/5;
                enum subscriber;
                enum unknown;
              }
            }
          }
        }
      }
      container outgoing {
        description
          "Options for outgoing IEs and messages";
        list ie {
          description
            "Information Elements";
          key "id";
          leaf id {
            description
              "Information element type";
            type enumeration {
              enum called-number;
              enum called-subaddr;
              enum caller-number;
              enum caller-subaddr;
              enum connected-number;
              enum connected-subaddr;
              enum display;
              enum extended-facility;
              enum facility;
              enum high-layer-compat;
              enum low-layer-compat;
              enum network-facility;
              enum notify-indicator;
              enum progress-indicator;
              enum redirecting-number;
              enum user-user;
            }
          }
        }
      }
    }
  }

  augment "/ios:native/ios:interface/ios:Serial" {
    uses config-isdn-interface-cli-grouping;
  }

  augment "/ios:native" {
    uses config-isdn-global-cli-grouping;
  }
}
