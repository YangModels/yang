module Cisco-IOS-XE-device-sensor {
  yang-version 1.1;
  namespace "http://cisco.com/ns/yang/Cisco-IOS-XE-device-sensor";
  prefix ios-ds;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Device Sensor Yang model.
     Copyright (c) 2016 by Cisco Systems, Inc.
     All rights reserved.";

  revision 2026-02-01 {
    description
      "- Adding device sensor
       - Adding device sensor mdns tlv name options
       - filter spec fix for cdp, lldp, dhcp and dhcpv6
       - Reducing filter list xpath for cdp, lldp, dhcp and dhcpv6
       - Adding device-sensor dhcpv6-snooping per interface configuration";
    cisco-semver:module-version "1.4.0";
  }
  revision 2024-03-01 {
    description
      "- Adding device sensor mdns configuration commands
       - Adding dhcpv6 options";
    cisco-semver:module-version "1.3.0";
  }
  revision 2022-11-01 {
    description
      "- Update yang-version to 1.1";
    cisco-semver:module-version "1.2.0";
  }
  revision 2021-11-01 {
    description
      "- Adding device sensor configuration commands
       - Add internal semantic version";
    cisco-semver:module-version "1.1.0";
  }
  revision 2019-07-01 {
    description
      "Establish semantic version baseline";
    cisco-semver:module-version "1.0.0";
  }
  revision 2017-02-07 {
    description
      "Initial revision";
  }

  grouping filter-spec-inc-exc-deprecate-grouping {
    container exclude {
      status deprecated;
      description
        "Exclude Filter";
      list list {
        status deprecated;
        description
          "Protocol Filter Spec list";
        key "name";
        leaf name {
          status deprecated;
          type string;
        }
      }
      leaf all {
        description
          "All";
        status deprecated;
        type empty;
      }
    }
    container include {
      description
        "Include Filter";
      status deprecated;
      list list {
        description
          "Protocol Filter Spec list";
        status deprecated;
        key "name";
        leaf name {
          status deprecated;
          type string;
        }
      }
    }
  }

  grouping cdp-filter-list-grouping {
    container tlv {
      description
        "tlv types list";
      leaf-list name-list {
        description
          "tlv type names";
        type enumeration {
          enum address-type {
            value 1;
            description
              "Address Type";
          }
          enum capabilities-type {
            value 2;
            description
              "Capabilities Type";
          }
          enum cos-type {
            value 3;
            description
              "COS Type";
          }
          enum device-name {
            value 4;
            description
              "Device Name";
          }
          enum duplex-type {
            value 5;
            description
              "Duplex Type";
          }
          enum external-port-id-type {
            value 6;
            description
              "External Port Id Type";
          }
          enum ipprefix-type {
            value 7;
            description
              "IP Prefix Type";
          }
          enum mgmt-address-type {
            value 8;
            description
              "Management Address Type";
          }
          enum mtu-type {
            value 9;
            description
              "MTU Type";
          }
          enum native-vlan-type {
            value 10;
            description
              "Native VLAN Type";
          }
          enum platform-type {
            value 11;
            description
              "Platform Type";
          }
          enum port-id-type {
            value 12;
            description
              "Port Id type";
          }
          enum power-available-type {
            value 13;
            description
              "Power Available Type";
          }
          enum power-request-type {
            value 14;
            description
              "External Port Id Type";
          }
          enum power-type {
            value 15;
            description
              "Power Type";
          }
          enum protocol-hello-type {
            value 16;
            description
              "Protocol Hello Type";
          }
          enum trigger-type {
            value 17;
            description
              "Trigger Type";
          }
          enum trust-type {
            value 18;
            description
              "Trust Type";
          }
          enum twoway-connectivity-type {
            value 19;
            description
              "Twoway Connectivity Type";
          }
          enum unidirectional-mode-type {
            value 20;
            description
              "Unidirectional Mode Type";
          }
          enum version-type {
            value 21;
            description
              "Version Type";
          }
          enum vtp-mgmt-domain-type {
            value 22;
            description
              "VTP Management Domain Type";
          }
          enum vvid-type {
            value 23;
            description
              "VVID Type";
          }
        }
      }
      container name {
        status deprecated;
        description
          "tlv names";
        leaf address-type {
          status deprecated;
          description
            "Address Type";
          type empty;
        }
        leaf capabilities-type {
          status deprecated;
          description
            "Capabilities Type";
          type empty;
        }
        leaf cos-type {
          status deprecated;
          description
            "COS Type";
          type empty;
        }
        leaf device-name {
          status deprecated;
          description
            "Device Name";
          type empty;
        }
        leaf duplex-type {
          status deprecated;
          description
            "Duplex Type";
          type empty;
        }
        leaf external-port-id-type {
          status deprecated;
          description
            "External Port Id Type";
          type empty;
        }
        leaf ipprefix-type {
          status deprecated;
          description
            "IP Prefix Type";
          type empty;
        }
        leaf mgmt-address-type {
          status deprecated;
          description
            "Management Address Type";
          type empty;
        }
        leaf mtu-type {
          status deprecated;
          description
            "MTU Type";
          type empty;
        }
        leaf native-vlan-type {
          status deprecated;
          description
            "Native VLAN Type";
          type empty;
        }
        leaf platform-type {
          status deprecated;
          description
            "Platform Type";
          type empty;
        }
        leaf port-id-type {
          status deprecated;
          description
            "Port Id type";
          type empty;
        }
        leaf power-available-type {
          status deprecated;
          description
            "Power Available Type";
          type empty;
        }
        leaf power-request-type {
          status deprecated;
          description
            "External Port Id Type";
          type empty;
        }
        leaf power-type {
          status deprecated;
          description
            "Power Type";
          type empty;
        }
        leaf protocol-hello-type {
          status deprecated;
          description
            "Protocol Hello Type";
          type empty;
        }
        leaf trigger-type {
          status deprecated;
          description
            "Trigger Type";
          type empty;
        }
        leaf trust-type {
          status deprecated;
          description
            "Trust Type";
          type empty;
        }
        leaf twoway-connectivity-type {
          status deprecated;
          description
            "Twoway Connectivity Type";
          type empty;
        }
        leaf unidirectional-mode-type {
          status deprecated;
          description
            "Unidirectional Mode Type";
          type empty;
        }
        leaf version-type {
          status deprecated;
          description
            "Version Type";
          type empty;
        }
        leaf vtp-mgmt-domain-type {
          status deprecated;
          description
            "VTP Management Domain Type";
          type empty;
        }
        leaf vvid-type {
          status deprecated;
          description
            "VVID Type";
          type empty;
        }
      }
      container number {
        description
          "tlv type numbers";
        list tlv-number {
          key "tlv-number";
          leaf tlv-number {
            description
              "TLV Type Number";
            type uint16 {
              range "1..65535";
            }
          }
        }
      }
    }
  }

  grouping lldp-filter-list-grouping {
    container tlv {
      description
        "tlv types list";
      leaf-list name-list {
        description
          "tlv type names";
        type enumeration {
          enum chassis-id {
            value 1;
            description
              "Chassis Id";
          }
          enum end-of-lldpdu {
            value 2;
            description
              "End Of LLDP";
          }
          enum management-address {
            value 3;
            description
              "Management Address";
          }
          enum port-description {
            value 4;
            description
              "Port Description";
          }
          enum port-id {
            value 5;
            description
              "Port Id";
          }
          enum system-capabilities {
            value 6;
            description
              "System Capabilities";
          }
          enum system-description {
            value 7;
            description
              "System Description";
          }
          enum system-name {
            value 8;
            description
              "System Name";
          }
          enum time-to-live {
            value 9;
            description
              "Time To Live";
          }
        }
      }
      container name {
        status deprecated;
        description
          "tlv names";
        leaf chassis-id {
          status deprecated;
          description
            "Chassis Id";
          type empty;
        }
        leaf end-of-lldpdu {
          status deprecated;
          description
            "End Of LLDP";
          type empty;
        }
        leaf management-address {
          status deprecated;
          description
            "Management Address";
          type empty;
        }
        leaf port-description {
          status deprecated;
          description
            "Port Description";
          type empty;
        }
        leaf port-id {
          status deprecated;
          description
            "Port Id";
          type empty;
        }
        leaf system-capabilities {
          status deprecated;
          description
            "System Capabilities";
          type empty;
        }
        leaf system-description {
          status deprecated;
          description
            "System Description";
          type empty;
        }
        leaf system-name {
          status deprecated;
          description
            "System Name";
          type empty;
        }
        leaf time-to-live {
          status deprecated;
          description
            "Time To Live";
          type empty;
        }
      }
      container number {
        description
          "tlv type numbers";
        list tlv-nnumber {
          key "tlv-number";
          leaf tlv-number {
            description
              "LLDP Type Number";
            type uint8 {
              range "0..127";
            }
          }
        }
      }
    }
  }

  grouping dhcp-filter-list-grouping {
    container option {
      description
        "option types list";
      leaf-list name-list {
        description
          "option type names";
        type enumeration {
          enum all-subnets-local {
            value 1;
            description
              "All Subnets Local";
          }
          enum arp-cache-timeout {
            value 2;
            description
              "ARP Cache Timeout";
          }
          enum authentication {
            value 3;
            description
              "Authentication";
          }
          enum auto-configure {
            value 4;
            description
              "Autoconfiguration";
          }
          enum bcmcs-servers-a {
            value 5;
            description
              "BCMCS Controller IPv4 address list";
          }
          enum bcmcs-servers-d {
            value 6;
            description
              "BCMCS Controller Domain Name list";
          }
          enum boot-file {
            value 7;
            description
              "Boot File Name";
          }
          enum boot-size {
            value 8;
            description
              "Boot Size";
          }
          enum broadcast-address {
            value 9;
            description
              "Broadcast Address";
          }
          enum cablelabs-client-configuration {
            value 10;
            description
              "Cable labs Client Configuration";
          }
          enum cisco-auto-configure {
            value 11;
            description
              "Cisco Autoconfiguration";
          }
          enum cisco-client-last-transaction-time {
            value 12;
            description
              "Cisco Client Last Transaction Time";
          }
          enum cisco-client-requested-host-name {
            value 13;
            description
              "Cisco Client Requested Host Name";
          }
          enum cisco-leased-ip {
            value 14;
            description
              "Cisco Leased IP";
          }
          enum cisco-vpn-id {
            value 15;
            description
              "Cisco VPN Identifier";
          }
          enum class-identifier {
            value 16;
            description
              "Class Identifier";
          }
          enum classless-static-route {
            value 17;
            description
              "Classless Static Route";
          }
          enum client-fqdn {
            value 18;
            description
              "Client FQDN";
          }
          enum client-identifier {
            value 19;
            description
              "Client Identifier";
          }
          enum cookie-servers {
            value 20;
            description
              "Cookie Servers";
          }
          enum default-ip-ttl {
            value 21;
            description
              "Default IP Time To Live";
          }
          enum default-tcp-ttl {
            value 22;
            description
              "Default TCP Time To Live";
          }
          enum domain-name {
            value 23;
            description
              "Domain Name";
          }
          enum domain-name-servers {
            value 24;
            description
              "Domain Name Servers";
          }
          enum domain-search {
            value 25;
            description
              "Domain Search";
          }
          enum ethernet-encapsulation {
            value 26;
            description
              "IEEE 802.3 Encapsulation";
          }
          enum extensions-path {
            value 27;
            description
              "Extensions Path";
          }
          enum finger-servers {
            value 28;
            description
              "Finger Server";
          }
          enum font-servers {
            value 29;
            description
              "X Window Font";
          }
          enum geo-conf {
            value 30;
            description
              "Geo Conf Option";
          }
          enum geo-conf-civic {
            value 31;
            description
              "Geo conf Civic";
          }
          enum host-name {
            value 32;
            description
              "Host Name";
          }
          enum i-sns {
            value 33;
            description
              "Internet Storage Name Service";
          }
          enum impress-servers {
            value 34;
            description
              "Impress Servers";
          }
          enum initial-url {
            value 35;
            description
              "Initial URL";
          }
          enum interface-mtu {
            value 36;
            description
              "Interface MTU";
          }
          enum ip-forwarding {
            value 37;
            description
              "IP Forwarding";
          }
          enum irc-servers {
            value 38;
            description
              "IRC Server";
          }
          enum ldap-url {
            value 39;
            description
              "LDAP URL";
          }
          enum lease-time {
            value 40;
            description
              "Address Time";
          }
          enum log-servers {
            value 41;
            description
              "Log Servers";
          }
          enum lpr-servers {
            value 42;
            description
              "LPR Servers";
          }
          enum lq-associated-ip {
            value 43;
            description
              "Lease Query Associated IPs";
          }
          enum lq-client-last-transaction-time {
            value 44;
            description
              "Lease Query Client last transaction time";
          }
          enum mask-supplier {
            value 45;
            description
              "Mask Supplier";
          }
          enum max-dgram-reassembly {
            value 46;
            description
              "Maximum Datagram Reassembly";
          }
          enum max-message-size {
            value 47;
            description
              "Maximum Message Size";
          }
          enum mcns-security-server {
            value 48;
            description
              "MCNS Security Server";
          }
          enum merit-dump {
            value 49;
            description
              "Merit Dump";
          }
          enum message {
            value 50;
            description
              "Message";
          }
          enum mobile-ip-home-agents {
            value 51;
            description
              "Mobile IP Home Agent";
          }
          enum name-servers {
            value 52;
            description
              "Name Servers";
          }
          enum name-service-search {
            value 53;
            description
              "Name Service Search";
          }
          enum nds-context {
            value 54;
            description
              "NDS Context";
          }
          enum nds-servers {
            value 55;
            description
              "NDS Servers";
          }
          enum nds-tree {
            value 56;
            description
              "NDS Tree Name";
          }
          enum netbios-dd-servers {
            value 57;
            description
              "NetBIOS Distribution Servers";
          }
          enum netbios-name-servers {
            value 58;
            description
              "NetBIOS Name Servers";
          }
          enum netbios-node-type {
            value 59;
            description
              "NetBIOS Node Type";
          }
          enum netbios-scope {
            value 60;
            description
              "NetBIOS Scope";
          }
          enum netinfo-parent-server-address {
            value 61;
            description
              "Netinfo Parent Server Address";
          }
          enum netinfo-parent-server-tag {
            value 62;
            description
              "Netinfo Parent Server Tag";
          }
          enum netware-ip-domain {
            value 63;
            description
              "Netware/IP Domain";
          }
          enum netware-ip-information {
            value 64;
            description
              "Netware/IP Option";
          }
          enum nis-domain {
            value 65;
            description
              "NIS Domain";
          }
          enum nis-plus-domain {
            value 66;
            description
              "NIS Domain Name";
          }
          enum nis-plus-servers {
            value 67;
            description
              "NIS Server Address";
          }
          enum nis-servers {
            value 68;
            description
              "NIS Servers";
          }
          enum nntp-servers {
            value 69;
            description
              "NNTP Server";
          }
          enum non-local-source-routing {
            value 70;
            description
              "Non Local Source Routing";
          }
          enum ntp-servers {
            value 71;
            description
              "NTP Servers";
          }
          enum option-overload {
            value 72;
            description
              "Options Overload";
          }
          enum parameter-request-list {
            value 73;
            description
              "Parameter List";
          }
          enum path-mtu-aging-timeout {
            value 74;
            description
              "Path MTU Aging Timeout";
          }
          enum path-mtu-plateau-tables {
            value 75;
            description
              "Path MTU Plateau Tables";
          }
          enum perform-mask-discovery {
            value 76;
            description
              "Perform Mask Discovery";
          }
          enum policy-filters {
            value 77;
            description
              "Policy Filters";
          }
          enum pop3-servers {
            value 78;
            description
              "POP3 Server";
          }
          enum pxe-client-arch {
            value 79;
            description
              "PXE Client Architecture";
          }
          enum pxe-client-machine-id {
            value 80;
            description
              "PXE Client Machine ID";
          }
          enum pxe-client-network-id {
            value 81;
            description
              "PXE Client Network ID";
          }
          enum rapid-commit {
            value 82;
            description
              "Rapid Commit";
          }
          enum rebinding-time {
            value 83;
            description
              "Rebinding Time";
          }
          enum relay-agent-info {
            value 84;
            description
              "Relay Agent information";
          }
          enum renewal-time {
            value 85;
            description
              "Renewing Time";
          }
          enum requested-address {
            value 86;
            description
              "Address Request";
          }
          enum resource-location-servers {
            value 87;
            description
              "Resource Location Servers";
          }
          enum root-path {
            value 88;
            description
              "Root Path";
          }
          enum router-discovery {
            value 89;
            description
              "Router Discovery";
          }
          enum router-solicitation-address {
            value 90;
            description
              "Router Solicitation Address";
          }
          enum routers {
            value 91;
            description
              "Routers";
          }
          enum server-identifier {
            value 92;
            description
              "Server ID";
          }
          enum sip-servers {
            value 93;
            description
              "SIP Servers";
          }
          enum slp-directory-agent {
            value 94;
            description
              "Service Location Protocol Directory Agent";
          }
          enum slp-service-scope {
            value 95;
            description
              "SLP Service Scope";
          }
          enum smtp-servers {
            value 96;
            description
              "SMTP Server";
          }
          enum static-routes {
            value 97;
            description
              "Static Routes";
          }
          enum streettalk-directory-assistance-servers {
            value 98;
            description
              "STDA Server";
          }
          enum streettalk-servers {
            value 99;
            description
              "StreetTalk Server";
          }
          enum subnet-alloc {
            value 100;
            description
              "Subnet Allocation";
          }
          enum subnet-mask {
            value 101;
            description
              "Subnet Mask";
          }
          enum subnet-selection {
            value 102;
            description
              "Subnet Selection";
          }
          enum swap-server {
            value 103;
            description
              "Swap Server";
          }
          enum tcp-keepalive-garbage {
            value 104;
            description
              "TCP Keepalive Garbage";
          }
          enum tcp-keepalive-interval {
            value 105;
            description
              "TCP Keepalive Interval";
          }
          enum tftp-server {
            value 106;
            description
              "TFTP Server Name";
          }
          enum time-offset {
            value 107;
            description
              "Time Offset";
          }
          enum time-servers {
            value 108;
            description
              "Time Servers";
          }
          enum trailer-encapsulation {
            value 109;
            description
              "Trailer Encapsulation";
          }
          enum user-auth {
            value 110;
            description
              "User Authentication";
          }
          enum user-class-id {
            value 111;
            description
              "User Class ID";
          }
          enum v-i-vendor-class {
            value 112;
            description
              "Vendor Identifying Vendor Class";
          }
          enum v-i-vendor-opts {
            value 113;
            description
              "Vendor Identifying Vendor-Specific Options";
          }
          enum vendor-encapsulated-options {
            value 114;
            description
              "Vendor Encapsulated Options";
          }
          enum vpn-id {
            value 115;
            description
              "VPN Identifier";
          }
          enum www-servers {
            value 116;
            description
              "WWW Server";
          }
          enum x-display-managers {
            value 117;
            description
              "X Window Managers";
          }
        }
      }
      container name {
        status deprecated;
        description
          "option names";
        leaf all-subnets-local {
          status deprecated;
          description
            "All Subnets Local";
          type empty;
        }
        leaf arp-cache-timeout {
          status deprecated;
          description
            "ARP Cache Timeout";
          type empty;
        }
        leaf authentication {
          status deprecated;
          description
            "Authentication";
          type empty;
        }
        leaf auto-configure {
          status deprecated;
          description
            "Autoconfiguration";
          type empty;
        }
        leaf bcmcs-servers-a {
          status deprecated;
          description
            "BCMCS Controller IPv4 address list";
          type empty;
        }
        leaf bcmcs-servers-d {
          status deprecated;
          description
            "BCMCS Controller Domain Name list";
          type empty;
        }
        leaf boot-file {
          status deprecated;
          description
            "Boot File Name";
          type empty;
        }
        leaf boot-size {
          status deprecated;
          description
            "Boot Size";
          type empty;
        }
        leaf broadcast-address {
          status deprecated;
          description
            "Broadcast Address";
          type empty;
        }
        leaf cablelabs-client-configuration {
          status deprecated;
          description
            "Cable labs Client Configuration";
          type empty;
        }
        leaf cisco-auto-configure {
          status deprecated;
          description
            "Cisco Autoconfiguration";
          type empty;
        }
        leaf cisco-client-last-transaction-time {
          status deprecated;
          description
            "Cisco Client Last Transaction Time";
          type empty;
        }
        leaf cisco-client-requested-host-name {
          status deprecated;
          description
            "Cisco Client Requested Host Name";
          type empty;
        }
        leaf cisco-leased-ip {
          status deprecated;
          description
            "Cisco Leased IP";
          type empty;
        }
        leaf cisco-vpn-id {
          status deprecated;
          description
            "Cisco VPN Identifier";
          type empty;
        }
        leaf class-identifier {
          status deprecated;
          description
            "Class Identifier";
          type empty;
        }
        leaf classless-static-route {
          status deprecated;
          description
            "Classless Static Route";
          type empty;
        }
        leaf client-fqdn {
          status deprecated;
          description
            "Client FQDN";
          type empty;
        }
        leaf client-identifier {
          status deprecated;
          description
            "Client Identifier";
          type empty;
        }
        leaf cookie-servers {
          status deprecated;
          description
            "Cookie Servers";
          type empty;
        }
        leaf default-ip-ttl {
          status deprecated;
          description
            "Default IP Time To Live";
          type empty;
        }
        leaf default-tcp-ttl {
          status deprecated;
          description
            "Default TCP Time To Live";
          type empty;
        }
        leaf domain-name {
          status deprecated;
          description
            "Domain Name";
          type empty;
        }
        leaf domain-name-servers {
          status deprecated;
          description
            "Domain Name Servers";
          type empty;
        }
        leaf domain-search {
          status deprecated;
          description
            "Domain Search";
          type empty;
        }
        leaf ethernet-encapsulation {
          status deprecated;
          description
            "IEEE 802.3 Encapsulation";
          type empty;
        }
        leaf extensions-path {
          status deprecated;
          description
            "Extensions Path";
          type empty;
        }
        leaf finger-servers {
          status deprecated;
          description
            "Finger Server";
          type empty;
        }
        leaf font-servers {
          status deprecated;
          description
            "X Window Font";
          type empty;
        }
        leaf geo-conf {
          status deprecated;
          description
            "Geo Conf Option";
          type empty;
        }
        leaf geo-conf-civic {
          status deprecated;
          description
            "Geo conf Civic";
          type empty;
        }
        leaf host-name {
          status deprecated;
          description
            "Host Name";
          type empty;
        }
        leaf i-sns {
          status deprecated;
          description
            "Internet Storage Name Service";
          type empty;
        }
        leaf impress-servers {
          status deprecated;
          description
            "Impress Servers";
          type empty;
        }
        leaf initial-url {
          status deprecated;
          description
            "Initial URL";
          type empty;
        }
        leaf interface-mtu {
          status deprecated;
          description
            "Interface MTU";
          type empty;
        }
        leaf ip-forwarding {
          status deprecated;
          description
            "IP Forwarding";
          type empty;
        }
        leaf irc-servers {
          status deprecated;
          description
            "IRC Server";
          type empty;
        }
        leaf ldap-url {
          status deprecated;
          description
            "LDAP URL";
          type empty;
        }
        leaf lease-time {
          status deprecated;
          description
            "Address Time";
          type empty;
        }
        leaf log-servers {
          status deprecated;
          description
            "Log Servers";
          type empty;
        }
        leaf lpr-servers {
          status deprecated;
          description
            "LPR Servers";
          type empty;
        }
        leaf lq-associated-ip {
          status deprecated;
          description
            "Lease Query Associated IPs";
          type empty;
        }
        leaf lq-client-last-transaction-time {
          status deprecated;
          description
            "Lease Query Client last transaction time";
          type empty;
        }
        leaf mask-supplier {
          status deprecated;
          description
            "Mask Supplier";
          type empty;
        }
        leaf max-dgram-reassembly {
          status deprecated;
          description
            "Maximum Datagram Reassembly";
          type empty;
        }
        leaf max-message-size {
          status deprecated;
          description
            "Maximum Message Size";
          type empty;
        }
        leaf mcns-security-server {
          status deprecated;
          description
            "MCNS Security Server";
          type empty;
        }
        leaf merit-dump {
          status deprecated;
          description
            "Merit Dump";
          type empty;
        }
        leaf message {
          status deprecated;
          description
            "Message";
          type empty;
        }
        leaf mobile-ip-home-agents {
          status deprecated;
          description
            "Mobile IP Home Agent";
          type empty;
        }
        leaf name-servers {
          status deprecated;
          description
            "Name Servers";
          type empty;
        }
        leaf name-service-search {
          status deprecated;
          description
            "Name Service Search";
          type empty;
        }
        leaf nds-context {
          status deprecated;
          description
            "NDS Context";
          type empty;
        }
        leaf nds-servers {
          status deprecated;
          description
            "NDS Servers";
          type empty;
        }
        leaf nds-tree {
          status deprecated;
          description
            "NDS Tree Name";
          type empty;
        }
        leaf netbios-dd-servers {
          status deprecated;
          description
            "NetBIOS Distribution Servers";
          type empty;
        }
        leaf netbios-name-servers {
          status deprecated;
          description
            "NetBIOS Name Servers";
          type empty;
        }
        leaf netbios-node-type {
          status deprecated;
          description
            "NetBIOS Node Type";
          type empty;
        }
        leaf netbios-scope {
          status deprecated;
          description
            "NetBIOS Scope";
          type empty;
        }
        leaf netinfo-parent-server-address {
          status deprecated;
          description
            "Netinfo Parent Server Address";
          type empty;
        }
        leaf netinfo-parent-server-tag {
          status deprecated;
          description
            "Netinfo Parent Server Tag";
          type empty;
        }
        leaf netware-ip-domain {
          status deprecated;
          description
            "Netware/IP Domain";
          type empty;
        }
        leaf netware-ip-information {
          status deprecated;
          description
            "Netware/IP Option";
          type empty;
        }
        leaf nis-domain {
          status deprecated;
          description
            "NIS Domain";
          type empty;
        }
        leaf nis-plus-domain {
          status deprecated;
          description
            "NIS Domain Name";
          type empty;
        }
        leaf nis-plus-servers {
          status deprecated;
          description
            "NIS Server Address";
          type empty;
        }
        leaf nis-servers {
          status deprecated;
          description
            "NIS Servers";
          type empty;
        }
        leaf nntp-servers {
          status deprecated;
          description
            "NNTP Server";
          type empty;
        }
        leaf non-local-source-routing {
          status deprecated;
          description
            "Non Local Source Routing";
          type empty;
        }
        leaf ntp-servers {
          status deprecated;
          description
            "NTP Servers";
          type empty;
        }
        leaf option-overload {
          status deprecated;
          description
            "Options Overload";
          type empty;
        }
        leaf parameter-request-list {
          status deprecated;
          description
            "Parameter List";
          type empty;
        }
        leaf path-mtu-aging-timeout {
          status deprecated;
          description
            "Path MTU Aging Timeout";
          type empty;
        }
        leaf path-mtu-plateau-tables {
          status deprecated;
          description
            "Path MTU Plateau Tables";
          type empty;
        }
        leaf perform-mask-discovery {
          status deprecated;
          description
            "Perform Mask Discovery";
          type empty;
        }
        leaf policy-filters {
          status deprecated;
          description
            "Policy Filters";
          type empty;
        }
        leaf pop3-servers {
          status deprecated;
          description
            "POP3 Server";
          type empty;
        }
        leaf pxe-client-arch {
          status deprecated;
          description
            "PXE Client Architecture";
          type empty;
        }
        leaf pxe-client-machine-id {
          status deprecated;
          description
            "PXE Client Machine ID";
          type empty;
        }
        leaf pxe-client-network-id {
          status deprecated;
          description
            "PXE Client Network ID";
          type empty;
        }
        leaf rapid-commit {
          status deprecated;
          description
            "Rapid Commit";
          type empty;
        }
        leaf rebinding-time {
          status deprecated;
          description
            "Rebinding Time";
          type empty;
        }
        leaf relay-agent-info {
          status deprecated;
          description
            "Relay Agent information";
          type empty;
        }
        leaf renewal-time {
          status deprecated;
          description
            "Renewing Time";
          type empty;
        }
        leaf requested-address {
          status deprecated;
          description
            "Address Request";
          type empty;
        }
        leaf resource-location-servers {
          status deprecated;
          description
            "Resource Location Servers";
          type empty;
        }
        leaf root-path {
          status deprecated;
          description
            "Root Path";
          type empty;
        }
        leaf router-discovery {
          status deprecated;
          description
            "Router Discovery";
          type empty;
        }
        leaf router-solicitation-address {
          status deprecated;
          description
            "Router Solicitation Address";
          type empty;
        }
        leaf routers {
          status deprecated;
          description
            "Routers";
          type empty;
        }
        leaf server-identifier {
          status deprecated;
          description
            "Server ID";
          type empty;
        }
        leaf sip-servers {
          status deprecated;
          description
            "SIP Servers";
          type empty;
        }
        leaf slp-directory-agent {
          status deprecated;
          description
            "Service Location Protocol Directory Agent";
          type empty;
        }
        leaf slp-service-scope {
          status deprecated;
          description
            "SLP Service Scope";
          type empty;
        }
        leaf smtp-servers {
          status deprecated;
          description
            "SMTP Server";
          type empty;
        }
        leaf static-routes {
          status deprecated;
          description
            "Static Routes";
          type empty;
        }
        leaf streettalk-directory-assistance-servers {
          status deprecated;
          description
            "STDA Server";
          type empty;
        }
        leaf streettalk-servers {
          status deprecated;
          description
            "StreetTalk Server";
          type empty;
        }
        leaf subnet-alloc {
          status deprecated;
          description
            "Subnet Allocation";
          type empty;
        }
        leaf subnet-mask {
          status deprecated;
          description
            "Subnet Mask";
          type empty;
        }
        leaf subnet-selection {
          status deprecated;
          description
            "Subnet Selection";
          type empty;
        }
        leaf swap-server {
          status deprecated;
          description
            "Swap Server";
          type empty;
        }
        leaf tcp-keepalive-garbage {
          status deprecated;
          description
            "TCP Keepalive Garbage";
          type empty;
        }
        leaf tcp-keepalive-interval {
          status deprecated;
          description
            "TCP Keepalive Interval";
          type empty;
        }
        leaf tftp-server {
          status deprecated;
          description
            "TFTP Server Name";
          type empty;
        }
        leaf time-offset {
          status deprecated;
          description
            "Time Offset";
          type empty;
        }
        leaf time-servers {
          status deprecated;
          description
            "Time Servers";
          type empty;
        }
        leaf trailer-encapsulation {
          status deprecated;
          description
            "Trailer Encapsulation";
          type empty;
        }
        leaf user-auth {
          status deprecated;
          description
            "User Authentication";
          type empty;
        }
        leaf user-class-id {
          status deprecated;
          description
            "User Class ID";
          type empty;
        }
        leaf v-i-vendor-class {
          status deprecated;
          description
            "Vendor Identifying Vendor Class";
          type empty;
        }
        leaf v-i-vendor-opts {
          status deprecated;
          description
            "Vendor Identifying Vendor-Specific Options";
          type empty;
        }
        leaf vendor-encapsulated-options {
          status deprecated;
          description
            "Vendor Encapsulated Options";
          type empty;
        }
        leaf vpn-id {
          status deprecated;
          description
            "VPN Identifier";
          type empty;
        }
        leaf www-servers {
          status deprecated;
          description
            "WWW Server";
          type empty;
        }
        leaf x-display-managers {
          status deprecated;
          description
            "X Window Managers";
          type empty;
        }
      }
      container number {
        description
          "option type numbers";
        list option-number {
          key "option-number";
          leaf option-number {
            description
              "DHCP Option Type number";
            type uint8 {
              range "1..255";
            }
          }
        }
      }
    }
  }

  grouping mdns-filter-list-grouping {
    container tlv {
      description
        "tlv types list";
      leaf-list name {
        description
          "tlv type names";
        type enumeration {
          enum pointer-records {
            value 1;
            description
              "pointer record";
          }
          enum text-records {
            value 2;
            description
              "text record";
          }
          enum srv-records {
            value 3;
            description
              "service record";
          }
          enum device-version {
            value 4;
            description
              "device version";
          }
        }
      }
      leaf-list number {
        description
          "tlv type numbers";
        type uint8 {
          range "1..16";
        }
      }
    }
  }

  grouping dhcpv6-filter-list-grouping {
    container option {
      description
        "option types list";
      leaf-list name-list {
        description
          "option type names";
        type enumeration {
          enum client-id {
            value 1;
            description
              "Client ID";
          }
          enum server-id {
            value 2;
            description
              "Server ID";
          }
          enum ia-na {
            value 3;
            description
              "IA NA";
          }
          enum ia-ta {
            value 4;
            description
              "IA TA";
          }
          enum ia-addr {
            value 5;
            description
              "IA Address";
          }
          enum oro {
            value 6;
            description
              "ORO";
          }
          enum reference {
            value 7;
            description
              "Reference";
          }
          enum elapsed-time {
            value 8;
            description
              "Elapsed Time";
          }
          enum relay-msg {
            value 9;
            description
              "Relay Message";
          }
          enum auth {
            value 10;
            description
              "Auth";
          }
          enum unicast {
            value 11;
            description
              "Unicast";
          }
          enum status-code {
            value 12;
            description
              "Status Code";
          }
          enum rapid-commit {
            value 13;
            description
              "Rapid Commit";
          }
          enum user-class {
            value 14;
            description
              "User Class";
          }
          enum vendor-class {
            value 15;
            description
              "Vendor Class";
          }
          enum vendor-options {
            value 16;
            description
              "Vendor OPTs";
          }
          enum interface-id {
            value 17;
            description
              "Interface ID";
          }
          enum re-configure-msg {
            value 18;
            description
              "Re-configure Message";
          }
          enum re-configure-accept {
            value 19;
            description
              "Re-configure Accept";
          }
          enum sip-domain {
            value 20;
            description
              "SIP Domain";
          }
          enum sip-address {
            value 21;
            description
              "SIP Address";
          }
          enum dns-servers {
            value 22;
            description
              "DNS Servers";
          }
          enum domain-list {
            value 23;
            description
              "Domain List";
          }
          enum ia-pd {
            value 24;
            description
              "IA PD";
          }
          enum ia-prefix {
            value 25;
            description
              "IA Prefix";
          }
          enum nis-address {
            value 26;
            description
              "NIS Address";
          }
          enum nisp-address {
            value 27;
            description
              "NISP Address";
          }
          enum nis-domain {
            value 28;
            description
              "NIS Domain";
          }
          enum nisp-domain {
            value 29;
            description
              "NISP Domain";
          }
          enum sntp-address {
            value 30;
            description
              "SNTP Address";
          }
          enum info-refresh-time {
            value 31;
            description
              "Info Refresh Time";
          }
          enum vendor-opts-boot-file {
            value 32;
            description
              "Vendor Opts Boot File";
          }
          enum remote-id {
            value 33;
            description
              "Remote ID";
          }
          enum lease-query-query {
            value 34;
            description
              "Lease Query";
          }
          enum lease-query-client-data {
            value 35;
            description
              "Lease Query Client Data";
          }
          enum lease-query-client-time {
            value 36;
            description
              "Lease Query Client Time";
          }
          enum lease-query-relay-data {
            value 37;
            description
              "Lease Query Relay Data";
          }
          enum lease-query-client-link {
            value 38;
            description
              "Lease Query Client Link";
          }
          enum mud-uri {
            value 39;
            description
              "MUD URI";
          }
        }
      }
      container name {
        status deprecated;
        description
          "option names";
        leaf client-id {
          status deprecated;
          description
            "Client ID";
          type empty;
        }
        leaf server-id {
          status deprecated;
          description
            "Server ID";
          type empty;
        }
        leaf ia-na {
          status deprecated;
          description
            "IA NA";
          type empty;
        }
        leaf ia-ta {
          status deprecated;
          description
            "IA TA";
          type empty;
        }
        leaf ia-addr {
          status deprecated;
          description
            "IA Address";
          type empty;
        }
        leaf oro {
          status deprecated;
          description
            "ORO";
          type empty;
        }
        leaf reference {
          status deprecated;
          description
            "Reference";
          type empty;
        }
        leaf elapsed-time {
          status deprecated;
          description
            "Elapsed Time";
          type empty;
        }
        leaf relay-msg {
          status deprecated;
          description
            "Relay Message";
          type empty;
        }
        leaf auth {
          status deprecated;
          description
            "Auth";
          type empty;
        }
        leaf unicast {
          status deprecated;
          description
            "Unicast";
          type empty;
        }
        leaf status-code {
          status deprecated;
          description
            "Status Code";
          type empty;
        }
        leaf rapid-commit {
          status deprecated;
          description
            "Rapid Commit";
          type empty;
        }
        leaf user-class {
          status deprecated;
          description
            "User Class";
          type empty;
        }
        leaf vendor-class {
          status deprecated;
          description
            "Vendor Class";
          type empty;
        }
        leaf vendor-options {
          status deprecated;
          description
            "Vendor OPTs";
          type empty;
        }
        leaf interface-id {
          status deprecated;
          description
            "Interface ID";
          type empty;
        }
        leaf re-configure-msg {
          status deprecated;
          description
            "Re-configure Message";
          type empty;
        }
        leaf re-configure-accept {
          status deprecated;
          description
            "Re-configure Accept";
          type empty;
        }
        leaf sip-domain {
          status deprecated;
          description
            "SIP Domain";
          type empty;
        }
        leaf sip-address {
          status deprecated;
          description
            "SIP Address";
          type empty;
        }
        leaf dns-servers {
          status deprecated;
          description
            "DNS Servers";
          type empty;
        }
        leaf domain-list {
          status deprecated;
          description
            "Domain List";
          type empty;
        }
        leaf ia-pd {
          status deprecated;
          description
            "IA PD";
          type empty;
        }
        leaf ia-prefix {
          status deprecated;
          description
            "IA Prefix";
          type empty;
        }
        leaf nis-address {
          status deprecated;
          description
            "NIS Address";
          type empty;
        }
        leaf nisp-address {
          status deprecated;
          description
            "NISP Address";
          type empty;
        }
        leaf nis-domain {
          status deprecated;
          description
            "NIS Domain";
          type empty;
        }
        leaf nisp-domain {
          status deprecated;
          description
            "NISP Domain";
          type empty;
        }
        leaf sntp-address {
          status deprecated;
          description
            "SNTP Address";
          type empty;
        }
        leaf info-refresh-time {
          status deprecated;
          description
            "Info Refresh Time";
          type empty;
        }
        leaf vendor-opts-boot-file {
          status deprecated;
          description
            "Vendor Opts Boot File";
          type empty;
        }
        leaf remote-id {
          status deprecated;
          description
            "Remote ID";
          type empty;
        }
        leaf lease-query-query {
          status deprecated;
          description
            "Lease Query";
          type empty;
        }
        leaf lease-query-client-data {
          status deprecated;
          description
            "Lease Query Client Data";
          type empty;
        }
        leaf lease-query-client-time {
          status deprecated;
          description
            "Lease Query Client Time";
          type empty;
        }
        leaf lease-query-relay-data {
          status deprecated;
          description
            "Lease Query Relay Data";
          type empty;
        }
        leaf lease-query-client-link {
          status deprecated;
          description
            "Lease Query Client Link";
          type empty;
        }
        leaf mud-uri {
          status deprecated;
          description
            "MUD URI";
          type empty;
        }
      }
      container number {
        description
          "option type numbers";
        list option-number {
          key "option-number";
          leaf option-number {
            description
              "DHCPv6 Option Type number";
            type uint8 {
              range "1..255";
            }
          }
        }
      }
    }
  }

  grouping config-device-sensor-grouping {
    container device-sensor {
      description
        "IOS Sensor Commands";
      leaf accounting {
        description
          "Trigger accounting updates with sensor TLVs/Options";
        type empty;
      }
      container notify {
        description
          "Options for when to trigger identity update events";
        leaf all-changes {
          description
            "Trigger identity update when TLVs are added/modified/removed";
          type empty;
        }
      }
      container filter-list {
        description
          "Sensor Protocol Filter List Configuration";
        container dhcp {
          description
            "DHCP Filter List";
          list list {
            description
              "Protocol Filter List";
            key "name";
            leaf name {
              type string;
            }
            uses dhcp-filter-list-grouping;
          }
        }
        container dhcpv6 {
          description
            "DHCPv6 Filter List";
          list list {
            description
              "Protocol Filter List";
            key "name";
            leaf name {
              type string;
            }
            uses dhcpv6-filter-list-grouping;
          }
        }
        container lldp {
          description
            "LLDP Filter List";
          list list {
            description
              "Protocol Filter List";
            key "name";
            leaf name {
              type string;
            }
            uses lldp-filter-list-grouping;
          }
        }
        container cdp {
          description
            "CDP Filter List";
          list list {
            description
              "Protocol Filter List";
            key "name";
            leaf name {
              type string;
            }
            uses cdp-filter-list-grouping;
          }
        }
        container mdns {
          description
            "MDNS Filter List";
          list list {
            description
              "Protocol Filter List";
            key "name";
            leaf name {
              type string;
            }
            uses mdns-filter-list-grouping;
          }
        }
      }
      container filter-spec {
        description
          "Sensor Protocol Filter Spec Configuration";
        container cdp {
          description
            "CDP Filter Spec";
          choice incl-excl {
            case excl-case {
              container exclude-select {
                description
                  "Exclude Filter";
                choice excl {
                  case list-case {
                    leaf list {
                      description
                        "Protocol Filter Spec list";
                      must '../../../../ios-ds:filter-list/ios-ds:cdp/ios-ds:list[name=current()]' {
                        error-message "CDP filter List does not exist ";
                      }
                      type string;
                    }
                  }
                  case all-case {
                    leaf all {
                      description
                        "All";
                      type empty;
                    }
                  }
                }
              }
            }
            case incl-clase {
              container include-select {
                description
                  "Include Filter";
                leaf list {
                  description
                    "Protocol Filter Spec list";
                  must '../../../../ios-ds:filter-list/ios-ds:cdp/ios-ds:list[name=current()]' {
                    error-message "CDP filter List does not exist ";
                  }
                  type string;
                }
              }
            }
          }
          uses filter-spec-inc-exc-deprecate-grouping;
        }
        container dhcp {
          description
            "DHCP Filter Spec";
          choice incl-excl {
            case excl-case {
              container exclude-select {
                description
                  "Exclude Filter";
                choice excl {
                  case list-case {
                    leaf list {
                      description
                        "Protocol Filter Spec list";
                      must '../../../../ios-ds:filter-list/ios-ds:dhcp/ios-ds:list[name=current()]' {
                        error-message "DHCP filter List does not exist ";
                      }
                      type string;
                    }
                  }
                  case all-case {
                    leaf all {
                      description
                        "All";
                      type empty;
                    }
                  }
                }
              }
            }
            case incl-clase {
              container include-select {
                description
                  "Include Filter";
                leaf list {
                  description
                    "Protocol Filter Spec list";
                  must '../../../../ios-ds:filter-list/ios-ds:dhcp/ios-ds:list[name=current()]' {
                    error-message "DHCP filter List does not exist ";
                  }
                  type string;
                }
              }
            }
          }
          uses filter-spec-inc-exc-deprecate-grouping;
        }
        container lldp {
          description
            "LLDP Filter Spec";
          choice incl-excl {
            case excl-case {
              container exclude-select {
                description
                  "Exclude Filter";
                choice excl {
                  case list-case {
                    leaf list {
                      description
                        "Protocol Filter Spec list";
                      must '../../../../ios-ds:filter-list/ios-ds:lldp/ios-ds:list[name=current()]' {
                        error-message "LLDP filter List does not exist ";
                      }
                      type string;
                    }
                  }
                  case all-case {
                    leaf all {
                      description
                        "All";
                      type empty;
                    }
                  }
                }
              }
            }
            case incl-clase {
              container include-select {
                description
                  "Include Filter";
                leaf list {
                  description
                    "Protocol Filter Spec list";
                  must '../../../../ios-ds:filter-list/ios-ds:lldp/ios-ds:list[name=current()]' {
                    error-message "LLDP filter List does not exist ";
                  }
                  type string;
                }
              }
            }
          }
          uses filter-spec-inc-exc-deprecate-grouping;
        }
        container dhcpv6 {
          description
            "DHCPV6 Filter Spec";
          choice incl-excl {
            case excl-case {
              container exclude-select {
                description
                  "Exclude Filter";
                choice excl {
                  case list-case {
                    leaf list {
                      description
                        "Protocol Filter Spec list";
                      must '../../../../ios-ds:filter-list/ios-ds:dhcpv6/ios-ds:list[name=current()]' {
                        error-message "DHCPv6 filter List does not exist ";
                      }
                      type string;
                    }
                  }
                  case all-case {
                    leaf all {
                      description
                        "All";
                      type empty;
                    }
                  }
                }
              }
            }
            case incl-clase {
              container include-select {
                description
                  "Include Filter";
                leaf list {
                  description
                    "Protocol Filter Spec list";
                  must '../../../../ios-ds:filter-list/ios-ds:dhcpv6/ios-ds:list[name=current()]' {
                    error-message "DHCPv6 filter List does not exist ";
                  }
                  type string;
                }
              }
            }
          }
          uses filter-spec-inc-exc-deprecate-grouping;
        }
        container mdns {
          description
            "MDNS Filter Spec";
          choice incl-excl {
            case incl-case {
              container include {
                description
                  "Include Filter";
                leaf list {
                  description
                    "Protocol Filter Spec list";
                  must '../../../../ios-ds:filter-list/ios-ds:mdns/ios-ds:list[name=current()]' {
                    error-message "Mdns List does not exist ";
                  }
                  type string;
                }
              }
            }
            case excl-case {
              container exclude {
                description
                  "Exclude Filter";
                choice excl {
                  case list-case {
                    leaf list {
                      description
                        "Protocol Filter Spec list";
                      must '../../../../ios-ds:filter-list/ios-ds:mdns/ios-ds:list[name=current()]' {
                        error-message "Mdns list does not exist ";
                      }
                      type string;
                    }
                  }
                  case all-case {
                    leaf all {
                      description
                        "Exclude All";
                      type empty;
                    }
                  }
                }
              }
            }
          }
        }
      }
      container tlv {
        description
          "Device-sensor protocol tlvs";
        leaf limit {
          description
            "Protocol Tlv Limit (Default: 128)";
          type uint16 {
            range "1..1024";
          }
        }
      }
    }
  }

  grouping config-interface-device-sensor-grouping {
    container device-sensor {
      description
        "Interface Config Commands for device-sensor";
      leaf dhcpv6-snooping {
        description
          "Enable dhcpv6 for this port";
        type empty;
      }
    }
  }

  augment "/ios:native" {
    uses config-device-sensor-grouping;
  }

  augment "/ios:native/ios:interface/ios:GigabitEthernet" {
    uses config-interface-device-sensor-grouping;
  }

  augment "/ios:native/ios:interface/ios:TwoGigabitEthernet" {
    uses config-interface-device-sensor-grouping;
  }

  augment "/ios:native/ios:interface/ios:FiveGigabitEthernet" {
    uses config-interface-device-sensor-grouping;
  }

  augment "/ios:native/ios:interface/ios:AppGigabitEthernet" {
    uses config-interface-device-sensor-grouping;
  }

  augment "/ios:native/ios:interface/ios:TenGigabitEthernet" {
    uses config-interface-device-sensor-grouping;
  }

  augment "/ios:native/ios:interface/ios:TwentyFiveGigE" {
    uses config-interface-device-sensor-grouping;
  }

  augment "/ios:native/ios:interface/ios:FortyGigabitEthernet" {
    uses config-interface-device-sensor-grouping;
  }

  augment "/ios:native/ios:interface/ios:HundredGigE" {
    uses config-interface-device-sensor-grouping;
  }

  augment "/ios:native/ios:interface/ios:Port-channel" {
    uses config-interface-device-sensor-grouping;
  }

  augment "/ios:native/ios:interface/ios:Vlan" {
    uses config-interface-device-sensor-grouping;
  }
}
