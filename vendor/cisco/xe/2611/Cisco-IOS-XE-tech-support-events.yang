module Cisco-IOS-XE-tech-support-events {
  yang-version 1.1;
  namespace "http://cisco.com/ns/yang/Cisco-IOS-XE-tech-support-events";
  prefix tech-support-ios-xe-events;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Copyright (c) 2023 by Cisco Systems, Inc.
     All rights reserved.";

  revision 2023-11-01 {
    description
      "Initial revision";
    reference
      "1.0.0";
    cisco-semver:module-version "1.0.0";
  }

  typedef tech-support-status {
    type enumeration {
      enum in-progress {
        value 0;
        description
          "The tech-support generation is in progress.";
      }
      enum success {
        value 1;
        description
          "The tech-support file/archive has been successfully generated.";
      }
      enum fail {
        value 2;
        description
          "The tech-support generation has failed.";
      }
    }
    description
      "States to represent status of tech-support generation";
  }

  typedef tech-support-error-types {
    type enumeration {
      enum error-ok {
        value 0;
        description
          "The tech-support RPC did not hit any error.";
      }
      enum no-space {
        value 1;
        description
          "Insufficient amount of space in the drive where tech-support file/archive was to be generated.
           Ensure there is at least 5 percent space available in the drive mention in file path.";
      }
      enum drive-invalid {
        value 2;
        description
          "No valid drive on the device.";
      }
      enum archive-gen-fail {
        value 3;
        description
          "There was an error while generating tech-support archive.";
      }
      enum file-gen-fail {
        value 4;
        description
          "There was an error while generating tech-support file.";
      }
      enum operation-not-supported {
        value 5;
        description
          "An unsupported operation was attempted while generating the tech-support
           file/archive.";
      }
      enum system-fail {
        value 6;
        description
          "There was an internal issue with the system such as low
            memory, a particular operation failing etc.";
      }
      enum unable-to-process-request {
        value 7;
        description
          "The tech-support call-backs to generate the file/archive, was not executed.";
      }
      enum platform-not-supported {
        value 8;
        description
          "The tech-support RPC is not supported on this platform";
      }
    }
    description
      "Various errors that could occur if debug bundle generate failed";
  }

  grouping tech-support-notif-fields {
    description
      "Information about the execution, which will be sent by the debug bundle generation process";
    leaf file-name {
      type string;
      description
        "File name of the tech-support archive/file";
    }
    leaf status {
      type tech-support-ios-xe-events:tech-support-status;
      description
        "Status of debug-bundle/tech-support generation";
    }
    leaf error-code {
      type tech-support-ios-xe-events:tech-support-error-types;
      description
        "If there is any error, the corresponding error code will be returned to the user.
         If there is no error, the default error code of 'no-error' is returned to the user.";
    }
  }

  notification tech-support-event {
    description
      "Notification for tech-support archive and file actions";
    uses tech-support-ios-xe-events:tech-support-notif-fields;
  }
}
