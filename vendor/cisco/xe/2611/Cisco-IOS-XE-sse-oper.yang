module Cisco-IOS-XE-sse-oper {
  yang-version 1.1;
  namespace "http://cisco.com/ns/yang/Cisco-IOS-XE-sse-oper";
  prefix sse-ios-xe-oper;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Secure Service Edge (SSE) operational data.
     Copyright (c) 2023-2024 by Cisco Systems, Inc.
     All rights reserved.";

  revision 2024-03-01 {
    description
      "- Added new type for Secure Service Edge (SSE) context metadata sharing
       - Added new enum for Secure Service Edge (SSE) tracker status";
    reference
      "1.1.0";
    cisco-semver:module-version "1.1.0";
  }
  revision 2023-11-01 {
    description
      "Initial revision";
    reference
      "1.0.0";
    cisco-semver:module-version "1.0.0";
  }

  typedef sse-tunnel-local-status {
    type enumeration {
      enum sse-tunnel-local-status-up {
        value 0;
        description
          "Local tunnel status is up";
      }
      enum sse-tunnel-local-status-down {
        value 1;
        description
          "Local tunnel status is down";
      }
      enum sse-tunnel-local-status-degraded {
        value 2;
        description
          "Local tunnel status is degraded";
      }
    }
    description
      "Local status of the tunnel";
  }

  typedef sse-tunnel-ha-pair-role {
    type enumeration {
      enum sse-ha-pair-active {
        value 0;
        description
          "Role of the tunnel is active";
      }
      enum sse-ha-pair-backup {
        value 1;
        description
          "Role of the tunnel is backup";
      }
    }
    description
      "High availability role of the tunnel";
  }

  typedef sse-tunnel-type-on-device {
    type enumeration {
      enum sse-tunnel-type-on-device-ipsec {
        value 0;
        description
          "Tunnel type is IPSEC";
      }
      enum sse-tunnel-type-on-device-is-gre {
        value 1;
        description
          "Tunnel type is GRE";
      }
    }
    description
      "Tunnel type on the device";
  }

  typedef sse-tunnel-tracker-state {
    type enumeration {
      enum sse-tunnel-tracker-state-down {
        value 0;
        description
          "Tracker state is down";
      }
      enum sse-tunnel-tracker-state-up {
        value 1;
        description
          "Tracker state is up";
      }
      enum sse-tunnel-tracker-state-na {
        value 2;
        description
          "Tracker state is not applicable";
      }
    }
    description
      "Tracker state for the tunnel";
  }

  typedef sse-tunnel-ctxt-mdata-sharing-type {
    type bits {
      bit sse-tcsm-disabled {
        position 0;
        description
          "Metadata sharing with Secure Service Edge (SSE)  is disabled";
      }
      bit sse-tcsm-src-vpn {
        position 1;
        description
          "Source virtual private network metadata shared with Secure Service Edge (SSE)";
      }
      bit sse-tcsm-sgt {
        position 2;
        description
          "Secure Group Tag (SGT) metadata shared with Secure Service Edge (SSE)";
      }
    }
    description
      "Metadata type shared with Secure Service Edge (SSE)";
  }

  grouping sse-tunnel-info {
    description
      "Tunnel information for the Secure Service Edge (SSE)";
    leaf tunnel-name {
      type string;
      description
        "Tunnel name on the device";
    }
    leaf host-name {
      type string;
      description
        "Host name of the device";
    }
    leaf site-id {
      type uint32;
      description
        "Site identification for the device";
    }
    leaf tunnel-id {
      type uint64;
      description
        "Tunnel identifier on the Secure Service Edge (SSE)";
    }
    leaf sse-tunnel-name {
      type string;
      description
        "Tunnel name on the Secure Service Edge (SSE)";
    }
    leaf tunnel-type {
      type sse-ios-xe-oper:sse-tunnel-type-on-device;
      description
        "Tunnel type";
    }
    leaf ha-pair-role {
      type sse-ios-xe-oper:sse-tunnel-ha-pair-role;
      description
        "High availability role of the tunnel";
    }
    leaf sse-provider {
      type string;
      description
        "Secure Service Edge (SSE) provider name";
    }
    leaf data-center-ip {
      type inet:ip-address;
      description
        "Data center IP address";
    }
    leaf tunnel-local-status {
      type sse-ios-xe-oper:sse-tunnel-local-status;
      description
        "Local tunnel status";
    }
    leaf tracker-state {
      type sse-ios-xe-oper:sse-tunnel-tracker-state;
      description
        "Tracker state for the tunnel";
    }
    leaf sse-tcsm {
      type sse-ios-xe-oper:sse-tunnel-ctxt-mdata-sharing-type;
      description
        "Metadata sharing type with Secure Service Edge (SSE)";
    }
  }

  container sse-oper-data {
    config false;
    description
      "Secure Service Edge (SSE) operational data";
    list sse-tunnel-info {
      key "tunnel-name";
      description
        "Tunnel information for the Secure Service Edge (SSE)";
      uses sse-ios-xe-oper:sse-tunnel-info;
    }
  }
}
