module Cisco-IOS-XE-interface-bw-events {
  yang-version 1.1;
  namespace "http://cisco.com/ns/yang/Cisco-IOS-XE-interface-bw-events";
  prefix interface-bw-ios-xe-events;

  import Cisco-IOS-XE-ios-common-oper {
    prefix ios-common-ios-xe-oper;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Copyright (c) 2024 by Cisco Systems, Inc.
     All rights reserved.";

  revision 2024-11-01 {
    description
      "Initial revision";
    reference
      "1.0.0";
    cisco-semver:module-version "1.0.0";
  }

  typedef interface-bw-traffic-direction {
    type enumeration {
      enum if-bw-downstream {
        value 0;
        description
          "Downstream traffic direction.";
      }
      enum if-bw-upstream {
        value 1;
        description
          "Upstream traffic direction.";
      }
    }
    description
      "Traffic direction for interface-bw notifications.";
  }

  grouping interface-bw {
    description
      "Notification field for interface bandwidth events";
    leaf severity-level {
      type ios-common-ios-xe-oper:notification-severity;
      description
        "Event severity";
    }
    leaf host-name {
      type string;
      description
        "Host name of the device";
    }
    leaf system-ip {
      type inet:ip-address;
      description
        "System IP of the device";
    }
    leaf vpn-id {
      type uint32;
      description
        "VPN ID";
    }
    leaf if-name {
      type string;
      description
        "Interface name";
    }
    leaf if-cfg-bw-kbps {
      type uint32;
      units "kbps";
      description
        "Interface bandwidth";
    }
    leaf traffic-direction {
      type interface-bw-ios-xe-events:interface-bw-traffic-direction;
      description
        "Traffic direction";
    }
    leaf duration {
      type uint32;
      units "seconds";
      description
        "Duration";
    }
  }

  notification interface-bw {
    description
      "Notification for interface bandwidth event";
    uses interface-bw-ios-xe-events:interface-bw;
  }
}
