module Cisco-IOS-XE-statistics {
  yang-version 1.1;
  namespace "http://cisco.com/ns/yang/Cisco-IOS-XE-statistics";
  prefix ios-statistics;

  import Cisco-IOS-XE-native {
    prefix ios;
  }
  import Cisco-IOS-XE-features {
    prefix ios-features;
  }

  organization
    "Cisco Systems, Inc.";
  contact
    "Cisco Systems, Inc.
     Customer Service
     Postal: 170 W Tasman Drive
     San Jose, CA 95134
     Tel: +1 1800 553-NETS
     E-mail: cs-yang@cisco.com";
  description
    "Cisco XE statistics Yang model.
     Copyright (c) 2025 by Cisco Systems, Inc.
     All rights reserved.";

  revision 2026-02-01 {
    description
      "Initial revision.";
  }

  typedef table-type {
    type enumeration {
      enum interface;
    }
  }

  grouping config-stats {
    container statistics {
      description
        "Statistics collection";
      if-feature "ios-features:stats-configuration";
      list table {
        description
          "List of different statistics";
        key "type";
        leaf type {
          description
            "Type of statistics";
          type table-type;
        }
        leaf collection-interval {
          description
            "Statistics collection interval";
          type uint8 {
            range "1";
          }
        }
      }
    }
  }

  augment "/ios:native" {
    uses config-stats;
  }
}
