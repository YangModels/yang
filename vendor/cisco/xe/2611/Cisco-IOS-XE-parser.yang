submodule Cisco-IOS-XE-parser {
  yang-version 1.1;
  belongs-to Cisco-IOS-XE-native {
    prefix ios;
  }

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Parser Yang model.
     Copyright (c) 2016-2019 by Cisco Systems, Inc.
     All rights reserved.";

  revision 2024-11-01 {
    description
      "- Added IP named extended access-list configuration mode
       - Added model change for privilege commands";
    cisco-semver:module-version "1.3.1";
  }
  revision 2024-03-01 {
    description
      "- new yang models added for parser cache";
    cisco-semver:module-version "1.2.0";
  }
  revision 2022-11-01 {
    description
      "- Update yang-version to 1.1";
    cisco-semver:module-version "1.1.0";
  }
  revision 2019-07-01 {
    description
      "Establish semantic version baseline";
    cisco-semver:module-version "1.0.0";
  }
  revision 2019-01-30 {
    description
      "Add secret type 8 and type 9 for parser view";
  }
  revision 2018-03-01 {
    description
      "Add Parser view secret extensions";
  }
  revision 2018-01-16 {
    description
      "Add privilege modes";
  }
  revision 2017-11-29 {
    description
      "Add parser view";
  }
  revision 2017-02-07 {
    description
      "Initial revision";
  }

  grouping all-command-gouping {
    list command-list {
      key "command";
      leaf command {
        description
          "Keywords of the command";
        type string;
      }
      leaf all {
        description
          "wild card support";
        type empty;
      }
    }
  }

  grouping config-exec-options-grouping {
    container exclude {
      description
        "Exclude the command from the view";
      uses all-command-gouping;
    }
    container include {
      description
        "Add command to the view";
      uses all-command-gouping;
    }
    container include-exclusive {
      description
        "Include in this view but exclude from others";
      uses all-command-gouping;
    }
  }

  grouping parser-view-common-options-grouping {
    container secret {
      description
        "Set a secret for the current view";
      leaf type {
        type enumeration {
          enum 0;
          enum 5;
          enum 8;
          enum 9;
        }
      }
      leaf secret {
        type string;
      }
    }
  }

  grouping config-parser-grouping {
    container parser {
      description
        "Configure parser";
      leaf cache {
        description
          "Configure parser cache";
        type boolean;
        default "true";
      }
      container config {
        description
          "Configure config generation";
        leaf cache {
          description
            "Cache the configuration";
          type enumeration {
            enum interface;
          }
        }
        leaf partition {
          description
            "Enable configuration Partitioning";
          type empty;
        }
      }
      container view {
        description
          "View Commands";
        list view-name-list {
          key "name";
          leaf name {
            description
              "View Name";
            type string;
          }
          leaf inclusive {
            description
              "SuperView Commands";
            type empty;
          }
          uses parser-view-common-options-grouping;
          container commands {
            description
              "Configure commands for a view";
            container exec {
              description
                "Exec mode";
              uses config-exec-options-grouping;
            }
            container configure {
              description
                "Global configuration mode";
              uses config-exec-options-grouping;
            }
          }
        }
        list view-name-superview-list {
          key "name";
          leaf name {
            description
              "View Name";
            type string;
          }
          leaf superview {
            description
              "SuperView Commands";
            type empty;
          }
          uses parser-view-common-options-grouping;
          list view {
            description
              "View Name";
            key "view-name";
            leaf view-name {
              type leafref {
                path "../../../view-name-list/name";
              }
            }
          }
        }
      }
    }
  }

  grouping privilege-mode-common {
    list level {
      description
        "Set privilege level of command";
      key "privilege";
      leaf privilege {
        type uint8;
      }
      list command-list {
        key "command";
        leaf command {
          description
            "There are side effects";
          type string;
        }
      }
    }
    list reset {
      key "command";
      leaf command {
        type string;
      }
    }
  }

  grouping config-privilege-grouping {
    container privilege {
      description
        "Command privilege parameters";
      list mode {
        key "name";
        leaf name {
          type enumeration {
            enum configure;
            enum exec;
            enum interface;
            enum router;
            enum crypto-map;
            enum ipenacl;
          }
        }
        container all {
          uses privilege-mode-common;
        }
        uses privilege-mode-common;
      }
    }
  }
}
