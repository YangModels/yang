module Cisco-IOS-XE-ida {
  yang-version 1.1;
  namespace "http://cisco.com/ns/yang/Cisco-IOS-XE-ida";
  prefix ios-ida;

  import Cisco-IOS-XE-native {
    prefix ios;
  }

  organization
    "Cisco Systems, Inc.";
  contact
    "Cisco Systems, Inc.
     Customer Service
     Postal: 170 W Tasman Drive
     San Jose, CA 95134
     Tel: +1 1800 553-NETS
     E-mail: cs-yang@cisco.com";
  description
    "Cisco XE REP  Yang Model.
     Copyright (c)  2023  by Cisco Systems, Inc.
     All rights reserved.";

  revision 2023-07-01 {
    description
      "Initial revision";
  }

  grouping config-interface-ida-grouping {
    container ida {
      list transport-profile {
        description
          "Transport Profile Configuration";
        max-elements 1;
        key "name";
        leaf name {
          description
            "Profile Name";
          type string {
            length "1..64";
          }
        }
        leaf callhome-url {
          description
            "Callhome server <url>";
          type string {
            length "1..256";
          }
        }
        leaf reconnect-timer {
          description
            "Profile reconnect timer (default 60 seconds)";
          type uint16 {
            range "30..3600";
          }
        }
        leaf remote-trustpoint {
          description
            "Trustpoint to use for authenticating the server";
          type string {
            length "1..256";
          }
        }
        leaf execution-url {
          description
            "Local Execution server <url>";
          type string {
            length "1..256";
          }
        }
        leaf local-trustpoint {
          description
            "Trustpoint to use for connection with server";
          type string {
            length "1..256";
          }
        }
        leaf proxy-addr {
          description
            "Proxy Address";
          type string {
            length "1..40";
          }
        }
        leaf active {
          type empty;
        }
        leaf keepalive-timer {
          description
            "Profile keepalive timer (default 300 seconds)";
          type uint16 {
            range "30..3600";
          }
        }
      }
    }
  }

  augment "/ios:native" {
    uses config-interface-ida-grouping;
  }
}
