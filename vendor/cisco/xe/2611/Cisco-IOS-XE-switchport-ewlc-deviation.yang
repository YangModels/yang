module Cisco-IOS-XE-switchport-ewlc-deviation {
  yang-version 1.1;
  namespace "http://cisco.com/ns/yang/Cisco-IOS-XE-switchport-ewlc-deviation";
  prefix ios-sw-ewlc-de;

  import Cisco-IOS-XE-native {
    prefix ios;
  }

  organization
    "Cisco Systems";
  description
    "Cisco XE Native switchport eWLC Deviation YANG module for IOS
     Copyright (c) 2025 by Cisco Systems, Inc.
     All rights reserved.";

  revision 2025-07-01 {
    description
      " - Add deviation for switchport
        - Add Port-channel interface switchport default value deviation";
  }

  deviation "/ios:native/ios:interface/ios:Port-channel/ios:switchport-conf/ios:switchport" {
    deviate add {
      default "true";
    }
  }
}
