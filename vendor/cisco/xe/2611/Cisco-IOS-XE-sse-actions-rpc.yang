module Cisco-IOS-XE-sse-actions-rpc {
  yang-version 1.1;
  namespace "http://cisco.com/ns/yang/Cisco-IOS-XE-sse-actions-rpc";
  prefix sse-actions-rpc;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for SSE action RPC.
     Copyright (c) 2023 by Cisco Systems, Inc.
     All rights reserved.";

  revision 2024-03-01 {
    description
      "Added an RPC to setup GRE tunnels ";
    reference
      "1.1.0";
    cisco-semver:module-version "1.1.0";
  }
  revision 2023-11-01 {
    description
      "Initial revision";
    reference
      "1.0.0";
    cisco-semver:module-version "1.0.0";
  }

  typedef sse-ike-id-type {
    type enumeration {
      enum sse-ike-id-type-any {
        value 0;
        description
          "IKE identifier is any IPV4/IPV6 address";
      }
      enum sse-ike-id-type-ipv4-addr {
        value 1;
        description
          "IKE identifier is IPV4 address";
      }
      enum sse-ike-id-fqdn {
        value 2;
        description
          "IKE identifier is FQDN";
      }
      enum sse-ike-id-user-fqdn {
        value 3;
        description
          "IKE identifier is user FQDN";
      }
      enum sse-ike-id-ipv4-addr-subnet {
        value 4;
        description
          "IKE identifier is IPV4 subnet";
      }
      enum sse-ike-id-ipv6-addr {
        value 5;
        description
          "IKE identifier is IPV6 address";
      }
      enum sse-ike-id-ipv6-addr-subnet {
        value 6;
        description
          "IKE identifier is IPV6 address subnet";
      }
      enum sse-ike-id-ipv4-addr-range {
        value 7;
        description
          "IKE identifier is IPV4 address range";
      }
      enum sse-ike-id-ipv6-addr-range {
        value 8;
        description
          "IKE identifier is IPV6 address range";
      }
      enum sse-ike-id-der-asn1-dn {
        value 9;
        description
          "IKE identifier is ASN";
      }
      enum sse-ike-id-der-asn1-gn {
        value 10;
        description
          "IKE identifier is ASN GN";
      }
      enum sse-ike-id-key-id {
        value 11;
        description
          "IKE identifier is key identifier";
      }
    }
    description
      "IKE identifier for SSE tunnel";
  }

  typedef sse-ike-auth-method {
    type enumeration {
      enum sse-ike-no-method {
        value 0;
        description
          "No authorization method";
      }
      enum sse-ike-rsa-sig {
        value 1;
        description
          "Authorization method is RSA";
      }
      enum sse-ike-preshared {
        value 2;
        description
          "Authorization method is pre shared key";
      }
      enum sse-ike-dss-sig {
        value 3;
        description
          "Authorization method is DSS";
      }
      enum sse-ike-ecdsa-256-sig {
        value 4;
        description
          "Authorization method is ECDSA";
      }
      enum sse-ike-ecdsa-384-sig {
        value 5;
        description
          "Authorization is ECDSA";
      }
      enum sse-ike-anyconnect-eap {
        value 6;
        description
          "Authorization method is any connect EAP";
      }
      enum sse-ike-eap {
        value 7;
        description
          "Authorization method is EAP";
      }
    }
    description
      "Authorization method for IKE";
  }

  typedef sse-tunnel-type {
    type enumeration {
      enum sse-tunnel-type-ipsec {
        value 0;
        description
          "Tunnel type is IPSEC";
      }
      enum sse-tunnel-type-gre {
        value 1;
        description
          "Tunnel type is GRE";
      }
    }
    description
      "Tunnel type of SSE";
  }

  grouping sse-ipsec-tunnel-params {
    description
      "IPSEC tunnel parameters for SSE";
    leaf tunnel-name {
      type string {
        length "1..127";
      }
      mandatory true;
      description
        "Tunnel name";
    }
    leaf dc-ip-addr {
      type inet:ip-address;
      mandatory true;
      description
        "Data center IP address";
    }
    leaf tunnel-id {
      type uint64;
      mandatory true;
      description
        "Tunnel identifier";
    }
    leaf sse-tunnel-name {
      type string {
        length "1..127";
      }
      mandatory true;
      description
        "Tunnel name on the SSE";
    }
    leaf tunnel-type {
      type sse-actions-rpc:sse-tunnel-type;
      mandatory true;
      description
        "Type of SSE tunnel";
    }
    leaf sse-provider {
      type string {
        length "1..127";
      }
      mandatory true;
      description
        "SSE provider name";
    }
    choice remote-id-type-choice {
      mandatory true;
      description
        "Choice for remote identifier";
      case sse-ike-id-type-any {
        leaf remote-ip-any {
          type inet:ip-address;
          mandatory true;
          description
            "Remote any IPV4/IPV6 address";
        }
      }
      case sse-ike-id-type-ipv4-addr {
        leaf remote-ip-addr {
          type inet:ip-address;
          mandatory true;
          description
            "Remote IPV4 address";
        }
      }
      case sse-ike-id-fqdn {
        leaf remote-id-fqdn {
          type string {
            length "1..127";
          }
          mandatory true;
          description
            "Remote identifier is FQDN";
        }
      }
      case sse-ike-id-user-fqdn {
        leaf remote-id-user-fqdn {
          type string {
            length "1..127";
          }
          mandatory true;
          description
            "Remote identifier is user FQDN";
        }
      }
      case sse-ike-id-key-id {
        leaf remote-key-id {
          type string {
            length "1..127";
          }
          mandatory true;
          description
            "Remote identifier is key identifier";
        }
      }
    }
    choice local-auth-method-choice {
      mandatory true;
      description
        "Local authentication method choice";
      case sse-ike-preshared {
        leaf local-key {
          type string {
            length "1..127";
          }
          mandatory true;
          description
            "Local key is pre shared key";
        }
      }
    }
    choice remote-auth-method-choice {
      mandatory true;
      description
        "Remote authorization method choice";
      case sse-ike-preshared {
        leaf remote-key {
          type string {
            length "1..127";
          }
          mandatory true;
          description
            "Remote key is pre shared key";
        }
      }
    }
    choice local-id-type-choice {
      mandatory true;
      description
        "Choice for local identifier";
      case sse-ike-id-type-any {
        leaf local-ip-any {
          type inet:ip-address;
          mandatory true;
          description
            "Local any IPV4/IPV6 address";
        }
      }
      case sse-ike-id-type-ipv4-addr {
        leaf local-ip-addr {
          type inet:ip-address;
          mandatory true;
          description
            "Local IPV4 address";
        }
      }
      case sse-ike-id-fqdn {
        leaf local-id-fqdn {
          type string {
            length "1..127";
          }
          mandatory true;
          description
            "FQDN is the local identifier";
        }
      }
      case sse-ike-id-user-fqdn {
        leaf local-id-user-fqdn {
          type string {
            length "1..127";
          }
          mandatory true;
          description
            "User FQDN is the local identifier";
        }
      }
      case sse-ike-id-key-id {
        leaf local-key-id {
          type string {
            length "1..127";
          }
          mandatory true;
          description
            "Local identifier is key string";
        }
      }
    }
  }

  grouping sse-gre-tunnel-params {
    description
      "Generic Routing Encapsulation (GRE) parameters for the Secure Service Edge (SSE) tunnel";
    leaf tunnel-name {
      type string {
        length "1..127";
      }
      mandatory true;
      description
        "Tunnel name on the device";
    }
    leaf tunnel-id {
      type uint64;
      mandatory true;
      description
        "Tunnel identifier on the Secure Service Edge (SSE)";
    }
    leaf sse-tunnel-name {
      type string {
        length "1..127";
      }
      mandatory true;
      description
        "Tunnel name on the Secure Service Edge (SSE)";
    }
    leaf sse-provider {
      type string {
        length "1..127";
      }
      mandatory true;
      description
        "Secure Service Edge (SSE) provider name";
    }
    leaf tunnel-type {
      type sse-actions-rpc:sse-tunnel-type;
      mandatory true;
      description
        "Tunnel type on Secure Service Edge (SSE)";
    }
    leaf dc-ip-addr {
      type inet:ip-address;
      mandatory true;
      description
        "Data center IP address";
    }
  }

  grouping sse-ipsec-tunnel-params-all {
    description
      "Contains the tunnel parameters for SSE";
    list sse-ipsec-tunnel-list {
      description
        "List of IPSEC tunnel parameters to be set for each
         tunnel in the SSE";
      uses sse-actions-rpc:sse-ipsec-tunnel-params;
    }
  }

  grouping sse-gre-tunnel-params-all {
    description
      "Generic Routing Encapsulation (GRE) tunnel parameters for the Secure Service Edge (SSE) ";
    list sse-gre-tunnel {
      description
        "List of Generic Routing Encapsulation (GRE) tunnels for the Secure Service Edge (SSE)";
      uses sse-actions-rpc:sse-gre-tunnel-params;
    }
  }

  rpc set-sse-ipsec-tunnel {
    description
      "RPC to set IPSEC tunnel parameters";
    input {
      uses sse-actions-rpc:sse-ipsec-tunnel-params-all;
    }
  }

  rpc set-sse-gre-tunnels {
    description
      "RPC to setup multiple Generic Routing Encapsulation (GRE) tunnels";
    input {
      uses sse-actions-rpc:sse-gre-tunnel-params-all;
    }
  }
}
