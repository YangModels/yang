module Cisco-IOS-XE-sr-oper {
  yang-version 1.1;
  namespace "http://cisco.com/ns/yang/Cisco-IOS-XE-sr-oper";
  prefix sr-ios-xe-oper;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Segment Routing (SR) operational data.
     Copyright (c) 2025 by Cisco Systems, Inc.
     All rights reserved.";

  revision 2026-02-01 {
    description
      "Initial revision";
    reference
      "1.0.0";
    cisco-semver:module-version "1.0.0";
  }

  grouping te-policy-counters {
    description
      "SR TE policy counters type";
    leaf in-pkts {
      type uint64;
      description
        "Specifies the number of input packets received by the Segment Routing TE policy.";
    }
    leaf in-octets {
      type uint64;
      description
        "Specifies the total number of input octets received by the Segment Routing TE policy.";
    }
  }

  grouping te-policy-key {
    description
      "SR TE policy key";
    leaf color {
      type uint32;
      description
        "Indicates the color identifier associated with the Segment Routing TE policy.";
    }
    leaf endp {
      type inet:ip-address;
      description
        "Specifies the endpoint IP address for the Segment Routing TE policy.";
    }
  }

  grouping te-policy-param {
    description
      "SR TE policy parameters";
    leaf name {
      type string;
      description
        "Specifies the name of the Segment Routing TE policy.";
    }
    container counters {
      description
        "Contains the counters associated with the Segment Routing TE policy, including packet and octet statistics.";
      uses sr-ios-xe-oper:te-policy-counters;
    }
  }

  container sr-oper-data {
    config false;
    description
      "SR operational data";
    list sr-te-policy {
      key "color endp";
      description
        "Provides operational data for Segment Routing Traffic Engineering (TE) policies.";
      uses sr-ios-xe-oper:te-policy-param;
      uses sr-ios-xe-oper:te-policy-key;
    }
  }
}
