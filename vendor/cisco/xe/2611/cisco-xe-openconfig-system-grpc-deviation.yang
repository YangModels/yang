module cisco-xe-openconfig-system-grpc-deviation {
  namespace "http://cisco.com/ns/cisco-xe-openconfig-system-grpc-deviation";
  prefix oc-system-grpc-devs;

  import openconfig-system {
    prefix oc-sys;
  }
  import openconfig-system-grpc {
    prefix oc-sys-grpc;
  }

  organization
    "Cisco Systems, Inc.";
  contact
    "Cisco Systems, Inc.
     Customer Service

     Postal: 170 W Tasman Drive
     San Jose, CA 95134

     Tel: +1 1800 553-NETS

     E-mail: cs-yang@cisco.com";
  description
    "This module defines deviation statements for openconfig-system-grpc module.";

  revision 2021-10-22 {
    description
      "Initial Revision";
  }

  deviation "/oc-sys:system/oc-sys-grpc:grpc-servers/oc-sys-grpc:grpc-server" {
    deviate add {
      max-elements 2;
    }
  }

  deviation "/oc-sys:system/oc-sys-grpc:grpc-servers/oc-sys-grpc:grpc-server/oc-sys-grpc:config/oc-sys-grpc:name" {
    deviate replace {
      type string {
        pattern '(in)?secure-grpc' {
          error-message "Can only configure 'insecure-grpc' or 'secure-grpc' as names";
        }
      }
    }
  }

  deviation "/oc-sys:system/oc-sys-grpc:grpc-servers/oc-sys-grpc:grpc-server/oc-sys-grpc:config/oc-sys-grpc:listen-addresses" {
    deviate not-supported;
    description
      "Currently not supported";
  }

  deviation "/oc-sys:system/oc-sys-grpc:grpc-servers/oc-sys-grpc:grpc-server/oc-sys-grpc:state/oc-sys-grpc:listen-addresses" {
    deviate not-supported;
    description
      "Currently not supported";
  }
}
