module Cisco-IOS-XE-cloud-services-oper {
  yang-version 1.1;
  namespace "http://cisco.com/ns/yang/Cisco-IOS-XE-cloud-services-oper";
  prefix cloud-services-oper-data;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG
     definitions for operational data for cloud services.
     Copyright (c) 2023-2024 by Cisco Systems, Inc.
     All rights reserved.";

  revision 2024-03-01 {
    description
      "Initial revision";
    reference
      "1.0.0";
    cisco-semver:module-version "1.0.0";
  }

  typedef spaces-onboarding-conn-state {
    type enumeration {
      enum spaces-conn-invalid {
        value 0;
        description
          "Invalid state";
      }
      enum spaces-conn-init {
        value 1;
        description
          "Initial state: onboarding did not start";
      }
      enum spaces-conn-otp {
        value 2;
        description
          "OTP credentials received";
      }
      enum spaces-conn-upg-in-prog {
        value 3;
        description
          "OTP upgrade is in progress";
      }
      enum spaces-conn-auth-token {
        value 4;
        description
          "Auth-Token has been received";
      }
      enum spaces-conn-auth-in-prog {
        value 5;
        description
          "Authorization in progress";
      }
      enum spaces-conn-onboarded {
        value 6;
        description
          "Fully onboarded";
      }
    }
    description
      "Spaces connection state";
  }

  typedef otp-install-status {
    type enumeration {
      enum otp-install-invalid {
        value 0;
        description
          "Invalid OTP";
      }
      enum otp-install-ok {
        value 1;
        description
          "OTP installed successfully";
      }
      enum otp-install-wrong-state {
        value 2;
        description
          "OTP cannot be installed because onboarding machinery is not in init state";
      }
      enum otp-install-decode-err {
        value 3;
        description
          "OTP cannot be installed because of decoding errors";
      }
      enum otp-install-sign-verify-fail {
        value 4;
        description
          "OTP cannot be installed because of signature verification failures";
      }
      enum otp-install-expired {
        value 5;
        description
          "OTP is installed but is expired";
      }
    }
    description
      "Spaces OTP status";
  }

  grouping st-cloudm-spaces-status {
    description
      "DNA-Spaces connection status";
    leaf conn-attempts {
      type uint64;
      description
        "Number of connections attempts";
    }
    leaf token-reqs {
      type uint64;
      description
        "Number of access token requests";
    }
    leaf token-resps {
      type uint64;
      description
        "Number of access token responses";
    }
    leaf token-req-http-errors {
      type uint64;
      description
        "Number of HTTP errors in access token requests";
    }
    leaf otp-upg-reqs {
      type uint64;
      description
        "Number of OTP upgrade requests";
    }
    leaf otp-upg-resps {
      type uint64;
      description
        "Number of OTP upgrade responses";
    }
    leaf otp-upg-http-errors {
      type uint64;
      description
        "Number of HTTP errors in OTP upgrade requests";
    }
    leaf conn-state {
      type cloud-services-oper-data:spaces-onboarding-conn-state;
      description
        "State of the connection";
    }
    leaf auth-token-valid {
      type empty;
      description
        "The Auth-Token is valid";
    }
    leaf auth-token-install {
      type yang:date-and-time;
      description
        "When the Auth-Token has been installed";
    }
    leaf otp-status {
      type cloud-services-oper-data:otp-install-status;
      description
        "The OTP install status";
    }
  }

  container cloud-services-oper-data {
    config false;
    description
      "Cloud services operational data";
    container spaces-status {
      presence "spaces-status";
      description
        "Cloud services Spaces connection status";
      uses cloud-services-oper-data:st-cloudm-spaces-status;
    }
  }
}
