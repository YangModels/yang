module Cisco-IOS-XE-meraki-leds-actions-rpc {
  yang-version 1.1;
  namespace "http://cisco.com/ns/yang/Cisco-IOS-XE-meraki-leds-actions-rpc";
  prefix meraki-leds-actions-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for various LEDs actions on devices managed by Meraki.
     Copyright (c) 2023-2025 by Cisco Systems, Inc.
     All rights reserved.";

  revision 2026-02-01 {
    description
      "Added additional enumerated values for system LED state";
    reference
      "2.1.0";
    cisco-semver:module-version "2.1.0";
  }
  revision 2024-07-01 {
    description
      "Renamed switch number to chassis number";
    reference
      "2.0.0";
    cisco-semver:module-version "2.0.0";
  }
  revision 2024-03-01 {
    description
      "Initial revision";
    reference
      "1.0.0";
    cisco-semver:module-version "1.0.0";
  }

  typedef system-led-state {
    type enumeration {
      enum system-led-off {
        value 0;
        description
          "System LED is off";
      }
      enum system-led-solid-green {
        value 1;
        description
          "System LED is solid green";
      }
      enum system-led-blink-green {
        value 2;
        description
          "System LED is blinking green";
      }
      enum system-led-solid-amber {
        value 3;
        description
          "System LED is solid amber";
      }
      enum system-led-blink-amber {
        value 4;
        description
          "System LED is blinking amber";
      }
      enum system-led-rainbow {
        value 5;
        description
          "System LED is alternating between colors";
      }
      enum system-led-solid-white {
        value 6;
        description
          "System LED is solid white";
      }
      enum system-led-blink-white {
        value 7;
        description
          "System LED is blinking white";
      }
      enum system-led-alt-green-red {
        value 8;
        description
          "System LED is alternating between green and red";
      }
      enum system-led-solid-red {
        value 9;
        description
          "System LED is solid red";
      }
      enum system-led-blink-red {
        value 10;
        description
          "System LED is blinking red";
      }
    }
    description
      "State of the system LED";
  }

  typedef blink-action-type {
    type enumeration {
      enum blink-action-stop {
        value 0;
        description
          "Blink stop action";
      }
      enum blink-action-start {
        value 1;
        description
          "Blink start action";
      }
    }
    description
      "Blink action type";
  }

  grouping system-led-change {
    description
      "Set the system LED state based on chassis number";
    leaf chassis-number {
      type uint8 {
        range "0..16";
      }
      description
        "Chassis number or switch number";
    }
    leaf led-state {
      type meraki-leds-actions-rpc:system-led-state;
      mandatory true;
      description
        "New system LED state";
    }
  }

  grouping blink-leds-params {
    description
      "Trigger blinking of front LEDs on target chassis number";
    leaf chassis-number {
      type uint8 {
        range "0..16";
      }
      description
        "Chassis number or switch number, by default active switch/chassis will be targeted";
    }
    leaf action {
      type meraki-leds-actions-rpc:blink-action-type;
      mandatory true;
      description
        "Blinking start or stop action";
    }
    leaf duration {
      when "../action='blink-action-start'";
      type uint16 {
        range "5 .. 1800";
      }
      default "300";
      description
        "Duration in seconds, After expiry of this period blinking stops";
    }
  }

  rpc set-system-led-state {
    description
      "Set the system LED state for a device.";
    input {
      uses meraki-leds-actions-rpc:system-led-change;
    }
  }

  rpc blink-leds-cmd {
    description
      "Trigger for start/stop blinking device front LEDs";
    input {
      uses meraki-leds-actions-rpc:blink-leds-params;
    }
  }
}
