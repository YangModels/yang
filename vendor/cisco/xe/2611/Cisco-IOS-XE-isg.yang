module Cisco-IOS-XE-isg {
  yang-version 1.1;
  namespace "http://cisco.com/ns/yang/Cisco-IOS-XE-isg";
  prefix ios-isg;

  import cisco-semver {
    prefix cisco-semver;
  }
  import Cisco-IOS-XE-tunnel {
    prefix ios-tun;
  }
  import Cisco-IOS-XE-native {
    prefix ios;
  }
  import Cisco-IOS-XE-policy {
    prefix ios-pol;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Intelligent Subscriber Gateway (ISG) Yang model.
     Copyright (c) 2018-2019 by Cisco Systems, Inc.
     All rights reserved.";

  revision 2025-07-01 {
    description
      "- Added FiftyGigabitEthernet interface support";
    cisco-semver:module-version "2.2.0";
  }
  revision 2022-11-01 {
    description
      "- Update yang-version to 1.1";
    cisco-semver:module-version "2.1.0";
  }
  revision 2021-03-01 {
    description
      " Correct xpath in when statement and removed tailf:cli-diff-dependencies";
    cisco-semver:module-version "2.0.0";
  }
  revision 2019-11-01 {
    description
      "- Initial revision";
    cisco-semver:module-version "1.0.0";
  }

  typedef isg-action-type {
    type enumeration {
      enum authenticate;
      enum authorize;
      enum collect;
      enum default-apply;
      enum default-exit;
      enum if;
      enum log-session-state;
      enum post-account-logon-delay;
      enum proxy;
      enum service;
      enum service-policy;
      enum set;
      enum set-param;
      enum set-timer;
      enum substitute;
    }
  }

  grouping common-initiator-grouping {
    container dhcp {
      choice dhcp-choice {
        case dhcp-case {
          leaf dhcp-node {
            description
              "Session Initiator type - DHCP";
            type empty;
          }
        }
        case dhcp-class-aware-case {
          leaf class-aware {
            description
              "Influence the class name for DHCP";
            type empty;
          }
        }
      }
    }
    leaf radius-proxy {
      description
        "Session Initiator type - Radius Proxy";
      type empty;
    }
  }

  grouping common-interface-subscriber-grouping {
    container l2-connected {
      description
        "Layer 2 connected IP sessions";
      presence "true";
      must 'not (../routed )' {
        error-message "First unconfigure ip subscriber command,before configuring this command";
      }
      container initiator {
        description
          "IP session initiation configuration options";
        uses common-initiator-grouping;
        container unclassified {
          description
            "IP session initiated by unclassified traffic";
          container mac-address {
            description
              "IP session initiated by Unclassified MAC addr";
            leaf mac-address-node {
              must 'not ((../ipv4 ) or(../ipv6))' {
                error-message "First unconfigure other initiator command,before configuring this command";
              }
              type empty;
            }
            leaf ipv4 {
              description
                "Session initiated by unclassified MAC address IPv4 traffic only";
              must 'not ((../mac-address-node ) or(../ipv6))' {
                error-message "First unconfigure other initiator command,before configuring this command";
              }
              type empty;
            }
            leaf ipv6 {
              description
                "Session initiated by unclassified MAC address IPv6 traffic only";
              must 'not ((../ipv4 ) or(../mac-address-node))' {
                error-message "First unconfigure other initiator command,before configuring this command";
              }
              type empty;
            }
          }
        }
      }
    }
    container routed {
      description
        "Routed IP sessions";
      presence "true";
      must 'not (../l2-connected )' {
        error-message "First unconfigure ip subscriber command,before configuring this command";
      }
      container initiator {
        description
          "IP session initiation configuration options";
        uses common-initiator-grouping;
        container unclassified {
          description
            "IP session initiated by unclassified traffic";
          container ip-address {
            description
              "IP session initiated by Unclassified MAC address";
            leaf ip-address-node {
              must 'not ((../ipv4 ) or(../ipv6/ipv6-node))' {
                error-message "First unconfigure other initiator command,before configuring this command";
              }
              type empty;
            }
            leaf ipv4 {
              description
                "Session initiated by unclassified IPv4 traffic only";
              must 'not ((../ip-address-node ) or(../ipv6/ipv6-node))' {
                error-message "First unconfigure other initiator command,before configuring this command";
              }
              type empty;
            }
            container ipv6 {
              leaf ipv6-node {
                description
                  "Session initiated by unclassified IPv6 traffic only";
                must 'not ((../../ip-address-node ) or(../../ipv4))' {
                  error-message "First unconfigure other initiator command,before configuring this command";
                }
                type empty;
              }
            }
          }
        }
      }
    }
  }

  grouping config-interface-ip-subscriber-grouping {
    container subscriber {
      description
        "ip subscriber";
      uses common-interface-subscriber-grouping;
    }
  }

  grouping config-tunnel-interface-ip-subscriber-grouping {
    container subscriber {
      description
        "ip subscriber";
      when '(../../ios-tun:tunnel/ios-tun:mode/ios-tun:ethernet-config/ios-tun:gre/ios-tun:ipv4)';
      uses common-interface-subscriber-grouping;
    }
  }

  grouping isg-aaa-identifier-grouping {
    leaf identifier {
      type enumeration {
        enum authenticated-domain;
        enum authenticated-username;
        enum auto-detect;
        enum circuit-id;
        enum ctag-cos;
        enum ctag-vlan-id;
        enum dnis;
        enum generic-service-name;
        enum hostname;
        enum mac-address;
        enum nas-port;
        enum payload-etype;
        enum peer-ip-address;
        enum remote-id;
        enum source-ip-address;
        enum stag-cos;
        enum stag-type;
        enum stag-vlan-id;
        enum tunnel-name;
        enum unauthenticated-domain;
        enum unauthenticated-username;
        enum vc-id;
        enum vendor-class-id;
      }
    }
  }

  grouping isg-aaa-list-config-grouping {
    choice method {
      leaf method-list-name {
        description
          "Method list name";
        type string {
          length "1..256";
        }
      }
      leaf default {
        description
          "The default authentication list";
        type empty;
      }
    }
  }

  grouping config-isg-policy-map-grouping {
    container isg-class {
      description
        "ISG policy class config";
      list control-class {
        description
          "A control class-map to match against for this policy-map";
        key "name event";
        leaf name {
          description
            "Name of control class-map to reference";
          type union {
            type enumeration {
              enum always;
            }
            type string;
          }
          must "(((/ios:native/ios:policy/ios-pol:class-map[ios-pol:name = current()])and (/ios:native/ios:policy/ios-pol:class-map[ios-pol:type = 'control']))or (current() = 'always'))" {
            error-message
              "class map does not exist
               or currently active on a policy";
          }
        }
        leaf event {
          description
            "The event type this control class-map triggers upon";
          type enumeration {
            enum access-reject;
            enum account-logoff;
            enum account-logon;
            enum acct-notification;
            enum credit-exhausted;
            enum dummy-event;
            enum flow-timeout;
            enum quota-depleted;
            enum radius-timeout;
            enum service-failed;
            enum service-start;
            enum session-default-service;
            enum session-restart;
            enum session-service-found;
            enum session-start;
            enum timed-policy-expiry;
          }
        }
        leaf type {
          description
            "The class-map type";
          type enumeration {
            enum control;
          }
        }
        list action {
          description
            "list of actions per event";
          key "action-number";
          leaf action-number {
            description
              "Action number - 1 for 1st action to perform, 2 for 2nd..";
            type uint8 {
              range "1..254";
            }
          }
          choice action-param {
            case authenticate-case {
              container authenticate {
                description
                  "action authenticate";
                leaf authenticate-only {
                  description
                    "Authenticate the user";
                  type empty;
                }
                container aaa {
                  description
                    "Specify AAA parameters";
                  container list {
                    description
                      "Specify an AAA method list that key collection should be made with";
                    uses isg-aaa-list-config-grouping;
                  }
                }
              }
            }
            case authorize-case {
              container authorize {
                description
                  "Authorize the user";
                container aaa {
                  description
                    "Specify AAA parameters";
                  choice list-name {
                    case named-list-case {
                      leaf name {
                        description
                          "aaa method list name";
                        type string;
                      }
                    }
                    case method-list-case {
                      container list {
                        choice method {
                          case method-name-case {
                            leaf name {
                              description
                                "Method list name";
                              type string;
                            }
                          }
                          case default-case {
                            leaf default {
                              description
                                "The default authentication list";
                              type empty;
                            }
                          }
                        }
                      }
                    }
                  }
                  leaf password {
                    description
                      "Specify a password to be used for AAA request";
                    type string;
                  }
                  uses isg-aaa-identifier-grouping;
                }
                uses isg-aaa-identifier-grouping;
              }
            }
            case collect-case {
              container collect {
                description
                  "An identifier to collect from the access protocol";
                leaf identifier {
                  description
                    "ISG session identifiers";
                  type enumeration {
                    enum aaa-acct-enable;
                    enum authen-status;
                    enum authenticated-domain;
                    enum authenticated-username;
                    enum can-access-type-redirect;
                    enum circuit-id;
                    enum dnis;
                    enum generic-service-name;
                    enum mac-address;
                    enum media;
                    enum mlp-negotiated;
                    enum nas-port;
                    enum no-username;
                    enum p2p-circuit-status;
                    enum protocol;
                    enum remote-id;
                    enum resource-type-determined;
                    enum service-name;
                    enum source-ip-address;
                    enum timer;
                    enum transitioned-from-default;
                    enum tunnel-name;
                    enum unauthenticated-domain;
                    enum unauthenticated-username;
                    enum virtual-access;
                    enum virtual-circuit;
                    enum vrf;
                  }
                }
              }
            }
            case default-apply-case {
              leaf default-apply {
                description
                  "Apply default policy map";
                type empty;
              }
            }
            case default-exit-case {
              leaf default-exit {
                description
                  "Exit default policy map";
                type empty;
              }
            }
            case post-account-logon-delay-case {
              container post-account-logon-delay {
                description
                  "Set portal response delay post account logon";
                leaf timer {
                  description
                    "Timer value in milliseconds";
                  type uint32 {
                    range "1..2147483647";
                  }
                }
              }
            }
            case service-case {
              container service {
                description
                  "Specify a service to apply to the user";
                leaf disconnect {
                  description
                    "Disconnects the session";
                  type empty;
                }
              }
            }
            case service-policy-case {
              container service-policy {
                description
                  "Service-policy apply and unapply";
                leaf type {
                  description
                    "refer either control and service policies";
                  type enumeration {
                    enum service;
                  }
                }
                leaf unapply {
                  description
                    "Specify a service profile to unapply";
                  type empty;
                }
                leaf name {
                  description
                    "Specify a named service to apply";
                  type string;
                }
              }
            }
            case set-timer-case {
              container set-timer {
                description
                  "Set a timer to execute a rule on its expiry";
                leaf timer {
                  description
                    "Name of Timer";
                  type string;
                }
                leaf timer-value {
                  description
                    "Timer value in minutes";
                  type uint16 {
                    range "1..10100";
                  }
                }
              }
            }
          }
        }
      }
    }
  }

  augment "/ios:native/ios:policy/ios-pol:policy-map" {
    uses config-isg-policy-map-grouping;
  }

  augment "/ios:native/ios:interface/ios:FastEthernet/ios:ip" {
    uses config-interface-ip-subscriber-grouping;
  }

  augment "/ios:native/ios:interface/ios:GigabitEthernet/ios:ip" {
    uses config-interface-ip-subscriber-grouping;
  }

  augment "/ios:native/ios:interface/ios:TenGigabitEthernet/ios:ip" {
    uses config-interface-ip-subscriber-grouping;
  }

  augment "/ios:native/ios:interface/ios:FiveGigabitEthernet/ios:ip" {
    uses config-interface-ip-subscriber-grouping;
  }

  augment "/ios:native/ios:interface/ios:TwentyFiveGigE/ios:ip" {
    uses config-interface-ip-subscriber-grouping;
  }

  augment "/ios:native/ios:interface/ios:TwoGigabitEthernet/ios:ip" {
    uses config-interface-ip-subscriber-grouping;
  }

  augment "/ios:native/ios:interface/ios:FortyGigabitEthernet/ios:ip" {
    uses config-interface-ip-subscriber-grouping;
  }

  augment "/ios:native/ios:interface/ios:FiftyGigabitEthernet/ios:ip" {
    uses config-interface-ip-subscriber-grouping;
  }

  augment "/ios:native/ios:interface/ios:HundredGigE/ios:ip" {
    uses config-interface-ip-subscriber-grouping;
  }

  augment "/ios:native/ios:interface/ios:Port-channel/ios:ip" {
    uses config-interface-ip-subscriber-grouping;
  }

  augment "/ios:native/ios:interface/ios:Tunnel/ios:ip" {
    uses config-tunnel-interface-ip-subscriber-grouping;
  }

  augment "/ios:native/ios:interface/ios:BDI/ios:ip" {
    uses config-interface-ip-subscriber-grouping;
  }
}
