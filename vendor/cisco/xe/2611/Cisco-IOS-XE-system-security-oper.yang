module Cisco-IOS-XE-system-security-oper {
  yang-version 1.1;
  namespace "http://cisco.com/ns/yang/Cisco-IOS-XE-system-security-oper";
  prefix system-security-ios-xe-oper;

  import Cisco-IOS-XE-system-security-types {
    prefix system-security-types;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for operational data related to system security.
     Copyright (c) 2025 by Cisco Systems, Inc.
     All rights reserved.";

  revision 2026-02-01 {
    description
      "Initial revision";
    reference
      "1.0.0";
    cisco-semver:module-version "1.0.0";
  }

  grouping sys-insec-conf-details {
    description
      "System's insecure configuration CLI details";
    leaf index {
      type uint16;
      description
        "Insecure configuration CLI Index";
    }
    container insec-data {
      description
        "Insecure configuration data";
      uses system-security-types:sys-insec-info;
    }
  }

  container system-security-oper-data {
    config false;
    description
      "Operational data related to system security";
    list sys-insec-conf {
      key "index";
      description
        "List of insecure configurations in the system";
      uses system-security-ios-xe-oper:sys-insec-conf-details;
    }
  }
}
