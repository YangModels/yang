/*
 * Generated by confdc --mib2yang-std
 * Source: mgmt/dmi/model/mib/src/CISCO-TAP2-MIB.mib
 */
/*
 * This YANG module has been generated by smidump 0.5.0:
 *
 *      smidump -f yang CISCO-TAP2-MIB
 *
 * Do not edit. Edit the source file instead!
 */

module CISCO-TAP2-MIB {

  namespace "urn:ietf:params:xml:ns:yang:smiv2:CISCO-TAP2-MIB";
  prefix CISCO-TAP2-MIB;

  import IF-MIB {
    prefix "if-mib";
  }

  import INET-ADDRESS-MIB {
    prefix "inet-address";
  }

  import SNMP-FRAMEWORK-MIB {
    prefix "snmp-framework";
  }

  import SNMPv2-TC {
    prefix "snmpv2-tc";
  }

  import ietf-inet-types {
    prefix "inet";
  }

  import ietf-yang-smiv2 {
    prefix "smiv2";
  }

  import ietf-yang-types {
    prefix "yang";
  }

  organization
   "Cisco Systems, Inc.";

  contact
   "Cisco Systems
    Customer Service
    
    
    Postal:170 W. Tasman Drive
    San Jose, CA  95134
    USA
    
    
    Tel:+1 800 553-NETS
    
    
    E-mail:cs-li@cisco.com";

  description
   "This module manages Cisco's intercept feature.
    This MIB replaces CISCO-TAP-MIB. This MIB defines
    a generic stream table that contains fields common to
    all intercept types. Specific intercept filters are
    defined in extension MIBs. They are CISCO-IP-TAP-MIB
    for IP intercepts, CISCO-802-TAP-MIB for IEEE 802
    intercepts and CISCO-USER-CONNECTION-TAP-MIB for
    RADIUS-based user connection intercepts.";

  revision 2009-11-06 {
    description
     "Mediation Device could be accepting PacketCable1.5
      based information using Radius packets. A radius 
      server may define a secret key which is shared
      with the client. In addition, a new CISCO-VOIP-TAP-MIB
      is being defined and the cTap2StreamType is being 
      updated to reflect that.
      - Updated cTap2MediationTransport with radius(6) option.
      - Added new TC Ctap2RadiusKey.
      - Added cTap2MediationRadiusKey.
      - Update cTap2StreamType with voip(6).
      - Deprecated ciscoTap2MIBComplianceRev3.
      - Added ciscoTap2MIBComplianceRev4.
      - Added ciscoTap2MediationComplianceGroupSup1.
      - Update cTap2MediationCapabilities.";
  }

  revision 2008-09-10 {
    description
     "Added the 'mobility' enum to cTap2StreamType as a
      specific filter defined by CISCO-MOBILITY-TAP-MIB.";
  }

  revision 2007-12-21 {
    description
     "- Added support for cTap2DebugUserTable.
      - Added new enumeration rtp to
        'cTap2MediationTransport' object.
      - Added new enumeration rtp to 
        'cTap2MediationCapabilities' object.
      - Added ciscoTap2MIBComplianceRev3 compliance
        which deprecates ciscoTap2MIBComplianceRev2.
      - Added ciscoTap2DebugComplianceGroupRev1
        compliance Group which deprecates
        ciscoTap2DebugComplianceGroup.";
  }

  revision 2006-11-27 {
    description
     "- Following objects are added in table
      cTap2StreamTable to support counter64 data 
          cTap2StreamInterceptedHCPackets 
          cTap2StreamInterceptHCDrops  
      
      - Added ciscoTap2StreamHCStatsGroup OBJECT-GROUP 
      - Added ciscoTap2MIBComplianceRev2 compliance 
      which deprecates ciscoTap2MIBCompliance.";
  }

  revision 2004-03-11 {
    description
     "Added a new type to cTap2StreamType for intercepting
      sessions/flows of Mobile subscribers in wireless CDMA
      technology. Specific intercept filter is defined in
      CISCO-CDMA-PDSN-TAP-MIB.";
  }

  revision 2004-01-27 {
    description
     "Initial version of this MIB module.";
  }

  typedef Ctap2Dscp {
    type int32 {
      range "0..63";
    }
    description
     "An integer that is in the range of the DiffServ codepoint
      values.";
  }

  typedef Ctap2RadiusKey {
    type binary {
      length "0..64";
    }
    description
     "The authentication key shared between radius client & server.";
  }


  container CISCO-TAP2-MIB {
    config false;

    container cTap2MediationGroup {
      smiv2:oid "1.3.6.1.4.1.9.9.399.1.1";

      leaf cTap2MediationNewIndex {
        type int32 {
          range "1..2147483647";
        }
        description
         "This object contains a value which may be used as an index
          value for a new cTap2MediationEntry. Whenever read, the agent
          will change the value to a new non-conflicting value.  This is
          to reduce the probability of errors during creation of new
          cTap2MediationTable entries.";
        smiv2:max-access "read-only";
        smiv2:oid "1.3.6.1.4.1.9.9.399.1.1.1";
      }

      leaf cTap2MediationCapabilities {
        type bits {
          bit ipV4SrcInterface {
            position "0";
          }
          bit ipV6SrcInterface {
            position "1";
          }
          bit udp {
            position "2";
          }
          bit rtpNack {
            position "3";
          }
          bit tcp {
            position "4";
          }
          bit sctp {
            position "5";
          }
          bit rtp {
            position "6";
          }
          bit radius {
            position "7";
          }
        }
        description
         "This object displays the device capabilities with respect to
          certain fields in Mediation Device table. This may be dependent
          on hardware capabilities, software capabilities.
          The following values may be supported:
              ipV4SrcInterface:  SNMP ifIndex Value may be used to select
                                 the interface (denoted by
                                 cTap2MediationSrcInterface) on the
                                 intercepting device from which to
                                 transmit intercepted data to an IPv4
                                 address Mediation Device.
          
          
              ipV6SrcInterface:  SNMP ifIndex Value may be used to select
                                 the interface (denoted by
                                 cTap2MediationSrcInterface) on the
                                 intercepting device from which to
                                 transmit intercepted data to an IPv6
                                 address Mediation Device.
          
          
              udp:               UDP may be used as transport protocol
                                 (denoted by cTap2MediationTransport) in
                                 transferring intercepted data to the
                                 Mediation Device.
          
          
              rtcpNack:          RTP with Nack resilience may be used
                                 as transport protocol (denoted by
                                 cTap2MediationTransport) in transferring
                                 intercepted data to the Mediation
                                 Device.
          
              tcp:               TCP may be used as transport protocol
                                 (denoted by cTap2MediationTransport) in
                                 transferring intercepted data to the
                                 Mediation Device.
          
          
              sctp:              SCTP may be used as transport protocol
                                 (denoted by cTap2MediationTransport) in
                                 transferring intercepted data to the
                                 Mediation Device.
          
              rtp:               RTP may be used as transport protocol
                                 (denoted by cTap2MediationTransport) in
                                 transferring intercepted data to the
                                 Mediation Device. 
          
              radius:            Radius may be used as transport protocol
                                 (denoted by cTap2MediationTransport) in
                                 transferring intercepted information to 
                                 the Mediation Device.";
        smiv2:max-access "read-only";
        smiv2:oid "1.3.6.1.4.1.9.9.399.1.1.3";
      }
    }

    container cTap2DebugGroup {
      smiv2:oid "1.3.6.1.4.1.9.9.399.1.3";

      leaf cTap2DebugAge {
        type int32 {
          range "1..2147483647";
        }
        description
         "This object contains the duration in minutes for which an
          entry in cTap2DebugTable is maintained by the implementing
          device after which the entry is deleted. The management
          station also has the option of deleting the entry itself
          by setting cTap2DebugStatus.";
        smiv2:max-access "read-only";
        smiv2:oid "1.3.6.1.4.1.9.9.399.1.3.1";
      }

      leaf cTap2DebugMaxEntries {
        type int32 {
          range "1..2147483647";
        }
        description
         "This object contains the maximum number of debug messages
          maintained by the implementing device at a time. If this 
          limit is crossed, most recent message will replace the
          least recent message.";
        smiv2:max-access "read-only";
        smiv2:oid "1.3.6.1.4.1.9.9.399.1.3.2";
      }
    }

    container cTap2MediationTable {
      description
       "This table lists the Mediation Devices with which the
        intercepting device communicates. These may be on the same or
        different Mediation Devices.
        
        
        This table is written by the Mediation Device, and is always
        volatile. This is because intercepts may disappear during a
        restart of the intercepting equipment.
        
        Entries are added to this table via cTap2MediationStatus in 
        accordance with the RowStatus convention.";
      smiv2:oid "1.3.6.1.4.1.9.9.399.1.1.2";

      list cTap2MediationEntry {
        key "cTap2MediationContentId";
        description
         "The entry describes a single session maintained with an
          application on a Mediation Device.";
        smiv2:oid "1.3.6.1.4.1.9.9.399.1.1.2.1";

        leaf cTap2MediationContentId {
          type int32 {
            range "1..2147483647";
          }
          description
           "cTap2MediationContentId is a session identifier, from the
            intercept application's perspective, and a content identifier
            from the Mediation Device's perspective. The Mediation Device
            is responsible for making sure these are unique, although the
            SNMP RowStatus row creation process will help by not allowing
            it to create conflicting entries. Before creating a new entry,
            a value for this variable may be obtained by reading
            cTap2MediationNewIndex to reduce the probability of a value
            collision.";
          smiv2:max-access "not-accessible";
          smiv2:oid "1.3.6.1.4.1.9.9.399.1.1.2.1.1";
        }

        leaf cTap2MediationDestAddressType {
          type inet-address:InetAddressType;
          description
           "The type of cTap2MediationDestAddress.";
          smiv2:max-access "read-write";
          smiv2:oid "1.3.6.1.4.1.9.9.399.1.1.2.1.2";
        }

        leaf cTap2MediationDestAddress {
          type inet-address:InetAddress;
          description
           "The IP Address of the Mediation Device's network interface
            to which to direct intercepted traffic.";
          smiv2:max-access "read-write";
          smiv2:oid "1.3.6.1.4.1.9.9.399.1.1.2.1.3";
        }

        leaf cTap2MediationDestPort {
          type inet:port-number;
          description
           "The port number on the Mediation Device's network interface
            to which to direct intercepted traffic.";
          smiv2:max-access "read-write";
          smiv2:oid "1.3.6.1.4.1.9.9.399.1.1.2.1.4";
        }

        leaf cTap2MediationSrcInterface {
          type if-mib:InterfaceIndexOrZero;
          description
           "The interface on the intercepting device from which to
            transmit intercepted data. If zero, any interface may be used
            according to normal IP practice.";
          smiv2:max-access "read-write";
          smiv2:oid "1.3.6.1.4.1.9.9.399.1.1.2.1.5";
        }

        leaf cTap2MediationRtcpPort {
          type inet:port-number;
          description
           "The port number on the intercepting device to which the
            Mediation Devices directs RTCP Receiver Reports and Nacks.
            This object is only relevant when the value of
            cTap2MediationTransport is 'rtpNack'.
            
            
            This port is assigned by the intercepting device, rather than
            by the Mediation Device or manager application.  The value of
            this MIB object has no effect before activating the
            cTap2MediationEntry.";
          smiv2:max-access "read-only";
          smiv2:oid "1.3.6.1.4.1.9.9.399.1.1.2.1.6";
        }

        leaf cTap2MediationDscp {
          type CISCO-TAP2-MIB:Ctap2Dscp;
          description
           "The Differentiated Services Code Point the intercepting
            device applies to the IP packets encapsulating the
            intercepted traffic.";
          smiv2:defval "34";
          smiv2:max-access "read-write";
          smiv2:oid "1.3.6.1.4.1.9.9.399.1.1.2.1.7";
        }

        leaf cTap2MediationDataType {
          type int32 {
            range "0..127";
          }
          description
           "If RTP with Ack/Nack resilience is selected as a transport,
            the mediation process requires an RTP payload type for data
            transmissions, and a second RTP payload type for
            retransmissions.  This is the RTP payload type for
            transmissions.
            
            
            This object is only effective when the value of
            cTap2MediationTransport is 'rtpNack'.";
          smiv2:defval "0";
          smiv2:max-access "read-write";
          smiv2:oid "1.3.6.1.4.1.9.9.399.1.1.2.1.8";
        }

        leaf cTap2MediationRetransmitType {
          type int32 {
            range "0..127";
          }
          description
           "If RTP with Ack/Nack resilience is selected as a transport,
            the mediation process requires an RTP payload type for data
            transmissions, and a second RTP payload type for
            retransmissions.  This is the RTP payload type for
            retransmissions.
            
            
            This object is only effective when the value of
            cTap2MediationTransport is 'rtpNack'.";
          smiv2:defval "0";
          smiv2:max-access "read-write";
          smiv2:oid "1.3.6.1.4.1.9.9.399.1.1.2.1.9";
        }

        leaf cTap2MediationTimeout {
          type snmpv2-tc:DateAndTime;
          description
           "The time at which this row and all related Stream Table rows
            should be automatically removed, and the intercept function
            cease. Since the initiating network manager may be the only
            device able to manage a specific intercept or know of its
            existence, this acts as a fail-safe for the failure or removal
            of the network manager. The object is only effective when the
            value of cTap2MediationStatus is 'active'.";
          smiv2:max-access "read-write";
          smiv2:oid "1.3.6.1.4.1.9.9.399.1.1.2.1.10";
        }

        leaf cTap2MediationTransport {
          type enumeration {
            enum "udp" {
              value "1";
            }
            enum "rtpNack" {
              value "2";
            }
            enum "tcp" {
              value "3";
            }
            enum "sctp" {
              value "4";
            }
            enum "rtp" {
              value "5";
            }
            enum "radius" {
              value "6";
            }
          }
          description
           "The protocol used in transferring intercepted data to the
            Mediation Device. The following protocols may be supported:
                       udp:     PacketCable udp format
                       rtpNack: RTP with Nack resilience
                       tcp:     TCP with head of line blocking
                       sctp:    SCTP with head of line blocking 
                       rtp:     Realtime Transport Protocol(RTP)
                                packet format
                       radius:  Use Radius, PacketCable1.5 Event Message
                                to transport the intercepted information.";
          smiv2:max-access "read-write";
          smiv2:oid "1.3.6.1.4.1.9.9.399.1.1.2.1.11";
        }

        leaf cTap2MediationNotificationEnable {
          type boolean;
          description
           "This variable controls the generation of any notifications or
            informs by the MIB agent for this table entry.";
          smiv2:defval "true";
          smiv2:max-access "read-write";
          smiv2:oid "1.3.6.1.4.1.9.9.399.1.1.2.1.12";
        }

        leaf cTap2MediationStatus {
          type snmpv2-tc:RowStatus;
          description
           "The status of this conceptual row. This object is used to
            manage creation, modification and deletion of rows in this
            table.
            
            
            cTap2MediationTimeout may be modified at any time (even while
            the row is active). But when the row is active, the other
            writable objects may not be modified without setting its value
            to 'notInService'.
            
            
            The entry may not be deleted or deactivated by setting its
            value to 'destroy' or 'notInService' if there is any associated
            entry in cTap2StreamTable.";
          smiv2:max-access "read-write";
          smiv2:oid "1.3.6.1.4.1.9.9.399.1.1.2.1.13";
        }

        leaf cTap2MediationRadiusKey {
          type CISCO-TAP2-MIB:Ctap2RadiusKey;
          description
           "Radius Authentication Key is the shared secret key between 
            radius client and server.";
          smiv2:max-access "read-write";
          smiv2:oid "1.3.6.1.4.1.9.9.399.1.1.2.1.14";
        }
      }
    }

    container cTap2StreamTable {
      description
       "The Intercept Stream Table lists the traffic streams to be
        intercepted. The same data stream may be required by multiple 
        taps, and one might assume that often the intercepted stream 
        is a small subset of the traffic that could be intercepted.
        
        
        The Table consists of generic fields that are independent
        of the type of intercept. It contains type of the specific 
        filter which is defined in an extension MIB and counters to 
        account for packets intercepted or dropped by the attached
        filter specification.
        
        Note that the Mediation Device must make sure there is 
        only one type of specific filter created with the same 
        indices as that of a row in this table, otherwise the 
        later creations will fail. For example, if there is a 
        row in this table with index 1.2, there can be a 
        corresponding row with the same index either in 
        citapStreamTable, c8tapStreamTable or cuctTapStreamTable,
        but not all. 
        
        
        The first index indicates which Mediation Device the
        intercepted traffic will be diverted to. The second index
        permits multiple classifiers to be used together. 
        
        Entries are added to this table via cTap2StreamStatus in
        accordance with the RowStatus convention.";
      smiv2:oid "1.3.6.1.4.1.9.9.399.1.2.1";

      list cTap2StreamEntry {
        key "cTap2MediationContentId cTap2StreamIndex";
        description
         "A stream entry indicates a single data stream to be
          intercepted to a Mediation Device. Many selected data
          streams may go to the same application interface, and many
          application interfaces are supported.";
        smiv2:oid "1.3.6.1.4.1.9.9.399.1.2.1.1";

        leaf cTap2MediationContentId {
          type leafref {
            path "/CISCO-TAP2-MIB:CISCO-TAP2-MIB/CISCO-TAP2-MIB:cTap2MediationTable/CISCO-TAP2-MIB:cTap2MediationEntry/CISCO-TAP2-MIB:cTap2MediationContentId";
          }
        }

        leaf cTap2StreamIndex {
          type int32 {
            range "1..2147483647";
          }
          description
           "The index of the stream itself.";
          smiv2:max-access "not-accessible";
          smiv2:oid "1.3.6.1.4.1.9.9.399.1.2.1.1.1";
        }

        leaf cTap2StreamType {
          type enumeration {
            enum "ip" {
              value "1";
            }
            enum "mac" {
              value "2";
            }
            enum "userConnection" {
              value "3";
            }
            enum "msPdsn" {
              value "4";
            }
            enum "mobility" {
              value "5";
            }
            enum "voip" {
              value "6";
            }
          }
          description
           "Identifies the type of intercept filter associated to this
            generic stream. The following types of streams are supported:
                   ip:             The specific filter is an IP filter 
                                   with same indices as that of this 
                                   table. The exact filter is a row in 
                                   citapStreamTable of CISCO-IP-TAP-MIB.
                   mac:            The specific filter is a MAC filter
                                   with same indices as that of this table.
                                   The exact filter is a row in 
                                   c8tapStreamTable of CISCO-802-TAP-MIB.
                   userConnecton:  The specific filter is a user connection
                                   filter with same indices as that of 
                                   this table. The exact filter is a row 
                                   in cuctTapStreamTable of 
                                   CISCO-USER-CONNECTION-TAP-MIB.
                   msPdsn:         The specific filter is a Mobile Sub
                                   connection filter with same indices as
                                   that of this table. The exact filter
                                   is a row in ccptapStreamTable of 
                                   CISCO-CDMA-PDSN-TAP-MIB.
                   mobility:       The specific filter is a Mobile 
                                   Subscriber connection filter with same
                                   indices as that of this table. The exact
                                   filter is a row in cmtapStreamTable of 
                                   CISCO-MOBILITY-TAP-MIB.
                   voip:           The specific filter is a VoIP
                                   Subscriber filter with same
                                   indices as that of this table. The exact
                                   filter is a row in cvoiptapStreamTable of
                                   CISCO-VOIP-TAP-MIB.";
          smiv2:max-access "read-write";
          smiv2:oid "1.3.6.1.4.1.9.9.399.1.2.1.1.2";
        }

        leaf cTap2StreamInterceptEnable {
          type boolean;
          description
           "If 'true', the tap should intercept matching traffic. The
            value for this object should be set to 'true' only after an 
            additional filter specification has been attached to this 
            stream.";
          smiv2:defval "false";
          smiv2:max-access "read-write";
          smiv2:oid "1.3.6.1.4.1.9.9.399.1.2.1.1.3";
        }

        leaf cTap2StreamInterceptedPackets {
          type yang:counter32;
          description
           "The number of packets matching this data stream specification
            that have been intercepted.";
          smiv2:max-access "read-only";
          smiv2:oid "1.3.6.1.4.1.9.9.399.1.2.1.1.4";
        }

        leaf cTap2StreamInterceptDrops {
          type yang:counter32;
          description
           "The number of packets matching this data stream specification
            that, having been intercepted, were dropped in the lawful
            intercept process.";
          smiv2:max-access "read-only";
          smiv2:oid "1.3.6.1.4.1.9.9.399.1.2.1.1.5";
        }

        leaf cTap2StreamStatus {
          type snmpv2-tc:RowStatus;
          description
           "The status of this conceptual row. This object manages
            creation, modification, and deletion of rows in this table.
            cTap2StreamInterceptEnable may be modified any time even the
            value of this entry rowStatus object is 'active'.  When other
            rows must be changed, cTap2StreamStatus must be first set to
            'notInService'.";
          smiv2:max-access "read-write";
          smiv2:oid "1.3.6.1.4.1.9.9.399.1.2.1.1.6";
        }

        leaf cTap2StreamInterceptedHCPackets {
          type yang:counter64;
          description
           "The number of packets matching this data stream specification
            that have been intercepted. This object is a 64-bit version of
            cTap2StreamInterceptedPackets.";
          smiv2:max-access "read-only";
          smiv2:oid "1.3.6.1.4.1.9.9.399.1.2.1.1.7";
        }

        leaf cTap2StreamInterceptHCDrops {
          type yang:counter64;
          description
           "The number of packets matching this data stream specification
            that, having been intercepted, were dropped in the lawful
            intercept process. This object is a 64-bit version of
            cTap2StreamInterceptDrops.";
          smiv2:max-access "read-only";
          smiv2:oid "1.3.6.1.4.1.9.9.399.1.2.1.1.8";
        }
      }
    }

    container cTap2DebugTable {
      description
       "A table that contains Lawful Intercept debug messages
        generated by the implementing device. This table is used 
        by ciscoTap2MediationDebug and ciscoTap2StreamDebug 
        notifications.
        
        An entry in this table contains a debug message which is
        regarding either a Mediation Device or a intercept stream 
        created by a Mediation Device. The Mediation device is 
        identified by cTap2DebugMediationId whose value is
        that of cTap2MediationContentId of cTapMediationEntry.
        The stream is identified by cTap2DebugMediationId and
        cTap2DebugStreamId whose values are that of 
        cTap2MediationContentId and cTap2StreamIndex of 
        the corresponding cTap2StreamEntry.
        
        Note that cTap2DebugStreamId may be zero for an entry,
        in which case the debug message is regarding a Medation
        Device.
        
        Entries are added to this table via cTap2DebugStatus in
        accordance with the RowStatus convention.";
      smiv2:oid "1.3.6.1.4.1.9.9.399.1.3.3";

      list cTap2DebugEntry {
        key "cTap2DebugIndex";
        description
         "A list of the debug messages.";
        smiv2:oid "1.3.6.1.4.1.9.9.399.1.3.3.1";

        leaf cTap2DebugIndex {
          type int32 {
            range "1..2147483647";
          }
          description
           "Index to the debug table.";
          smiv2:max-access "not-accessible";
          smiv2:oid "1.3.6.1.4.1.9.9.399.1.3.3.1.1";
        }

        leaf cTap2DebugMediationId {
          type uint32;
          description
           "The value of this object is that of cTap2MediationContentId
            identifying an entry in cTap2MediationTable. Note this object
            may contain a value for which an entry in cTap2MediationTable
            does not exist. This happens when creation of an entry in
            cTap2MediationTable fails and this debug message conveys more
            detailed information regarding the failure.";
          smiv2:max-access "read-only";
          smiv2:oid "1.3.6.1.4.1.9.9.399.1.3.3.1.2";
        }

        leaf cTap2DebugStreamId {
          type uint32;
          description
           "The value of this object is that of cTap2StreamIndex of an
            entry in cTap2StreamTable. This object along with
            cTap2DebugMediationId identifies an entry in cTap2StreamTable.
            The value of this object may be zero, in which this debug
            message is regarding a Mediation Device, but not a particular
            stream.  Note this object may contain a value for which an 
            entry in cTap2MediationTable does not exist. This happens 
            when creation of an entry in cTap2StreamTable fails.";
          smiv2:max-access "read-only";
          smiv2:oid "1.3.6.1.4.1.9.9.399.1.3.3.1.3";
        }

        leaf cTap2DebugMessage {
          type snmp-framework:SnmpAdminString;
          description
           "A text string contains the debug message.";
          smiv2:max-access "read-only";
          smiv2:oid "1.3.6.1.4.1.9.9.399.1.3.3.1.4";
        }

        leaf cTap2DebugStatus {
          type snmpv2-tc:RowStatus;
          description
           "The status of this conceptual row. A row in this table is
            created by the implementing device. A management station cannot
            modify any of the objects in this row, except deleting the row
            by setting this object to 'destroy'.";
          smiv2:max-access "read-write";
          smiv2:oid "1.3.6.1.4.1.9.9.399.1.3.3.1.5";
        }
      }
    }

    container cTap2DebugUserTable {
      description
       "The User Table lists information of all the users configured
        in the system who are given permission by different Mediation
        Devices to access Lawful Intercept CLIs.
        
        This table will have dependancy on cTap2MediationTable. When
        entry in cTap2MediationTable is deleted or moved to
        'notInService', entries corresponding cTap2MediationContentId
        in this table will be deleted.";
      smiv2:oid "1.3.6.1.4.1.9.9.399.1.3.4";

      list cTap2DebugUserEntry {
        key "cTap2MediationContentId cTap2DebugUserName";
        description
         "A conceptual row in the cTap2DebugUserTable. Each row
          represents name of user on the router to whom Mediation Device
          with CCCid represented by cTap2MediationContentId has given
          access to Lawful Intercept commands and cTap2DebugUserTimeout
          represents the time when the entry will expire.";
        smiv2:oid "1.3.6.1.4.1.9.9.399.1.3.4.1";

        leaf cTap2MediationContentId {
          type leafref {
            path "/CISCO-TAP2-MIB:CISCO-TAP2-MIB/CISCO-TAP2-MIB:cTap2MediationTable/CISCO-TAP2-MIB:cTap2MediationEntry/CISCO-TAP2-MIB:cTap2MediationContentId";
          }
        }

        leaf cTap2DebugUserName {
          type snmp-framework:SnmpAdminString {
            length "1..255";
          }
          description
           "A human readable string representing the name of debug user
            who will have access to Lawful Intercept commands.";
          smiv2:max-access "not-accessible";
          smiv2:oid "1.3.6.1.4.1.9.9.399.1.3.4.1.1";
        }

        leaf cTap2DebugUserTimeout {
          type snmpv2-tc:DateAndTime;
          description
           "This object specifies the time at which the row will be
            removed from the table by the system. The value of this object
            is only effective when the value of corresponding instance of
            cTap2DebugUserStatus is 'active'.";
          smiv2:max-access "read-write";
          smiv2:oid "1.3.6.1.4.1.9.9.399.1.3.4.1.2";
        }

        leaf cTap2DebugUserStorageType {
          type snmpv2-tc:StorageType;
          description
           "This object specifies the storage type of this conceptual row.
            If it is set to 'nonVolatile', this entry can be saved into
            non-volatile memory.";
          smiv2:defval "volatile";
          smiv2:max-access "read-write";
          smiv2:oid "1.3.6.1.4.1.9.9.399.1.3.4.1.3";
        }

        leaf cTap2DebugUserStatus {
          type snmpv2-tc:RowStatus;
          description
           "The status of this conceptual row. This object manages
            creation, modification, and deletion of rows in this table.
            cTap2DebugUserTimeout may be modified any time even when the
            value of this entry rowStatus object is 'active'.";
          smiv2:max-access "read-write";
          smiv2:oid "1.3.6.1.4.1.9.9.399.1.3.4.1.4";
        }
      }
    }
  }

  notification ciscoTap2MIBActive {
    description
     "This Notification is sent when an intercepting router or
      switch is first capable of intercepting a packet corresponding
      to a configured data stream. The value of the corresponding 
      cTap2StreamType which identifies the actual intercept stream
      type is included in this notification.
      
      
      This notification may be generated in conjunction with the
      intercept application, which is designed to expect the
      notification to be sent as reliably as possible, e.g., through
      the use of a finite number of retransmissions until
      acknowledged, as and when such mechanisms are available; for
      example, with SNMPv3, this would be an InformRequest.  Filter
      installation can take a long period of time, during which call
      progress may be delayed.";
    smiv2:oid "1.3.6.1.4.1.9.9.399.0.1";
  }

  notification ciscoTap2MediationTimedOut {
    description
     "When an intercept is autonomously removed by an intercepting
      device, such as due to the time specified in
      cTap2MediationTimeout arriving, the device notifies the manager
      of the action.";
    smiv2:oid "1.3.6.1.4.1.9.9.399.0.2";

    container object-1 {

      leaf cTap2MediationContentId {
        type leafref {
          path "/CISCO-TAP2-MIB:CISCO-TAP2-MIB/CISCO-TAP2-MIB:cTap2MediationTable/CISCO-TAP2-MIB:cTap2MediationEntry/CISCO-TAP2-MIB:cTap2MediationContentId";
        }
      }

      leaf cTap2MediationStatus {
        type leafref {
          path "/CISCO-TAP2-MIB:CISCO-TAP2-MIB/CISCO-TAP2-MIB:cTap2MediationTable/CISCO-TAP2-MIB:cTap2MediationEntry/CISCO-TAP2-MIB:cTap2MediationStatus";
        }
      }
    }
  }

  notification ciscoTap2MediationDebug {
    description
     "When there is intervention needed due to some events related
      to entries configured in cTap2MediationTable, the device
      notifies the manager of the event.
      
      
      This notification may be generated in conjunction with the
      intercept application, which is designed to expect the
      notification to be sent as reliably as possible, e.g., through
      the use of a finite number of retransmissions until
      acknowledged, as and when such mechanisms are available; for
      example, with SNMPv3, this would be an InformRequest.";
    smiv2:oid "1.3.6.1.4.1.9.9.399.0.3";

    container object-1 {

      leaf cTap2DebugIndex {
        type leafref {
          path "/CISCO-TAP2-MIB:CISCO-TAP2-MIB/CISCO-TAP2-MIB:cTap2DebugTable/CISCO-TAP2-MIB:cTap2DebugEntry/CISCO-TAP2-MIB:cTap2DebugIndex";
        }
      }

      leaf cTap2DebugMediationId {
        type leafref {
          path "/CISCO-TAP2-MIB:CISCO-TAP2-MIB/CISCO-TAP2-MIB:cTap2DebugTable/CISCO-TAP2-MIB:cTap2DebugEntry/CISCO-TAP2-MIB:cTap2DebugMediationId";
        }
      }
    }

    container object-2 {

      leaf cTap2DebugIndex {
        type leafref {
          path "/CISCO-TAP2-MIB:CISCO-TAP2-MIB/CISCO-TAP2-MIB:cTap2DebugTable/CISCO-TAP2-MIB:cTap2DebugEntry/CISCO-TAP2-MIB:cTap2DebugIndex";
        }
      }

      leaf cTap2DebugMessage {
        type leafref {
          path "/CISCO-TAP2-MIB:CISCO-TAP2-MIB/CISCO-TAP2-MIB:cTap2DebugTable/CISCO-TAP2-MIB:cTap2DebugEntry/CISCO-TAP2-MIB:cTap2DebugMessage";
        }
      }
    }
  }

  notification ciscoTap2StreamDebug {
    description
     "When there is intervention needed due to some events related
      to entries configured in cTap2StreamTable, the device
      notifies the manager of the event.
      
      
      This notification may be generated in conjunction with the
      intercept application, which is designed to expect the
      notification to be sent as reliably as possible, e.g., through
      the use of a finite number of retransmissions until
      acknowledged, as and when such mechanisms are available; for
      example, with SNMPv3, this would be an InformRequest.";
    smiv2:oid "1.3.6.1.4.1.9.9.399.0.4";

    container object-1 {

      leaf cTap2DebugIndex {
        type leafref {
          path "/CISCO-TAP2-MIB:CISCO-TAP2-MIB/CISCO-TAP2-MIB:cTap2DebugTable/CISCO-TAP2-MIB:cTap2DebugEntry/CISCO-TAP2-MIB:cTap2DebugIndex";
        }
      }

      leaf cTap2DebugMediationId {
        type leafref {
          path "/CISCO-TAP2-MIB:CISCO-TAP2-MIB/CISCO-TAP2-MIB:cTap2DebugTable/CISCO-TAP2-MIB:cTap2DebugEntry/CISCO-TAP2-MIB:cTap2DebugMediationId";
        }
      }
    }

    container object-2 {

      leaf cTap2DebugIndex {
        type leafref {
          path "/CISCO-TAP2-MIB:CISCO-TAP2-MIB/CISCO-TAP2-MIB:cTap2DebugTable/CISCO-TAP2-MIB:cTap2DebugEntry/CISCO-TAP2-MIB:cTap2DebugIndex";
        }
      }

      leaf cTap2DebugStreamId {
        type leafref {
          path "/CISCO-TAP2-MIB:CISCO-TAP2-MIB/CISCO-TAP2-MIB:cTap2DebugTable/CISCO-TAP2-MIB:cTap2DebugEntry/CISCO-TAP2-MIB:cTap2DebugStreamId";
        }
      }
    }

    container object-3 {

      leaf cTap2DebugIndex {
        type leafref {
          path "/CISCO-TAP2-MIB:CISCO-TAP2-MIB/CISCO-TAP2-MIB:cTap2DebugTable/CISCO-TAP2-MIB:cTap2DebugEntry/CISCO-TAP2-MIB:cTap2DebugIndex";
        }
      }

      leaf cTap2DebugMessage {
        type leafref {
          path "/CISCO-TAP2-MIB:CISCO-TAP2-MIB/CISCO-TAP2-MIB:cTap2DebugTable/CISCO-TAP2-MIB:cTap2DebugEntry/CISCO-TAP2-MIB:cTap2DebugMessage";
        }
      }
    }
  }

  notification ciscoTap2Switchover {
    description
     "This notification is sent when there is a redundant (standby)
      route processor available on the intercepting device and the
      current active processor is going down causing standby to
      takeover. Note that this notification may be sent by the
      intercepting device only when it had a chance to know before it
      goes down.
      
      Mediation device when received this notification should assume 
      that configured intercepts on the intercepting device no longer
      exist, when the standby processor takes control. This means that
      the Mediation device should again configure the intercepts.";
    smiv2:oid "1.3.6.1.4.1.9.9.399.0.5";
  }

  smiv2:alias "ciscoTap2MIB" {
    smiv2:oid "1.3.6.1.4.1.9.9.399";
  }

  smiv2:alias "ciscoTap2MIBNotifs" {
    smiv2:oid "1.3.6.1.4.1.9.9.399.0";
  }

  smiv2:alias "ciscoTap2MIBObjects" {
    smiv2:oid "1.3.6.1.4.1.9.9.399.1";
  }

  smiv2:alias "cTap2MediationGroup" {
    smiv2:oid "1.3.6.1.4.1.9.9.399.1.1";
  }

  smiv2:alias "cTap2StreamGroup" {
    smiv2:oid "1.3.6.1.4.1.9.9.399.1.2";
  }

  smiv2:alias "cTap2DebugGroup" {
    smiv2:oid "1.3.6.1.4.1.9.9.399.1.3";
  }

  smiv2:alias "ciscoTap2MIBConform" {
    smiv2:oid "1.3.6.1.4.1.9.9.399.2";
  }

  smiv2:alias "ciscoTap2MIBCompliances" {
    smiv2:oid "1.3.6.1.4.1.9.9.399.2.1";
  }

  smiv2:alias "ciscoTap2MIBGroups" {
    smiv2:oid "1.3.6.1.4.1.9.9.399.2.2";
  }

}
