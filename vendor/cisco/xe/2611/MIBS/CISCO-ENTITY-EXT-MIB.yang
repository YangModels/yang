/*
 * Generated by confdc --mib2yang-std
 * Source: mgmt/dmi/model/mib/src/CISCO-ENTITY-EXT-MIB.mib
 */
/*
 * This YANG module has been generated by smidump 0.5.0:
 *
 *      smidump -f yang CISCO-ENTITY-EXT-MIB
 *
 * Do not edit. Edit the source file instead!
 */

module CISCO-ENTITY-EXT-MIB {

  namespace "urn:ietf:params:xml:ns:yang:smiv2:CISCO-ENTITY-EXT-MIB";
  prefix CISCO-ENTITY-EXT-MIB;

  import CISCO-TC {
    prefix "cisco-tc";
  }

  import ENTITY-MIB {
    prefix "entity-mib";
  }

  import SNMP-FRAMEWORK-MIB {
    prefix "snmp-framework";
  }

  import ietf-yang-smiv2 {
    prefix "smiv2";
  }

  organization
   "Cisco Systems, Inc.";

  contact
   "Cisco Systems
    Customer Service
    
    Postal: 170 W. Tasman Drive
    San Jose, CA 95134
    USA
    
    Tel: +1 800 553-NETS
    
    E-mail: cs-snmp@cisco.com";

  description
   "This MIB is an extension of the ENTITY-MIB
    specified in RFC2737.
    
    This MIB module contains  Cisco-defined  extensions 
    to the  entityPhysicalTable to represent information
    related to entities of class module(entPhysicalClass
    = 'module') which have a Processor.
    
    A processor module is defined as a physical entity
    that has a CPU, RAM and NVRAM  so that
    it can independently
       - load a bootable image
       - save configuration.
    This module is the entry point for external
    applications like SNMP Manager, CLI, FTP etc.
    
    Line card is an interface card         with at least a 
    Processor and RAM. This might be referred to as 
    Service Module in some cisco products.
    
    A configuration register is  a 16 bit 
    software register.
    The configuration register is mainly used to 
    check for instructions on where to find the Cisco 
    Operating System software.
    Some other functions of configuration register are:
     - To select a boot source and default boot filename.
     - To enable or disable the Break function.
     - To control broadcast addresses.
     - To set the console terminal baud rate.
     - To load operating software from Flash memory.
     - To allow us to manually boot the system using the 
       boot command at the bootstrap program prompt.
    
    Booting is the process of initializing the
    hardware and starting the Operating System.";

  revision 2008-11-24 {
    description
     "Added following new objects to ceExtPhysicalProcessorTable.
      ceExtProcessorRamOverflow and ceExtHCProcessorRam
      
      Added following new groups to ciscoEntityExtMIBGroups.
      ceExtPhyProcessorOverflowGroup and ceExtPhyProcessorHCGroup.
      
      Added a new compliance ciscoEntityExtMIBComplianceRev3 which
      deprecates ciscoEntityExtMIBComplianceRev2.";
  }

  revision 2004-07-06 {
    description
     "Added a new table object 'ceExtEntPhysicalTable' .";
  }

  revision 2004-03-03 {
    description
     "Importing Unsigned32 from SNMPv2-SMI, instead of CISCO-TC.";
  }

  revision 2004-01-26 {
    description
     "Added new enum to ceExtEntityLEDType.";
  }

  revision 2003-08-24 {
    description
     "Added ceExtEntityLEDTable.  Added ceExtKickstartImageList to
      ceExtConfigRegTable.
      Added new group ciscoEntityExtLEDGroup.
      Added group ceExtSysBootImageListGroupRev1.";
  }

  revision 2001-05-17 {
    description
     "Corrected the description for the TC
      ConfigRegisterValue.";
  }

  revision 2001-04-05 {
    description
     "Initial version of this MIB module.";
  }

  typedef ConfigRegisterValue {
    type string;
    description
     "An Integer containing the value of config register.
      
      The definition of individual bits from right to left 
      when set are as follows:
      
      00 to        
      03                Boot Fields(Refer below for
                     explanation).
      
      04 to 
      05                Not Used.
      
      06                Causes system software to ignore the 
                     contents of NVRAM.
      
      07                Enable the original equipment 
                     manufacturer (OEM) bit.
      
      08                The Break function is disabled.
      
      09                Not used.
      
      10                Broadcast based on 0.0.0.0 IP address.
      
      11 to 
      12                Defines the console baud rate as below:
                     Bits 11 & 12 unset: 9600 baud(default),
                     Bit 11 set & 12 unset: 4800 baud,
                     Bit 11 unset & 12 set: 1200 baud,
                     Bit 11 set & 12 set: 2400 baud
      
      13                Boots default Flash software if 
                     network boot fails.
      
      14                IP broadcasts do not have network 
                     numbers.
      
      15                Enables diagnostic messages and ignores 
                     the contents of NVRAM.
      
      
      Meanings for different values of Boot Fields
      (Bits 00 to 03) are explained below:
      
      Value(in hex)        Description
      ------------    -----------
      00                On powerup or reload, the system
                     remains at the ROM monitor prompt 
                     (rommon>), awaiting a user command 
                     to boot the system manually by means 
                     of the rommon boot command.
      
      01                On powerup or reload, the system loads
                     the system image found in onboard 
                     Flash memory.
      
      02 to                On powerup or reload, the system loads
      0F                the system image specified by 
                     ceExtSysBootImageList.
                     It tries to boot the
                     image in the order in which 
                     the image names are entered in 
                     ceExtSysBootImageList. If 
                     it cannot boot any image in the
                     ceExtSysBootImageList, it 
                     stays in ROM monitor mode.";
    smiv2:display-hint "2x";
  }

  typedef BootImageList {
    type binary {
      length "0..255";
    }
    description
     "This contains a list of  boot images,
      each separated by the ';' (semi-colon) character.  
      The following provides a syntax for parsing a single
      boot image list item.
      
      <device>:[filename] | <URL>
      
      <device> can be (but not limited to):
         flash, bootflash, slot0, rom, C
      The transfer protocol used in the <URL>
      can be (but not limited to):
          tftp, ftp, rcp, mop.
      
      The following is en example containing two boot image
      names:  
         disk0:c7100-ik2s-mz;tftp://dirt/c7100-ik2s-mz
      
      If the filename is not  specified, then the
      first file on the <device> will be used.
      
         If the last two characters in the returned value
      are ';+' this indicates that additional boot image
      items are configured on the device but can not
      be returned because the maximum string size limitation
      would be exceeded.
      
      For example:
         disk0:image1;disk0:image2;+";
  }


  container CISCO-ENTITY-EXT-MIB {
    config false;

    container ceExtPhysicalProcessorTable {
      description
       "The ceExtPhysicalProcessorTable extends
        the ENTITY-MIB entPhysicalTable for modules
        (Non FRUs(Field Replacable Units) or FRUs).";
      reference
       "RFC2737: Section 2.12.1";
      smiv2:oid "1.3.6.1.4.1.9.9.195.1.1";

      list ceExtPhysicalProcessorEntry {
        key "entPhysicalIndex";
        description
         "A ceExtPhysicalProcessorTable entry extends
          a corresponding entPhysicalTable entry of class
          module(entPhysicalClass = 'module').
          
          A processor module or line card which 
          has a processor will have an entry in
          this table.
          
          A processor module or line card having
          multiple processors and is a SMP(Symmetric
          multi processor) system will have only 
          one entry corresponding to all the processors 
          since the resources defined below are shared.
          
          A processor module or line card having
          multiple processors and is not an SMP system
          would register the processors as separate entities.
          
          Entries are created by the agent at the system power-up
          or module insertion.
          
          Entries are removed when the module is reset or removed.";
        smiv2:oid "1.3.6.1.4.1.9.9.195.1.1.1";

        leaf entPhysicalIndex {
          type leafref {
            path "/entity-mib:ENTITY-MIB/entity-mib:entPhysicalTable/entity-mib:entPhysicalEntry/entity-mib:entPhysicalIndex";
          }
        }

        leaf ceExtProcessorRam {
          type uint32;
          units "bytes";
          description
           "Total number of bytes of RAM available on the
            Processor.";
          smiv2:max-access "read-only";
          smiv2:oid "1.3.6.1.4.1.9.9.195.1.1.1.1";
        }

        leaf ceExtNVRAMSize {
          type uint32;
          units "bytes";
          description
           "Total number of bytes of NVRAM in the entity.
            
            A value of 0 for this object means the entity
            does not support NVRAM or NVRAM information 
            is not available.";
          smiv2:max-access "read-only";
          smiv2:oid "1.3.6.1.4.1.9.9.195.1.1.1.2";
        }

        leaf ceExtNVRAMUsed {
          type uint32;
          units "bytes";
          description
           "Number of bytes of NVRAM in use. This object
            is irrelevant if ceExtNVRAMSize is 0.";
          smiv2:max-access "read-only";
          smiv2:oid "1.3.6.1.4.1.9.9.195.1.1.1.3";
        }

        leaf ceExtProcessorRamOverflow {
          type uint32;
          units "bytes";
          description
           "This object represents the upper 32-bit of ceExtProcessorRam.
            This object needs to be supported only if the available RAM
            bytes exceeds 32-bit, otherwise this object value would be set
            to 0.";
          smiv2:max-access "read-only";
          smiv2:oid "1.3.6.1.4.1.9.9.195.1.1.1.4";
        }

        leaf ceExtHCProcessorRam {
          type cisco-tc:Unsigned64;
          units "bytes";
          description
           "This object represents the total number of bytes of RAM
            available on the Processor. This object is a 64-bit version
            of ceExtProcessorRam.";
          smiv2:max-access "read-only";
          smiv2:oid "1.3.6.1.4.1.9.9.195.1.1.1.5";
        }
      }
    }

    container ceExtConfigRegTable {
      description
       "The ceExtConfigRegTable extends
        the ENTITY-MIB entPhysicalTable.";
      reference
       "RFC2737: Section 2.12.1";
      smiv2:oid "1.3.6.1.4.1.9.9.195.1.2";

      list ceExtConfigRegEntry {
        key "entPhysicalIndex";
        description
         "A ceExtConfigRegTable entry extends
          a corresponding entPhysicalTable entry of class
          module which has a configuration register.
          
          Entries are created by the agent at the system power-up
          or module insertion.
          
          Entries are removed when the module is reset or 
          removed.";
        smiv2:oid "1.3.6.1.4.1.9.9.195.1.2.1";

        leaf entPhysicalIndex {
          type leafref {
            path "/entity-mib:ENTITY-MIB/entity-mib:entPhysicalTable/entity-mib:entPhysicalEntry/entity-mib:entPhysicalIndex";
          }
        }

        leaf ceExtConfigRegister {
          type CISCO-ENTITY-EXT-MIB:ConfigRegisterValue;
          description
           "The value of configuration register with which
            the processor module booted.";
          smiv2:max-access "read-only";
          smiv2:oid "1.3.6.1.4.1.9.9.195.1.2.1.1";
        }

        leaf ceExtConfigRegNext {
          type CISCO-ENTITY-EXT-MIB:ConfigRegisterValue;
          description
           "The value of configuration register in the
            processor module at next reboot. Just after 
            the reboot this has the same value as 
            ceExtConfigRegister.";
          smiv2:max-access "read-write";
          smiv2:oid "1.3.6.1.4.1.9.9.195.1.2.1.2";
        }

        leaf ceExtSysBootImageList {
          type CISCO-ENTITY-EXT-MIB:BootImageList;
          description
           "The list of system boot images which
            can be used for booting.";
          smiv2:defval "";
          smiv2:max-access "read-write";
          smiv2:oid "1.3.6.1.4.1.9.9.195.1.2.1.3";
        }

        leaf ceExtKickstartImageList {
          type CISCO-ENTITY-EXT-MIB:BootImageList;
          description
           "The list of system kickstart images which
            can be used for booting.";
          smiv2:defval "";
          smiv2:max-access "read-write";
          smiv2:oid "1.3.6.1.4.1.9.9.195.1.2.1.4";
        }
      }
    }

    container ceExtEntityLEDTable {
      description
       "A table containing information of LED on an entity.";
      smiv2:oid "1.3.6.1.4.1.9.9.195.1.3";

      list ceExtEntityLEDEntry {
        key "entPhysicalIndex ceExtEntityLEDType";
        description
         "An entry (conceptual row) in the ceExtEntityLEDTable,
          containing information about an LED on an entity, identified by 
          entPhysicalIndex.";
        smiv2:oid "1.3.6.1.4.1.9.9.195.1.3.1";

        leaf entPhysicalIndex {
          type leafref {
            path "/entity-mib:ENTITY-MIB/entity-mib:entPhysicalTable/entity-mib:entPhysicalEntry/entity-mib:entPhysicalIndex";
          }
        }

        leaf ceExtEntityLEDType {
          type enumeration {
            enum "status" {
              value "1";
            }
            enum "system" {
              value "2";
            }
            enum "active" {
              value "3";
            }
            enum "power" {
              value "4";
            }
            enum "battery" {
              value "5";
            }
          }
          description
           "The type of LED on this entity.
            'status' - indicates the entity status.
            'system' - indicates the overall system status. 
            'active' - the redundancy status of a module, for e.g.
                       supervisor module. 
            'power'  - indicates sufficient power availability for all 
                       modules.
            'battery'- indicates the battery status.";
          reference
           "Cisco MDS 9500 Series Hardware Installation Guide,
            Product Overview.";
          smiv2:max-access "not-accessible";
          smiv2:oid "1.3.6.1.4.1.9.9.195.1.3.1.1";
        }

        leaf ceExtEntityLEDColor {
          type enumeration {
            enum "off" {
              value "1";
            }
            enum "green" {
              value "2";
            }
            enum "amber" {
              value "3";
            }
            enum "red" {
              value "4";
            }
          }
          description
           "The color of the LED.";
          reference
           "Cisco MDS 9500 Series Multilayer Switches, Product
            Overview.";
          smiv2:max-access "read-only";
          smiv2:oid "1.3.6.1.4.1.9.9.195.1.3.1.2";
        }
      }
    }
  }

  smiv2:alias "ceExtEntPhysicalTable" {
    description
     "This table contains additional information about
      a particular physical entity.
      This table augments the 'entPhysicalTable'  of
      the ENTITY-MIB.";
    reference
     "RFC2737: Section 2.12.1";
    smiv2:oid "1.3.6.1.4.1.9.9.195.1.4";
  }

  smiv2:alias "ceExtEntPhysicalEntry" {
    description
     "An entry (conceptual row) in the 'ceExtEntPhysicalTable',
      containing additional information about a physical entity, 
      identified by 'entPhysicalIndex'.";
    smiv2:oid "1.3.6.1.4.1.9.9.195.1.4.1";
  }

  augment "/entity-mib:ENTITY-MIB/entity-mib:entPhysicalTable/entity-mib:entPhysicalEntry" {
    description
     "An entry (conceptual row) in the 'ceExtEntPhysicalTable',
      containing additional information about a physical entity, 
      identified by 'entPhysicalIndex'.";
    smiv2:oid "1.3.6.1.4.1.9.9.195.1.4.1";

    leaf ceEntPhysicalSecondSerialNum {
      type snmp-framework:SnmpAdminString {
        length "0..32";
      }
      description
       "This object represents the vendor-specific second
        serial number string for the physical entity. 
        The first serial number string of the physical
        entity is represented in the value of corresponding 
        instance of the 'entPhysicalSerialNum' object.
        
        On the first instantiation of an physical entity, the value
        of this object is the correct vendor-assigned second 
        serial number, if this information is available to the agent. 
        
        If the second serial number is unknown or non-existent, then 
        the value of this object will be a zero-length string instead.
        
        Note that implementations which can correctly identify the
        second serial numbers of all installed physical entities do 
        not need to provide write access to this object. 
        Agents which cannot provide non-volatile storage for the 
        second serial number strings are not required to implement 
        write access for this object.
        
        Not every physical component will have a serial number, or
        even need one.  Physical entities for which the associated
        value of the entPhysicalIsFRU object is equal to 'false(2)'
        (e.g., the repeater ports within a repeater module), do not
        need their own unique serial number. An agent does not have
        to provide write access for such entities, and may return a
        zero-length string.
        
        If write access is implemented for an instance of
        'ceEntPhysicalSecondSerialNum', and a value is written into 
        the instance, the agent must retain the supplied value in the
        'ceEntPhysicalSecondSerialNum' instance associated with the 
        same physical entity for as long as that entity remains
        instantiated. This includes instantiations across all re-
        initializations/reboots of the network management system,
        including those which result in a change of the physical
        entity's entPhysicalIndex value.";
      smiv2:defval "";
      smiv2:max-access "read-write";
      smiv2:oid "1.3.6.1.4.1.9.9.195.1.4.1.1";
    }
  }

  smiv2:alias "ciscoEntityExtMIB" {
    smiv2:oid "1.3.6.1.4.1.9.9.195";
  }

  smiv2:alias "ciscoEntityExtMIBObjects" {
    smiv2:oid "1.3.6.1.4.1.9.9.195.1";
  }

  smiv2:alias "ceExtMIBNotificationPrefix" {
    smiv2:oid "1.3.6.1.4.1.9.9.195.2";
  }

  smiv2:alias "ciscoEntityExtMIBNotifications" {
    smiv2:oid "1.3.6.1.4.1.9.9.195.2.0";
  }

  smiv2:alias "ciscoEntityExtMIBConformance" {
    smiv2:oid "1.3.6.1.4.1.9.9.195.3";
  }

  smiv2:alias "ciscoEntityExtMIBCompliances" {
    smiv2:oid "1.3.6.1.4.1.9.9.195.3.1";
  }

  smiv2:alias "ciscoEntityExtMIBGroups" {
    smiv2:oid "1.3.6.1.4.1.9.9.195.3.2";
  }

}
