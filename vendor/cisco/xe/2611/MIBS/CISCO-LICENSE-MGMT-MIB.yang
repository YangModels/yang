/*
 * Generated by confdc --mib2yang-std
 * Source: mgmt/dmi/model/mib/src/patched/CISCO-LICENSE-MGMT-MIB.mib
 */
/*
 * This YANG module has been generated by smidump 0.5.0:
 *
 *      smidump -f yang CISCO-LICENSE-MGMT-MIB
 *
 * Do not edit. Edit the source file instead!
 */

module CISCO-LICENSE-MGMT-MIB {

  namespace "urn:ietf:params:xml:ns:yang:smiv2:CISCO-LICENSE-MGMT-MIB";
  prefix CISCO-LICENSE-MGMT-MIB;

  import ENTITY-MIB {
    prefix "entity-mib";
  }

  import INET-ADDRESS-MIB {
    prefix "inet-address";
  }

  import SNMP-FRAMEWORK-MIB {
    prefix "snmp-framework";
  }

  import SNMPv2-TC {
    prefix "snmpv2-tc";
  }

  import ietf-yang-smiv2 {
    prefix "smiv2";
  }

  organization
   "Cisco Systems Inc.";

  contact
   "Cisco Systems
    Customer Service
    
    Postal: 170 W Tasman Drive
    
    San Jose, CA  95134
    
    USA
    
    Tel: +1 800 553 -NETS
    
    E-mail: cs-snmp@cisco.com";

  description
   "The MIB module for managing licenses on the system.
    The licensing mechanism provides flexibility to
    enforce licensing for various features in the system.
    
    The following text introduces different concepts and
    terms those are necessary to understand the MIB definition
    and to perform license management.
    
    UDI
        Universal Device Identifier that uniquely identifies a
        device. It comprises of product ID, version ID and serial
        number of the device.
    
    NODE LOCKED LICENSE:
        Node locked licenses are locked to one of the device
        identifiers in the system. For example, the license
        can be locked to the UDI value of one of the devices
        in the system. Locking a license to an UDI guarantees
        that the license will not be moved to a device with a
        different UDI.
    
    NON-NODE LOCKED LICENSE:
        Non-node locked licenses are not locked to any device
        identifier. They can be used on other similar devices.
    
    METERED LICENSE:
        Metered licenses are valid for limited period of time
        and they expire after that. This period is the usage
        period of a license and it is not based on real time
        clock, but system clock.
    
    EULA:
        End User License Agreement.
    
    EVALUATION LICENSE:
        Evaluation licenses are non-node locked metered
        licenses which are valid only for a limited period.
        They are used only when there are no permanent,
        extension or grace period licenses for a feature.
        User will have to accept EULA (End User License
        Agreement) before using an evaluation license. Even
        though they are not node locked, their usage is
        recorded on the device.
    
    RIGHT TO USE (RTU) LICENSE:
        Right to use license is a non-node locked metered
        license which is in evaluation mode for a limited
        time after which it is converted to Right To Use (RTU) 
        license and is valid for the lifetime of the product.
        User will have to accept EULA (End User License Agreement)
        before using this license. Even though it is not node
        locked, usage information is recorded on the device.
    
    EXTENSION LICENSE:
        Extension licenses are node locked metered licenses.
        These licenses are issued by Cisco's licensing portal.
        These licenses need to be installed using management
        interfaces on the device. User will have to accept an
        EULA as part of installation of extension license.
    
    GRACE PERIOD LICENSE:
        Grace period licenses are node locked metered licenses.
        These licenses are issued by Cisco's licensing portal
        as part of the permission ticket to rehost a license.
        These licenses are installed on the device as part of
        the rehost operation. User will have to accept an
        EULA as part of the rehost operation for this type
        of license. Details on permission ticket, rehost
        operations are provided further down in this
        description clause.
    
    PERMANENT LICENSE:
        Permanent licenses are node locked licenses that have
        no usage period associated with them. These licenses
        are issued by Cisco's licensing portal. These licenses
        need to be installed using management interfaces on
        the device. Once these licenses are installed, they
        will provide needed permission for the feature/image
        across different versions.
    
    COUNTED LICENSE:
        Counted licenses limit the number of similar entities
        that can use the license. For example, a counted
        license when used by a feature can limit the number
        of IP phones that can connect or the number of tunnels
        that can be created.
    
    UNCOUNTED LICENSE:
        Uncounted licenses do not limit the number of similar
        entities that can use the licenses.
    
    License can be enforced at the image level or at the feature
    level and this MIB module supports both.
    
    IMAGE LEVEL LICENSING:
        A universal image that contains all levels of
        software packages is loaded on to the device. At boot
        time, the device determines the highest level of license
        and brings up the appropriate software features or
        subsystems.
    
    FEATURE LEVEL LICENSING:
        Feature level licensing will support enforcement of
        license at individual feature. Features have to check
        for their licenses before enabling themselves. If it
        does not have a license, the feature should disable
        itself.
    
        There is a one-to-one relationship between
        a feature and a license. That is, a feature can use
        only one license at a time and a license can be used
        by only one feature at a time.
    
    LICENSE LINE:
        A License line is an atomic set of ASCII characters
        arranged in a particular format that holds the license
        for a single feature within it. A line has all the
        necessary fields and attributes that make it a valid,
        non-tamper able and complete license.
    
    LICENSE FILE:
        File generated by Cisco licensing portal. It is used
        to install license on product. It has a user readable
        part and it contains one or more license lines.
    
    DEVICE CREDENTIALS:
        Device credentials file is a document that is generated
        by a licensed device. This document establishes the
        identity of the device and proves that the sender/user
        has/had authorized access to the device.
    
    REHOST:
        Rehost operation allows a node locked license that
        is installed on a device to be installed on other
        similar device. As part of rehost operation, a device
        processes the permission ticket, revokes the license(s)
        on the device and generates a rehost ticket as the
        proof of revocation. This rehost ticket needs to be
        presented to the Cisco's licensing portal to get the
        license transferred on to a new similar device.
    
    PERMISSION TICKET:
        Permission ticket is a document generated by Cisco
        licensing portal that allows a device to rehost its
        licenses.
    
    REHOST TICKET:
        Rehost ticket is document generated by a device after
        it has applied a permission ticket. The rehost ticket
        is a proof of revocation.
    
    LICENSING PORTAL:
        Generates licenses, permission tickets and verifies
        device credentials and rehost tickets.
    
    This MIB module provides MIB objects to install, clear,
    revoke licenses. It also provides objects to regenerate
    last rehost ticket, backup all the licenses installed
    on a device, generate & export EULA for licenses.
    
    STEPS TO INSTALL A LICENSE:
        To install a license, the management application
        1. Retrieves device credentials of the device.
        2. Communicates with Cisco's licensing portal to get
           the license file, uses device credentials to identify
           the device
        3. Executes the license install action.
    
    STEPS TO CLEAR A LICENSE:
        To clear a license, the management application
        1. Identifies the license to be cleared using license
           index.
        2. Executes the license clear action.
    
    STEPS TO REHOST A LICENSE:
        To rehost a license, the management application
        1. Retrieves device credentials of the device.
        2. Communicates with Cisco's licensing portal to get
           the permission ticket, uses device credentials to
           identify the device.
        3. Executes the processPermissionTicket action. Device
           revokes the license and generates rehost ticket to be
           submitted as proof of revocation.
        4. Retrieves device credentials of the device where the
           license needs to be transferred to.
        5. Submits rehost ticket as proof of revocation to
           Cisco's licensing portal, uses device credentials of
           the new device to identify the device, gets license
           file.
        6. Executes the license install action on the new
           device.
    
    STEPS TO REGENERATE LAST REHOST TICKET:
        To regenerate last rehost ticket, the management
    application
        1. Retrieves device credentials of the device.
        2. Uses already obtained permission ticket or
           communicates with Cisco's licensing portal to get
           the permission ticket, uses device credentials to
           identify the device.
        3. Executes the regenerateLastRehostTicket action.
           Device generates rehost ticket to be submitted as
           proof of revocation.
    
    STEPS TO BACKUP ALL LICENSES:
        To backup all licenses installed in the device, the
        management application
        1. Specifies the backup file path.
        2. Executes the license backup action.
    
    STEPS TO GENERATE & EXPORT EULA:
        To install certain kind of licenses, the management
        application must accept EULA first. The management
        application can generate and export EULA for one or
        more licenses with out installing licenses as follows.
        1. Specifies the license file path that has licenses to be
           installed
        2. Specifies the EULA file path where EULA need to be
           exported to
        3. Executes the generate EULA action.
    
    To support the various license actions, this MIB module
    also defines MIB objects to know if a device supports
    licensing, retrieve device credentials, retrieve
    information on license stores in the device.
    
    It also defines MIB objects to expose management
    information associated with the licenses installed on the
    device, with the licensable features in the software image.
    
    This MIB module also defines various notifications that
    will be triggered to asynchronously notify the management
    application of any critical events.
    
    This MIB module is defined generically so it can be
    implemented on stand alone devices or stack of devices.
    In stack of devices, one device in the stack acts as
    master agent and rest are slave agents. Each device in the
    stack has its own UDI. The master agent receives requests
    on behalf of all the devices in the stack including itself
    and delegates it to other devices as needed. It also
    collects responses from other devices and sends them to
    the management application. Examples of such devices include
    stackable switches, devices with route processor and line
    cards. On the other hand, stand alone device is a single
    device and has only one UDI associated with it.
    
    entPhysicalIndex imported from ENTITY-MIB is used to
    identify the device uniquely. It is specified as the index
    or one of the index for tables in this MIB as needed.";

  revision 2012-04-19 {
    description
     "This version of the MIB adds support for Permanent Right to use (RTU)
      licensing. The revisions are:
      o Updated clmgmtLicenseType object to support the following new
        types of license:
        permanentRightToUse
      
      The new module compliance is ciscoLicenseMgmtComplianceRev1.";
  }

  revision 2011-04-19 {
    description
     "This version of the MIB adds support for Right to use (RTU)
      licensing. The revisions are:
      o Added RTU license definition to MIB description above.
      o Updated clmgmtLicenseType object to support the following new
        types of license:
        evalRightToUse
        rightToUse
      o Added following objects to clmgmtLicenseInfoTable
        clmgmtLicensePeriodUsed
      o Added following objects to clmgmtLicensableFeatureTable
        clmgmtFeaturePeriodUsed
      o Added the following notifications
        clmgmtLicenseEvalRTUTransitionWarning
        clmgmtLicenseEvalRTUTransition
      o Added the following conformance groups
        clmgmtLicenseRTUGroup
        clmgmtLicenseRTUUsageNotifGroup
      
      The new module compliance is ciscoLicenseMgmtComplianceRev1.";
  }

  revision 2008-11-21 {
    description
     "This version of the MIB adds support for subscription
      licensing. Subscription licenses provide software
      enforcement for a licensed feature for a fixed calendar
      period. The revisions are:
      o Updated clmgmtLicenseType object to support the following three
        new types of licenses:
              paidSubscription
              evaluationSubscription
              extensionSubscription 
      o Added following objects to clmgmtLicenseInfoTable
              clmgmtLicenseStartDate
              clmgmtLicenseEndDate
      o Added following objects to clmgmtLicensableFeatureTable
              clmgmtFeatureStartDate
              clmgmtFeatureEndDate
      o Added the following notifications
              clmgmtLicenseSubscriptionExpiryWarning
              clmgmtLicenseSubscriptionExtExpiryWarning
              clmgmtLicenseSubscriptionExpired
      o Added the following conformance groups
              clmgmtLicenseSubscriptionGroup
              clmgmtLicenseSubscriptionUsageNotifGroup
      The new module compliance is ciscoLicenseMgmtComplianceRev1.";
  }

  revision 2006-10-03 {
    description
     "Initial version of this MIB module.";
  }

  typedef ClmgmtLicenseIndex {
    type uint32 {
      range "1..4294967295";
    }
    description
     "A unique value, for each license in the managed system.
      It is not necessary to have values assigned contiguously.
      The value for each license must remain constant
      at least from one re-initialization of the entity's
      network management system to the next re-initialization";
  }

  typedef ClmgmtLicenseIndexOrZero {
    type uint32;
    description
     "This textual convention is an extension of the ClmgmtLicenseIndex
      convention.  The latter defines a greater than zero value
      used to identify a license in the managed system.  This
      extension permits the additional value of zero. The value
      zero is object-specific and must therefore be defined as
      part of the description of any object which uses this
      syntax. Examples of the usage of zero might include
      situations where license was not present or unknown.";
  }

  typedef ClmgmtLicenseTransferProtocol {
    type enumeration {
      enum "none" {
        value "1";
      }
      enum "local" {
        value "2";
      }
      enum "tftp" {
        value "3";
      }
      enum "ftp" {
        value "4";
      }
      enum "rcp" {
        value "5";
      }
      enum "http" {
        value "6";
      }
      enum "scp" {
        value "7";
      }
      enum "sftp" {
        value "8";
      }
    }
    description
     "The transfer protocol that should be used for copying files
      when performing license management. When the protocol is
      set to local(2), local file system (flash or disk) is used.
      Different agents may support different transfer protocols
      and the management application is expected to some how determine
      which protocol is supported and use.";
  }

  typedef ClmgmtLicenseActionState {
    type enumeration {
      enum "none" {
        value "1";
      }
      enum "pending" {
        value "2";
      }
      enum "inProgress" {
        value "3";
      }
      enum "successful" {
        value "4";
      }
      enum "partiallySuccessful" {
        value "5";
      }
      enum "failed" {
        value "6";
      }
    }
    description
     "The state of license action execution.
      
      none(1)                - action is not yet scheduled to be
                               executed.
      
      pending(2)             - All the required parameters for the
                               action are set and the action is
                               scheduled to be executed.
      
      inProgress(3)          - action execution has started and is
                               in progress.
      
      successful(4)          - action has completed successfully.
      
      partiallySuccessful(5) - action has completed, but was
                               partially successful. Management
                               application can query additional MIB
                               objects to know what is successful
                               and what has failed. These addtional
                               objects are listed in the
                               description of the corresponding
                               action tables.
      
      failed(6)              - action has failed.";
  }

  typedef ClmgmtLicenseActionFailCause {
    type enumeration {
      enum "none" {
        value "1";
      }
      enum "generalFailure" {
        value "2";
      }
      enum "transferProtocolNotSupported" {
        value "3";
      }
      enum "fileServerNotReachable" {
        value "4";
      }
      enum "unrecognizedEntPhysicalIndex" {
        value "5";
      }
      enum "invalidLicenseFilePath" {
        value "6";
      }
      enum "invalidLicenseFile" {
        value "7";
      }
      enum "invalidLicenseLine" {
        value "8";
      }
      enum "licenseAlreadyExists" {
        value "9";
      }
      enum "licenseNotValidForDevice" {
        value "10";
      }
      enum "invalidLicenseCount" {
        value "11";
      }
      enum "invalidLicensePeriod" {
        value "12";
      }
      enum "licenseInUse" {
        value "13";
      }
      enum "invalidLicenseStore" {
        value "14";
      }
      enum "licenseStorageFull" {
        value "15";
      }
      enum "invalidPermissionTicketFile" {
        value "16";
      }
      enum "invalidPermissionTicket" {
        value "17";
      }
      enum "invalidRehostTicketFile" {
        value "18";
      }
      enum "invalidRehostTicket" {
        value "19";
      }
      enum "invalidLicenseBackupFile" {
        value "20";
      }
      enum "licenseClearInProgress" {
        value "21";
      }
      enum "invalidLicenseEULAFile" {
        value "22";
      }
    }
    description
     "Reason for license action failure. Defines error codes for
      all the license actions.
      
      none(1)                    - action execution has not
                                   started yet. If the action
                                   is completed and the action
                                   is successful, then also
                                   none(1) is returned to
                                   indicate that there are no
                                   errors.
      generalFailure(2)          - General licensing failure.
                                   This will be used for resource
                                   unavailability failures.
                                   Ex: Lack of memory.
      transferProtocolNotSupported(3) - protocol selected is not
                                        supported.
      fileServerNotReachable(4) - file server is not reachable.
      unrecognizedEntPhysicalIndex(5) - entPhysicalIndex is not
                                        valid
      invalidLicenseFilePath(6)  - The license file path is not
                                   accessible.
      invalidLicenseFile(7)      - Contents of license file are
                                   not valid.
      invalidLicenseLine(8)      - License string in the license
                                   file is not valid.
      licenseAlreadyExists(9)    - Management application is trying
                                   to install a license that already
                                   exists.
      licenseNotValidForDevice(10) - This license is not valid for
                                    the device/entPhysicalIndex
                                    specified.
      invalidLicenseCount(11)     - Invalid count for this counted
                                   license.
      invalidLicensePeriod(12)   - Validity period is invalid for
                                   this expiring license.
      licenseInUse(13)           - License file is in use by a
                                   feature/image.
      invalidLicenseStore(14)    - License store is not valid.
      licenseStorageFull(15)     - There is no more space in the
                                   license storage.
      invalidPermissionTicketFile(16) - The permission ticket file
                                        path is not accecssible.
      invalidPermissionTicket(17) - The permission ticket file
                                    contents are not valid.
      invalidRehostTicketFile(18) - The rehost ticket file path is
                                    not accessible.
      invalidRehostTicket(19)     - The rehost ticket file contents
                                    are not valid.
      invalidLicenseBackupFile(20) - License backup store path
                                     is not accessible.
      licenseClearInProgress(21)  - When license clear action is
                                    in progress, license backup
                                    action is not permitted to
                                    avoid race conditions. This
                                    error code is sent back in
                                    response to a license backup
                                    action when a license clear
                                    action is in progress or in
                                    pending state. Try again in few
                                    seconds.
      invalidLicenseEULAFile(22) -  EULA file path is not accessible.";
  }


  container CISCO-LICENSE-MGMT-MIB {
    config false;

    container clmgmtLicenseConfiguration {
      smiv2:oid "1.3.6.1.4.1.9.9.543.1.1";

      leaf clmgmtNextFreeLicenseActionIndex {
        type uint32 {
          range "1..4294967295";
        }
        description
         "This object contains appropriate value for
          clmgmtLicenseActionIndex that can be used to create
          an entry in clmgmtLicenseActionTable. The management application
          should read this object first and then use this as the
          value for clmgmtLicenseActionIndex to avoid collisions
          when creating entries in clmgmtLicenseActionTable.
          Following this approach does not guarantee collision free
          row creation, but will reduce the probability. The
          collision will happen if two management applications read this
          object at the same time and attempt to create an entry
          with this value at the same time. In this case, the
          management application whose request is processed after the first
          request will get an error and the process of reading this object
          and entry creation needs to be repeated.";
        smiv2:max-access "read-only";
        smiv2:oid "1.3.6.1.4.1.9.9.543.1.1.1";
      }
    }

    container clmgmtLicenseDeviceInformation {
      smiv2:oid "1.3.6.1.4.1.9.9.543.1.3";

      leaf clmgmtNextFreeDevCredExportActionIndex {
        type uint32;
        description
         "This object contains appropriate value for
          clmgmtDevCredExportActionIndex that can be used to create
          an entry in clmgmtDevCredExportActionTable. The management
          application should read this object first and then use this
          as the value for clmgmtDevCredExportActionIndex to avoid
          collisions when creating entries in
          clmgmtDevCredExportActionTable. Following this approach does
          not guarantee collision free row creation, but will reduce
          the probability. The collision will happen if two
          management applications read this object at the same time and
          attempt to create an entry with this value at the same time.
          In this case, the management application whose request is
          processed after the first request will get an error and the
          process of reading this object and entry creation needs to be
          repeated.";
        smiv2:max-access "read-only";
        smiv2:oid "1.3.6.1.4.1.9.9.543.1.3.1";
      }
    }

    container clmgmtLicenseNotifObjects {
      smiv2:oid "1.3.6.1.4.1.9.9.543.1.4";

      leaf clmgmtLicenseUsageNotifEnable {
        type boolean;
        description
         "This object indicates whether the device should generate
          the notifications related to usage of licenses. This object
          enables/disables sending following notifications:
              clmgmtLicenseExpired 
              clmgmtLicenseExpiryWarning
              clmgmtLicenseUsageCountExceeded
              clmgmtLicenseUsageCountAboutToExceed
              clmgmtLicenseSubscriptionExpiryWarning
              clmgmtLicenseSubscriptionExtExpiryWarning
              clmgmtLicenseSubscriptionExpired
              clmgmtLicenseEvalRTUTransitionWarning
              clmgmtLicenseEvalRTUTransition";
        smiv2:defval "true";
        smiv2:max-access "read-write";
        smiv2:oid "1.3.6.1.4.1.9.9.543.1.4.1";
      }

      leaf clmgmtLicenseDeploymentNotifEnable {
        type boolean;
        description
         "This object indicates whether the device should generate
          notifications related to license deployment. This object
          enables/disables sending following notifications:
              clmgmtLicenseInstalled
              clmgmtLicenseCleared
              clmgmtLicenseRevoked
              clmgmtLicenseEULAAccepted";
        smiv2:defval "true";
        smiv2:max-access "read-write";
        smiv2:oid "1.3.6.1.4.1.9.9.543.1.4.2";
      }

      leaf clmgmtLicenseErrorNotifEnable {
        type enumeration {
          enum "other" {
            value "0";
          }
          enum "true" {
            value "1";
          }
          enum "false" {
            value "2";
          }
        }
        description
         "This object indicates whether the device should generate
          notifications related to error conditions in enforcing
          licensing. This object enables/disables sending following
          notifications:
              clmgmtLicenseNotEnforced";
        smiv2:defval "true";
        smiv2:max-access "read-write";
        smiv2:oid "1.3.6.1.4.1.9.9.543.1.4.3";
      }
    }

    container clmgmtLicenseActionTable {
      description
       "A table for invoking license management actions. Management
        application must create a row in this table to trigger any of
        the license management actions. The following are different
        actions that can be executed using this table.
            1. install
            2. clear
            3. processPermissionTicket
            4. regenerateLastRehostTicket
            5. backup
            6. generateEULA
        
        Refer to the description of clmgmtLicenseAction for more
        information on what these actions do on the device.
        Once the request completes, the management application should
        retrieve the values of the objects of interest, and then
        delete the entry.  In order to prevent old entries from
        clogging the table, entries will be aged out, but an entry
        will never be deleted within 5 minutes of completion.";
      smiv2:oid "1.3.6.1.4.1.9.9.543.1.1.2";

      list clmgmtLicenseActionEntry {
        key "clmgmtLicenseActionIndex";
        description
         "An entry for each action that is being executed or was
          executed recently. The management application executes an
          action
          by creating this entry. This can be done in the following
          2 methods
          
          1. CREATE-AND-GO method
              Management application sets clmgmtLicenseActionRowStatus to
              createAndGo(4) and all other required objects to valid
              values in a single SNMP SET request. If all the values
              are valid, the device creates the entry and executes the
              action. If the SET request fails, the entry will not be
              created.
          2. CREATE-AND-WAIT method
              Management application sets clmgmtLicenseActionRowStatus to
              createAndWait(5) to create an entry. Management application
              can set all other required objects to valid
              values in more than one SNMP SET request. If SET request
              for any of the objects fails, management application can
          set
              just only that object. Once all the required objects
              are set to valid values, management application triggers
          action
              execution by setting clmgmtLicenseActionRowStatus to
              active(1).
          
          To stop the action from being executed, the management
          application
          can delete the entry by setting clmgmtLicenseActionRowStatus
          to destroy(6) when clmgmtLicenseActionState is pending(2).
          
          The status of action execution can be known by querying
          clmgmtLicenseActionState. If the action is still in
          pending(2) or in inProgress(3) state, the management
          application need to check back again after few seconds.
          Once the action completes and status of the action is
          failed(6), the reason for failure can be retrieved
          from clmgmtLicenseActionFailCause. If the status of the
          action is partiallySuccessful(5), results of individual
          licenses can be queried from clmgmtLicenseActionResultTable.
          
          Not all objects in the entry are needed to execute every
          action. Below is the list of actions and the required
          objects that are needed to be set for executing that
          action.
          
          1. Installing a license
             The following MIB objects need to be set for installing a
             license
               a. clmgmtLicenseActionTransferProtocol
               b. clmgmtLicenseServerAddressType
               c. clmgmtLicenseServerAddress
               d. clmgmtLicenseServerUsername
               e. clmgmtLicenseServerPassword
               f. clmgmtLicenseFile
               g. clmgmtLicenseStore
               h. clmgmtLicenseStopOnFailure
               i. clmgmtLicenseAcceptEULA
               j. clmgmtLicenseAction
          
             clmgmtLicenseActionEntPhysicalIndex need not be set
             explicitly for license installs. License itself identifes
             the device where the license needs to be installed.
          
             clmgmtLicenseStore need to be set to store the licenses
             in a non-default license store. But, if a license file
             has more than one license and licenses need to be
             installed on multiple devices (for example to multiple
             members with in a stack), then value of clmgmtLicenseStore
             is ignored and the licenses will be installed in default
             license stores of the respective devices.
          
          2. Clearing a license
             The following MIB objects need to be set for clearing a
             license
               a. clmgmtLicenseActionEntPhysicalIndex
               b. clmgmtLicenseActionLicenseIndex
               c. clmgmtLicenseStore
               d. clmgmtLicenseAction
          
          3. Revoking a license
             The following MIB objects need to be set for revoking a
             license
               a. clmgmtLicenseActionTransferProtocol
               b. clmgmtLicenseServerAddressType
               c. clmgmtLicenseServerAddress
               d. clmgmtLicenseServerUsername
               e. clmgmtLicenseServerPassword
               f. clmgmtLicensePermissionTicketFile
               g. clmgmtLicenseRehostTicketFile
               h. clmgmtLicenseStopOnFailure
               i. clmgmtLicenseAction
          
          4. Regenerate last rehost ticket
             The following MIB objects need to be set for regenerating
             last rehost ticket
               a. clmgmtLicenseActionTransferProtocol
               b. clmgmtLicenseServerAddressType
               c. clmgmtLicenseServerAddress
               d. clmgmtLicenseServerUsername
               e. clmgmtLicenseServerPassword
               f. clmgmtLicensePermissionTicketFile
               g. clmgmtLicenseRehostTicketFile
               h. clmgmtLicenseStopOnFailure
               i. clmgmtLicenseAction
          
          
          5. Save all licenses to a backup storage
             The following MIB objects need to be set for storing all
             licenses to a backup store
               a. clmgmtLicenseActionEntPhysicalIndex
               b. clmgmtLicenseActionTransferProtocol
               c. clmgmtLicenseServerAddressType
               d. clmgmtLicenseServerAddress
               e. clmgmtLicenseServerUsername
               f. clmgmtLicenseServerPassword
               g. clmgmtLicenseBackupFile
               h. clmgmtLicenseAction
          
          6. Generate and export EULA if the licenses need EULA to be
             accepted for installing.
             The following MIB objects need to be set exporting required
             EULAs
               a. clmgmtLicenseActionTransferProtocol
               b. clmgmtLicenseServerAddressType
               c. clmgmtLicenseServerAddress
               d. clmgmtLicenseServerUsername
               e. clmgmtLicenseServerPassword
               f. clmgmtLicenseFile
               g. clmgmtLicenseEULAFile
               h. clmgmtLicenseAction
          
          For any action, if clmgmtLicenseActionTransferProtocol
          is set to local(2), the following objects need not be set.
               a. clmgmtLicenseServerAddressType
               b. clmgmtLicenseServerAddress
               c. clmgmtLicenseServerUsername
               d. clmgmtLicenseServerPassword
          
          Entry can be deleted except when clmgmtLicenseAction is set
          to pending(2). All entries are volatile and are cleared
          on agent reset.";
        smiv2:oid "1.3.6.1.4.1.9.9.543.1.1.2.1";

        leaf clmgmtLicenseActionIndex {
          type uint32 {
            range "1..4294967295";
          }
          description
           "This object uniquely identifies a row in
            clmgmtLicenseActionTable. The management application should choose
            this value by reading clmgmtNextFreeLicenseActionIndex
            while creating an entry in this table. If an entry already
            exists with this index, the creation of the entry will not
            continue and error will be returned. The management application
            should read the value of clmgmtNextFreeLicenseActionIndex
            again and retry with the new value for this object.";
          smiv2:max-access "not-accessible";
          smiv2:oid "1.3.6.1.4.1.9.9.543.1.1.2.1.1";
        }

        leaf clmgmtLicenseActionEntPhysicalIndex {
          type entity-mib:PhysicalIndexOrZero;
          description
           "This object represents the entPhysicalIndex of the device
            where the action is being executed. This object is mainly
            used in devices where one device is acting as a master and
            rest of the devices as slaves. The master device is
            responsible for SNMP communication with the management
            application. Examples include stackable switches, devices
            with route processor and line card configuration. If this
            object is not set, the license action will be executed on
            the master device. Note: This object need not be set if
            there is a stand alone device";
          smiv2:defval "0";
          smiv2:max-access "read-write";
          smiv2:oid "1.3.6.1.4.1.9.9.543.1.1.2.1.2";
        }

        leaf clmgmtLicenseActionTransferProtocol {
          type CISCO-LICENSE-MGMT-MIB:ClmgmtLicenseTransferProtocol;
          description
           "This object represents the transfer protocol to be used
            when copying files as specified in the following objects.
            1. clmgmtLicenseFile
            2. clmgmtLicensePermissionTicketFile
            3. clmgmtLicenseRehostTicketFile
            4. clmgmtLicenseBackupFile
            
            Note: This object need not be set if the all the files
            required for the action are in device's local file system.";
          smiv2:defval "none";
          smiv2:max-access "read-write";
          smiv2:oid "1.3.6.1.4.1.9.9.543.1.1.2.1.3";
        }

        leaf clmgmtLicenseServerAddressType {
          type inet-address:InetAddressType;
          description
           "This object indicates the transport type of the
            address contained in clmgmtLicenseServerAddress object.
            This must be set when clmgmtLicenseActionTransferProtocol
            is not none(1) or local(2).";
          smiv2:defval "unknown";
          smiv2:max-access "read-write";
          smiv2:oid "1.3.6.1.4.1.9.9.543.1.1.2.1.4";
        }

        leaf clmgmtLicenseServerAddress {
          type inet-address:InetAddress;
          description
           "This object indicates the ip address of the server from
            which the files must be read or written to if
            clmgmtLicenseActionTransferProtocol is not none(1) or
            local(2).
            
            All bits as 0s or 1s for clmgmtLicenseServerAddress are not
            allowed.
            
            The format of this address depends on the value of the
            clmgmtLicenseServerAddressType object";
          smiv2:defval "";
          smiv2:max-access "read-write";
          smiv2:oid "1.3.6.1.4.1.9.9.543.1.1.2.1.5";
        }

        leaf clmgmtLicenseServerUsername {
          type snmp-framework:SnmpAdminString {
            length "0..96";
          }
          description
           "This object indicates the remote user name for accessing
            files via ftp, rcp, sftp or scp protocols. This object must
            be set when the clmgmtLicenseActionTransferProtocol is
            ftp(4), rcp(5), scp(7) or sftp(8). If
            clmgmtLicenseActionTransferProtocol is rcp(5), the remote
            username is sent as the server username in an rcp command
            request sent by the system to a remote rcp server.";
          smiv2:defval "";
          smiv2:max-access "read-write";
          smiv2:oid "1.3.6.1.4.1.9.9.543.1.1.2.1.6";
        }

        leaf clmgmtLicenseServerPassword {
          type snmp-framework:SnmpAdminString {
            length "0..96";
          }
          description
           "This object indicates the password used by ftp, sftp or
            scp for copying a file to/from an ftp/sftp/scp server.
            This object must be set when the
            clmgmtLicenseActionTransferProtocol is ftp(4) or scp(7)
            or sftp(8). Reading it returns a zero-length string for
            security reasons.";
          smiv2:defval "";
          smiv2:max-access "read-write";
          smiv2:oid "1.3.6.1.4.1.9.9.543.1.1.2.1.7";
        }

        leaf clmgmtLicenseFile {
          type snmp-framework:SnmpAdminString {
            length "0..255";
          }
          description
           "This object represents the location of the license file
            on the server identified by clmgmtLicenseServerAddress. This
            object MUST be set to a valid value before or concurrently
            with setting the value of the clmgmtLicenseAction object to
            install(2). For other operations, the value of this
            object is not considered, it is irrelevant.";
          smiv2:defval "";
          smiv2:max-access "read-write";
          smiv2:oid "1.3.6.1.4.1.9.9.543.1.1.2.1.8";
        }

        leaf clmgmtLicenseStore {
          type uint32;
          description
           "This object represents the clmgmtLicenseStoreIndex of the
            license store to use within the device. The license store
            can be a local disk or flash. A device can have more than
            one license stores. If this object is not set, the license
            will be stored in the default license store as exposed by
            clmgmtDefaultLicenseStore object.";
          smiv2:defval "0";
          smiv2:max-access "read-write";
          smiv2:oid "1.3.6.1.4.1.9.9.543.1.1.2.1.9";
        }

        leaf clmgmtLicenseActionLicenseIndex {
          type CISCO-LICENSE-MGMT-MIB:ClmgmtLicenseIndexOrZero;
          description
           "This object indicates the the license index of the license
            that is the subject of this action. This is used for
            identifying a license for performing actions specific to
            that license. This object need to be set only if
            clmgmtLicenseAction is set to clear(4). The value of this
            object is same as the clmgmtLicenseIndex object in
            clmgmtLicenseInfoEntry for license that is subject of this
            action.";
          smiv2:defval "0";
          smiv2:max-access "read-write";
          smiv2:oid "1.3.6.1.4.1.9.9.543.1.1.2.1.10";
        }

        leaf clmgmtLicensePermissionTicketFile {
          type snmp-framework:SnmpAdminString {
            length "0..255";
          }
          description
           "This object indicates the file name of the permission
            ticket. This object need to be set only if
            clmgmtLicenseAction is set to processPermissionTicket(4)
            or regenerateLastRehostTicket(5) actions. The permission
            ticket is obtained from Cisco licensing portal to revoke
            a license. The management application must set this object
            to valid value before invoking the action.";
          smiv2:defval "";
          smiv2:max-access "read-write";
          smiv2:oid "1.3.6.1.4.1.9.9.543.1.1.2.1.11";
        }

        leaf clmgmtLicenseRehostTicketFile {
          type snmp-framework:SnmpAdminString {
            length "0..255";
          }
          description
           "This object indicates the file where the rehost ticket
            generated by the device need to be exported to. The rehost
            ticket is generated as a result of processPermissionTicket
            and regenerateLastRehostTicket actions. After generating
            the rehost ticket, the device exports the rehost ticket
            contents to this file. This object need to be set only
            if clmgmtLicenseAction is set to processPermissionTicket(4)
            or regenerateLastRehostTicket(5) actions.";
          smiv2:defval "";
          smiv2:max-access "read-write";
          smiv2:oid "1.3.6.1.4.1.9.9.543.1.1.2.1.12";
        }

        leaf clmgmtLicenseBackupFile {
          type snmp-framework:SnmpAdminString {
            length "0..255";
          }
          description
           "This object indicates the file where all the licenses in
            the device need to be backed up. This object need to be set
            only if clmgmtLicenseAction is set to backup(6) and the
            management application must set the value of this  object
            to valid value before invoking action.";
          smiv2:defval "";
          smiv2:max-access "read-write";
          smiv2:oid "1.3.6.1.4.1.9.9.543.1.1.2.1.13";
        }

        leaf clmgmtLicenseStopOnFailure {
          type boolean;
          description
           "This object indicates whether the license action should
            stop if the action on a license fails. This object is
            applicable only if there are more than one licenses
            involved in an action.";
          smiv2:defval "false";
          smiv2:max-access "read-write";
          smiv2:oid "1.3.6.1.4.1.9.9.543.1.1.2.1.14";
        }

        leaf clmgmtLicenseAction {
          type enumeration {
            enum "noOp" {
              value "1";
            }
            enum "install" {
              value "2";
            }
            enum "clear" {
              value "3";
            }
            enum "processPermissionTicket" {
              value "4";
            }
            enum "regenerateLastRehostTicket" {
              value "5";
            }
            enum "backup" {
              value "6";
            }
            enum "generateEULA" {
              value "7";
            }
          }
          description
           "This object indicates the the command/action to be executed.
            
            Command                        Remarks
            -------                        -------
            noOp(1)                        No operation will be
                                           performed.
            
            install(2)                     Installs the license.
            
            clear(3)                       Clears the license.
            
            processPermissionTicket(4)     Processes thee permission
                                           ticket and generates and
                                           exports rehost ticket.
            
            regenerateLastRehostTicket(5)  Generates and exports the
                                           last generated rehost
                                           ticket.
            
            backup(6)                      Backs up all the licenses
                                           installed currently onto a
                                           backup store.
            
            generateEULA(7)                Checks whether the licenses
                                           in the license file need EULA
                                           acceptance and uploads the
                                           needed EULA contents to a file.";
          smiv2:defval "noOp";
          smiv2:max-access "read-write";
          smiv2:oid "1.3.6.1.4.1.9.9.543.1.1.2.1.15";
        }

        leaf clmgmtLicenseActionState {
          type CISCO-LICENSE-MGMT-MIB:ClmgmtLicenseActionState;
          description
           "This object indicates the state of this license action.";
          smiv2:max-access "read-only";
          smiv2:oid "1.3.6.1.4.1.9.9.543.1.1.2.1.16";
        }

        leaf clmgmtLicenseJobQPosition {
          type uint32;
          description
           "This object represents the position of the action
            in the license action job queue that is maintained
            internally. Only actions in pending(2) state will
            be put in the queue until they are executed. By
            reading this object, the management application can make
            intelligent decision on whether to execute another
            action that it is planning on. For example, if there
            is already a license clear action in the queue in
            pending(2) state, management application can choose to
            defer its license back up action to a later time. This
            object will return a value of 0 if the action is not in
            pending(2) state.";
          smiv2:max-access "read-only";
          smiv2:oid "1.3.6.1.4.1.9.9.543.1.1.2.1.17";
        }

        leaf clmgmtLicenseActionFailCause {
          type CISCO-LICENSE-MGMT-MIB:ClmgmtLicenseActionFailCause;
          description
           "This object indicates the reason for this license action
            failure. The value of this object is valid only when
            clmgmtLicenseActionState is failed(6).";
          smiv2:max-access "read-only";
          smiv2:oid "1.3.6.1.4.1.9.9.543.1.1.2.1.18";
        }

        leaf clmgmtLicenseActionStorageType {
          type snmpv2-tc:StorageType;
          description
           "This object indicates the storage type for this conceptual
            row. Conceptual rows having the value 'permanent' need not
            allow write-access to any columnar objects in the row.";
          smiv2:defval "volatile";
          smiv2:max-access "read-write";
          smiv2:oid "1.3.6.1.4.1.9.9.543.1.1.2.1.19";
        }

        leaf clmgmtLicenseActionRowStatus {
          type snmpv2-tc:RowStatus;
          description
           "This object indicates the the status of this table entry.
            Once the entry status is set to active(1), the associated
            entry cannot be modified until the action completes
            (clmgmtLicenseConfigCommandStatus is set to a value
            other than inProgress(3)). Once the action completes
            the only operation possible after this is to delete
            the row. It is recommended that the management application
            should delete entries in this table after reading
            the result. In order to prevent old entries from
            clogging the table, entries will be aged out, but an
            entry will never be deleted within 5 minutes of
            completion";
          smiv2:max-access "read-write";
          smiv2:oid "1.3.6.1.4.1.9.9.543.1.1.2.1.20";
        }

        leaf clmgmtLicenseAcceptEULA {
          type boolean;
          description
           "This object indicates whether the End User License Agreement
            needed for installing the licenses is accepted.
            
            true(1) - EULA is read and accepted
            false(2) - EULA is not accepted
            
            Management application should set this object to true(1) when
            installing licenses that need EULA acceptance.";
          smiv2:defval "false";
          smiv2:max-access "read-write";
          smiv2:oid "1.3.6.1.4.1.9.9.543.1.1.2.1.21";
        }

        leaf clmgmtLicenseEULAFile {
          type snmp-framework:SnmpAdminString {
            length "0..255";
          }
          description
           "This object indicates the file where all the End User License
            Agreements (EULAs) need to be exported to. This object need to
            be set only if clmgmtLicenseAction is set to generateEULA(7) and
            the management application must set the value of this object to
            valid value before invoking action.";
          smiv2:defval "";
          smiv2:max-access "read-write";
          smiv2:oid "1.3.6.1.4.1.9.9.543.1.1.2.1.22";
        }
      }
    }

    container clmgmtLicenseActionResultTable {
      description
       "This table contains results of license action if the
        license action involves multiple licenses. Entries in this
        table are not created for actions where there is
        only license that is subject of the action. For
        example, if there are 3 licenses in a license file
        when executing license install action, 3 entries will
        be created in this table, one for each license.";
      smiv2:oid "1.3.6.1.4.1.9.9.543.1.1.3";

      list clmgmtLicenseActionResultEntry {
        key "clmgmtLicenseActionIndex clmgmtLicenseNumber";
        description
         "An entry in clmgmtLicenseActionResultTable. Each entry
          contains result of the action for a single license.
          These entries are created immediately after action
          execution when the action involves multiple licenses.
          These entries get automatically deleted when the
          corresponding entry in clmgmtLicenseActionTable
          is deleted.";
        smiv2:oid "1.3.6.1.4.1.9.9.543.1.1.3.1";

        leaf clmgmtLicenseActionIndex {
          type leafref {
            path "/CISCO-LICENSE-MGMT-MIB:CISCO-LICENSE-MGMT-MIB/CISCO-LICENSE-MGMT-MIB:clmgmtLicenseActionTable/CISCO-LICENSE-MGMT-MIB:clmgmtLicenseActionEntry/CISCO-LICENSE-MGMT-MIB:clmgmtLicenseActionIndex";
          }
        }

        leaf clmgmtLicenseNumber {
          type uint32 {
            range "1..4294967295";
          }
          description
           "This object indicates the sequence number of this license
            in the list of licenses on which the action is executed.
            For example, if there are 3 licenses in a license file
            when executing license install action, this object will
            have values 1, 2 and 3 respectively as ordered in the
            license file.";
          smiv2:max-access "not-accessible";
          smiv2:oid "1.3.6.1.4.1.9.9.543.1.1.3.1.1";
        }

        leaf clmgmtLicenseIndivActionState {
          type CISCO-LICENSE-MGMT-MIB:ClmgmtLicenseActionState;
          description
           "This object indicates the state of action on this
            individual license.";
          smiv2:max-access "read-only";
          smiv2:oid "1.3.6.1.4.1.9.9.543.1.1.3.1.2";
        }

        leaf clmgmtLicenseIndivActionFailCause {
          type CISCO-LICENSE-MGMT-MIB:ClmgmtLicenseActionFailCause;
          description
           "This object indicates the reason for action failure on this
            individual license";
          smiv2:max-access "read-only";
          smiv2:oid "1.3.6.1.4.1.9.9.543.1.1.3.1.3";
        }
      }
    }

    container clmgmtLicenseStoreInfoTable {
      description
       "This table contains information about all the license
        stores allocated on the device.";
      smiv2:oid "1.3.6.1.4.1.9.9.543.1.2.1";

      list clmgmtLicenseStoreInfoEntry {
        key "entPhysicalIndex clmgmtLicenseStoreIndex";
        description
         "An entry in clmgmtLicenseStoreInfoTable. Each entry
          contains information about a license store allocated
          on the device";
        smiv2:oid "1.3.6.1.4.1.9.9.543.1.2.1.1";

        leaf entPhysicalIndex {
          type leafref {
            path "/entity-mib:ENTITY-MIB/entity-mib:entPhysicalTable/entity-mib:entPhysicalEntry/entity-mib:entPhysicalIndex";
          }
        }

        leaf clmgmtLicenseStoreIndex {
          type uint32 {
            range "1..4294967295";
          }
          description
           "This object uniquely identifies a license store within
            the device.";
          smiv2:max-access "not-accessible";
          smiv2:oid "1.3.6.1.4.1.9.9.543.1.2.1.1.1";
        }

        leaf clmgmtLicenseStoreName {
          type snmp-framework:SnmpAdminString {
            length "0..255";
          }
          description
           "This object indicates the name of the license store
            within the device. It is a file in device's local file
            system i.e., either on a local disk or flash or some
            other storage media. For example, the value of this
            object can be 'disk1:lic_store_1.txt' or
            'flash:lic_store_2.txt";
          smiv2:max-access "read-only";
          smiv2:oid "1.3.6.1.4.1.9.9.543.1.2.1.1.2";
        }

        leaf clmgmtLicenseStoreTotalSize {
          type uint32;
          units "bytes";
          description
           "This object indicates the total number of bytes that are
            allocated to the license store.";
          smiv2:max-access "read-only";
          smiv2:oid "1.3.6.1.4.1.9.9.543.1.2.1.1.3";
        }

        leaf clmgmtLicenseStoreSizeRemaining {
          type uint32;
          units "bytes";
          description
           "This object indicates the number of bytes still remaining
            to be used for new license installations in the license
            store.";
          smiv2:max-access "read-only";
          smiv2:oid "1.3.6.1.4.1.9.9.543.1.2.1.1.4";
        }
      }
    }

    container clmgmtLicenseDeviceInfoTable {
      description
       "This table contains objects that provide licensing related
        information at the device level. Entries will exist
        only for entities that support licensing. For example,
        if it is a stand alone device and supports licensing,
        then there will be only one entry in this table. If
        it is stackable switch then there will be multiple
        entries with one entry for each device in the stack.";
      smiv2:oid "1.3.6.1.4.1.9.9.543.1.2.2";

      list clmgmtLicenseDeviceInfoEntry {
        key "entPhysicalIndex";
        description
         "An entry in clmgmtLicenseDeviceInfoTable. Each entry
          contains device level licensing information for a device.";
        smiv2:oid "1.3.6.1.4.1.9.9.543.1.2.2.1";

        leaf entPhysicalIndex {
          type leafref {
            path "/entity-mib:ENTITY-MIB/entity-mib:entPhysicalTable/entity-mib:entPhysicalEntry/entity-mib:entPhysicalIndex";
          }
        }

        leaf clmgmtDefaultLicenseStore {
          type uint32 {
            range "1..4294967295";
          }
          description
           "This object indicates the clmgmtLicenseStoreIndex of
            default store in the device. There will be only one
            default license store per device. If no license store
            is specified during license install, this default license
            store will be used.";
          smiv2:max-access "read-only";
          smiv2:oid "1.3.6.1.4.1.9.9.543.1.2.2.1.1";
        }
      }
    }

    container clmgmtLicenseInfoTable {
      description
       "This table contains information about all the licenses
        installed on the device.";
      smiv2:oid "1.3.6.1.4.1.9.9.543.1.2.3";

      list clmgmtLicenseInfoEntry {
        key "entPhysicalIndex clmgmtLicenseStoreUsed clmgmtLicenseIndex";
        description
         "An entry in clmgmtLicenseInfoTable. Each entry contains
          information about a license installed on the device. This
          entry gets created when a license is installed successfully.
          Management application can not create these entries directly, but
          will do so indirectly by executing license install action.
          Some of these entries may already exist that correspond to
          demo licenses even before management application installs any
          licenses.";
        smiv2:oid "1.3.6.1.4.1.9.9.543.1.2.3.1";

        leaf entPhysicalIndex {
          type leafref {
            path "/entity-mib:ENTITY-MIB/entity-mib:entPhysicalTable/entity-mib:entPhysicalEntry/entity-mib:entPhysicalIndex";
          }
        }

        leaf clmgmtLicenseStoreUsed {
          type uint32 {
            range "1..4294967295";
          }
          description
           "This object represents the license store that is used for
            storing this license. This object will have the same value
            as clmgmtLicenseStoreIndex in clmgmtLicenseStoreInfoEntry
            of the license store used.";
          smiv2:max-access "not-accessible";
          smiv2:oid "1.3.6.1.4.1.9.9.543.1.2.3.1.1";
        }

        leaf clmgmtLicenseIndex {
          type CISCO-LICENSE-MGMT-MIB:ClmgmtLicenseIndex;
          description
           "This object uniquely identifies a license within
            the device.";
          smiv2:max-access "not-accessible";
          smiv2:oid "1.3.6.1.4.1.9.9.543.1.2.3.1.2";
        }

        leaf clmgmtLicenseFeatureName {
          type snmp-framework:SnmpAdminString {
            length "0..128";
          }
          description
           "This object indicates the name of the feature that is
            using or can use this license. A license can be used by
            only one feature. Examples of feature name are: 'IPBASE',
            'ADVIPSERVICE'.";
          smiv2:max-access "read-only";
          smiv2:oid "1.3.6.1.4.1.9.9.543.1.2.3.1.3";
        }

        leaf clmgmtLicenseFeatureVersion {
          type snmp-framework:SnmpAdminString {
            length "0..128";
          }
          description
           "This object indicates the version of the feature that is
            using or can use this license. Examples of feature version
            are: '1.0', '2.0'";
          smiv2:max-access "read-only";
          smiv2:oid "1.3.6.1.4.1.9.9.543.1.2.3.1.4";
        }

        leaf clmgmtLicenseType {
          type enumeration {
            enum "demo" {
              value "1";
            }
            enum "extension" {
              value "2";
            }
            enum "gracePeriod" {
              value "3";
            }
            enum "permanent" {
              value "4";
            }
            enum "paidSubscription" {
              value "5";
            }
            enum "evaluationSubscription" {
              value "6";
            }
            enum "extensionSubscription" {
              value "7";
            }
            enum "evalRightToUse" {
              value "8";
            }
            enum "rightToUse" {
              value "9";
            }
            enum "permanentRightToUse" {
              value "10";
            }
          }
          description
           "This object identifies type of license. Licenses may have
            validity period defined in terms of time duration that the
            license is valid for or it may be defined in terms of actual
            calendar dates. Subscription licenses are licenses that have
            validity period defined in terms of calendar dates.
            
            demo(1)               - demo(evaluation license) license.
            extension(2)          - Extension(expiring) license.
            gracePeriod(3)        - Grace period license.
            permanent(4)          - permanent license, the license has no
                                    expiry date.
            paidSubscription(5)   - Paid subscription licenses are the
            licenses
                                    which are purchased by customers. These
                                    licenses have a start date  and end date
                                    associated with them.
            evaluationSubscription(6)-Evaluation subscription licenses are
                                      the trial licenses. These licenses
                                      are node locked and it can be obtained
                                      only once for an UDI. They are valid
                                      based on calendar days. These licenses
                                      have a start date and an end date
                                      associated with them and are issued
                                      once per UDI.
            extensionSubscription(7)- Extension subscription licenses are
                                      similar to evaluation subscription
                                      licenses but these licenses are issued
                                      based on customer request. There are
                                      no restrictions on the number of
                                      licenses available for a UDI.
            evalRightToUse(8)       - Evaluation Right to use (RTU)
            license.
            rightToUse(9)           - Right to use (RTU) license.
            permanentRightToUse(10) ? Right To Use license right after it is configured 
                                      and is valid for the lifetime of the product. 
                                      This is a Right To Use license which is not in 
                                      evaluation mode for a limited time.";
          smiv2:max-access "read-only";
          smiv2:oid "1.3.6.1.4.1.9.9.543.1.2.3.1.5";
        }

        leaf clmgmtLicenseCounted {
          type boolean;
          description
           "This object indicates whether the license is counted
            license.
            true(1)  - counted license
            false(2) - uncounted license";
          smiv2:max-access "read-only";
          smiv2:oid "1.3.6.1.4.1.9.9.543.1.2.3.1.6";
        }

        leaf clmgmtLicenseValidityPeriod {
          type uint32;
          units "seconds";
          description
           "This object indicates the time period the license is valid for.
            This object is applicable only if clmgmtLicenseType is demo(1),
            or extension(2) or gracePeriod(3) or evalRightToUse(8). The
            object will return 0 for other license types.";
          smiv2:max-access "read-only";
          smiv2:oid "1.3.6.1.4.1.9.9.543.1.2.3.1.7";
        }

        leaf clmgmtLicenseValidityPeriodRemaining {
          type uint32;
          units "seconds";
          description
           "This object indicates the time period remaining before the
            license expires or transitions to rightToUse(9) license. This
            object is applicable only if clmgmtLicenseType is demo(1), or
            extension(2) or gracePeriod(3) or evalRightToUse(8). The object
            will contain 0 for other license types.";
          smiv2:max-access "read-only";
          smiv2:oid "1.3.6.1.4.1.9.9.543.1.2.3.1.8";
        }

        leaf clmgmtLicenseExpiredPeriod {
          type uint32;
          units "seconds";
          description
           "This object indicates the elapsed time period since the license
            expired. This object is applicable only if clmgmtLicenseType
            is demo(1), or extension(2) or gracePeriod(3). Also, this
            value of this object will be valid only after the license
            expires. The object will return 0 for other license types
            or before the license expiry.";
          smiv2:max-access "read-only";
          smiv2:oid "1.3.6.1.4.1.9.9.543.1.2.3.1.9";
        }

        leaf clmgmtLicenseMaxUsageCount {
          type uint32;
          description
           "This object indicates the maximum number of entities that
            can use this license. This object is applicable only if
            clmgmtLicenseCounted is true(1). The entity that is being
            counted can be anything and it depends on the licensable
            feature.";
          smiv2:max-access "read-only";
          smiv2:oid "1.3.6.1.4.1.9.9.543.1.2.3.1.10";
        }

        leaf clmgmtLicenseUsageCountRemaining {
          type uint32;
          description
           "This object indicates the number of entities that can
            still use this license. This object is applicable only
            if clmgmtLicenseCounted is true(1).";
          smiv2:max-access "read-only";
          smiv2:oid "1.3.6.1.4.1.9.9.543.1.2.3.1.11";
        }

        leaf clmgmtLicenseEULAStatus {
          type boolean;
          description
           "This object indicates whether the user accepted
            End User License Agreement for this license.
            
            true(1)  - EULA accpeted
            false(2) - EULA not accepted";
          smiv2:max-access "read-only";
          smiv2:oid "1.3.6.1.4.1.9.9.543.1.2.3.1.12";
        }

        leaf clmgmtLicenseComments {
          type snmp-framework:SnmpAdminString {
            length "0..255";
          }
          description
           "This object represents the user modifiable comments
            about the license. This object is initially populated
            with comments from the license file.";
          smiv2:max-access "read-write";
          smiv2:oid "1.3.6.1.4.1.9.9.543.1.2.3.1.13";
        }

        leaf clmgmtLicenseStatus {
          type enumeration {
            enum "inactive" {
              value "1";
            }
            enum "notInUse" {
              value "2";
            }
            enum "inUse" {
              value "3";
            }
            enum "expiredInUse" {
              value "4";
            }
            enum "expiredNotInUse" {
              value "5";
            }
            enum "usageCountConsumed" {
              value "6";
            }
          }
          description
           "This object represents status of the license.
            
            inactive(1)           - license is installed, but
                                    not active.
            notInUse(2)           - license is installed and
                                    available for use.
            inUse(3)              - the license is being used (by
                                    a feature).
            expiredInUse(4)       - license is expired but still
                                    being held by the feature.
            expiredNotInUse(5)    - license is expired and not being
                                    held by any feature.
            usageCountConsumed(6) - number of entities using this
                                    licenses has reached the allowed
                                    limit, no new entities are allowed
                                    to use this license.";
          smiv2:max-access "read-only";
          smiv2:oid "1.3.6.1.4.1.9.9.543.1.2.3.1.14";
        }

        leaf clmgmtLicenseStartDate {
          type snmpv2-tc:DateAndTime;
          description
           "This object indicates the start date for a subscription
            license. It is optional for subscription linceses to have a
            start date associated with them, they may only have an end
            date associated with them. This object may be applicable only
            when clmgmtLicenseType is paidSubscription(5),
            evaluationSubscription(6) or extensionSubscription (7).      
            The object will contain an octet string of length 0 when it is
            not applicable.";
          smiv2:max-access "read-only";
          smiv2:oid "1.3.6.1.4.1.9.9.543.1.2.3.1.15";
        }

        leaf clmgmtLicenseEndDate {
          type snmpv2-tc:DateAndTime;
          description
           "This object indicates the end date for a subscription license.
            This object is applicable only when clmgmtLicenseType is
            paidSubscription(5), evaluationSubscription(6) or
            extensionSubscription (7). The object will contain an octet
            string of length 0 when it is not applicable.";
          smiv2:max-access "read-only";
          smiv2:oid "1.3.6.1.4.1.9.9.543.1.2.3.1.16";
        }

        leaf clmgmtLicensePeriodUsed {
          type uint32;
          units "seconds";
          description
           "This object indicates the time period used for the
            Right to use (RTU) licenses. This object is applicable for all
            RTU licenses.";
          smiv2:max-access "read-only";
          smiv2:oid "1.3.6.1.4.1.9.9.543.1.2.3.1.17";
        }
      }
    }

    container clmgmtLicensableFeatureTable {
      description
       "This table contains list of licensable features in the
        image. All the licensable features will have an entry each
        in this table irrespective of whether they are using any
        licenses currently. Entries in this table are created by
        the agent one for each licensable feature in the image.
        These entries remain in the table permanently and can not
        be deleted. Management application can not create or delete
        entries from this table.";
      smiv2:oid "1.3.6.1.4.1.9.9.543.1.2.4";

      list clmgmtLicensableFeatureEntry {
        key "entPhysicalIndex clmgmtFeatureIndex";
        description
         "An entry in clmgmtLicensableFeatureTable. Each entry represents
          a licensable feature.";
        smiv2:oid "1.3.6.1.4.1.9.9.543.1.2.4.1";

        leaf entPhysicalIndex {
          type leafref {
            path "/entity-mib:ENTITY-MIB/entity-mib:entPhysicalTable/entity-mib:entPhysicalEntry/entity-mib:entPhysicalIndex";
          }
        }

        leaf clmgmtFeatureIndex {
          type uint32 {
            range "1..4294967295";
          }
          description
           "This object uniquely identifies a licensable feature in
            the device.";
          smiv2:max-access "not-accessible";
          smiv2:oid "1.3.6.1.4.1.9.9.543.1.2.4.1.1";
        }

        leaf clmgmtFeatureName {
          type snmp-framework:SnmpAdminString {
            length "0..128";
          }
          description
           "This object indicates the name of the licensable feature
            in the device. Examples of feature names are: 'IPBASE',
            'ADVIPSERVICE'";
          smiv2:max-access "read-only";
          smiv2:oid "1.3.6.1.4.1.9.9.543.1.2.4.1.2";
        }

        leaf clmgmtFeatureVersion {
          type snmp-framework:SnmpAdminString {
            length "0..32";
          }
          description
           "This object indicates the version of the licensable
            feature in the device. Examples of feature versions
            are: '1.0' or '2.0'";
          smiv2:max-access "read-only";
          smiv2:oid "1.3.6.1.4.1.9.9.543.1.2.4.1.3";
        }

        leaf clmgmtFeatureValidityPeriodRemaining {
          type uint32;
          units "seconds";
          description
           "This object indicates the time period remaining before
            the feature's license expires or transitions. This object is
            applicable only if clmgmtLicenseType of the license used by
            this feature is demo(1), or extension(2) or gracePeriod(3) or
            evalRightToUse(8).
            
            The object will contain 0 if other types of license is used
            or if the feature does not use any license. If the
            feature is using multiple licenses, this period will
            represent the cumulative period remaining from all the
            licenses used by this feature.";
          smiv2:max-access "read-only";
          smiv2:oid "1.3.6.1.4.1.9.9.543.1.2.4.1.4";
        }

        leaf clmgmtFeatureWhatIsCounted {
          type snmp-framework:SnmpAdminString {
            length "0..128";
          }
          description
           "This object represents the entity that is being counted
            by this feature. Examples of entities are IP Phones, number
            of sessions etc. This object is only applicable for
            features that use counting licenses. For other features,
            this object will return empty string.";
          smiv2:max-access "read-only";
          smiv2:oid "1.3.6.1.4.1.9.9.543.1.2.4.1.5";
        }

        leaf clmgmtFeatureStartDate {
          type snmpv2-tc:DateAndTime;
          description
           "This object indicates the license start date of the feature.
            This object is applicable if at least one of the licenses used
            for this feature has a valid start date. The start date will
            be the earliest of the valid start dates of all the licenses
            used for this feature. If none of the licenses used for this
            feature have a valid start date then this object will contain an
            octet string of length 0.";
          smiv2:max-access "read-only";
          smiv2:oid "1.3.6.1.4.1.9.9.543.1.2.4.1.6";
        }

        leaf clmgmtFeatureEndDate {
          type snmpv2-tc:DateAndTime;
          description
           "This object indicates the license end date of the feature.
            This object is applicable if at least one of the licenses used
            for this feature has a valid end date. The end date will
            be the latest of the valid end dates of all the licenses
            used for this feature. If none of the licenses used for this
            feature have a valid end date then this object will contain an
            octet string of length 0.";
          smiv2:max-access "read-only";
          smiv2:oid "1.3.6.1.4.1.9.9.543.1.2.4.1.7";
        }

        leaf clmgmtFeaturePeriodUsed {
          type uint32;
          units "seconds";
          description
           "This object indicates the license period used for the feature.";
          smiv2:max-access "read-only";
          smiv2:oid "1.3.6.1.4.1.9.9.543.1.2.4.1.8";
        }
      }
    }

    container clmgmtDevCredExportActionTable {
      description
       "A table for triggering device credentials export action.
        Management application must create this entry to trigger the
        export of device credentials from the device to a file.
        
        Once the request completes, the management application should
        retrieve the values of the objects of interest, and then
        delete the entry.  In order to prevent old entries from
        clogging the table, entries will be aged out, but an entry
        will never be deleted within 5 minutes of completion.";
      smiv2:oid "1.3.6.1.4.1.9.9.543.1.3.2";

      list clmgmtDevCredExportActionEntry {
        key "clmgmtDevCredExportActionIndex";
        description
         "An entry for each device credential export action that
          is being executed or was executed recently. The management
          application triggers the export by creating an entry in this
          table. This can be done in the following 2 methods
          
          1. CREATE-AND-GO method
              Management application sets clmgmtDevCredExportActionStatus
              to createAndGo(4) and all other required objects to valid
              values in a single SNMP SET request. If all the values
              are valid, the device creates the entry and executes the
              action. If the SET request fails, the entry will not be
              created.
          2. CREATE-AND-WAIT method
              Management application sets clmgmtDevCredExportActionStatus to
              createAndWait(5) to create an entry. Management application
              can set all other required objects to valid
              values in more than one SNMP SET request. If SET request
              for any of the objects fails, management application can set
              just only that object. Once all the required objects
              are set to valid values, management application triggers action
              execution by setting clmgmtDevCredExportActionStatus to
              active(1).
          
          To stop the action from being executed, the management application
          can delete the entry by setting clmgmtDevCredExportActionStatus
          to destroy(6) when clmgmtDevCredCommandState is pending(2).
          
          The status of action execution can be known by querying
          clmgmtDevCredCommandState. If the action is still in
          pending(2) or inProgress(3), the management application need to
          check back again after few seconds. Once the action completes
          and if status of the action is failed(6), the reason for
          failure can be retrieved from clmgmtDevCredCommandFailCause.
          
          Entry can be deleted except when clmgmtLicenseAction is set
          to inProgress(3). All entries in this table are volatile
          and are cleared on agent reset.";
        smiv2:oid "1.3.6.1.4.1.9.9.543.1.3.2.1";

        leaf clmgmtDevCredExportActionIndex {
          type uint32 {
            range "1..4294967295";
          }
          description
           "This object uniquely identifies a row in
            clmgmtDevCredExportActionTable. The management application
            chooses this value by reading
            clmgmtNextFreeDevCredExportActionIndex while creating an
            entry in this table. If an entry already exists with this
            index, the creation of the entry will not continue and
            error will be returned. The management application should
            read the value of clmgmtNextFreeDevCredExportActionIndex
            again and retry with the new value for this object.";
          smiv2:max-access "not-accessible";
          smiv2:oid "1.3.6.1.4.1.9.9.543.1.3.2.1.1";
        }

        leaf clmgmtDevCredEntPhysicalIndex {
          type entity-mib:PhysicalIndexOrZero;
          description
           "This object represents the entPhysicalIndex of the device
            for which the device credentials are being retrieved. This
            object is mainly used in devices where one device is acting
            as a master and rest of the devices as slaves. The master
            device is responsible for SNMP communication with the
            manager. Examples include stackable switches, devices with
            router processor and line cards.
            
            Note: This object need not be set if it is a stand alone
            device";
          smiv2:defval "0";
          smiv2:max-access "read-write";
          smiv2:oid "1.3.6.1.4.1.9.9.543.1.3.2.1.2";
        }

        leaf clmgmtDevCredTransferProtocol {
          type CISCO-LICENSE-MGMT-MIB:ClmgmtLicenseTransferProtocol;
          description
           "This object indicates the transfer protocol to be used when
            copying files as specified in the following objects.
            1. clmgmtDevCredExportFile
            .";
          smiv2:defval "none";
          smiv2:max-access "read-write";
          smiv2:oid "1.3.6.1.4.1.9.9.543.1.3.2.1.3";
        }

        leaf clmgmtDevCredServerAddressType {
          type inet-address:InetAddressType;
          description
           "This object indicates the transport type of the
            address contained in clmgmtDevCredServerAddress object.
            This must be set when clmgmtDevCredTransferProtocol
            is not none(1) or local(2).";
          smiv2:defval "unknown";
          smiv2:max-access "read-write";
          smiv2:oid "1.3.6.1.4.1.9.9.543.1.3.2.1.4";
        }

        leaf clmgmtDevCredServerAddress {
          type inet-address:InetAddress;
          description
           "This object indicates the the ip address of the server
            from which the files must be read or written to if 
            clmgmtDevCredTransferProtocol is not none(1) or local(2).
            
            All bits as 0s or 1s for clmgmtDevCredServerAddress are not
            allowed.
            
            The format of this address depends on the value of the
            clmgmtDevCredServerAddressType object";
          smiv2:defval "";
          smiv2:max-access "read-write";
          smiv2:oid "1.3.6.1.4.1.9.9.543.1.3.2.1.5";
        }

        leaf clmgmtDevCredServerUsername {
          type snmp-framework:SnmpAdminString {
            length "0..96";
          }
          description
           "This object indicates the remote user name for accessing
            files via ftp, rcp, sftp or scp protocols. This object
            must be set when the clmgmtDevCredTransferProtocol is
            ftp(4), rcp(5), scp(7) or sftp(8). If
            clmgmtDevCredTransferProtocol is rcp(5), the remote
            username is sent as the server username in an rcp command
            request sent by the system to a remote rcp server.";
          smiv2:defval "";
          smiv2:max-access "read-write";
          smiv2:oid "1.3.6.1.4.1.9.9.543.1.3.2.1.6";
        }

        leaf clmgmtDevCredServerPassword {
          type snmp-framework:SnmpAdminString {
            length "0..96";
          }
          description
           "This object indicates the password used by ftp, sftp or
            scp for copying a file to/from an ftp/sftp/scp server. 
            This object must be set when the
            clmgmtDevCredTransferProtocol is ftp(4) or scp(7) or
            sftp(8). Reading it returns a zero-length string for 
            security reasons.";
          smiv2:defval "";
          smiv2:max-access "read-write";
          smiv2:oid "1.3.6.1.4.1.9.9.543.1.3.2.1.7";
        }

        leaf clmgmtDevCredExportFile {
          type snmp-framework:SnmpAdminString {
            length "0..255";
          }
          description
           "This object represents file where device credentials needs
            to be exported to.";
          smiv2:max-access "read-write";
          smiv2:oid "1.3.6.1.4.1.9.9.543.1.3.2.1.8";
        }

        leaf clmgmtDevCredCommand {
          type enumeration {
            enum "noOp" {
              value "1";
            }
            enum "getDeviceCredentials" {
              value "2";
            }
          }
          description
           "This object indicates the the command to be executed.
            
            Command                          Remarks
            -------                          -------
            noOp(1)                         No operation will be
                                            performed.
            
            getDeviceCredentials(2)         Exports device credentials";
          smiv2:defval "noOp";
          smiv2:max-access "read-write";
          smiv2:oid "1.3.6.1.4.1.9.9.543.1.3.2.1.9";
        }

        leaf clmgmtDevCredCommandState {
          type CISCO-LICENSE-MGMT-MIB:ClmgmtLicenseActionState;
          description
           "This object indicates the state of the action that is
            executed as a result of setting clmgmtDevCredRowStatus
            to active(1).";
          smiv2:max-access "read-only";
          smiv2:oid "1.3.6.1.4.1.9.9.543.1.3.2.1.10";
        }

        leaf clmgmtDevCredCommandFailCause {
          type enumeration {
            enum "none" {
              value "1";
            }
            enum "unknownError" {
              value "2";
            }
            enum "transferProtocolNotSupported" {
              value "3";
            }
            enum "fileServerNotReachable" {
              value "4";
            }
            enum "unrecognizedEntPhysicalIndex" {
              value "5";
            }
            enum "invalidFile" {
              value "6";
            }
          }
          description
           "This object indicates the the reason for device
            credentials export operation failure.
            
            The value of this object is valid only when
            clmgmtDevCredCommandState is failed(6).
            
            none(1)         - action execution has not started yet.
                              If the action is completed and the 
                              action is successful, then also
                              none(1) is returned to indicate that
                              there are no errors.
            unknownError(2) - reason for failure is unknown,
                              operation failed, no operation is
                              performed
            transferProtocolNotSupported(3) - clmgmtDevCredTransferProtocol
                                              given is not supported.
            fileServerNotReachable(4)       - file server is not reachable.
            unrecognizedEntPhysicalIndex(5) - entPhysicalIndex is not
                                              valid
            invalidFile(6)  - The target file specified is not valid.";
          smiv2:max-access "read-only";
          smiv2:oid "1.3.6.1.4.1.9.9.543.1.3.2.1.11";
        }

        leaf clmgmtDevCredStorageType {
          type snmpv2-tc:StorageType;
          description
           "This object indicates the storage type for this conceptual
            row. Conceptual rows having the value 'permanent' need not
            allow write-access to any columnar objects in the row.";
          smiv2:defval "volatile";
          smiv2:max-access "read-write";
          smiv2:oid "1.3.6.1.4.1.9.9.543.1.3.2.1.12";
        }

        leaf clmgmtDevCredRowStatus {
          type snmpv2-tc:RowStatus;
          description
           "This object indicates the the status of this table entry.
            Once the entry status is set to active(1), the associated
            entry cannot be modified until the action completes
            (clmgmtDevCredCommandStatus is set to a value
            other than inProgress(3)). Once the action completes
            the only operation possible after this is to delete
            the row.
            
            clmgmtDevCredExportFile is a mandatory object to be
            set when creating this entry.";
          smiv2:max-access "read-write";
          smiv2:oid "1.3.6.1.4.1.9.9.543.1.3.2.1.13";
        }
      }
    }
  }

  notification clmgmtLicenseExpired {
    description
     "This notification is sent, when a feature license
      expires. This notification will be sent continuously
      every week even after the expiry to alert the management
      application.";
    smiv2:oid "1.3.6.1.4.1.9.9.543.0.1";

    container object-1 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureName {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureName";
        }
      }
    }

    container object-2 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureVersion {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureVersion";
        }
      }
    }
  }

  notification clmgmtLicenseExpiryWarning {
    description
     "This notification is sent when a license is about to
      expire. This notification will go out multiple times.
      First notification goes out when expiry day is 4 weeks
      ahead, second notification when expiry day is 3 weeks
      ahead, third notification when expiry day is 2 weeks
      ahead. This notification will go out daily in the
      last week of license expiry.";
    smiv2:oid "1.3.6.1.4.1.9.9.543.0.2";

    container object-1 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureName {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureName";
        }
      }
    }

    container object-2 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureVersion {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureVersion";
        }
      }
    }

    container object-3 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureValidityPeriodRemaining {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureValidityPeriodRemaining";
        }
      }
    }
  }

  notification clmgmtLicenseUsageCountExceeded {
    description
     "This notification is sent when clmgmtLicenseUsageCountRemaining
      has reached clmgmtLicenseMaxUsageCount for a counting license.";
    smiv2:oid "1.3.6.1.4.1.9.9.543.0.3";

    container object-1 {

      leaf entPhysicalIndex {
        type leafref {
          path "/entity-mib:ENTITY-MIB/entity-mib:entPhysicalTable/entity-mib:entPhysicalEntry/entity-mib:entPhysicalIndex";
        }
      }

      leaf clmgmtLicenseStoreUsed {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseStoreUsed";
        }
      }

      leaf clmgmtLicenseIndex {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseIndex";
        }
      }

      leaf clmgmtLicenseFeatureName {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseFeatureName";
        }
      }
    }

    container object-2 {

      leaf entPhysicalIndex {
        type leafref {
          path "/entity-mib:ENTITY-MIB/entity-mib:entPhysicalTable/entity-mib:entPhysicalEntry/entity-mib:entPhysicalIndex";
        }
      }

      leaf clmgmtLicenseStoreUsed {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseStoreUsed";
        }
      }

      leaf clmgmtLicenseIndex {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseIndex";
        }
      }

      leaf clmgmtLicenseFeatureVersion {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseFeatureVersion";
        }
      }
    }

    container object-3 {

      leaf entPhysicalIndex {
        type leafref {
          path "/entity-mib:ENTITY-MIB/entity-mib:entPhysicalTable/entity-mib:entPhysicalEntry/entity-mib:entPhysicalIndex";
        }
      }

      leaf clmgmtLicenseStoreUsed {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseStoreUsed";
        }
      }

      leaf clmgmtLicenseIndex {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseIndex";
        }
      }

      leaf clmgmtLicenseMaxUsageCount {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseMaxUsageCount";
        }
      }
    }

    container object-4 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureWhatIsCounted {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureWhatIsCounted";
        }
      }
    }

    container object-5 {

      leaf entPhysicalIndex {
        type leafref {
          path "/entity-mib:ENTITY-MIB/entity-mib:entPhysicalTable/entity-mib:entPhysicalEntry/entity-mib:entPhysicalIndex";
        }
      }

      leaf clmgmtLicenseStoreUsed {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseStoreUsed";
        }
      }

      leaf clmgmtLicenseIndex {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseIndex";
        }
      }

      leaf clmgmtLicenseComments {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseComments";
        }
      }
    }
  }

  notification clmgmtLicenseUsageCountAboutToExceed {
    description
     "This notification is sent when clmgmtLicenseUsageCountRemaining
      has reached 80% of clmgmtLicenseMaxUsageCount for a counting
      license. This is a warning notification to the management
      application that very soon the maximum count will be reached
      and after that the device will not allow new entities to
      make use of this license.";
    smiv2:oid "1.3.6.1.4.1.9.9.543.0.4";

    container object-1 {

      leaf entPhysicalIndex {
        type leafref {
          path "/entity-mib:ENTITY-MIB/entity-mib:entPhysicalTable/entity-mib:entPhysicalEntry/entity-mib:entPhysicalIndex";
        }
      }

      leaf clmgmtLicenseStoreUsed {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseStoreUsed";
        }
      }

      leaf clmgmtLicenseIndex {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseIndex";
        }
      }

      leaf clmgmtLicenseFeatureName {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseFeatureName";
        }
      }
    }

    container object-2 {

      leaf entPhysicalIndex {
        type leafref {
          path "/entity-mib:ENTITY-MIB/entity-mib:entPhysicalTable/entity-mib:entPhysicalEntry/entity-mib:entPhysicalIndex";
        }
      }

      leaf clmgmtLicenseStoreUsed {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseStoreUsed";
        }
      }

      leaf clmgmtLicenseIndex {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseIndex";
        }
      }

      leaf clmgmtLicenseFeatureVersion {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseFeatureVersion";
        }
      }
    }

    container object-3 {

      leaf entPhysicalIndex {
        type leafref {
          path "/entity-mib:ENTITY-MIB/entity-mib:entPhysicalTable/entity-mib:entPhysicalEntry/entity-mib:entPhysicalIndex";
        }
      }

      leaf clmgmtLicenseStoreUsed {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseStoreUsed";
        }
      }

      leaf clmgmtLicenseIndex {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseIndex";
        }
      }

      leaf clmgmtLicenseMaxUsageCount {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseMaxUsageCount";
        }
      }
    }

    container object-4 {

      leaf entPhysicalIndex {
        type leafref {
          path "/entity-mib:ENTITY-MIB/entity-mib:entPhysicalTable/entity-mib:entPhysicalEntry/entity-mib:entPhysicalIndex";
        }
      }

      leaf clmgmtLicenseStoreUsed {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseStoreUsed";
        }
      }

      leaf clmgmtLicenseIndex {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseIndex";
        }
      }

      leaf clmgmtLicenseUsageCountRemaining {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseUsageCountRemaining";
        }
      }
    }

    container object-5 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureWhatIsCounted {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureWhatIsCounted";
        }
      }
    }

    container object-6 {

      leaf entPhysicalIndex {
        type leafref {
          path "/entity-mib:ENTITY-MIB/entity-mib:entPhysicalTable/entity-mib:entPhysicalEntry/entity-mib:entPhysicalIndex";
        }
      }

      leaf clmgmtLicenseStoreUsed {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseStoreUsed";
        }
      }

      leaf clmgmtLicenseIndex {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseIndex";
        }
      }

      leaf clmgmtLicenseComments {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseComments";
        }
      }
    }
  }

  notification clmgmtLicenseInstalled {
    description
     "This notification is sent when a license is installed
      successfully.";
    smiv2:oid "1.3.6.1.4.1.9.9.543.0.5";

    container object-1 {

      leaf entPhysicalIndex {
        type leafref {
          path "/entity-mib:ENTITY-MIB/entity-mib:entPhysicalTable/entity-mib:entPhysicalEntry/entity-mib:entPhysicalIndex";
        }
      }

      leaf clmgmtLicenseStoreUsed {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseStoreUsed";
        }
      }

      leaf clmgmtLicenseIndex {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseIndex";
        }
      }

      leaf clmgmtLicenseFeatureName {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseFeatureName";
        }
      }
    }

    container object-2 {

      leaf entPhysicalIndex {
        type leafref {
          path "/entity-mib:ENTITY-MIB/entity-mib:entPhysicalTable/entity-mib:entPhysicalEntry/entity-mib:entPhysicalIndex";
        }
      }

      leaf clmgmtLicenseStoreUsed {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseStoreUsed";
        }
      }

      leaf clmgmtLicenseIndex {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseIndex";
        }
      }

      leaf clmgmtLicenseFeatureVersion {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseFeatureVersion";
        }
      }
    }

    container object-3 {

      leaf entPhysicalIndex {
        type leafref {
          path "/entity-mib:ENTITY-MIB/entity-mib:entPhysicalTable/entity-mib:entPhysicalEntry/entity-mib:entPhysicalIndex";
        }
      }

      leaf clmgmtLicenseStoreUsed {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseStoreUsed";
        }
      }

      leaf clmgmtLicenseIndex {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseIndex";
        }
      }

      leaf clmgmtLicenseType {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseType";
        }
      }
    }

    container object-4 {

      leaf entPhysicalIndex {
        type leafref {
          path "/entity-mib:ENTITY-MIB/entity-mib:entPhysicalTable/entity-mib:entPhysicalEntry/entity-mib:entPhysicalIndex";
        }
      }

      leaf clmgmtLicenseStoreUsed {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseStoreUsed";
        }
      }

      leaf clmgmtLicenseIndex {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseIndex";
        }
      }

      leaf clmgmtLicenseComments {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseComments";
        }
      }
    }
  }

  notification clmgmtLicenseCleared {
    description
     "This notification is sent when a license is cleared
      successfully.";
    smiv2:oid "1.3.6.1.4.1.9.9.543.0.6";

    container object-1 {

      leaf entPhysicalIndex {
        type leafref {
          path "/entity-mib:ENTITY-MIB/entity-mib:entPhysicalTable/entity-mib:entPhysicalEntry/entity-mib:entPhysicalIndex";
        }
      }

      leaf clmgmtLicenseStoreUsed {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseStoreUsed";
        }
      }

      leaf clmgmtLicenseIndex {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseIndex";
        }
      }

      leaf clmgmtLicenseFeatureName {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseFeatureName";
        }
      }
    }

    container object-2 {

      leaf entPhysicalIndex {
        type leafref {
          path "/entity-mib:ENTITY-MIB/entity-mib:entPhysicalTable/entity-mib:entPhysicalEntry/entity-mib:entPhysicalIndex";
        }
      }

      leaf clmgmtLicenseStoreUsed {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseStoreUsed";
        }
      }

      leaf clmgmtLicenseIndex {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseIndex";
        }
      }

      leaf clmgmtLicenseFeatureVersion {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseFeatureVersion";
        }
      }
    }

    container object-3 {

      leaf entPhysicalIndex {
        type leafref {
          path "/entity-mib:ENTITY-MIB/entity-mib:entPhysicalTable/entity-mib:entPhysicalEntry/entity-mib:entPhysicalIndex";
        }
      }

      leaf clmgmtLicenseStoreUsed {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseStoreUsed";
        }
      }

      leaf clmgmtLicenseIndex {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseIndex";
        }
      }

      leaf clmgmtLicenseType {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseType";
        }
      }
    }

    container object-4 {

      leaf entPhysicalIndex {
        type leafref {
          path "/entity-mib:ENTITY-MIB/entity-mib:entPhysicalTable/entity-mib:entPhysicalEntry/entity-mib:entPhysicalIndex";
        }
      }

      leaf clmgmtLicenseStoreUsed {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseStoreUsed";
        }
      }

      leaf clmgmtLicenseIndex {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseIndex";
        }
      }

      leaf clmgmtLicenseComments {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseComments";
        }
      }
    }
  }

  notification clmgmtLicenseRevoked {
    description
     "This notification is sent when a license is revoked
      successfully.";
    smiv2:oid "1.3.6.1.4.1.9.9.543.0.7";

    container object-1 {

      leaf entPhysicalIndex {
        type leafref {
          path "/entity-mib:ENTITY-MIB/entity-mib:entPhysicalTable/entity-mib:entPhysicalEntry/entity-mib:entPhysicalIndex";
        }
      }

      leaf clmgmtLicenseStoreUsed {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseStoreUsed";
        }
      }

      leaf clmgmtLicenseIndex {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseIndex";
        }
      }

      leaf clmgmtLicenseFeatureName {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseFeatureName";
        }
      }
    }

    container object-2 {

      leaf entPhysicalIndex {
        type leafref {
          path "/entity-mib:ENTITY-MIB/entity-mib:entPhysicalTable/entity-mib:entPhysicalEntry/entity-mib:entPhysicalIndex";
        }
      }

      leaf clmgmtLicenseStoreUsed {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseStoreUsed";
        }
      }

      leaf clmgmtLicenseIndex {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseIndex";
        }
      }

      leaf clmgmtLicenseFeatureVersion {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseFeatureVersion";
        }
      }
    }

    container object-3 {

      leaf entPhysicalIndex {
        type leafref {
          path "/entity-mib:ENTITY-MIB/entity-mib:entPhysicalTable/entity-mib:entPhysicalEntry/entity-mib:entPhysicalIndex";
        }
      }

      leaf clmgmtLicenseStoreUsed {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseStoreUsed";
        }
      }

      leaf clmgmtLicenseIndex {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseIndex";
        }
      }

      leaf clmgmtLicenseType {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseType";
        }
      }
    }

    container object-4 {

      leaf entPhysicalIndex {
        type leafref {
          path "/entity-mib:ENTITY-MIB/entity-mib:entPhysicalTable/entity-mib:entPhysicalEntry/entity-mib:entPhysicalIndex";
        }
      }

      leaf clmgmtLicenseStoreUsed {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseStoreUsed";
        }
      }

      leaf clmgmtLicenseIndex {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseIndex";
        }
      }

      leaf clmgmtLicenseComments {
        type leafref {
          path "/CISCO-LICENSE-MGMT-MIB:CISCO-LICENSE-MGMT-MIB/CISCO-LICENSE-MGMT-MIB:clmgmtLicenseInfoTable/CISCO-LICENSE-MGMT-MIB:clmgmtLicenseInfoEntry/CISCO-LICENSE-MGMT-MIB:clmgmtLicenseComments";
        }
      }
    }
  }

  notification clmgmtLicenseEULAAccepted {
    description
     "This notification is sent when a user accepts End User
      License Agreement (EULA) for a license.";
    smiv2:oid "1.3.6.1.4.1.9.9.543.0.8";

    container object-1 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureName {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureName";
        }
      }
    }

    container object-2 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureVersion {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureVersion";
        }
      }
    }
  }

  notification clmgmtLicenseNotEnforced {
    description
     "This notification is sent when a license does not
      exist for a feature, but the feature is a mandatory
      feature and it should run. This notification will be
      sent out periodically to indicate that there is no
      license installed for this feature and it needs to
      be done as soon as possible.";
    smiv2:oid "1.3.6.1.4.1.9.9.543.0.9";

    container object-1 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureName {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureName";
        }
      }
    }

    container object-2 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureVersion {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureVersion";
        }
      }
    }
  }

  notification clmgmtLicenseSubscriptionExpiryWarning {
    description
     "This notification is sent when a subscription license of a
      feature is about to expire. This notification will be sent as
      per the following schedule:
      Once a week for the last eight weeks
      Once a day for the last week
      Once a hour for the last day";
    smiv2:oid "1.3.6.1.4.1.9.9.543.0.10";

    container object-1 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureName {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureName";
        }
      }
    }

    container object-2 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureVersion {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureVersion";
        }
      }
    }

    container object-3 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureEndDate {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureEndDate";
        }
      }
    }
  }

  notification clmgmtLicenseSubscriptionExtExpiryWarning {
    description
     "This notification is sent when the subscription license end
      date of a feature is reached but extension period is left. This
      notification will be sent once a day after the license end date
      is reached.";
    smiv2:oid "1.3.6.1.4.1.9.9.543.0.11";

    container object-1 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureName {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureName";
        }
      }
    }

    container object-2 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureVersion {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureVersion";
        }
      }
    }

    container object-3 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureEndDate {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureEndDate";
        }
      }
    }
  }

  notification clmgmtLicenseSubscriptionExpired {
    description
     "This notification will be sent after a subscription license
      of a feature completely expires. It will be sent once a day
      after the license has completely expired";
    smiv2:oid "1.3.6.1.4.1.9.9.543.0.12";

    container object-1 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureName {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureName";
        }
      }
    }

    container object-2 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureVersion {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureVersion";
        }
      }
    }

    container object-3 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureEndDate {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureEndDate";
        }
      }
    }
  }

  notification clmgmtLicenseEvalRTUTransitionWarning {
    description
     "This notification is sent when Evaluation to Right to use (RTU)
      license transition is about to happen. The first notification
      will be sent 10 days before the transition and second
      notification will be sent 5 days before the transition.";
    smiv2:oid "1.3.6.1.4.1.9.9.543.0.13";

    container object-1 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureName {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureName";
        }
      }
    }

    container object-2 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureVersion {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureVersion";
        }
      }
    }

    container object-3 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureValidityPeriodRemaining {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureValidityPeriodRemaining";
        }
      }
    }
  }

  notification clmgmtLicenseEvalRTUTransition {
    description
     "This notification is sent, when a feature license transitions
      from a evaluation to a Right to use (RTU) license.";
    smiv2:oid "1.3.6.1.4.1.9.9.543.0.14";

    container object-1 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureName {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureName";
        }
      }
    }

    container object-2 {

      leaf entPhysicalIndex {
        type leafref {
          path "/entity-mib:ENTITY-MIB/entity-mib:entPhysicalTable/entity-mib:entPhysicalEntry/entity-mib:entPhysicalIndex";
        }
      }

      leaf clmgmtFeatureIndex {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureIndex";
        }
      }

      leaf clmgmtFeatureVersion {
        type leafref {
          path "/CISCO-LICENSE-MGMT-MIB:CISCO-LICENSE-MGMT-MIB/CISCO-LICENSE-MGMT-MIB:clmgmtLicensableFeatureTable/CISCO-LICENSE-MGMT-MIB:clmgmtLicensableFeatureEntry/CISCO-LICENSE-MGMT-MIB:clmgmtFeatureVersion";
        }
      }
    }
  }

  smiv2:alias "ciscoLicenseMgmtMIB" {
    smiv2:oid "1.3.6.1.4.1.9.9.543";
  }

  smiv2:alias "ciscoLicenseMgmtMIBNotifs" {
    smiv2:oid "1.3.6.1.4.1.9.9.543.0";
  }

  smiv2:alias "ciscoLicenseMgmtMIBObjects" {
    smiv2:oid "1.3.6.1.4.1.9.9.543.1";
  }

  smiv2:alias "clmgmtLicenseConfiguration" {
    smiv2:oid "1.3.6.1.4.1.9.9.543.1.1";
  }

  smiv2:alias "clmgmtLicenseInformation" {
    smiv2:oid "1.3.6.1.4.1.9.9.543.1.2";
  }

  smiv2:alias "clmgmtLicenseDeviceInformation" {
    smiv2:oid "1.3.6.1.4.1.9.9.543.1.3";
  }

  smiv2:alias "clmgmtLicenseNotifObjects" {
    smiv2:oid "1.3.6.1.4.1.9.9.543.1.4";
  }

  smiv2:alias "ciscoLicenseMgmtMIBConform" {
    smiv2:oid "1.3.6.1.4.1.9.9.543.2";
  }

  smiv2:alias "ciscoLicenseMgmtCompliances" {
    smiv2:oid "1.3.6.1.4.1.9.9.543.2.1";
  }

  smiv2:alias "ciscoLicenseMgmtGroups" {
    smiv2:oid "1.3.6.1.4.1.9.9.543.2.2";
  }

}
