/*
 * Generated by confdc --mib2yang-std
 * Source: mgmt/dmi/model/mib/src/CISCO-IETF-ATM2-PVCTRAP-MIB-EXTN.mib
 */
/*
 * This YANG module has been generated by smidump 0.5.0:
 *
 *      smidump -f yang CISCO-IETF-ATM2-PVCTRAP-MIB-EXTN
 *
 * Do not edit. Edit the source file instead!
 */

module CISCO-IETF-ATM2-PVCTRAP-MIB-EXTN {

  namespace "urn:ietf:params:xml:ns:yang:smiv2:CISCO-IETF-ATM2-PVCTRAP-MIB-EXTN";
  prefix CISCO-IETF-ATM2-PVCTRAP-MIB-EXTN;

  import ATM-MIB {
    prefix "atm-mib";
  }

  import IF-MIB {
    prefix "if-mib";
  }

  import ietf-yang-smiv2 {
    prefix "smiv2";
  }

  import ietf-yang-types {
    prefix "yang";
  }

  organization
   "Cisco Systems, Inc.";

  contact
   "       Cisco Systems
    Customer Service
    
    Postal: 170 W Tasman Drive
    San Jose, CA  95134
    USA
    
    Tel: +1 800 553-NETS
    
    E-mail: cs-atm@cisco.com";

  description
   "This MIB Module is a supplement to the
    CISCO-IETF-ATM2-PVCTRAP-MIB.";

  revision 2000-07-11 {
    description
     "[Revision added by libsmi due to a LAST-UPDATED clause.]";
  }


  container CISCO-IETF-ATM2-PVCTRAP-MIB-EXTN {
    config false;

    container atmCurrentStatusChangePVclTable {
      description
       "A table indicating all VCLs for which there is an
        active row in the atmVclTable having an atmVclConnKind
        value of `pvc' and atmVclOperStatus to have changed in the
        last PVC notification interval.";
      smiv2:oid "1.3.6.1.4.1.9.10.31.1.2";

      list atmCurrentStatusChangePVclEntry {
        key "ifIndex atmVclVpi atmVclVci";
        description
         "Each entry in the table represents a VCL for which
          there is an active row in the atmVclTable having an
          atmVclConnKind value of `pvc' and atmVclOperStatus
          to have changed in the last PVC notification interval.";
        smiv2:oid "1.3.6.1.4.1.9.10.31.1.2.1";

        leaf ifIndex {
          type leafref {
            path "/if-mib:IF-MIB/if-mib:ifTable/if-mib:ifEntry/if-mib:ifIndex";
          }
        }

        leaf atmVclVpi {
          type leafref {
            path "/atm-mib:ATM-MIB/atm-mib:atmVclTable/atm-mib:atmVclEntry/atm-mib:atmVclVpi";
          }
        }

        leaf atmVclVci {
          type leafref {
            path "/atm-mib:ATM-MIB/atm-mib:atmVclTable/atm-mib:atmVclEntry/atm-mib:atmVclVci";
          }
        }

        leaf atmPVclStatusTransition {
          type yang:counter32;
          description
           "The number of state transitions that has happened 
            on this PVCL in the last notification interval.";
          smiv2:max-access "read-only";
          smiv2:oid "1.3.6.1.4.1.9.10.31.1.2.1.1";
        }

        leaf atmPVclStatusChangeStart {
          type yang:timestamp;
          description
           "The time stamp at which this PVCL changed state for the
            first time in  the last notification interval.";
          smiv2:max-access "read-only";
          smiv2:oid "1.3.6.1.4.1.9.10.31.1.2.1.2";
        }

        leaf atmPVclStatusChangeEnd {
          type yang:timestamp;
          description
           "The time stamp of the last state change of this PVCL
            in the last notification interval.";
          smiv2:max-access "read-only";
          smiv2:oid "1.3.6.1.4.1.9.10.31.1.2.1.3";
        }
      }
    }

    container atmStatusChangePVclRangeTable {
      description
       "A table indicating more than one VCLs in a consecutive 
        range and for each VCL there is an active row in the 
        atmVclTable having an atmVclConnKind value of `pvc'
        and atmVclOperStatus to have changed in the same
        direction in the last PVC notification interval.";
      smiv2:oid "1.3.6.1.4.1.9.10.31.1.3";

      list atmStatusChangePVclRangeEntry {
        key "ifIndex atmVclVpi rangeIndex";
        description
         "Each entry in this table represents a range of VCLs and 
          for each VCL there is an active row in the atmVclTable having
          an atmVclConnKind value of 'pvc' and atmVclOperStatus to have
          changed in the same direction in the last notification 
          interval.";
        smiv2:oid "1.3.6.1.4.1.9.10.31.1.3.1";

        leaf ifIndex {
          type leafref {
            path "/if-mib:IF-MIB/if-mib:ifTable/if-mib:ifEntry/if-mib:ifIndex";
          }
        }

        leaf atmVclVpi {
          type leafref {
            path "/atm-mib:ATM-MIB/atm-mib:atmVclTable/atm-mib:atmVclEntry/atm-mib:atmVclVpi";
          }
        }

        leaf rangeIndex {
          type yang:counter32;
          description
           "Index to represent different ranges, the first range is 
            indexed by value 0, the second by 1 and so on...";
          smiv2:max-access "not-accessible";
          smiv2:oid "1.3.6.1.4.1.9.10.31.1.4";
        }

        leaf atmPVclLowerRangeValue {
          type int32 {
            range "0..65536";
          }
          description
           "The first PVCL in a range of PVcls for which the 
            atmVclOperStatus to have changed in the last 
            notification interval.";
          smiv2:max-access "read-only";
          smiv2:oid "1.3.6.1.4.1.9.10.31.1.3.1.1";
        }

        leaf atmPVclHigherRangeValue {
          type int32 {
            range "0..65536";
          }
          description
           "The last PVCL in a range of PVcls for which the 
            atmOperStatus to have changed in the last 
            notification interval.";
          smiv2:max-access "read-only";
          smiv2:oid "1.3.6.1.4.1.9.10.31.1.3.1.2";
        }

        leaf atmPVclRangeStatusChangeStart {
          type yang:timestamp;
          description
           "The time stamp at which the first PVCL in the range
            changed state in the last notification interval.";
          smiv2:max-access "read-only";
          smiv2:oid "1.3.6.1.4.1.9.10.31.1.3.1.3";
        }

        leaf atmPVclRangeStatusChangeEnd {
          type yang:timestamp;
          description
           "The time stamp at which the last PVCL in the range
            changed state in the last notification interval.";
          smiv2:max-access "read-only";
          smiv2:oid "1.3.6.1.4.1.9.10.31.1.3.1.4";
        }
      }
    }
  }

  smiv2:alias "atmInterfaceExt2Table" {
    description
     "This table contains ATM interface monitoring
      information not defined in the
      atmInterfaceConfTable from the ATM-MIB and
      atmInterfaceExtTable CISCO-IETF-ATM2-PVCTRAP-MIB.";
    smiv2:oid "1.3.6.1.4.1.9.10.31.1.1";
  }

  smiv2:alias "atmInterfaceExt2Entry" {
    description
     "An entry extends the atmInterfaceConfEntry
      defined in ATM MIB.  Each entry corresponds
      to an ATM interface.";
    smiv2:oid "1.3.6.1.4.1.9.10.31.1.1.1";
  }

  augment "/atm-mib:ATM-MIB/atm-mib:atmInterfaceConfTable/atm-mib:atmInterfaceConfEntry" {
    description
     "An entry extends the atmInterfaceConfEntry
      defined in ATM MIB.  Each entry corresponds
      to an ATM interface.";
    smiv2:oid "1.3.6.1.4.1.9.10.31.1.1.1";

    leaf atmIntfCurrentlyDownToUpPVcls {
      type yang:gauge32;
      description
       "The current number PVCLs on this interface which 
        changed state to 'up' since the last 
        atmIntPvcUpTrap was sent.";
      smiv2:max-access "read-only";
      smiv2:oid "1.3.6.1.4.1.9.10.31.1.1.1.1";
    }

    leaf atmIntfOAMFailedPVcls {
      type yang:gauge32;
      description
       "The total number of PVCLs in this interface which 
        are currently in the oam loopback failed condition but 
        the status of each PVCL remain in the 'up' state.";
      smiv2:max-access "read-only";
      smiv2:oid "1.3.6.1.4.1.9.10.31.1.1.1.2";
    }

    leaf atmIntfCurrentlyOAMFailingPVcls {
      type yang:gauge32;
      description
       "The current number of PVCLs on this interface for which the
        oam loop back has failed but the status of each PVCL remain 
        in the 'up' state in the last notification interval.";
      smiv2:max-access "read-only";
      smiv2:oid "1.3.6.1.4.1.9.10.31.1.1.1.3";
    }
  }

  notification atmIntfPvcUpTrap {
    description
     "A notification indicating that one or more
      PVCLs on this interface has changed state back to 'up'
      since the last atmIntfPvcUpTrap was sent. If the trap 
      has not been sent for the last notification interval 
      it will be sent when a PVCL changes state back to 'up'.";
    smiv2:oid "1.3.6.1.4.1.9.10.31.2.1.0.1";

    container object-1 {

      leaf ifIndex {
        type leafref {
          path "/if-mib:IF-MIB/if-mib:ifTable/if-mib:ifEntry/if-mib:ifIndex";
        }
      }
    }

    container object-2 {

      leaf ifIndex {
        type leafref {
          path "/if-mib:IF-MIB/if-mib:ifTable/if-mib:ifEntry/if-mib:ifIndex";
        }
      }

      leaf atmIntfCurrentlyDownToUpPVcls {
        type leafref {
          path "/atm-mib:ATM-MIB/atm-mib:atmInterfaceConfTable/atm-mib:atmInterfaceConfEntry/CISCO-IETF-ATM2-PVCTRAP-MIB-EXTN:atmIntfCurrentlyDownToUpPVcls";
        }
      }
    }
  }

  notification atmIntfPvcOAMFailureTrap {
    description
     "A notification indicating that one or more
      PVCLs on this interface has OAM loop back failed 
      since the last atmIntfPvcOAMFailuresTrap was sent.
      If this trap has not been sent for the last
      atmIntfPvcNotificationInterval, then it will be
      sent on the next increment of atmIntfPvcOAMFailures.";
    smiv2:oid "1.3.6.1.4.1.9.10.31.2.1.0.2";

    container object-1 {

      leaf ifIndex {
        type leafref {
          path "/if-mib:IF-MIB/if-mib:ifTable/if-mib:ifEntry/if-mib:ifIndex";
        }
      }
    }

    container object-2 {

      leaf ifIndex {
        type leafref {
          path "/if-mib:IF-MIB/if-mib:ifTable/if-mib:ifEntry/if-mib:ifIndex";
        }
      }

      leaf atmIntfOAMFailedPVcls {
        type leafref {
          path "/atm-mib:ATM-MIB/atm-mib:atmInterfaceConfTable/atm-mib:atmInterfaceConfEntry/CISCO-IETF-ATM2-PVCTRAP-MIB-EXTN:atmIntfOAMFailedPVcls";
        }
      }
    }

    container object-3 {

      leaf ifIndex {
        type leafref {
          path "/if-mib:IF-MIB/if-mib:ifTable/if-mib:ifEntry/if-mib:ifIndex";
        }
      }

      leaf atmIntfCurrentlyOAMFailingPVcls {
        type leafref {
          path "/atm-mib:ATM-MIB/atm-mib:atmInterfaceConfTable/atm-mib:atmInterfaceConfEntry/CISCO-IETF-ATM2-PVCTRAP-MIB-EXTN:atmIntfCurrentlyOAMFailingPVcls";
        }
      }
    }
  }

  smiv2:alias "ciscoIetfAtm2PvctrapMIBExtn" {
    smiv2:oid "1.3.6.1.4.1.9.10.31";
  }

  smiv2:alias "atm2MIBObjectsExtn" {
    smiv2:oid "1.3.6.1.4.1.9.10.31.1";
  }

  smiv2:alias "atm2MIBTrapsExtn" {
    smiv2:oid "1.3.6.1.4.1.9.10.31.2";
  }

  smiv2:alias "atmPvcTrapsExtn" {
    smiv2:oid "1.3.6.1.4.1.9.10.31.2.1";
  }

  smiv2:alias "atmPvcTrapsPrefixExtn" {
    smiv2:oid "1.3.6.1.4.1.9.10.31.2.1.0";
  }

  smiv2:alias "pvctrapMIBExtnConformance" {
    smiv2:oid "1.3.6.1.4.1.9.10.31.3";
  }

  smiv2:alias "pvctrapMIBExtnConformanceCompliances" {
    smiv2:oid "1.3.6.1.4.1.9.10.31.3.1";
  }

  smiv2:alias "pvctrapMIBExtnConformanceGroups" {
    smiv2:oid "1.3.6.1.4.1.9.10.31.3.2";
  }

}
