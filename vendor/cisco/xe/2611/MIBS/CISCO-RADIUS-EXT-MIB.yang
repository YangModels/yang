/*
 * Generated by confdc --mib2yang-std
 * Source: mgmt/dmi/model/mib/src/patched/CISCO-RADIUS-EXT-MIB.mib
 */
/*
 * This YANG module has been generated by smidump 0.5.0:
 *
 *      smidump -f yang CISCO-RADIUS-EXT-MIB
 *
 * Do not edit. Edit the source file instead!
 */

module CISCO-RADIUS-EXT-MIB {

  namespace "urn:ietf:params:xml:ns:yang:smiv2:CISCO-RADIUS-EXT-MIB";
  prefix CISCO-RADIUS-EXT-MIB;

  import SNMPv2-TC {
    prefix "snmpv2-tc";
  }

  import ietf-inet-types {
    prefix "inet";
  }

  import ietf-yang-smiv2 {
    prefix "smiv2";
  }

  import ietf-yang-types {
    prefix "yang";
  }

  organization
   "Cisco Systems, Inc.";

  contact
   "Cisco Systems
    Customer Service
    
    Postal: 170 W Tasman Drive
    San Jose, CA  95134
    USA
    
    Tel: +1 800 553-NETS
    
    E-mail: cs-aaa@cisco.com";

  description
   "This MIB module defines objects describing RADIUS (Remote
    Access Dialin User Service), serving as an extension of the
    following MIB modules: 
    - 
        - RADIUS-AUTH-CLIENT-MIB [RFC4668] 
        - RADIUS-AUTH-SERVER-MIB [RFC4669] 
        - RADIUS-ACC-CLIENT-MIB [RFC4670] 
        - RADIUS-ACC-SERVER-MIB [RFC4671] 
        - RADIUS-DYNAUTH-CLIENT-MIB [RFC4672] 
        - RADIUS-DYNAUTH-SERVER-MIB [RFC4673] 
    - 
    [RFC4668] D. Nelson, RADIUS Authentication Client MIB for IPv6,
    
    RFC-4668, August 2006. 
    - 
    [RFC4669] D. Nelson, RADIUS Authentication Server MIB for IPv6,
    
    RFC-4669, August 2006. 
    - 
    [RFC4670] D. Nelson, RADIUS Accounting Client MIB for IPv6,
    RFC-4670, August 2006. 
    - 
    [RFC4671] D. Nelson, RADIUS Accounting Server MIB for IPv6,
    RFC-4671, August 2006. 
    - 
    [RFC4672] S. De Cnodder, N. Jonnala, M. Chiba, RADIUS Dynamic 
    Authorization Client MIB, RFC-4672, September 2006. 
    - 
    [RFC4673] S. De Cnodder, N. Jonnala, M. Chiba, RADIUS Dynamic 
    Authorization Server MIB, RFC-4673, September 2006.";

  revision 2010-05-25 {
    description
     "Modified 'max-access' of creAuthClientLastUsedSourceId and
      creAcctClientLastUsedSourceId";
  }

  revision 2010-05-20 {
    description
     "Initial Version";
  }

  typedef RadiusSourceIdentifier {
    type uint32 {
      range "0..255";
    }
    description
     "This textual convention represents the range of identifers used
      when 'extended RADIUS source port' is configured.";
  }


  container CISCO-RADIUS-EXT-MIB {
    config false;

    container creClientGlobal {
      smiv2:oid "1.3.6.1.4.1.9.9.736.1.1";

      leaf creClientTotalMaxInQLength {
        type yang:gauge32;
        units "RADIUS packets";
        description
         "This object indicates the maximum length of the queue which
          stores the incoming RADIUS packets.";
        smiv2:max-access "read-only";
        smiv2:oid "1.3.6.1.4.1.9.9.736.1.1.1";
      }

      leaf creClientTotalMaxWaitQLength {
        type yang:gauge32;
        units "RADIUS packets";
        description
         "This object indicates the maximum length of the queue which
          stores the pending RADIUS packets for which the responses are
          outstanding.";
        smiv2:max-access "read-only";
        smiv2:oid "1.3.6.1.4.1.9.9.736.1.1.2";
      }

      leaf creClientTotalMaxDoneQLength {
        type yang:gauge32;
        units "RADIUS packets";
        description
         "This object indicates the maximum length of the queue which
          stores those RADIUS packets for which the responses are
          received.";
        smiv2:max-access "read-only";
        smiv2:oid "1.3.6.1.4.1.9.9.736.1.1.3";
      }

      leaf creClientTotalAccessRejects {
        type yang:counter32;
        units "RADIUS packets";
        description
         "This object indicates the number of access reject packets
          received by the RADIUS client.";
        smiv2:max-access "read-only";
        smiv2:oid "1.3.6.1.4.1.9.9.736.1.1.4";
      }

      leaf creClientTotalAverageResponseDelay {
        type snmpv2-tc:TimeInterval;
        description
         "This object indicates the overall response delay experienced
          by RADIUS packets (both authentication and accounting).";
        smiv2:max-access "read-only";
        smiv2:oid "1.3.6.1.4.1.9.9.736.1.1.5";
      }

      leaf creClientSourcePortRangeStart {
        type inet:port-number;
        description
         "If the 'extended RADIUS source ports' is configured, multiple
          source ports are used for sending out RADIUS authentication or
          accounting requests.  This MIB object indicates the port value
          from where this range starts.";
        smiv2:max-access "read-only";
        smiv2:oid "1.3.6.1.4.1.9.9.736.1.1.6";
      }

      leaf creClientSourcePortRangeEnd {
        type inet:port-number;
        description
         "If the 'extended RADIUS source port' is configured, multiple
          source ports are used for sending out RADIUS authentication or
          accounting requests.  This MIB object indicates the port value
          where this range ends.";
        smiv2:max-access "read-only";
        smiv2:oid "1.3.6.1.4.1.9.9.736.1.1.7";
      }

      leaf creClientLastUsedSourcePort {
        type inet:port-number;
        description
         "If the 'extended RADIUS source ports' is configured, multiple
          source ports are used for sending out RADIUS authentication or
          accounting requests.  This MIB object indicates the last source
          port that was used to send out a RADIUS authentication or
          accounting request.";
        smiv2:max-access "read-only";
        smiv2:oid "1.3.6.1.4.1.9.9.736.1.1.8";
      }

      leaf creClientLastUsedSourceId {
        type CISCO-RADIUS-EXT-MIB:RadiusSourceIdentifier;
        description
         "This MIB object indicates the last source identifier that was
          used to send out a RADIUS packet when 'extended RADIUS source
          ports' is configured.  The source identifier is a counter that
          is incremented everytime a RADIUS authentication or an
          accounting packet is sent.";
        smiv2:max-access "read-only";
        smiv2:oid "1.3.6.1.4.1.9.9.736.1.1.9";
      }
    }

    container creClientAuthentication {
      smiv2:oid "1.3.6.1.4.1.9.9.736.1.2";

      leaf creAuthClientBadAuthenticators {
        type yang:counter32;
        units "RADIUS packets";
        description
         "This object indicates the number of RADIUS authentication
          response packets received which contained invalid
          authenticators.";
        smiv2:max-access "read-only";
        smiv2:oid "1.3.6.1.4.1.9.9.736.1.2.1";
      }

      leaf creAuthClientUnknownResponses {
        type yang:counter32;
        units "RADIUS packets";
        description
         "This object indicates the number of unknown RADIUS
          authentication responses received.";
        smiv2:max-access "read-only";
        smiv2:oid "1.3.6.1.4.1.9.9.736.1.2.2";
      }

      leaf creAuthClientTotalPacketsWithResponses {
        type yang:counter32;
        units "RADIUS packets";
        description
         "This object indicates the number of RADIUS authentication
          packets that received responses.";
        smiv2:max-access "read-only";
        smiv2:oid "1.3.6.1.4.1.9.9.736.1.2.3";
      }

      leaf creAuthClientBufferAllocFailures {
        type yang:counter32;
        units "buffer failures";
        description
         "This object indicates the number of buffer allocation
          failures encountered during RADIUS request formation.";
        smiv2:max-access "read-only";
        smiv2:oid "1.3.6.1.4.1.9.9.736.1.2.4";
      }

      leaf creAuthClientTotalResponses {
        type yang:counter32;
        units "RADIUS packets";
        description
         "This object indicates the number of RADIUS authentication
          response packets received by the RADIUS client.";
        smiv2:max-access "read-only";
        smiv2:oid "1.3.6.1.4.1.9.9.736.1.2.5";
      }

      leaf creAuthClientTotalPacketsWithoutResponses {
        type yang:counter32;
        units "RADIUS packets";
        description
         "This object indicates the number of RADIUS authentication
          packets that never received a response.";
        smiv2:max-access "read-only";
        smiv2:oid "1.3.6.1.4.1.9.9.736.1.2.6";
      }

      leaf creAuthClientAverageResponseDelay {
        type snmpv2-tc:TimeInterval;
        description
         "This object indicates the average response delay experienced
          for RADIUS authentication requests.";
        smiv2:max-access "read-only";
        smiv2:oid "1.3.6.1.4.1.9.9.736.1.2.7";
      }

      leaf creAuthClientMaxResponseDelay {
        type snmpv2-tc:TimeInterval;
        description
         "This object indicates the maximum delay experienced for RADIUS
          authentication requests.";
        smiv2:max-access "read-only";
        smiv2:oid "1.3.6.1.4.1.9.9.736.1.2.8";
      }

      leaf creAuthClientMaxBufferSize {
        type uint32 {
          range "0..4294967295";
        }
        units "bytes";
        description
         "This object indicates the maximum buffer size for RADIUS
          authentication packet.";
        smiv2:max-access "read-only";
        smiv2:oid "1.3.6.1.4.1.9.9.736.1.2.9";
      }

      leaf creAuthClientTimeouts {
        type yang:counter32;
        units "timeouts";
        description
         "This object indicates the number of timeouts that have occurred
          for RADIUS authentication.  After a timeout the client may
          retry sending the request to the same server or to a different
          server or give up depending on the configuration.";
        smiv2:max-access "read-only";
        smiv2:oid "1.3.6.1.4.1.9.9.736.1.2.10";
      }

      leaf creAuthClientDupIDs {
        type yang:counter32;
        units "RADIUS packets";
        description
         "This object indicates the number of times client has received
          duplicate authentication responses with the same identifier. 
          Out of these two packets, the later packet is considered as a
          true match.";
        smiv2:max-access "read-only";
        smiv2:oid "1.3.6.1.4.1.9.9.736.1.2.11";
      }

      leaf creAuthClientMalformedResponses {
        type yang:counter32;
        units "RADIUS packets";
        description
         "This object indicates the number of malformed RADIUS
          authentication responses received.  Malformed packets include
          packets with an invalid length.";
        smiv2:max-access "read-only";
        smiv2:oid "1.3.6.1.4.1.9.9.736.1.2.12";
      }

      leaf creAuthClientLastUsedSourceId {
        type CISCO-RADIUS-EXT-MIB:RadiusSourceIdentifier;
        description
         "This MIB object indicates the last source identifier that was
          used to send out a RADIUS authentication request when 'extended
          RADIUS source ports' is configured.  The source identifier is a
          counter that is incremented everytime a RADIUS authentication
          request is sent.";
        smiv2:max-access "read-only";
        smiv2:oid "1.3.6.1.4.1.9.9.736.1.2.13";
      }
    }

    container creClientAccounting {
      smiv2:oid "1.3.6.1.4.1.9.9.736.1.3";

      leaf creAcctClientBadAuthenticators {
        type yang:counter32;
        units "RADIUS packets";
        description
         "This object indicates the number of RADIUS Accounting-Response
          packets received with invalid authenticators.";
        smiv2:max-access "read-only";
        smiv2:oid "1.3.6.1.4.1.9.9.736.1.3.1";
      }

      leaf creAcctClientUnknownResponses {
        type yang:counter32;
        units "RADIUS packets";
        description
         "This object indicates the number of unknown RADIUS accounting
          responses received.";
        smiv2:max-access "read-only";
        smiv2:oid "1.3.6.1.4.1.9.9.736.1.3.2";
      }

      leaf creAcctClientTotalPacketsWithResponses {
        type yang:counter32;
        units "RADIUS packets";
        description
         "This object indicates the number of RADIUS accounting packets
          that received responses.";
        smiv2:max-access "read-only";
        smiv2:oid "1.3.6.1.4.1.9.9.736.1.3.3";
      }

      leaf creAcctClientBufferAllocFailures {
        type yang:counter32;
        units "buffer failures";
        description
         "This object indicates the number of buffer allocation failures
          encountered for RADIUS accounting request.";
        smiv2:max-access "read-only";
        smiv2:oid "1.3.6.1.4.1.9.9.736.1.3.4";
      }

      leaf creAcctClientTotalResponses {
        type yang:counter32;
        units "RADIUS packets";
        description
         "This object indicates the number of RADIUS accounting response
          packets received by the RADIUS client.";
        smiv2:max-access "read-only";
        smiv2:oid "1.3.6.1.4.1.9.9.736.1.3.5";
      }

      leaf creAcctClientTotalPacketsWithoutResponses {
        type yang:counter32;
        units "RADIUS packets";
        description
         "This object indicates the number of RADIUS accounting packets
          that never received a response.";
        smiv2:max-access "read-only";
        smiv2:oid "1.3.6.1.4.1.9.9.736.1.3.6";
      }

      leaf creAcctClientAverageResponseDelay {
        type snmpv2-tc:TimeInterval;
        description
         "This object indicates the average response delay experienced
          for RADIUS accounting.";
        smiv2:max-access "read-only";
        smiv2:oid "1.3.6.1.4.1.9.9.736.1.3.7";
      }

      leaf creAcctClientMaxResponseDelay {
        type snmpv2-tc:TimeInterval;
        description
         "This object indicates the maximum delay experienced for RADIUS
          accounting.";
        smiv2:max-access "read-only";
        smiv2:oid "1.3.6.1.4.1.9.9.736.1.3.8";
      }

      leaf creAcctClientMaxBufferSize {
        type uint32 {
          range "0..4294967295";
        }
        units "bytes";
        description
         "This object indicates the maximum buffer size for RADIUS
          accounting packets.";
        smiv2:max-access "read-only";
        smiv2:oid "1.3.6.1.4.1.9.9.736.1.3.9";
      }

      leaf creAcctClientTimeouts {
        type yang:counter32;
        units "timeouts";
        description
         "This object indicates the number of timeouts that have occurred
          for RADIUS accounting.  After a timeout the client may retry
          sending the request to the same server or to a different
          server or give up depending on the configuration.";
        smiv2:max-access "read-only";
        smiv2:oid "1.3.6.1.4.1.9.9.736.1.3.10";
      }

      leaf creAcctClientDupIDs {
        type yang:counter32;
        units "RADIUS packets";
        description
         "This object indicates the number of times client has received
          duplicate accounting responses with the same identifier.  Out
          of these two packets, the later packet is considered as a true
          match.";
        smiv2:max-access "read-only";
        smiv2:oid "1.3.6.1.4.1.9.9.736.1.3.11";
      }

      leaf creAcctClientMalformedResponses {
        type yang:counter32;
        units "RADIUS packets";
        description
         "This object indicates the number of malformed RADIUS accounting
          responses received.  Malformed packets include packets with an
          invalid length.";
        smiv2:max-access "read-only";
        smiv2:oid "1.3.6.1.4.1.9.9.736.1.3.12";
      }

      leaf creAcctClientLastUsedSourceId {
        type CISCO-RADIUS-EXT-MIB:RadiusSourceIdentifier;
        description
         "This MIB object indicates the last source identifier that was
          used to send out a RADIUS accounting request when 'extended
          RADIUS source ports' is configured.  The source identifier is a
          counter that is incremented everytime a RADIUS accounting
          request is sent.";
        smiv2:max-access "read-only";
        smiv2:oid "1.3.6.1.4.1.9.9.736.1.3.13";
      }
    }
  }

  smiv2:alias "ciscoRadiusExtMIB" {
    smiv2:oid "1.3.6.1.4.1.9.9.736";
  }

  smiv2:alias "cRadiusExtMIBObjects" {
    smiv2:oid "1.3.6.1.4.1.9.9.736.1";
  }

  smiv2:alias "creClientGlobal" {
    smiv2:oid "1.3.6.1.4.1.9.9.736.1.1";
  }

  smiv2:alias "creClientAuthentication" {
    smiv2:oid "1.3.6.1.4.1.9.9.736.1.2";
  }

  smiv2:alias "creClientAccounting" {
    smiv2:oid "1.3.6.1.4.1.9.9.736.1.3";
  }

  smiv2:alias "creClientDynAuth" {
    smiv2:oid "1.3.6.1.4.1.9.9.736.1.4";
  }

  smiv2:alias "creServerGlobal" {
    smiv2:oid "1.3.6.1.4.1.9.9.736.1.5";
  }

  smiv2:alias "creServerAuthentication" {
    smiv2:oid "1.3.6.1.4.1.9.9.736.1.6";
  }

  smiv2:alias "creServerAccounting" {
    smiv2:oid "1.3.6.1.4.1.9.9.736.1.7";
  }

  smiv2:alias "creServerDynAuth" {
    smiv2:oid "1.3.6.1.4.1.9.9.736.1.8";
  }

  smiv2:alias "cRadiusExtMIBConformance" {
    smiv2:oid "1.3.6.1.4.1.9.9.736.2";
  }

  smiv2:alias "creMIBCompliances" {
    smiv2:oid "1.3.6.1.4.1.9.9.736.2.1";
  }

  smiv2:alias "creMIBGroups" {
    smiv2:oid "1.3.6.1.4.1.9.9.736.2.2";
  }

}
