/*
 * Generated by confdc --mib2yang-std
 * Source: mgmt/dmi/model/mib/src/CISCO-ATM-PVCTRAP-EXTN-MIB.mib
 */
/*
 * This YANG module has been generated by smidump 0.5.0:
 *
 *      smidump -f yang CISCO-ATM-PVCTRAP-EXTN-MIB
 *
 * Do not edit. Edit the source file instead!
 */

module CISCO-ATM-PVCTRAP-EXTN-MIB {

  namespace "urn:ietf:params:xml:ns:yang:smiv2:CISCO-ATM-PVCTRAP-EXTN-MIB";
  prefix CISCO-ATM-PVCTRAP-EXTN-MIB;

  import ATM-MIB {
    prefix "atm-mib";
  }

  import CISCO-IETF-ATM2-PVCTRAP-MIB {
    prefix "cisco-ietf";
  }

  import IF-MIB {
    prefix "if-mib";
  }

  import ietf-yang-smiv2 {
    prefix "smiv2";
  }

  import ietf-yang-types {
    prefix "yang";
  }

  organization
   "Cisco Systems, Inc.";

  contact
   "       Cisco Systems
    Customer Service
    
    Postal: 170 W Tasman Drive
    San Jose, CA  95134
    USA
    
    Tel: +1 800 553-NETS
    
    E-mail: cs-atm@cisco.com";

  description
   "This MIB Module is a supplement to the
    CISCO-IETF-ATM2-PVCTRAP-MIB.";

  revision 2003-01-20 {
    description
     "Initial version of this MIB module.";
  }

  typedef CatmOAMRecoveryType {
    type enumeration {
      enum "catmLoopbackOAMRecover" {
        value "1";
      }
      enum "catmSegmentCCOAMRecover" {
        value "2";
      }
      enum "catmEndCCOAMRecover" {
        value "4";
      }
      enum "catmAISRDIOAMRecover" {
        value "8";
      }
    }
    description
     "Enums to indicate different types of OAM recoveries .
      catmLoopbackOAMRecover  - The object in query is Loopback OAM
                                type of recovery.
      catmSegmentCCOAMRecover - The object in query is Segment CC
                                OAM type of recovery.
      catmEndCCOAMRecover     - The object in query is End-to-End 
                                CC OAM type of recovery.
      catmAISRDIOAMRecover    - The object in query is AISRDI OAM
                                type of recovery.";
  }

  typedef CatmOAMFailureType {
    type enumeration {
      enum "catmLoopbackOAMFailure" {
        value "1";
      }
      enum "catmSegmentCCOAMFailure" {
        value "2";
      }
      enum "catmEndCCOAMFailure" {
        value "4";
      }
      enum "catmAISRDIOAMFailure" {
        value "8";
      }
    }
    description
     "Enums to indicate different types of OAM recoveries .
      catmLoopbackOAMFailure  - The object in query is Loopback OAM
                                type of failure.
      catmSegmentCCOAMFailure - The object in query is Segment CC
                                OAM type of failure.
      catmEndCCOAMFailure     - The object in query is End-to-End 
                                CC OAM type of failure.
      catmAISRDIOAMFailure    - The object in query is AISRDI OAM
                                type of failure.";
  }


  container CISCO-ATM-PVCTRAP-EXTN-MIB {
    config false;

    container catmCurStatChangePVclTable {
      description
       "A table indicating all VCLs for which there is an
        active row in the atmVclTable having an atmVclConnKind
        value of `pvc' and atmVclOperStatus to have changed in the
        last corresponding PVC notification.";
      smiv2:oid "1.3.6.1.4.1.9.10.97.1.2";

      list catmCurStatChangePVclEntry {
        key "ifIndex atmVclVpi atmVclVci";
        description
         "Each entry in the table represents a VCL for which
          there is an active row in the atmVclTable having an
          atmVclConnKind value of `pvc' and atmVclOperStatus
          to have changed in the last corresponding PVC notification.";
        smiv2:oid "1.3.6.1.4.1.9.10.97.1.2.1";

        leaf ifIndex {
          type leafref {
            path "/if-mib:IF-MIB/if-mib:ifTable/if-mib:ifEntry/if-mib:ifIndex";
          }
        }

        leaf atmVclVpi {
          type leafref {
            path "/atm-mib:ATM-MIB/atm-mib:atmVclTable/atm-mib:atmVclEntry/atm-mib:atmVclVpi";
          }
        }

        leaf atmVclVci {
          type leafref {
            path "/atm-mib:ATM-MIB/atm-mib:atmVclTable/atm-mib:atmVclEntry/atm-mib:atmVclVci";
          }
        }

        leaf catmPVclStatusTransition {
          type yang:counter32;
          description
           "The number of state transitions that has happened 
            on this PVCL in the last corresponding notification.";
          smiv2:max-access "read-only";
          smiv2:oid "1.3.6.1.4.1.9.10.97.1.2.1.2";
        }

        leaf catmPVclStatusChangeStart {
          type yang:timestamp;
          description
           "The time stamp at which this PVCL changed state for the
            first time in  the last corresponding notification.";
          smiv2:max-access "read-only";
          smiv2:oid "1.3.6.1.4.1.9.10.97.1.2.1.3";
        }

        leaf catmPVclStatusChangeEnd {
          type yang:timestamp;
          description
           "The time stamp of the last state change of this PVCL
            in the last corresponding notification.";
          smiv2:max-access "read-only";
          smiv2:oid "1.3.6.1.4.1.9.10.97.1.2.1.4";
        }

        leaf catmPVclSegCCStatusTransition {
          type yang:counter32;
          description
           "The number of state transitions that has happened 
            on this PVCL in the last corresponding notification due
            to Segment CC OAM failure.";
          smiv2:max-access "read-only";
          smiv2:oid "1.3.6.1.4.1.9.10.97.1.2.1.5";
        }

        leaf catmPVclSegCCStatusChangeStart {
          type yang:timestamp;
          description
           "The time stamp at which this PVCL changed state for the
            first time in  the last corresponding notification due
            to Segment CC OAM failure.";
          smiv2:max-access "read-only";
          smiv2:oid "1.3.6.1.4.1.9.10.97.1.2.1.6";
        }

        leaf catmPVclSegCCStatusChangeEnd {
          type yang:timestamp;
          description
           "The time stamp of the last state change of this PVCL
            in the last corresponding notification due
            to Segment CC OAM failure.";
          smiv2:max-access "read-only";
          smiv2:oid "1.3.6.1.4.1.9.10.97.1.2.1.7";
        }

        leaf catmPVclEndCCStatusTransition {
          type yang:counter32;
          description
           "The number of state transitions that has happened 
            on this PVCL in the last corresponding notification due
            to End CC OAM failure.";
          smiv2:max-access "read-only";
          smiv2:oid "1.3.6.1.4.1.9.10.97.1.2.1.8";
        }

        leaf catmPVclEndCCStatusChangeStart {
          type yang:timestamp;
          description
           "The time stamp at which this PVCL changed state for the
            first time in  the last corresponding notification due
            to End CC OAM failure.";
          smiv2:max-access "read-only";
          smiv2:oid "1.3.6.1.4.1.9.10.97.1.2.1.9";
        }

        leaf catmPVclEndCCStatusChangeEnd {
          type yang:timestamp;
          description
           "The time stamp of the last state change of this PVCL
            in the last corresponding notification due
            to End CC OAM failure.";
          smiv2:max-access "read-only";
          smiv2:oid "1.3.6.1.4.1.9.10.97.1.2.1.10";
        }

        leaf catmPVclAISRDIStatusTransition {
          type yang:counter32;
          description
           "The number of state transitions that has happened 
            on this PVCL in the last corresponding notification due
            to AIS RDI OAM failure.";
          smiv2:max-access "read-only";
          smiv2:oid "1.3.6.1.4.1.9.10.97.1.2.1.11";
        }

        leaf catmPVclAISRDIStatusChangeStart {
          type yang:timestamp;
          description
           "The time stamp at which this PVCL changed state for the
            first time in  the last corresponding notification due
            to AIS RDI OAM failure.";
          smiv2:max-access "read-only";
          smiv2:oid "1.3.6.1.4.1.9.10.97.1.2.1.12";
        }

        leaf catmPVclAISRDIStatusChangeEnd {
          type yang:timestamp;
          description
           "The time stamp of the last state change of this PVCL
            in the last corresponding notification due
            to AIS RDI OAM failure.";
          smiv2:max-access "read-only";
          smiv2:oid "1.3.6.1.4.1.9.10.97.1.2.1.13";
        }

        leaf catmPVclCurFailTime {
          type yang:timestamp;
          description
           "The time stamp at which this PVCL changed state to DOWN
            last time in the last corresponding notification .";
          smiv2:max-access "read-only";
          smiv2:oid "1.3.6.1.4.1.9.10.97.1.2.1.14";
        }

        leaf catmPVclPrevRecoverTime {
          type yang:timestamp;
          description
           "The time stamp at which this PVCL changed state to UP
            last time in the previous corresponding notification .";
          smiv2:max-access "read-only";
          smiv2:oid "1.3.6.1.4.1.9.10.97.1.2.1.15";
        }

        leaf catmPVclFailureReason {
          type CISCO-ATM-PVCTRAP-EXTN-MIB:CatmOAMFailureType;
          description
           "Type of OAM failure.";
          smiv2:max-access "read-only";
          smiv2:oid "1.3.6.1.4.1.9.10.97.1.2.1.16";
        }
      }
    }

    container catmStatusChangePVclRangeTable {
      description
       "A table indicating more than one VCLs in a consecutive 
        range and for each VCL there is an active row in the 
        atmVclTable having an atmVclConnKind value of `pvc'
        and atmVclOperStatus to have changed in the same
        direction in the last corresponding PVC notification .";
      smiv2:oid "1.3.6.1.4.1.9.10.97.1.3";

      list catmStatusChangePVclRangeEntry {
        key "ifIndex atmVclVpi catmStatusChangePVclRangeIndex";
        description
         "Each entry in this table represents a range of VCLs and 
          for each VCL there is an active row in the atmVclTable having
          an atmVclConnKind value of 'pvc' and atmVclOperStatus to have
          changed in the same direction in the last notification 
          interval.";
        smiv2:oid "1.3.6.1.4.1.9.10.97.1.3.1";

        leaf ifIndex {
          type leafref {
            path "/if-mib:IF-MIB/if-mib:ifTable/if-mib:ifEntry/if-mib:ifIndex";
          }
        }

        leaf atmVclVpi {
          type leafref {
            path "/atm-mib:ATM-MIB/atm-mib:atmVclTable/atm-mib:atmVclEntry/atm-mib:atmVclVpi";
          }
        }

        leaf catmStatusChangePVclRangeIndex {
          type int32 {
            range "0..65535";
          }
          description
           "Index to represent different ranges, the first range is
            indexed by value 0, the second by 1 and so on...";
          smiv2:max-access "not-accessible";
          smiv2:oid "1.3.6.1.4.1.9.10.97.1.3.1.1";
        }

        leaf catmPVclLowerRangeValue {
          type int32 {
            range "0..65536";
          }
          description
           "The first PVCL in a range of PVCLs for which the 
            atmVclOperStatus to have changed in the last 
            corresponding notification due to Loopback OAM failure.";
          smiv2:max-access "read-only";
          smiv2:oid "1.3.6.1.4.1.9.10.97.1.3.1.2";
        }

        leaf catmPVclHigherRangeValue {
          type int32 {
            range "0..65536";
          }
          description
           "The last PVCL in a range of PVCLs for which the 
            atmOperStatus to have changed in the last 
            corresponding notification due to Loopback OAM failure.";
          smiv2:max-access "read-only";
          smiv2:oid "1.3.6.1.4.1.9.10.97.1.3.1.3";
        }

        leaf catmPVclRangeStatusChangeStart {
          type yang:timestamp;
          description
           "The time stamp at which the first PVCL in the range
            changed state in the last corresponding notification due 
            to Loopback OAM failure.";
          smiv2:max-access "read-only";
          smiv2:oid "1.3.6.1.4.1.9.10.97.1.3.1.4";
        }

        leaf catmPVclRangeStatusChangeEnd {
          type yang:timestamp;
          description
           "The time stamp at which the last PVCL in the range
            changed state in the last corresponding notification due 
            to Loopback OAM failure.";
          smiv2:max-access "read-only";
          smiv2:oid "1.3.6.1.4.1.9.10.97.1.3.1.5";
        }
      }
    }

    container catmSegCCStatusChPVclRangeTable {
      description
       "A table indicating more than one VCLs in a consecutive 
        range and for each VCL there is an active row in the 
        atmVclTable having an atmVclConnKind value of `pvc'
        and atmVclOperStatus to have changed due to segment CC 
        failure in the same direction in the last PVC 
        corresponding notification .";
      smiv2:oid "1.3.6.1.4.1.9.10.97.1.5";

      list catmSegCCStatusChPVclRangeEntry {
        key "ifIndex atmVclVpi catmStatusChangePVclRangeIndex";
        description
         "Each entry in this table represents a range of VCLs and 
          for each VCL there is an active row in the atmVclTable having
          an atmVclConnKind value of 'pvc' and atmVclOperStatus to have
          changed due to segment CC failure in the same direction 
          in the last corresponding notification .";
        smiv2:oid "1.3.6.1.4.1.9.10.97.1.5.1";

        leaf ifIndex {
          type leafref {
            path "/if-mib:IF-MIB/if-mib:ifTable/if-mib:ifEntry/if-mib:ifIndex";
          }
        }

        leaf atmVclVpi {
          type leafref {
            path "/atm-mib:ATM-MIB/atm-mib:atmVclTable/atm-mib:atmVclEntry/atm-mib:atmVclVpi";
          }
        }

        leaf catmStatusChangePVclRangeIndex {
          type leafref {
            path "/CISCO-ATM-PVCTRAP-EXTN-MIB:CISCO-ATM-PVCTRAP-EXTN-MIB/CISCO-ATM-PVCTRAP-EXTN-MIB:catmStatusChangePVclRangeTable/CISCO-ATM-PVCTRAP-EXTN-MIB:catmStatusChangePVclRangeEntry/CISCO-ATM-PVCTRAP-EXTN-MIB:catmStatusChangePVclRangeIndex";
          }
        }

        leaf catmPVclSegCCLowerRangeValue {
          type int32 {
            range "0..65536";
          }
          description
           "The first PVCL in a range of PVCLs for which the 
            atmVclOperStatus to have changed in the last 
            corresponding notification due to Segment CC OAM failure.";
          smiv2:max-access "read-only";
          smiv2:oid "1.3.6.1.4.1.9.10.97.1.5.1.1";
        }

        leaf catmPVclSegCCHigherRangeValue {
          type int32 {
            range "0..65536";
          }
          description
           "The last PVCL in a range of PVCLs for which the 
            atmOperStatus to have changed in the last 
            corresponding notification due to Segment CC OAM failure.";
          smiv2:max-access "read-only";
          smiv2:oid "1.3.6.1.4.1.9.10.97.1.5.1.2";
        }

        leaf catmPVclSegCCRangeStatusChStart {
          type yang:timestamp;
          description
           "The time stamp at which the first PVCL in the range
            changed state in the last corresponding notification due 
            to Segment CC OAM failure.";
          smiv2:max-access "read-only";
          smiv2:oid "1.3.6.1.4.1.9.10.97.1.5.1.3";
        }

        leaf catmPVclSegCCRangeStatusChEnd {
          type yang:timestamp;
          description
           "The time stamp at which the last PVCL in the range
            changed state in the last corresponding notification due 
            to Segment CC OAM failure.";
          smiv2:max-access "read-only";
          smiv2:oid "1.3.6.1.4.1.9.10.97.1.5.1.4";
        }
      }
    }

    container catmEndCCStatusChPVclRangeTable {
      description
       "A table indicating more than one VCLs in a consecutive 
        range and for each VCL there is an active row in the 
        atmVclTable having an atmVclConnKind value of `pvc'
        and atmVclOperStatus to have changed due to End CC failure
        in the same direction in the last PVC notification 
        interval.";
      smiv2:oid "1.3.6.1.4.1.9.10.97.1.6";

      list catmEndCCStatusChPVclRangeEntry {
        key "ifIndex atmVclVpi catmStatusChangePVclRangeIndex";
        description
         "Each entry in this table represents a range of VCLs and 
          for each VCL there is an active row in the atmVclTable having
          an atmVclConnKind value of 'pvc' and atmVclOperStatus to have
          changed due to End CC failure in the same direction in the 
          last corresponding notification .";
        smiv2:oid "1.3.6.1.4.1.9.10.97.1.6.1";

        leaf ifIndex {
          type leafref {
            path "/if-mib:IF-MIB/if-mib:ifTable/if-mib:ifEntry/if-mib:ifIndex";
          }
        }

        leaf atmVclVpi {
          type leafref {
            path "/atm-mib:ATM-MIB/atm-mib:atmVclTable/atm-mib:atmVclEntry/atm-mib:atmVclVpi";
          }
        }

        leaf catmStatusChangePVclRangeIndex {
          type leafref {
            path "/CISCO-ATM-PVCTRAP-EXTN-MIB:CISCO-ATM-PVCTRAP-EXTN-MIB/CISCO-ATM-PVCTRAP-EXTN-MIB:catmStatusChangePVclRangeTable/CISCO-ATM-PVCTRAP-EXTN-MIB:catmStatusChangePVclRangeEntry/CISCO-ATM-PVCTRAP-EXTN-MIB:catmStatusChangePVclRangeIndex";
          }
        }

        leaf catmPVclEndCCLowerRangeValue {
          type int32 {
            range "0..65536";
          }
          description
           "The first PVCL in a range of PVCLs for which the 
            atmVclOperStatus to have changed in the last 
            corresponding notification due to End CC OAM failure.";
          smiv2:max-access "read-only";
          smiv2:oid "1.3.6.1.4.1.9.10.97.1.6.1.1";
        }

        leaf catmPVclEndCCHigherRangeValue {
          type int32 {
            range "0..65536";
          }
          description
           "The last PVCL in a range of PVCLs for which the 
            atmOperStatus to have changed in the last 
            corresponding notification due to End CC OAM failure.";
          smiv2:max-access "read-only";
          smiv2:oid "1.3.6.1.4.1.9.10.97.1.6.1.2";
        }

        leaf catmPVclEndCCRangeStatusChStart {
          type yang:timestamp;
          description
           "The time stamp at which the first PVCL in the range
            changed state in the last corresponding notification due 
            to End CC OAM failure.";
          smiv2:max-access "read-only";
          smiv2:oid "1.3.6.1.4.1.9.10.97.1.6.1.3";
        }

        leaf catmPVclEndCCRangeStatusChEnd {
          type yang:timestamp;
          description
           "The time stamp at which the last PVCL in the range
            changed state in the last corresponding notification due 
            to End CC OAM failure.";
          smiv2:max-access "read-only";
          smiv2:oid "1.3.6.1.4.1.9.10.97.1.6.1.4";
        }
      }
    }

    container catmAISRDIStatusChPVclRangeTable {
      description
       "A table indicating more than one VCLs in a consecutive 
        range and for each VCL there is an active row in the 
        atmVclTable having an atmVclConnKind value of `pvc'
        and atmVclOperStatus to have changed due to AIS/RDI failure
        in the same direction in the last corresponding PVC 
        notification.";
      smiv2:oid "1.3.6.1.4.1.9.10.97.1.7";

      list catmAISRDIStatusChPVclRangeEntry {
        key "ifIndex atmVclVpi catmStatusChangePVclRangeIndex";
        description
         "Each entry in this table represents a range of VCLs and 
          for each VCL there is an active row in the atmVclTable having
          an atmVclConnKind value of 'pvc' and atmVclOperStatus to have
          changed due to AIS/RDI failure in the same direction in the 
          last corresponding notification .";
        smiv2:oid "1.3.6.1.4.1.9.10.97.1.7.1";

        leaf ifIndex {
          type leafref {
            path "/if-mib:IF-MIB/if-mib:ifTable/if-mib:ifEntry/if-mib:ifIndex";
          }
        }

        leaf atmVclVpi {
          type leafref {
            path "/atm-mib:ATM-MIB/atm-mib:atmVclTable/atm-mib:atmVclEntry/atm-mib:atmVclVpi";
          }
        }

        leaf catmStatusChangePVclRangeIndex {
          type leafref {
            path "/CISCO-ATM-PVCTRAP-EXTN-MIB:CISCO-ATM-PVCTRAP-EXTN-MIB/CISCO-ATM-PVCTRAP-EXTN-MIB:catmStatusChangePVclRangeTable/CISCO-ATM-PVCTRAP-EXTN-MIB:catmStatusChangePVclRangeEntry/CISCO-ATM-PVCTRAP-EXTN-MIB:catmStatusChangePVclRangeIndex";
          }
        }

        leaf catmPVclAISRDILowerRangeValue {
          type int32 {
            range "0..65536";
          }
          description
           "The first PVCL in a range of PVCLs for which the 
            atmVclOperStatus to have changed in the last 
            corresponding notification due to AISRDI OAM failure.";
          smiv2:max-access "read-only";
          smiv2:oid "1.3.6.1.4.1.9.10.97.1.7.1.1";
        }

        leaf catmPVclAISRDIHigherRangeValue {
          type int32 {
            range "0..65536";
          }
          description
           "The last PVCL in a range of PVCLs for which the 
            atmOperStatus to have changed in the last 
            corresponding notification due to AISRDI OAM failure.";
          smiv2:max-access "read-only";
          smiv2:oid "1.3.6.1.4.1.9.10.97.1.7.1.2";
        }

        leaf catmPVclAISRDIRangeStatusChStart {
          type yang:timestamp;
          description
           "The time stamp at which the first PVCL in the range
            changed state in the last corresponding notification due 
            to AISRDI OAM failure.";
          smiv2:max-access "read-only";
          smiv2:oid "1.3.6.1.4.1.9.10.97.1.7.1.3";
        }

        leaf catmPVclAISRDIRangeStatusChEnd {
          type yang:timestamp;
          description
           "The time stamp at which the last PVCL in the range
            changed state in the last corresponding notification due 
            to AISRDI OAM failure.";
          smiv2:max-access "read-only";
          smiv2:oid "1.3.6.1.4.1.9.10.97.1.7.1.4";
        }
      }
    }

    container catmDownPVclRangeTable {
      description
       "A table indicating more than one VCLs in a consecutive 
        range and for each VCL there is an active row in the 
        atmVclTable having an atmVclConnKind value of `pvc'
        and atmVclOperStatus to have detected as Down
        in the last corresponding PVC notification .";
      smiv2:oid "1.3.6.1.4.1.9.10.97.1.8";

      list catmDownPVclRangeEntry {
        key "ifIndex atmVclVpi catmStatusChangePVclRangeIndex";
        description
         "Each entry in this table represents a range of VCLs and 
          for each VCL there is an active row in the atmVclTable having
          an atmVclConnKind value of 'pvc' and  atmVclOperStatus to 
          have detected as Down in the last notification 
          interval.";
        smiv2:oid "1.3.6.1.4.1.9.10.97.1.8.1";

        leaf ifIndex {
          type leafref {
            path "/if-mib:IF-MIB/if-mib:ifTable/if-mib:ifEntry/if-mib:ifIndex";
          }
        }

        leaf atmVclVpi {
          type leafref {
            path "/atm-mib:ATM-MIB/atm-mib:atmVclTable/atm-mib:atmVclEntry/atm-mib:atmVclVpi";
          }
        }

        leaf catmStatusChangePVclRangeIndex {
          type leafref {
            path "/CISCO-ATM-PVCTRAP-EXTN-MIB:CISCO-ATM-PVCTRAP-EXTN-MIB/CISCO-ATM-PVCTRAP-EXTN-MIB:catmStatusChangePVclRangeTable/CISCO-ATM-PVCTRAP-EXTN-MIB:catmStatusChangePVclRangeEntry/CISCO-ATM-PVCTRAP-EXTN-MIB:catmStatusChangePVclRangeIndex";
          }
        }

        leaf catmDownPVclLowerRangeValue {
          type int32 {
            range "0..65536";
          }
          description
           "The first PVCL in a range of PVCLs for which the 
            atmVclOperStatus has been detected as Down in the 
            corresponding notification .";
          smiv2:max-access "read-only";
          smiv2:oid "1.3.6.1.4.1.9.10.97.1.8.1.1";
        }

        leaf catmDownPVclHigherRangeValue {
          type int32 {
            range "0..65536";
          }
          description
           "The last PVCL in a range of PVCLs for which the 
            atmVclOperStatus has been detected as Down in the 
            corresponding notification .";
          smiv2:max-access "read-only";
          smiv2:oid "1.3.6.1.4.1.9.10.97.1.8.1.2";
        }

        leaf catmDownPVclRangeStart {
          type yang:timestamp;
          description
           "The time stamp at which the first atmVclOperStatus
            is detected as Down on any of the PVCLs in the range
            in the corresponding notification .";
          smiv2:max-access "read-only";
          smiv2:oid "1.3.6.1.4.1.9.10.97.1.8.1.3";
        }

        leaf catmDownPVclRangeEnd {
          type yang:timestamp;
          description
           "The time stamp at which the last atmVclOperStatus
            is detected as Down on any of the PVCLs in the range
            in the corresponding notification .";
          smiv2:max-access "read-only";
          smiv2:oid "1.3.6.1.4.1.9.10.97.1.8.1.4";
        }

        leaf catmPrevUpPVclRangeStart {
          type yang:timestamp;
          description
           "The time stamp at which the first atmVclOperStatus
            is detected as Up on any of the PVCLs in the range
            in the previous catmIntfPvcUp2Trap notification.";
          smiv2:max-access "read-only";
          smiv2:oid "1.3.6.1.4.1.9.10.97.1.8.1.5";
        }

        leaf catmPrevUpPVclRangeEnd {
          type yang:timestamp;
          description
           "The time stamp at which the last atmVclOperStatus
            is detected as Up on any of the PVCLs in the range
            in the previous catmIntfPvcUp2Trap notification.";
          smiv2:max-access "read-only";
          smiv2:oid "1.3.6.1.4.1.9.10.97.1.8.1.6";
        }

        leaf catmPVclRangeFailureReason {
          type CISCO-ATM-PVCTRAP-EXTN-MIB:CatmOAMFailureType;
          description
           "Type of OAM failure.";
          smiv2:max-access "read-only";
          smiv2:oid "1.3.6.1.4.1.9.10.97.1.8.1.7";
        }
      }
    }

    container catmCurStatusUpPVclTable {
      description
       "A table indicating all VCLs for which there is an
        active row in the atmVclTable having an atmVclConnKind
        value of `pvc' and atmVclOperStatus to have changed to UP
        in the last corresponding PVC notification .";
      smiv2:oid "1.3.6.1.4.1.9.10.97.1.9";

      list catmCurStatusUpPVclEntry {
        key "ifIndex atmVclVpi atmVclVci";
        description
         "Each entry in the table represents a VCL for which
          there is an active row in the atmVclTable having an
          atmVclConnKind value of `pvc' and atmVclOperStatus
          to have changed to UP in the last PVC notification 
          interval.";
        smiv2:oid "1.3.6.1.4.1.9.10.97.1.9.1";

        leaf ifIndex {
          type leafref {
            path "/if-mib:IF-MIB/if-mib:ifTable/if-mib:ifEntry/if-mib:ifIndex";
          }
        }

        leaf atmVclVpi {
          type leafref {
            path "/atm-mib:ATM-MIB/atm-mib:atmVclTable/atm-mib:atmVclEntry/atm-mib:atmVclVpi";
          }
        }

        leaf atmVclVci {
          type leafref {
            path "/atm-mib:ATM-MIB/atm-mib:atmVclTable/atm-mib:atmVclEntry/atm-mib:atmVclVci";
          }
        }

        leaf catmPVclStatusUpTransition {
          type yang:gauge32;
          description
           "The number of Down to Up state transitions due to
            OAM loopback recovery that has happened on this PVCL 
            in the last corresponding notification .";
          smiv2:max-access "read-only";
          smiv2:oid "1.3.6.1.4.1.9.10.97.1.9.1.1";
        }

        leaf catmPVclStatusUpStart {
          type yang:timestamp;
          description
           "The time stamp at which this PVCL changed state to UP 
            for the first time due to OAM loopback recovery
            in the last corresponding notification .";
          smiv2:max-access "read-only";
          smiv2:oid "1.3.6.1.4.1.9.10.97.1.9.1.2";
        }

        leaf catmPVclStatusUpEnd {
          type yang:timestamp;
          description
           "The time stamp at which this PVCL changed state to UP 
            for the last time due to OAM loopback recovery
            in the last corresponding notification .";
          smiv2:max-access "read-only";
          smiv2:oid "1.3.6.1.4.1.9.10.97.1.9.1.3";
        }

        leaf catmPVclSegCCStatusUpTransition {
          type yang:gauge32;
          description
           "The number of Down to Up state transitions that has 
            happened on this PVCL in the last corresponding notification 
            due to Segment CC OAM recovery.";
          smiv2:max-access "read-only";
          smiv2:oid "1.3.6.1.4.1.9.10.97.1.9.1.4";
        }

        leaf catmPVclSegCCStatusUpStart {
          type yang:timestamp;
          description
           "The time stamp at which this PVCL changed state to Up for 
            the first time in the last corresponding notification due
            to Segment CC OAM recovery.";
          smiv2:max-access "read-only";
          smiv2:oid "1.3.6.1.4.1.9.10.97.1.9.1.5";
        }

        leaf catmPVclSegCCStatusUpEnd {
          type yang:timestamp;
          description
           "The time stamp of the last state change of this PVCL
            in the last corresponding notification due to Segment CC 
            OAM recovery.";
          smiv2:max-access "read-only";
          smiv2:oid "1.3.6.1.4.1.9.10.97.1.9.1.6";
        }

        leaf catmPVclEndCCStatusUpTransition {
          type yang:gauge32;
          description
           "The number of Down to UP state transitions that has 
            happened on this PVCL in the last notification 
            interval due to End CC OAM recovery.";
          smiv2:max-access "read-only";
          smiv2:oid "1.3.6.1.4.1.9.10.97.1.9.1.7";
        }

        leaf catmPVclEndCCStatusUpStart {
          type yang:timestamp;
          description
           "The time stamp at which this PVCL changed state to Up
            for the first time in the last corresponding notification 
            due to End CC OAM recovery.";
          smiv2:max-access "read-only";
          smiv2:oid "1.3.6.1.4.1.9.10.97.1.9.1.8";
        }

        leaf catmPVclEndCCStatusUpEnd {
          type yang:timestamp;
          description
           "The time stamp at which this PVCL changed state to Up
            for the last time in the last corresponding notification 
            due to End CC OAM recovery.";
          smiv2:max-access "read-only";
          smiv2:oid "1.3.6.1.4.1.9.10.97.1.9.1.9";
        }

        leaf catmPVclAISRDIStatusUpTransition {
          type yang:gauge32;
          description
           "The number of Down to Up state transitions that 
            has happened on this PVCL in the last notification 
            interval due to AIS RDI OAM recovery.";
          smiv2:max-access "read-only";
          smiv2:oid "1.3.6.1.4.1.9.10.97.1.9.1.10";
        }

        leaf catmPVclAISRDIStatusUpStart {
          type yang:timestamp;
          description
           "The time stamp at which this PVCL changed state to Up
            for the first time in the last corresponding notification 
            due to AIS/RDI OAM recovery.";
          smiv2:max-access "read-only";
          smiv2:oid "1.3.6.1.4.1.9.10.97.1.9.1.11";
        }

        leaf catmPVclAISRDIStatusUpEnd {
          type yang:timestamp;
          description
           "The time stamp at which this PVCL changed state to Up
            for the last time in the last corresponding notification 
            due to AIS/RDI OAM recovery.";
          smiv2:max-access "read-only";
          smiv2:oid "1.3.6.1.4.1.9.10.97.1.9.1.12";
        }

        leaf catmPVclCurRecoverTime {
          type yang:timestamp;
          description
           "The time stamp at which this PVCL changed state to UP
            last time in the last corresponding notification .";
          smiv2:max-access "read-only";
          smiv2:oid "1.3.6.1.4.1.9.10.97.1.9.1.13";
        }

        leaf catmPVclPrevFailTime {
          type yang:timestamp;
          description
           "The time stamp at which this PVCL changed state to DOWN
            last time in the previous corresponding notification .";
          smiv2:max-access "read-only";
          smiv2:oid "1.3.6.1.4.1.9.10.97.1.9.1.14";
        }

        leaf catmPVclRecoveryReason {
          type CISCO-ATM-PVCTRAP-EXTN-MIB:CatmOAMRecoveryType;
          description
           "Type of OAM Recovered";
          smiv2:max-access "read-only";
          smiv2:oid "1.3.6.1.4.1.9.10.97.1.9.1.15";
        }
      }
    }

    container catmStatusUpPVclRangeTable {
      description
       "A table indicating more than one VCLs in a consecutive 
        range and for each VCL there is an active row in the 
        atmVclTable having an atmVclConnKind value of `pvc'
        and loopback OAM status to have detected as recovered
        in the last corresponding PVC notification .";
      smiv2:oid "1.3.6.1.4.1.9.10.97.1.10";

      list catmStatusUpPVclRangeEntry {
        key "ifIndex atmVclVpi catmStatusChangePVclRangeIndex";
        description
         "Each entry in this table represents a range of VCLs and 
          for each VCL there is an active row in the atmVclTable having
          an atmVclConnKind value of 'pvc' and  loopback OAM status to 
          have detected as recovered in the last notification 
          interval.";
        smiv2:oid "1.3.6.1.4.1.9.10.97.1.10.1";

        leaf ifIndex {
          type leafref {
            path "/if-mib:IF-MIB/if-mib:ifTable/if-mib:ifEntry/if-mib:ifIndex";
          }
        }

        leaf atmVclVpi {
          type leafref {
            path "/atm-mib:ATM-MIB/atm-mib:atmVclTable/atm-mib:atmVclEntry/atm-mib:atmVclVpi";
          }
        }

        leaf catmStatusChangePVclRangeIndex {
          type leafref {
            path "/CISCO-ATM-PVCTRAP-EXTN-MIB:CISCO-ATM-PVCTRAP-EXTN-MIB/CISCO-ATM-PVCTRAP-EXTN-MIB:catmStatusChangePVclRangeTable/CISCO-ATM-PVCTRAP-EXTN-MIB:catmStatusChangePVclRangeEntry/CISCO-ATM-PVCTRAP-EXTN-MIB:catmStatusChangePVclRangeIndex";
          }
        }

        leaf catmPVclUpLowerRangeValue {
          type int32 {
            range "0..65536";
          }
          description
           "The first PVCL in a range of PVCLs for which the 
            Loopback OAM recovery has been detected in the last 
            corresponding notification .";
          smiv2:max-access "read-only";
          smiv2:oid "1.3.6.1.4.1.9.10.97.1.10.1.1";
        }

        leaf catmPVclUpHigherRangeValue {
          type int32 {
            range "0..65536";
          }
          description
           "The last PVCL in a range of PVCLs for which the 
            Loopback OAM recovery has been detected in the last 
            corresponding notification .";
          smiv2:max-access "read-only";
          smiv2:oid "1.3.6.1.4.1.9.10.97.1.10.1.2";
        }

        leaf catmPVclRangeStatusUpStart {
          type yang:timestamp;
          description
           "The time stamp at which the first Loopback OAM recovery
            is detected on any of the PVCLs in the range
            in the last corresponding notification .";
          smiv2:max-access "read-only";
          smiv2:oid "1.3.6.1.4.1.9.10.97.1.10.1.3";
        }

        leaf catmPVclRangeStatusUpEnd {
          type yang:timestamp;
          description
           "The time stamp at which the last Loopback OAM recovery
            is detected on any of the PVCLs in the range
            in the last corresponding notification .";
          smiv2:max-access "read-only";
          smiv2:oid "1.3.6.1.4.1.9.10.97.1.10.1.4";
        }
      }
    }

    container catmSegCCStatusUpPVclRangeTable {
      description
       "A table indicating more than one VCLs in a consecutive
        range and for each VCL there is an active row in the
        atmVclTable having an atmVclConnKind value of `pvc'
        and Segment CC OAM status to have detected as recovered
        in the last corresponding PVC notification .";
      smiv2:oid "1.3.6.1.4.1.9.10.97.1.11";

      list catmSegCCStatusUpPVclRangeEntry {
        key "ifIndex atmVclVpi catmStatusChangePVclRangeIndex";
        description
         "Each entry in this table represents a range of VCLs and
          for each VCL there is an active row in the atmVclTable having
          an atmVclConnKind value of 'pvc' and Segment CC OAM status to
          have detected as recovered in the last notification
          interval.";
        smiv2:oid "1.3.6.1.4.1.9.10.97.1.11.1";

        leaf ifIndex {
          type leafref {
            path "/if-mib:IF-MIB/if-mib:ifTable/if-mib:ifEntry/if-mib:ifIndex";
          }
        }

        leaf atmVclVpi {
          type leafref {
            path "/atm-mib:ATM-MIB/atm-mib:atmVclTable/atm-mib:atmVclEntry/atm-mib:atmVclVpi";
          }
        }

        leaf catmStatusChangePVclRangeIndex {
          type leafref {
            path "/CISCO-ATM-PVCTRAP-EXTN-MIB:CISCO-ATM-PVCTRAP-EXTN-MIB/CISCO-ATM-PVCTRAP-EXTN-MIB:catmStatusChangePVclRangeTable/CISCO-ATM-PVCTRAP-EXTN-MIB:catmStatusChangePVclRangeEntry/CISCO-ATM-PVCTRAP-EXTN-MIB:catmStatusChangePVclRangeIndex";
          }
        }

        leaf catmPVclSegCCUpLowerRangeValue {
          type int32 {
            range "0..65536";
          }
          description
           "The first PVCL in a range of PVCLs for which the
            Segment CC OAM recovery has been detected in the last
            corresponding notification .";
          smiv2:max-access "read-only";
          smiv2:oid "1.3.6.1.4.1.9.10.97.1.11.1.1";
        }

        leaf catmPVclSegCCUpHigherRangeValue {
          type int32 {
            range "0..65536";
          }
          description
           "The last PVCL in a range of PVCLs for which the
            Segment CC OAM recovery has been detected in the last
            corresponding notification .";
          smiv2:max-access "read-only";
          smiv2:oid "1.3.6.1.4.1.9.10.97.1.11.1.2";
        }

        leaf catmPVclSegCCRangeStatusUpStart {
          type yang:timestamp;
          description
           "The time stamp at which the first Segment CC OAM recovery
            is detected on any of the PVCLs in the range
            in the last corresponding notification .";
          smiv2:max-access "read-only";
          smiv2:oid "1.3.6.1.4.1.9.10.97.1.11.1.3";
        }

        leaf catmPVclSegCCRangeStatusUpEnd {
          type yang:timestamp;
          description
           "The time stamp at which the last Segment CC OAM recovery
            is detected on any of the PVCLs in the range
            in the last corresponding notification .";
          smiv2:max-access "read-only";
          smiv2:oid "1.3.6.1.4.1.9.10.97.1.11.1.4";
        }
      }
    }

    container catmEndCCStatusUpPVclRangeTable {
      description
       "A table indicating more than one VCLs in a consecutive
        range and for each VCL there is an active row in the
        atmVclTable having an atmVclConnKind value of `pvc'
        and End-to-End CC OAM status to have detected as recovered
        in the last corresponding PVC notification .";
      smiv2:oid "1.3.6.1.4.1.9.10.97.1.12";

      list catmEndCCStatusUpPVclRangeEntry {
        key "ifIndex atmVclVpi catmStatusChangePVclRangeIndex";
        description
         "Each entry in this table represents a range of VCLs and
          for each VCL there is an active row in the atmVclTable having
          an atmVclConnKind value of 'pvc' and End-to-End CC OAM status 
          to have detected as recovered in the last notification
          interval.";
        smiv2:oid "1.3.6.1.4.1.9.10.97.1.12.1";

        leaf ifIndex {
          type leafref {
            path "/if-mib:IF-MIB/if-mib:ifTable/if-mib:ifEntry/if-mib:ifIndex";
          }
        }

        leaf atmVclVpi {
          type leafref {
            path "/atm-mib:ATM-MIB/atm-mib:atmVclTable/atm-mib:atmVclEntry/atm-mib:atmVclVpi";
          }
        }

        leaf catmStatusChangePVclRangeIndex {
          type leafref {
            path "/CISCO-ATM-PVCTRAP-EXTN-MIB:CISCO-ATM-PVCTRAP-EXTN-MIB/CISCO-ATM-PVCTRAP-EXTN-MIB:catmStatusChangePVclRangeTable/CISCO-ATM-PVCTRAP-EXTN-MIB:catmStatusChangePVclRangeEntry/CISCO-ATM-PVCTRAP-EXTN-MIB:catmStatusChangePVclRangeIndex";
          }
        }

        leaf catmPVclEndCCUpLowerRangeValue {
          type int32 {
            range "0..65536";
          }
          description
           "The first PVCL in a range of PVCLs for which the
            End-to-End CC OAM recovery has been detected in the last
            corresponding notification .";
          smiv2:max-access "read-only";
          smiv2:oid "1.3.6.1.4.1.9.10.97.1.12.1.1";
        }

        leaf catmPVclEndCCUpHigherRangeValue {
          type int32 {
            range "0..65536";
          }
          description
           "The last PVCL in a range of PVCLs for which the
            End-to-End CC OAM recovery has been detected in the last
            corresponding notification .";
          smiv2:max-access "read-only";
          smiv2:oid "1.3.6.1.4.1.9.10.97.1.12.1.2";
        }

        leaf catmPVclEndCCRangeStatusUpStart {
          type yang:timestamp;
          description
           "The time stamp at which the first End-to-End CC OAM recovery
            is detected on any of the PVCLs in the range
            in the last corresponding notification .";
          smiv2:max-access "read-only";
          smiv2:oid "1.3.6.1.4.1.9.10.97.1.12.1.3";
        }

        leaf catmPVclEndCCRangeStatusUpEnd {
          type yang:timestamp;
          description
           "The time stamp at which the last End-to-End CC OAM recovery
            is detected on any of the PVCLs in the range
            in the last corresponding notification .";
          smiv2:max-access "read-only";
          smiv2:oid "1.3.6.1.4.1.9.10.97.1.12.1.4";
        }
      }
    }

    container catmAISRDIStatusUpPVclRangeTable {
      description
       "A table indicating more than one VCLs in a consecutive
        range and for each VCL there is an active row in the
        atmVclTable having an atmVclConnKind value of `pvc'
        and AISRDI OAM status to have detected as recovered
        in the last corresponding PVC notification .";
      smiv2:oid "1.3.6.1.4.1.9.10.97.1.13";

      list catmAISRDIStatusUpPVclRangeEntry {
        key "ifIndex atmVclVpi catmStatusChangePVclRangeIndex";
        description
         "Each entry in this table represents a range of VCLs and
          for each VCL there is an active row in the atmVclTable having
          an atmVclConnKind value of 'pvc' and AISRDI OAM status 
          to have detected as recovered in the last notification
          interval.";
        smiv2:oid "1.3.6.1.4.1.9.10.97.1.13.1";

        leaf ifIndex {
          type leafref {
            path "/if-mib:IF-MIB/if-mib:ifTable/if-mib:ifEntry/if-mib:ifIndex";
          }
        }

        leaf atmVclVpi {
          type leafref {
            path "/atm-mib:ATM-MIB/atm-mib:atmVclTable/atm-mib:atmVclEntry/atm-mib:atmVclVpi";
          }
        }

        leaf catmStatusChangePVclRangeIndex {
          type leafref {
            path "/CISCO-ATM-PVCTRAP-EXTN-MIB:CISCO-ATM-PVCTRAP-EXTN-MIB/CISCO-ATM-PVCTRAP-EXTN-MIB:catmStatusChangePVclRangeTable/CISCO-ATM-PVCTRAP-EXTN-MIB:catmStatusChangePVclRangeEntry/CISCO-ATM-PVCTRAP-EXTN-MIB:catmStatusChangePVclRangeIndex";
          }
        }

        leaf catmPVclAISRDIUpLowerRangeValue {
          type int32 {
            range "0..65536";
          }
          description
           "The first PVCL in a range of PVCLs for which the
            AISRDI OAM recovery has been detected in the last
            corresponding notification .";
          smiv2:max-access "read-only";
          smiv2:oid "1.3.6.1.4.1.9.10.97.1.13.1.1";
        }

        leaf catmPVclAISRDIUpHigherRangeValue {
          type int32 {
            range "0..65536";
          }
          description
           "The last PVCL in a range of PVCLs for which the
            AISRDI OAM recovery has been detected in the last
            corresponding notification .";
          smiv2:max-access "read-only";
          smiv2:oid "1.3.6.1.4.1.9.10.97.1.13.1.2";
        }

        leaf catmPVclAISRDIRangeStatusUpStart {
          type yang:timestamp;
          description
           "The time stamp at which the first AISRDI OAM recovery
            is detected on any of the PVCLs in the range
            in the last corresponding notification .";
          smiv2:max-access "read-only";
          smiv2:oid "1.3.6.1.4.1.9.10.97.1.13.1.3";
        }

        leaf catmPVclAISRDIRangeStatusUpEnd {
          type yang:timestamp;
          description
           "The time stamp at which the last AISRDI OAM recovery
            is detected on any of the PVCLs in the range
            in the last corresponding notification .";
          smiv2:max-access "read-only";
          smiv2:oid "1.3.6.1.4.1.9.10.97.1.13.1.4";
        }
      }
    }

    container catmUpPVclRangeTable {
      description
       "A table indicating more than one VCLs in a consecutive 
        range and for each VCL there is an active row in the 
        atmVclTable having an atmVclConnKind value of `pvc'
        and atmVclOperStatus to have detected as Up
        in the last corresponding PVC notification .";
      smiv2:oid "1.3.6.1.4.1.9.10.97.1.14";

      list catmUpPVclRangeEntry {
        key "ifIndex atmVclVpi catmStatusChangePVclRangeIndex";
        description
         "Each entry in this table represents a range of VCLs and 
          for each VCL there is an active row in the atmVclTable having
          an atmVclConnKind value of 'pvc' and  atmVclOperStatus to 
          have detected as Up in the last notification 
          interval.";
        smiv2:oid "1.3.6.1.4.1.9.10.97.1.14.1";

        leaf ifIndex {
          type leafref {
            path "/if-mib:IF-MIB/if-mib:ifTable/if-mib:ifEntry/if-mib:ifIndex";
          }
        }

        leaf atmVclVpi {
          type leafref {
            path "/atm-mib:ATM-MIB/atm-mib:atmVclTable/atm-mib:atmVclEntry/atm-mib:atmVclVpi";
          }
        }

        leaf catmStatusChangePVclRangeIndex {
          type leafref {
            path "/CISCO-ATM-PVCTRAP-EXTN-MIB:CISCO-ATM-PVCTRAP-EXTN-MIB/CISCO-ATM-PVCTRAP-EXTN-MIB:catmStatusChangePVclRangeTable/CISCO-ATM-PVCTRAP-EXTN-MIB:catmStatusChangePVclRangeEntry/CISCO-ATM-PVCTRAP-EXTN-MIB:catmStatusChangePVclRangeIndex";
          }
        }

        leaf catmUpPVclLowerRangeValue {
          type int32 {
            range "0..65536";
          }
          description
           "The first PVCL in a range of PVCLs for which the 
            atmVclOperStatus has been detected as Up in the 
            corresponding notification .";
          smiv2:max-access "read-only";
          smiv2:oid "1.3.6.1.4.1.9.10.97.1.14.1.1";
        }

        leaf catmUpPVclHigherRangeValue {
          type int32 {
            range "0..65536";
          }
          description
           "The last PVCL in a range of PVCLs for which the 
            atmVclOperStatus has been detected as Up in the 
            corresponding notification .";
          smiv2:max-access "read-only";
          smiv2:oid "1.3.6.1.4.1.9.10.97.1.14.1.2";
        }

        leaf catmUpPVclRangeStart {
          type yang:timestamp;
          description
           "The time stamp at which the first atmVclOperStatus
            is detected as Up on any of the PVCLs in the range
            in the corresponding notification .";
          smiv2:max-access "read-only";
          smiv2:oid "1.3.6.1.4.1.9.10.97.1.14.1.3";
        }

        leaf catmUpPVclRangeEnd {
          type yang:timestamp;
          description
           "The time stamp at which the last atmVclOperStatus
            is detected as Up on any of the PVCLs in the range
            in the corresponding notification .";
          smiv2:max-access "read-only";
          smiv2:oid "1.3.6.1.4.1.9.10.97.1.14.1.4";
        }

        leaf catmPrevDownPVclRangeStart {
          type yang:timestamp;
          description
           "The time stamp at which the first atmVclOperStatus
            is detected as Down on any of the PVCLs in the range
            in the previous catmIntfPvcDownTrap notification.";
          smiv2:max-access "read-only";
          smiv2:oid "1.3.6.1.4.1.9.10.97.1.14.1.5";
        }

        leaf catmPrevDownPVclRangeEnd {
          type yang:timestamp;
          description
           "The time stamp at which the last atmVclOperStatus
            is detected as Down on any of the PVCLs in the range
            in the previous catmIntfPvcDownTrap notification.";
          smiv2:max-access "read-only";
          smiv2:oid "1.3.6.1.4.1.9.10.97.1.14.1.6";
        }

        leaf catmPVclRangeRecoveryReason {
          type CISCO-ATM-PVCTRAP-EXTN-MIB:CatmOAMRecoveryType;
          description
           "Type of OAM Recovered";
          smiv2:max-access "read-only";
          smiv2:oid "1.3.6.1.4.1.9.10.97.1.14.1.7";
        }
      }
    }
  }

  smiv2:alias "catmInterfaceExt2Table" {
    description
     "This table contains ATM interface monitoring
      information not defined in the
      atmInterfaceConfTable from the ATM-MIB and
      atmInterfaceExtTable CISCO-IETF-ATM2-PVCTRAP-MIB.";
    smiv2:oid "1.3.6.1.4.1.9.10.97.1.1";
  }

  smiv2:alias "catmInterfaceExt2Entry" {
    description
     "An entry extends the atmInterfaceConfEntry
      defined in ATM MIB.  Each entry corresponds
      to an ATM interface.";
    smiv2:oid "1.3.6.1.4.1.9.10.97.1.1.1";
  }

  augment "/atm-mib:ATM-MIB/atm-mib:atmInterfaceConfTable/atm-mib:atmInterfaceConfEntry" {
    description
     "An entry extends the atmInterfaceConfEntry
      defined in ATM MIB.  Each entry corresponds
      to an ATM interface.";
    smiv2:oid "1.3.6.1.4.1.9.10.97.1.1.1";

    leaf catmIntfCurrentlyDownToUpPVcls {
      type yang:gauge32;
      description
       "The current number PVCLs on this interface which 
        changed state to 'up' since the last 
        atmIntPvcUp2Trap was sent.";
      smiv2:max-access "read-only";
      smiv2:oid "1.3.6.1.4.1.9.10.97.1.1.1.1";
    }

    leaf catmIntfOAMFailedPVcls {
      type yang:gauge32;
      description
       "The total number of PVCLs in this interface which 
        are currently in the OAM loopback failed condition but 
        the status of each PVCL remain in the 'up' state.";
      smiv2:max-access "read-only";
      smiv2:oid "1.3.6.1.4.1.9.10.97.1.1.1.2";
    }

    leaf catmIntfCurrentOAMFailingPVcls {
      type yang:gauge32;
      description
       "The current number of PVCLs on this interface for which the
        OAM loop back has failed but the status of each PVCL remain 
        in the 'up' state in the last notification interval.";
      smiv2:max-access "read-only";
      smiv2:oid "1.3.6.1.4.1.9.10.97.1.1.1.3";
    }

    leaf catmIntfSegCCOAMFailedPVcls {
      type yang:gauge32;
      description
       "The total number of PVCLs in this interface which 
        are currently in the Segment CC OAM failed condition 
        but the status of each PVCL remain in the 'up' state.";
      smiv2:max-access "read-only";
      smiv2:oid "1.3.6.1.4.1.9.10.97.1.1.1.4";
    }

    leaf catmIntfCurSegCCOAMFailingPVcls {
      type yang:gauge32;
      description
       "The current number of PVCLs on this interface for which the
        Segment CC OAM has failed but the status of each PVCL remain 
        in the 'up' state in the last notification interval.";
      smiv2:max-access "read-only";
      smiv2:oid "1.3.6.1.4.1.9.10.97.1.1.1.5";
    }

    leaf catmIntfEndCCOAMFailedPVcls {
      type yang:gauge32;
      description
       "The total number of PVCLs in this interface which 
        are currently in the End-to-End CC OAM failed condition 
        but the status of each PVCL remain in the 'up' state.";
      smiv2:max-access "read-only";
      smiv2:oid "1.3.6.1.4.1.9.10.97.1.1.1.6";
    }

    leaf catmIntfCurEndCCOAMFailingPVcls {
      type yang:gauge32;
      description
       "The current number of PVCLs on this interface for which the
        End-to-End CC OAM has failed but the status of each PVCL 
        remain in the 'up' state in the last notification interval.";
      smiv2:max-access "read-only";
      smiv2:oid "1.3.6.1.4.1.9.10.97.1.1.1.7";
    }

    leaf catmIntfAISRDIOAMFailedPVcls {
      type yang:gauge32;
      description
       "The total number of PVCLs in this interface which 
        are currently in the AIS RDI OAM failed condition but 
        the status of each PVCL remain in the 'up' state.";
      smiv2:max-access "read-only";
      smiv2:oid "1.3.6.1.4.1.9.10.97.1.1.1.8";
    }

    leaf catmIntfCurAISRDIOAMFailingPVcls {
      type yang:gauge32;
      description
       "The current number of PVCLs on this interface for which the
        AIS RDI OAM has failed but the status of each PVCL remain 
        in the 'up' state in the last notification interval.";
      smiv2:max-access "read-only";
      smiv2:oid "1.3.6.1.4.1.9.10.97.1.1.1.9";
    }

    leaf catmIntfAnyOAMFailedPVcls {
      type yang:gauge32;
      description
       "The total number of PVCLs in this interface which 
        are currently in any type of OAM failed condition but 
        the status of each PVCL remain in the 'up' state.";
      smiv2:max-access "read-only";
      smiv2:oid "1.3.6.1.4.1.9.10.97.1.1.1.10";
    }

    leaf catmIntfCurAnyOAMFailingPVcls {
      type yang:gauge32;
      description
       "The current number of PVCLs on this interface for which 
        any of OAM has failed but the status of each PVCL remain 
        in the 'up' state in the last notification interval.";
      smiv2:max-access "read-only";
      smiv2:oid "1.3.6.1.4.1.9.10.97.1.1.1.11";
    }

    leaf catmIntfTypeOfOAMFailure {
      type CISCO-ATM-PVCTRAP-EXTN-MIB:CatmOAMFailureType;
      description
       "Type of OAM failure.";
      smiv2:max-access "read-only";
      smiv2:oid "1.3.6.1.4.1.9.10.97.1.1.1.12";
    }

    leaf catmIntfOAMRcovedPVcls {
      type yang:gauge32;
      description
       "The total number of PVCLs in this interface which 
        are currently in the OAM loopback recovered condition and 
        the status of each PVCL is in the 'up' state.";
      smiv2:max-access "read-only";
      smiv2:oid "1.3.6.1.4.1.9.10.97.1.1.1.13";
    }

    leaf catmIntfCurrentOAMRcovingPVcls {
      type yang:gauge32;
      description
       "The current number of PVCLs on this interface for which the
        OAM loop back has recovered and the status of each PVCL is 
        in the 'up' state in the last notification interval.";
      smiv2:max-access "read-only";
      smiv2:oid "1.3.6.1.4.1.9.10.97.1.1.1.14";
    }

    leaf catmIntfSegCCOAMRcovedPVcls {
      type yang:gauge32;
      description
       "The total number of PVCLs in this interface which 
        are currently in the Segment CC OAM recovered condition 
        and the status of each PVCL is in the 'up' state.";
      smiv2:max-access "read-only";
      smiv2:oid "1.3.6.1.4.1.9.10.97.1.1.1.15";
    }

    leaf catmIntfCurSegCCOAMRcovingPVcls {
      type yang:gauge32;
      description
       "The current number of PVCLs on this interface for which the
        Segment CC OAM has recovered and the status of each PVCL is 
        in the 'up' state in the last notification interval.";
      smiv2:max-access "read-only";
      smiv2:oid "1.3.6.1.4.1.9.10.97.1.1.1.16";
    }

    leaf catmIntfEndCCOAMRcovedPVcls {
      type yang:gauge32;
      description
       "The total number of PVCLs in this interface which 
        are currently in the End-to-End CC OAM recovered condition 
        and the status of each PVCL is in the 'up' state.";
      smiv2:max-access "read-only";
      smiv2:oid "1.3.6.1.4.1.9.10.97.1.1.1.17";
    }

    leaf catmIntfCurEndCCOAMRcovingPVcls {
      type yang:gauge32;
      description
       "The current number of PVCLs on this interface for which the
        End-to-End CC OAM has recovered and the status of each PVCL 
        is in the 'up' state in the last notification interval.";
      smiv2:max-access "read-only";
      smiv2:oid "1.3.6.1.4.1.9.10.97.1.1.1.18";
    }

    leaf catmIntfAISRDIOAMRcovedPVcls {
      type yang:gauge32;
      description
       "The total number of PVCLs in this interface which 
        are currently in the AIS RDI OAM recovered condition and 
        the status of each PVCL is in the 'up' state.";
      smiv2:max-access "read-only";
      smiv2:oid "1.3.6.1.4.1.9.10.97.1.1.1.19";
    }

    leaf catmIntfCurAISRDIOAMRcovingPVcls {
      type yang:gauge32;
      description
       "The current number of PVCLs on this interface for which the
        AIS RDI OAM has recovered and the status of each PVCL is 
        in the 'up' state in the last notification interval.";
      smiv2:max-access "read-only";
      smiv2:oid "1.3.6.1.4.1.9.10.97.1.1.1.20";
    }

    leaf catmIntfAnyOAMRcovedPVcls {
      type yang:gauge32;
      description
       "The total number of PVCLs in this interface which 
        are currently in any type of OAM recovered condition and 
        the status of each PVCL is in the 'up' state.";
      smiv2:max-access "read-only";
      smiv2:oid "1.3.6.1.4.1.9.10.97.1.1.1.21";
    }

    leaf catmIntfCurAnyOAMRcovingPVcls {
      type yang:gauge32;
      description
       "The current number of PVCLs on this interface for which 
        any of OAM has recovered and the status of each PVCL is 
        in the 'up' state in the last notification interval.";
      smiv2:max-access "read-only";
      smiv2:oid "1.3.6.1.4.1.9.10.97.1.1.1.22";
    }

    leaf catmIntfTypeOfOAMRecover {
      type CISCO-ATM-PVCTRAP-EXTN-MIB:CatmOAMRecoveryType;
      description
       "Type of OAM Recovered";
      smiv2:max-access "read-only";
      smiv2:oid "1.3.6.1.4.1.9.10.97.1.1.1.23";
    }
  }

  notification catmIntfPvcUpTrap {
    status deprecated;
    description
     "A notification indicating that one or more
      PVCLs on this interface has changed state back to 'up'
      since the last catmIntfPvcUpTrap was sent.";
    smiv2:oid "1.3.6.1.4.1.9.10.97.2.0.1";

    container object-1 {

      leaf ifIndex {
        type leafref {
          path "/if-mib:IF-MIB/if-mib:ifTable/if-mib:ifEntry/if-mib:ifIndex";
        }
      }
    }

    container object-2 {

      leaf ifIndex {
        type leafref {
          path "/if-mib:IF-MIB/if-mib:ifTable/if-mib:ifEntry/if-mib:ifIndex";
        }
      }

      leaf catmIntfCurrentlyDownToUpPVcls {
        type leafref {
          path "/atm-mib:ATM-MIB/atm-mib:atmInterfaceConfTable/atm-mib:atmInterfaceConfEntry/CISCO-ATM-PVCTRAP-EXTN-MIB:catmIntfCurrentlyDownToUpPVcls";
        }
      }
    }
  }

  notification catmIntfPvcOAMFailureTrap {
    description
     "A notification indicating that one or more
      PVCLs on this interface has OAM loop back failed 
      since the last catmIntfPvcOAMFailuresTrap was sent.";
    smiv2:oid "1.3.6.1.4.1.9.10.97.2.0.2";

    container object-1 {

      leaf ifIndex {
        type leafref {
          path "/if-mib:IF-MIB/if-mib:ifTable/if-mib:ifEntry/if-mib:ifIndex";
        }
      }
    }

    container object-2 {

      leaf ifIndex {
        type leafref {
          path "/if-mib:IF-MIB/if-mib:ifTable/if-mib:ifEntry/if-mib:ifIndex";
        }
      }

      leaf catmIntfOAMFailedPVcls {
        type leafref {
          path "/atm-mib:ATM-MIB/atm-mib:atmInterfaceConfTable/atm-mib:atmInterfaceConfEntry/CISCO-ATM-PVCTRAP-EXTN-MIB:catmIntfOAMFailedPVcls";
        }
      }
    }

    container object-3 {

      leaf ifIndex {
        type leafref {
          path "/if-mib:IF-MIB/if-mib:ifTable/if-mib:ifEntry/if-mib:ifIndex";
        }
      }

      leaf catmIntfCurrentOAMFailingPVcls {
        type leafref {
          path "/atm-mib:ATM-MIB/atm-mib:atmInterfaceConfTable/atm-mib:atmInterfaceConfEntry/CISCO-ATM-PVCTRAP-EXTN-MIB:catmIntfCurrentOAMFailingPVcls";
        }
      }
    }
  }

  notification catmIntfPvcSegCCOAMFailureTrap {
    description
     "A notification indicating that one or more
      PVCLs on this interface has Segment CC OAM failure 
      since the last catmIntfPvcSegCCOAMFailureTrap was sent.";
    smiv2:oid "1.3.6.1.4.1.9.10.97.2.0.3";

    container object-1 {

      leaf ifIndex {
        type leafref {
          path "/if-mib:IF-MIB/if-mib:ifTable/if-mib:ifEntry/if-mib:ifIndex";
        }
      }
    }

    container object-2 {

      leaf ifIndex {
        type leafref {
          path "/if-mib:IF-MIB/if-mib:ifTable/if-mib:ifEntry/if-mib:ifIndex";
        }
      }

      leaf catmIntfSegCCOAMFailedPVcls {
        type leafref {
          path "/atm-mib:ATM-MIB/atm-mib:atmInterfaceConfTable/atm-mib:atmInterfaceConfEntry/CISCO-ATM-PVCTRAP-EXTN-MIB:catmIntfSegCCOAMFailedPVcls";
        }
      }
    }

    container object-3 {

      leaf ifIndex {
        type leafref {
          path "/if-mib:IF-MIB/if-mib:ifTable/if-mib:ifEntry/if-mib:ifIndex";
        }
      }

      leaf catmIntfCurSegCCOAMFailingPVcls {
        type leafref {
          path "/atm-mib:ATM-MIB/atm-mib:atmInterfaceConfTable/atm-mib:atmInterfaceConfEntry/CISCO-ATM-PVCTRAP-EXTN-MIB:catmIntfCurSegCCOAMFailingPVcls";
        }
      }
    }
  }

  notification catmIntfPvcEndCCOAMFailureTrap {
    description
     "A notification indicating that one or more
      PVCLs on this interface has End-to-End CC OAM failure 
      since the last catmIntfPvcEndCCOAMFailureTrap was sent.";
    smiv2:oid "1.3.6.1.4.1.9.10.97.2.0.4";

    container object-1 {

      leaf ifIndex {
        type leafref {
          path "/if-mib:IF-MIB/if-mib:ifTable/if-mib:ifEntry/if-mib:ifIndex";
        }
      }
    }

    container object-2 {

      leaf ifIndex {
        type leafref {
          path "/if-mib:IF-MIB/if-mib:ifTable/if-mib:ifEntry/if-mib:ifIndex";
        }
      }

      leaf catmIntfEndCCOAMFailedPVcls {
        type leafref {
          path "/atm-mib:ATM-MIB/atm-mib:atmInterfaceConfTable/atm-mib:atmInterfaceConfEntry/CISCO-ATM-PVCTRAP-EXTN-MIB:catmIntfEndCCOAMFailedPVcls";
        }
      }
    }

    container object-3 {

      leaf ifIndex {
        type leafref {
          path "/if-mib:IF-MIB/if-mib:ifTable/if-mib:ifEntry/if-mib:ifIndex";
        }
      }

      leaf catmIntfCurEndCCOAMFailingPVcls {
        type leafref {
          path "/atm-mib:ATM-MIB/atm-mib:atmInterfaceConfTable/atm-mib:atmInterfaceConfEntry/CISCO-ATM-PVCTRAP-EXTN-MIB:catmIntfCurEndCCOAMFailingPVcls";
        }
      }
    }
  }

  notification catmIntfPvcAISRDIOAMFailureTrap {
    description
     "A notification indicating that one or more
      PVCLs on this interface has AIS RDI OAM failure 
      since the last catmIntfPvcAISRDIOAMFailureTrap was sent.";
    smiv2:oid "1.3.6.1.4.1.9.10.97.2.0.5";

    container object-1 {

      leaf ifIndex {
        type leafref {
          path "/if-mib:IF-MIB/if-mib:ifTable/if-mib:ifEntry/if-mib:ifIndex";
        }
      }
    }

    container object-2 {

      leaf ifIndex {
        type leafref {
          path "/if-mib:IF-MIB/if-mib:ifTable/if-mib:ifEntry/if-mib:ifIndex";
        }
      }

      leaf catmIntfAISRDIOAMFailedPVcls {
        type leafref {
          path "/atm-mib:ATM-MIB/atm-mib:atmInterfaceConfTable/atm-mib:atmInterfaceConfEntry/CISCO-ATM-PVCTRAP-EXTN-MIB:catmIntfAISRDIOAMFailedPVcls";
        }
      }
    }

    container object-3 {

      leaf ifIndex {
        type leafref {
          path "/if-mib:IF-MIB/if-mib:ifTable/if-mib:ifEntry/if-mib:ifIndex";
        }
      }

      leaf catmIntfCurAISRDIOAMFailingPVcls {
        type leafref {
          path "/atm-mib:ATM-MIB/atm-mib:atmInterfaceConfTable/atm-mib:atmInterfaceConfEntry/CISCO-ATM-PVCTRAP-EXTN-MIB:catmIntfCurAISRDIOAMFailingPVcls";
        }
      }
    }
  }

  notification catmIntfPvcAnyOAMFailureTrap {
    description
     "A notification indicating that one or more
      PVCLs on this interface has one or more OAM failed 
      since the last catmIntfPvcAnyOAMFailureTrap was sent.";
    smiv2:oid "1.3.6.1.4.1.9.10.97.2.0.6";

    container object-1 {

      leaf ifIndex {
        type leafref {
          path "/if-mib:IF-MIB/if-mib:ifTable/if-mib:ifEntry/if-mib:ifIndex";
        }
      }
    }

    container object-2 {

      leaf ifIndex {
        type leafref {
          path "/if-mib:IF-MIB/if-mib:ifTable/if-mib:ifEntry/if-mib:ifIndex";
        }
      }

      leaf catmIntfAnyOAMFailedPVcls {
        type leafref {
          path "/atm-mib:ATM-MIB/atm-mib:atmInterfaceConfTable/atm-mib:atmInterfaceConfEntry/CISCO-ATM-PVCTRAP-EXTN-MIB:catmIntfAnyOAMFailedPVcls";
        }
      }
    }

    container object-3 {

      leaf ifIndex {
        type leafref {
          path "/if-mib:IF-MIB/if-mib:ifTable/if-mib:ifEntry/if-mib:ifIndex";
        }
      }

      leaf catmIntfCurAnyOAMFailingPVcls {
        type leafref {
          path "/atm-mib:ATM-MIB/atm-mib:atmInterfaceConfTable/atm-mib:atmInterfaceConfEntry/CISCO-ATM-PVCTRAP-EXTN-MIB:catmIntfCurAnyOAMFailingPVcls";
        }
      }
    }

    container object-4 {

      leaf ifIndex {
        type leafref {
          path "/if-mib:IF-MIB/if-mib:ifTable/if-mib:ifEntry/if-mib:ifIndex";
        }
      }

      leaf catmIntfTypeOfOAMFailure {
        type leafref {
          path "/atm-mib:ATM-MIB/atm-mib:atmInterfaceConfTable/atm-mib:atmInterfaceConfEntry/CISCO-ATM-PVCTRAP-EXTN-MIB:catmIntfTypeOfOAMFailure";
        }
      }
    }
  }

  notification catmIntfPvcOAMRecoverTrap {
    description
     "A notification indicating that one or more
      PVCLs on this interface has OAM loop back recovered 
      since the last catmIntfPvcOAMRecoversTrap was sent.";
    smiv2:oid "1.3.6.1.4.1.9.10.97.2.0.7";

    container object-1 {

      leaf ifIndex {
        type leafref {
          path "/if-mib:IF-MIB/if-mib:ifTable/if-mib:ifEntry/if-mib:ifIndex";
        }
      }
    }

    container object-2 {

      leaf ifIndex {
        type leafref {
          path "/if-mib:IF-MIB/if-mib:ifTable/if-mib:ifEntry/if-mib:ifIndex";
        }
      }

      leaf catmIntfOAMRcovedPVcls {
        type leafref {
          path "/atm-mib:ATM-MIB/atm-mib:atmInterfaceConfTable/atm-mib:atmInterfaceConfEntry/CISCO-ATM-PVCTRAP-EXTN-MIB:catmIntfOAMRcovedPVcls";
        }
      }
    }

    container object-3 {

      leaf ifIndex {
        type leafref {
          path "/if-mib:IF-MIB/if-mib:ifTable/if-mib:ifEntry/if-mib:ifIndex";
        }
      }

      leaf catmIntfCurrentOAMRcovingPVcls {
        type leafref {
          path "/atm-mib:ATM-MIB/atm-mib:atmInterfaceConfTable/atm-mib:atmInterfaceConfEntry/CISCO-ATM-PVCTRAP-EXTN-MIB:catmIntfCurrentOAMRcovingPVcls";
        }
      }
    }
  }

  notification catmIntfPvcSegCCOAMRecoverTrap {
    description
     "A notification indicating that one or more
      PVCLs on this interface has Segment CC OAM recovery 
      since the last catmIntfPvcSegCCOAMRecoverTrap was sent.";
    smiv2:oid "1.3.6.1.4.1.9.10.97.2.0.8";

    container object-1 {

      leaf ifIndex {
        type leafref {
          path "/if-mib:IF-MIB/if-mib:ifTable/if-mib:ifEntry/if-mib:ifIndex";
        }
      }
    }

    container object-2 {

      leaf ifIndex {
        type leafref {
          path "/if-mib:IF-MIB/if-mib:ifTable/if-mib:ifEntry/if-mib:ifIndex";
        }
      }

      leaf catmIntfSegCCOAMRcovedPVcls {
        type leafref {
          path "/atm-mib:ATM-MIB/atm-mib:atmInterfaceConfTable/atm-mib:atmInterfaceConfEntry/CISCO-ATM-PVCTRAP-EXTN-MIB:catmIntfSegCCOAMRcovedPVcls";
        }
      }
    }

    container object-3 {

      leaf ifIndex {
        type leafref {
          path "/if-mib:IF-MIB/if-mib:ifTable/if-mib:ifEntry/if-mib:ifIndex";
        }
      }

      leaf catmIntfCurSegCCOAMRcovingPVcls {
        type leafref {
          path "/atm-mib:ATM-MIB/atm-mib:atmInterfaceConfTable/atm-mib:atmInterfaceConfEntry/CISCO-ATM-PVCTRAP-EXTN-MIB:catmIntfCurSegCCOAMRcovingPVcls";
        }
      }
    }
  }

  notification catmIntfPvcEndCCOAMRecoverTrap {
    description
     "A notification indicating that one or more
      PVCLs on this interface has End-to-End CC OAM recovery 
      since the last catmIntfPvcEndCCOAMRecoverTrap was sent.";
    smiv2:oid "1.3.6.1.4.1.9.10.97.2.0.9";

    container object-1 {

      leaf ifIndex {
        type leafref {
          path "/if-mib:IF-MIB/if-mib:ifTable/if-mib:ifEntry/if-mib:ifIndex";
        }
      }
    }

    container object-2 {

      leaf ifIndex {
        type leafref {
          path "/if-mib:IF-MIB/if-mib:ifTable/if-mib:ifEntry/if-mib:ifIndex";
        }
      }

      leaf catmIntfEndCCOAMRcovedPVcls {
        type leafref {
          path "/atm-mib:ATM-MIB/atm-mib:atmInterfaceConfTable/atm-mib:atmInterfaceConfEntry/CISCO-ATM-PVCTRAP-EXTN-MIB:catmIntfEndCCOAMRcovedPVcls";
        }
      }
    }

    container object-3 {

      leaf ifIndex {
        type leafref {
          path "/if-mib:IF-MIB/if-mib:ifTable/if-mib:ifEntry/if-mib:ifIndex";
        }
      }

      leaf catmIntfCurEndCCOAMRcovingPVcls {
        type leafref {
          path "/atm-mib:ATM-MIB/atm-mib:atmInterfaceConfTable/atm-mib:atmInterfaceConfEntry/CISCO-ATM-PVCTRAP-EXTN-MIB:catmIntfCurEndCCOAMRcovingPVcls";
        }
      }
    }
  }

  notification catmIntfPvcAISRDIOAMRecoverTrap {
    description
     "A notification indicating that one or more
      PVCLs on this interface has AIS RDI OAM recovery 
      since the last catmIntfPvcAISRDIOAMRecoverTrap was sent.";
    smiv2:oid "1.3.6.1.4.1.9.10.97.2.0.10";

    container object-1 {

      leaf ifIndex {
        type leafref {
          path "/if-mib:IF-MIB/if-mib:ifTable/if-mib:ifEntry/if-mib:ifIndex";
        }
      }
    }

    container object-2 {

      leaf ifIndex {
        type leafref {
          path "/if-mib:IF-MIB/if-mib:ifTable/if-mib:ifEntry/if-mib:ifIndex";
        }
      }

      leaf catmIntfAISRDIOAMRcovedPVcls {
        type leafref {
          path "/atm-mib:ATM-MIB/atm-mib:atmInterfaceConfTable/atm-mib:atmInterfaceConfEntry/CISCO-ATM-PVCTRAP-EXTN-MIB:catmIntfAISRDIOAMRcovedPVcls";
        }
      }
    }

    container object-3 {

      leaf ifIndex {
        type leafref {
          path "/if-mib:IF-MIB/if-mib:ifTable/if-mib:ifEntry/if-mib:ifIndex";
        }
      }

      leaf catmIntfCurAISRDIOAMRcovingPVcls {
        type leafref {
          path "/atm-mib:ATM-MIB/atm-mib:atmInterfaceConfTable/atm-mib:atmInterfaceConfEntry/CISCO-ATM-PVCTRAP-EXTN-MIB:catmIntfCurAISRDIOAMRcovingPVcls";
        }
      }
    }
  }

  notification catmIntfPvcAnyOAMRecoverTrap {
    description
     "A notification indicating that one or more
      PVCLs on this interface has one or more OAM recovered 
      since the last catmIntfPvcAnyOAMRecoverTrap was sent.";
    smiv2:oid "1.3.6.1.4.1.9.10.97.2.0.11";

    container object-1 {

      leaf ifIndex {
        type leafref {
          path "/if-mib:IF-MIB/if-mib:ifTable/if-mib:ifEntry/if-mib:ifIndex";
        }
      }
    }

    container object-2 {

      leaf ifIndex {
        type leafref {
          path "/if-mib:IF-MIB/if-mib:ifTable/if-mib:ifEntry/if-mib:ifIndex";
        }
      }

      leaf catmIntfAnyOAMRcovedPVcls {
        type leafref {
          path "/atm-mib:ATM-MIB/atm-mib:atmInterfaceConfTable/atm-mib:atmInterfaceConfEntry/CISCO-ATM-PVCTRAP-EXTN-MIB:catmIntfAnyOAMRcovedPVcls";
        }
      }
    }

    container object-3 {

      leaf ifIndex {
        type leafref {
          path "/if-mib:IF-MIB/if-mib:ifTable/if-mib:ifEntry/if-mib:ifIndex";
        }
      }

      leaf catmIntfCurAnyOAMRcovingPVcls {
        type leafref {
          path "/atm-mib:ATM-MIB/atm-mib:atmInterfaceConfTable/atm-mib:atmInterfaceConfEntry/CISCO-ATM-PVCTRAP-EXTN-MIB:catmIntfCurAnyOAMRcovingPVcls";
        }
      }
    }

    container object-4 {

      leaf ifIndex {
        type leafref {
          path "/if-mib:IF-MIB/if-mib:ifTable/if-mib:ifEntry/if-mib:ifIndex";
        }
      }

      leaf catmIntfTypeOfOAMRecover {
        type leafref {
          path "/atm-mib:ATM-MIB/atm-mib:atmInterfaceConfTable/atm-mib:atmInterfaceConfEntry/CISCO-ATM-PVCTRAP-EXTN-MIB:catmIntfTypeOfOAMRecover";
        }
      }
    }
  }

  notification catmIntfPvcUp2Trap {
    description
     "A notification indicating that one or more
      PVCLs on this interface has changed state back to 'up'
      since the last catmIntfPvcUp2Trap was sent.";
    smiv2:oid "1.3.6.1.4.1.9.10.97.2.0.12";

    container object-1 {

      leaf ifIndex {
        type leafref {
          path "/if-mib:IF-MIB/if-mib:ifTable/if-mib:ifEntry/if-mib:ifIndex";
        }
      }
    }

    container object-2 {

      leaf ifIndex {
        type leafref {
          path "/if-mib:IF-MIB/if-mib:ifTable/if-mib:ifEntry/if-mib:ifIndex";
        }
      }

      leaf catmIntfCurrentlyDownToUpPVcls {
        type leafref {
          path "/atm-mib:ATM-MIB/atm-mib:atmInterfaceConfTable/atm-mib:atmInterfaceConfEntry/CISCO-ATM-PVCTRAP-EXTN-MIB:catmIntfCurrentlyDownToUpPVcls";
        }
      }
    }
  }

  notification catmIntfPvcDownTrap {
    description
     "A notification indicating that one or more
      PVCLs on this interface has changed state back to 'down'
      since the last catmIntfPvcDownTrap was sent.";
    smiv2:oid "1.3.6.1.4.1.9.10.97.2.0.13";

    container object-1 {

      leaf ifIndex {
        type leafref {
          path "/if-mib:IF-MIB/if-mib:ifTable/if-mib:ifEntry/if-mib:ifIndex";
        }
      }
    }

    container object-2 {

      leaf ifIndex {
        type leafref {
          path "/if-mib:IF-MIB/if-mib:ifTable/if-mib:ifEntry/if-mib:ifIndex";
        }
      }

      leaf atmIntfPvcFailures {
        type leafref {
          path "/atm-mib:ATM-MIB/atm-mib:atmInterfaceConfTable/atm-mib:atmInterfaceConfEntry/cisco-ietf:atmIntfPvcFailures";
        }
      }
    }

    container object-3 {

      leaf ifIndex {
        type leafref {
          path "/if-mib:IF-MIB/if-mib:ifTable/if-mib:ifEntry/if-mib:ifIndex";
        }
      }

      leaf atmIntfCurrentlyFailingPVcls {
        type leafref {
          path "/atm-mib:ATM-MIB/atm-mib:atmInterfaceConfTable/atm-mib:atmInterfaceConfEntry/cisco-ietf:atmIntfCurrentlyFailingPVcls";
        }
      }
    }
  }

  smiv2:alias "ciscoAtmPvcTrapExtnMIB" {
    smiv2:oid "1.3.6.1.4.1.9.10.97";
  }

  smiv2:alias "ciscoAtmPvcTrapExtnMIBObjects" {
    smiv2:oid "1.3.6.1.4.1.9.10.97.1";
  }

  smiv2:alias "cAtmPvcTrapExtnMIBNotifPrefix" {
    smiv2:oid "1.3.6.1.4.1.9.10.97.2";
  }

  smiv2:alias "cAtmPvcTrapExtnMIBNotif" {
    smiv2:oid "1.3.6.1.4.1.9.10.97.2.0";
  }

  smiv2:alias "ciscoAtmPvcTrapExtnMIBConformance" {
    smiv2:oid "1.3.6.1.4.1.9.10.97.3";
  }

  smiv2:alias "ciscoAtmPvcTrapExtnMIBCompliances" {
    smiv2:oid "1.3.6.1.4.1.9.10.97.3.1";
  }

  smiv2:alias "ciscoAtmPvcTrapExtnMIBGroups" {
    smiv2:oid "1.3.6.1.4.1.9.10.97.3.2";
  }

}
