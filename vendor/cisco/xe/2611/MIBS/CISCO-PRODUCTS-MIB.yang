/*
 * Generated by confdc --mib2yang-std
 * Source: mgmt/dmi/model/mib/src/CISCO-PRODUCTS-MIB.mib
 */
/*
 * This YANG module has been generated by smidump 0.5.0:
 *
 *      smidump -f yang CISCO-PRODUCTS-MIB
 *
 * Do not edit. Edit the source file instead!
 */

module CISCO-PRODUCTS-MIB {

  namespace "urn:ietf:params:xml:ns:yang:smiv2:CISCO-PRODUCTS-MIB";
  prefix CISCO-PRODUCTS-MIB;

  import ietf-yang-smiv2 {
    prefix "smiv2";
  }

  organization
   "Cisco Systems, Inc.";

  contact
   "       Cisco Systems
    Customer Service
    
    Postal: 170 W Tasman Drive
    San Jose, CA  95134
    USA
    
    Tel: +1 800 553-NETS
    
    E-mail: cs-snmp@cisco.com";

  description
   "This module defines the object identifiers that are
    assigned to various hardware platforms, and hence are
    returned as values for sysObjectID";

  revision 2014-11-06 {
    description
     "[Revision added by libsmi due to a LAST-UPDATED clause.]";
  }

  revision 2013-05-28 {
    description
     "Added following OIDs:
      ciscoMPX, ciscoNMCUEEC, ciscoWLSE1132, 
      ciscoME6340ACA, ciscoME6340DCA,
      ciscoME6340DCA, catalyst296024TT,
      catalyst296048TT";
  }

  revision 2005-04-20 {
    description
     "Removed DNP of catalyst6kGateway";
  }

  revision 2005-04-18 {
    description
     "Added following OIDs:
      ciscoNme16Es1GeNoPwr, ciscoNmeX24Es1GeNoPwr,
      ciscoNmeXd24Es2StNoPwr, ciscoNmeXd48Es2GeNoPwr,
      catalyst6kMsfc2a, ciscoEDI, ciscoCe611K9,
      ciscoWLSEs20.";
  }

  revision 2002-04-05 {
    description
     "CANA Assignments.";
  }

  revision 1995-05-31 {
    description
     "Miscellaneous updates.";
  }

  smiv2:alias "ciscoGatewayServer" {
    smiv2:oid "1.3.6.1.4.1.9.1.1";
  }

  smiv2:alias "ciscoTerminalServer" {
    smiv2:oid "1.3.6.1.4.1.9.1.2";
  }

  smiv2:alias "ciscoTrouter" {
    smiv2:oid "1.3.6.1.4.1.9.1.3";
  }

  smiv2:alias "ciscoProtocolTranslator" {
    smiv2:oid "1.3.6.1.4.1.9.1.4";
  }

  smiv2:alias "ciscoIGS" {
    smiv2:oid "1.3.6.1.4.1.9.1.5";
  }

  smiv2:alias "cisco3000" {
    smiv2:oid "1.3.6.1.4.1.9.1.6";
  }

  smiv2:alias "cisco4000" {
    smiv2:oid "1.3.6.1.4.1.9.1.7";
  }

  smiv2:alias "cisco7000" {
    smiv2:oid "1.3.6.1.4.1.9.1.8";
  }

  smiv2:alias "ciscoCS500" {
    smiv2:oid "1.3.6.1.4.1.9.1.9";
  }

  smiv2:alias "cisco2000" {
    smiv2:oid "1.3.6.1.4.1.9.1.10";
  }

  smiv2:alias "ciscoAGSplus" {
    smiv2:oid "1.3.6.1.4.1.9.1.11";
  }

  smiv2:alias "cisco7010" {
    smiv2:oid "1.3.6.1.4.1.9.1.12";
  }

  smiv2:alias "cisco2500" {
    smiv2:oid "1.3.6.1.4.1.9.1.13";
  }

  smiv2:alias "cisco4500" {
    smiv2:oid "1.3.6.1.4.1.9.1.14";
  }

  smiv2:alias "cisco2102" {
    smiv2:oid "1.3.6.1.4.1.9.1.15";
  }

  smiv2:alias "cisco2202" {
    smiv2:oid "1.3.6.1.4.1.9.1.16";
  }

  smiv2:alias "cisco2501" {
    smiv2:oid "1.3.6.1.4.1.9.1.17";
  }

  smiv2:alias "cisco2502" {
    smiv2:oid "1.3.6.1.4.1.9.1.18";
  }

  smiv2:alias "cisco2503" {
    smiv2:oid "1.3.6.1.4.1.9.1.19";
  }

  smiv2:alias "cisco2504" {
    smiv2:oid "1.3.6.1.4.1.9.1.20";
  }

  smiv2:alias "cisco2505" {
    smiv2:oid "1.3.6.1.4.1.9.1.21";
  }

  smiv2:alias "cisco2506" {
    smiv2:oid "1.3.6.1.4.1.9.1.22";
  }

  smiv2:alias "cisco2507" {
    smiv2:oid "1.3.6.1.4.1.9.1.23";
  }

  smiv2:alias "cisco2508" {
    smiv2:oid "1.3.6.1.4.1.9.1.24";
  }

  smiv2:alias "cisco2509" {
    smiv2:oid "1.3.6.1.4.1.9.1.25";
  }

  smiv2:alias "cisco2510" {
    smiv2:oid "1.3.6.1.4.1.9.1.26";
  }

  smiv2:alias "cisco2511" {
    smiv2:oid "1.3.6.1.4.1.9.1.27";
  }

  smiv2:alias "cisco2512" {
    smiv2:oid "1.3.6.1.4.1.9.1.28";
  }

  smiv2:alias "cisco2513" {
    smiv2:oid "1.3.6.1.4.1.9.1.29";
  }

  smiv2:alias "cisco2514" {
    smiv2:oid "1.3.6.1.4.1.9.1.30";
  }

  smiv2:alias "cisco2515" {
    smiv2:oid "1.3.6.1.4.1.9.1.31";
  }

  smiv2:alias "cisco3101" {
    smiv2:oid "1.3.6.1.4.1.9.1.32";
  }

  smiv2:alias "cisco3102" {
    smiv2:oid "1.3.6.1.4.1.9.1.33";
  }

  smiv2:alias "cisco3103" {
    smiv2:oid "1.3.6.1.4.1.9.1.34";
  }

  smiv2:alias "cisco3104" {
    smiv2:oid "1.3.6.1.4.1.9.1.35";
  }

  smiv2:alias "cisco3202" {
    smiv2:oid "1.3.6.1.4.1.9.1.36";
  }

  smiv2:alias "cisco3204" {
    smiv2:oid "1.3.6.1.4.1.9.1.37";
  }

  smiv2:alias "ciscoAccessProRC" {
    smiv2:oid "1.3.6.1.4.1.9.1.38";
  }

  smiv2:alias "ciscoAccessProEC" {
    smiv2:oid "1.3.6.1.4.1.9.1.39";
  }

  smiv2:alias "cisco1000" {
    smiv2:oid "1.3.6.1.4.1.9.1.40";
  }

  smiv2:alias "cisco1003" {
    smiv2:oid "1.3.6.1.4.1.9.1.41";
  }

  smiv2:alias "cisco2516" {
    smiv2:oid "1.3.6.1.4.1.9.1.42";
  }

  smiv2:alias "cisco1020" {
    smiv2:oid "1.3.6.1.4.1.9.1.43";
  }

  smiv2:alias "cisco1004" {
    smiv2:oid "1.3.6.1.4.1.9.1.44";
  }

  smiv2:alias "cisco7507" {
    smiv2:oid "1.3.6.1.4.1.9.1.45";
  }

  smiv2:alias "cisco7513" {
    smiv2:oid "1.3.6.1.4.1.9.1.46";
  }

  smiv2:alias "cisco7506" {
    smiv2:oid "1.3.6.1.4.1.9.1.47";
  }

  smiv2:alias "cisco7505" {
    smiv2:oid "1.3.6.1.4.1.9.1.48";
  }

  smiv2:alias "cisco1005" {
    smiv2:oid "1.3.6.1.4.1.9.1.49";
  }

  smiv2:alias "cisco4700" {
    smiv2:oid "1.3.6.1.4.1.9.1.50";
  }

  smiv2:alias "ciscoPro1003" {
    smiv2:oid "1.3.6.1.4.1.9.1.51";
  }

  smiv2:alias "ciscoPro1004" {
    smiv2:oid "1.3.6.1.4.1.9.1.52";
  }

  smiv2:alias "ciscoPro1005" {
    smiv2:oid "1.3.6.1.4.1.9.1.53";
  }

  smiv2:alias "ciscoPro1020" {
    smiv2:oid "1.3.6.1.4.1.9.1.54";
  }

  smiv2:alias "ciscoPro2500PCE" {
    smiv2:oid "1.3.6.1.4.1.9.1.55";
  }

  smiv2:alias "ciscoPro2501" {
    smiv2:oid "1.3.6.1.4.1.9.1.56";
  }

  smiv2:alias "ciscoPro2503" {
    smiv2:oid "1.3.6.1.4.1.9.1.57";
  }

  smiv2:alias "ciscoPro2505" {
    smiv2:oid "1.3.6.1.4.1.9.1.58";
  }

  smiv2:alias "ciscoPro2507" {
    smiv2:oid "1.3.6.1.4.1.9.1.59";
  }

  smiv2:alias "ciscoPro2509" {
    smiv2:oid "1.3.6.1.4.1.9.1.60";
  }

  smiv2:alias "ciscoPro2511" {
    smiv2:oid "1.3.6.1.4.1.9.1.61";
  }

  smiv2:alias "ciscoPro2514" {
    smiv2:oid "1.3.6.1.4.1.9.1.62";
  }

  smiv2:alias "ciscoPro2516" {
    smiv2:oid "1.3.6.1.4.1.9.1.63";
  }

  smiv2:alias "ciscoPro2519" {
    smiv2:oid "1.3.6.1.4.1.9.1.64";
  }

  smiv2:alias "ciscoPro2521" {
    smiv2:oid "1.3.6.1.4.1.9.1.65";
  }

  smiv2:alias "ciscoPro4500" {
    smiv2:oid "1.3.6.1.4.1.9.1.66";
  }

  smiv2:alias "cisco2517" {
    smiv2:oid "1.3.6.1.4.1.9.1.67";
  }

  smiv2:alias "cisco2518" {
    smiv2:oid "1.3.6.1.4.1.9.1.68";
  }

  smiv2:alias "cisco2519" {
    smiv2:oid "1.3.6.1.4.1.9.1.69";
  }

  smiv2:alias "cisco2520" {
    smiv2:oid "1.3.6.1.4.1.9.1.70";
  }

  smiv2:alias "cisco2521" {
    smiv2:oid "1.3.6.1.4.1.9.1.71";
  }

  smiv2:alias "cisco2522" {
    smiv2:oid "1.3.6.1.4.1.9.1.72";
  }

  smiv2:alias "cisco2523" {
    smiv2:oid "1.3.6.1.4.1.9.1.73";
  }

  smiv2:alias "cisco2524" {
    smiv2:oid "1.3.6.1.4.1.9.1.74";
  }

  smiv2:alias "cisco2525" {
    smiv2:oid "1.3.6.1.4.1.9.1.75";
  }

  smiv2:alias "ciscoPro751" {
    smiv2:oid "1.3.6.1.4.1.9.1.76";
  }

  smiv2:alias "ciscoPro752" {
    smiv2:oid "1.3.6.1.4.1.9.1.77";
  }

  smiv2:alias "ciscoPro753" {
    smiv2:oid "1.3.6.1.4.1.9.1.78";
  }

  smiv2:alias "ciscoPro901" {
    smiv2:oid "1.3.6.1.4.1.9.1.79";
  }

  smiv2:alias "ciscoPro902" {
    smiv2:oid "1.3.6.1.4.1.9.1.80";
  }

  smiv2:alias "cisco751" {
    smiv2:oid "1.3.6.1.4.1.9.1.81";
  }

  smiv2:alias "cisco752" {
    smiv2:oid "1.3.6.1.4.1.9.1.82";
  }

  smiv2:alias "cisco753" {
    smiv2:oid "1.3.6.1.4.1.9.1.83";
  }

  smiv2:alias "ciscoPro741" {
    smiv2:oid "1.3.6.1.4.1.9.1.84";
  }

  smiv2:alias "ciscoPro742" {
    smiv2:oid "1.3.6.1.4.1.9.1.85";
  }

  smiv2:alias "ciscoPro743" {
    smiv2:oid "1.3.6.1.4.1.9.1.86";
  }

  smiv2:alias "ciscoPro744" {
    smiv2:oid "1.3.6.1.4.1.9.1.87";
  }

  smiv2:alias "ciscoPro761" {
    smiv2:oid "1.3.6.1.4.1.9.1.88";
  }

  smiv2:alias "ciscoPro762" {
    smiv2:oid "1.3.6.1.4.1.9.1.89";
  }

  smiv2:alias "ciscoPro763" {
    smiv2:oid "1.3.6.1.4.1.9.1.90";
  }

  smiv2:alias "ciscoPro764" {
    smiv2:oid "1.3.6.1.4.1.9.1.91";
  }

  smiv2:alias "ciscoPro765" {
    smiv2:oid "1.3.6.1.4.1.9.1.92";
  }

  smiv2:alias "ciscoPro766" {
    smiv2:oid "1.3.6.1.4.1.9.1.93";
  }

  smiv2:alias "cisco741" {
    smiv2:oid "1.3.6.1.4.1.9.1.94";
  }

  smiv2:alias "cisco742" {
    smiv2:oid "1.3.6.1.4.1.9.1.95";
  }

  smiv2:alias "cisco743" {
    smiv2:oid "1.3.6.1.4.1.9.1.96";
  }

  smiv2:alias "cisco744" {
    smiv2:oid "1.3.6.1.4.1.9.1.97";
  }

  smiv2:alias "cisco761" {
    smiv2:oid "1.3.6.1.4.1.9.1.98";
  }

  smiv2:alias "cisco762" {
    smiv2:oid "1.3.6.1.4.1.9.1.99";
  }

  smiv2:alias "cisco763" {
    smiv2:oid "1.3.6.1.4.1.9.1.100";
  }

  smiv2:alias "cisco764" {
    smiv2:oid "1.3.6.1.4.1.9.1.101";
  }

  smiv2:alias "cisco765" {
    smiv2:oid "1.3.6.1.4.1.9.1.102";
  }

  smiv2:alias "cisco766" {
    smiv2:oid "1.3.6.1.4.1.9.1.103";
  }

  smiv2:alias "ciscoPro2520" {
    smiv2:oid "1.3.6.1.4.1.9.1.104";
  }

  smiv2:alias "ciscoPro2522" {
    smiv2:oid "1.3.6.1.4.1.9.1.105";
  }

  smiv2:alias "ciscoPro2524" {
    smiv2:oid "1.3.6.1.4.1.9.1.106";
  }

  smiv2:alias "ciscoLS1010" {
    smiv2:oid "1.3.6.1.4.1.9.1.107";
  }

  smiv2:alias "cisco7206" {
    smiv2:oid "1.3.6.1.4.1.9.1.108";
  }

  smiv2:alias "ciscoAS5200" {
    smiv2:oid "1.3.6.1.4.1.9.1.109";
  }

  smiv2:alias "cisco3640" {
    smiv2:oid "1.3.6.1.4.1.9.1.110";
  }

  smiv2:alias "ciscoCatalyst3500" {
    smiv2:oid "1.3.6.1.4.1.9.1.111";
  }

  smiv2:alias "ciscoWSX3011" {
    smiv2:oid "1.3.6.1.4.1.9.1.112";
  }

  smiv2:alias "cisco1601" {
    smiv2:oid "1.3.6.1.4.1.9.1.113";
  }

  smiv2:alias "cisco1602" {
    smiv2:oid "1.3.6.1.4.1.9.1.114";
  }

  smiv2:alias "cisco1603" {
    smiv2:oid "1.3.6.1.4.1.9.1.115";
  }

  smiv2:alias "cisco1604" {
    smiv2:oid "1.3.6.1.4.1.9.1.116";
  }

  smiv2:alias "ciscoPro1601" {
    smiv2:oid "1.3.6.1.4.1.9.1.117";
  }

  smiv2:alias "ciscoPro1602" {
    smiv2:oid "1.3.6.1.4.1.9.1.118";
  }

  smiv2:alias "ciscoPro1603" {
    smiv2:oid "1.3.6.1.4.1.9.1.119";
  }

  smiv2:alias "ciscoPro1604" {
    smiv2:oid "1.3.6.1.4.1.9.1.120";
  }

  smiv2:alias "ciscoWSX5301" {
    smiv2:oid "1.3.6.1.4.1.9.1.121";
  }

  smiv2:alias "cisco3620" {
    smiv2:oid "1.3.6.1.4.1.9.1.122";
  }

  smiv2:alias "ciscoPro3620" {
    smiv2:oid "1.3.6.1.4.1.9.1.123";
  }

  smiv2:alias "ciscoPro3640" {
    smiv2:oid "1.3.6.1.4.1.9.1.124";
  }

  smiv2:alias "cisco7204" {
    smiv2:oid "1.3.6.1.4.1.9.1.125";
  }

  smiv2:alias "cisco771" {
    smiv2:oid "1.3.6.1.4.1.9.1.126";
  }

  smiv2:alias "cisco772" {
    smiv2:oid "1.3.6.1.4.1.9.1.127";
  }

  smiv2:alias "cisco775" {
    smiv2:oid "1.3.6.1.4.1.9.1.128";
  }

  smiv2:alias "cisco776" {
    smiv2:oid "1.3.6.1.4.1.9.1.129";
  }

  smiv2:alias "ciscoPro2502" {
    smiv2:oid "1.3.6.1.4.1.9.1.130";
  }

  smiv2:alias "ciscoPro2504" {
    smiv2:oid "1.3.6.1.4.1.9.1.131";
  }

  smiv2:alias "ciscoPro2506" {
    smiv2:oid "1.3.6.1.4.1.9.1.132";
  }

  smiv2:alias "ciscoPro2508" {
    smiv2:oid "1.3.6.1.4.1.9.1.133";
  }

  smiv2:alias "ciscoPro2510" {
    smiv2:oid "1.3.6.1.4.1.9.1.134";
  }

  smiv2:alias "ciscoPro2512" {
    smiv2:oid "1.3.6.1.4.1.9.1.135";
  }

  smiv2:alias "ciscoPro2513" {
    smiv2:oid "1.3.6.1.4.1.9.1.136";
  }

  smiv2:alias "ciscoPro2515" {
    smiv2:oid "1.3.6.1.4.1.9.1.137";
  }

  smiv2:alias "ciscoPro2517" {
    smiv2:oid "1.3.6.1.4.1.9.1.138";
  }

  smiv2:alias "ciscoPro2518" {
    smiv2:oid "1.3.6.1.4.1.9.1.139";
  }

  smiv2:alias "ciscoPro2523" {
    smiv2:oid "1.3.6.1.4.1.9.1.140";
  }

  smiv2:alias "ciscoPro2525" {
    smiv2:oid "1.3.6.1.4.1.9.1.141";
  }

  smiv2:alias "ciscoPro4700" {
    smiv2:oid "1.3.6.1.4.1.9.1.142";
  }

  smiv2:alias "ciscoPro316T" {
    smiv2:oid "1.3.6.1.4.1.9.1.147";
  }

  smiv2:alias "ciscoPro316C" {
    smiv2:oid "1.3.6.1.4.1.9.1.148";
  }

  smiv2:alias "ciscoPro3116" {
    smiv2:oid "1.3.6.1.4.1.9.1.149";
  }

  smiv2:alias "catalyst116T" {
    smiv2:oid "1.3.6.1.4.1.9.1.150";
  }

  smiv2:alias "catalyst116C" {
    smiv2:oid "1.3.6.1.4.1.9.1.151";
  }

  smiv2:alias "catalyst1116" {
    smiv2:oid "1.3.6.1.4.1.9.1.152";
  }

  smiv2:alias "ciscoAS2509RJ" {
    smiv2:oid "1.3.6.1.4.1.9.1.153";
  }

  smiv2:alias "ciscoAS2511RJ" {
    smiv2:oid "1.3.6.1.4.1.9.1.154";
  }

  smiv2:alias "ciscoMC3810" {
    smiv2:oid "1.3.6.1.4.1.9.1.157";
  }

  smiv2:alias "cisco1503" {
    smiv2:oid "1.3.6.1.4.1.9.1.160";
  }

  smiv2:alias "cisco1502" {
    smiv2:oid "1.3.6.1.4.1.9.1.161";
  }

  smiv2:alias "ciscoAS5300" {
    smiv2:oid "1.3.6.1.4.1.9.1.162";
  }

  smiv2:alias "ciscoLS1015" {
    smiv2:oid "1.3.6.1.4.1.9.1.164";
  }

  smiv2:alias "cisco2501FRADFX" {
    smiv2:oid "1.3.6.1.4.1.9.1.165";
  }

  smiv2:alias "cisco2501LANFRADFX" {
    smiv2:oid "1.3.6.1.4.1.9.1.166";
  }

  smiv2:alias "cisco2502LANFRADFX" {
    smiv2:oid "1.3.6.1.4.1.9.1.167";
  }

  smiv2:alias "ciscoWSX5302" {
    smiv2:oid "1.3.6.1.4.1.9.1.168";
  }

  smiv2:alias "ciscoFastHub216T" {
    smiv2:oid "1.3.6.1.4.1.9.1.169";
  }

  smiv2:alias "catalyst2908xl" {
    smiv2:oid "1.3.6.1.4.1.9.1.170";
  }

  smiv2:alias "catalyst2916mxl" {
    smiv2:oid "1.3.6.1.4.1.9.1.171";
  }

  smiv2:alias "cisco1605" {
    smiv2:oid "1.3.6.1.4.1.9.1.172";
  }

  smiv2:alias "cisco12012" {
    smiv2:oid "1.3.6.1.4.1.9.1.173";
  }

  smiv2:alias "catalyst1912C" {
    smiv2:oid "1.3.6.1.4.1.9.1.175";
  }

  smiv2:alias "ciscoMicroWebServer2" {
    smiv2:oid "1.3.6.1.4.1.9.1.176";
  }

  smiv2:alias "ciscoFastHubBMMTX" {
    smiv2:oid "1.3.6.1.4.1.9.1.177";
  }

  smiv2:alias "ciscoFastHubBMMFX" {
    smiv2:oid "1.3.6.1.4.1.9.1.178";
  }

  smiv2:alias "ciscoUBR7246" {
    smiv2:oid "1.3.6.1.4.1.9.1.179";
  }

  smiv2:alias "cisco6400" {
    smiv2:oid "1.3.6.1.4.1.9.1.180";
  }

  smiv2:alias "cisco12004" {
    smiv2:oid "1.3.6.1.4.1.9.1.181";
  }

  smiv2:alias "cisco12008" {
    smiv2:oid "1.3.6.1.4.1.9.1.182";
  }

  smiv2:alias "catalyst2924XL" {
    smiv2:oid "1.3.6.1.4.1.9.1.183";
  }

  smiv2:alias "catalyst2924CXL" {
    smiv2:oid "1.3.6.1.4.1.9.1.184";
  }

  smiv2:alias "cisco2610" {
    smiv2:oid "1.3.6.1.4.1.9.1.185";
  }

  smiv2:alias "cisco2611" {
    smiv2:oid "1.3.6.1.4.1.9.1.186";
  }

  smiv2:alias "cisco2612" {
    smiv2:oid "1.3.6.1.4.1.9.1.187";
  }

  smiv2:alias "ciscoAS5800" {
    smiv2:oid "1.3.6.1.4.1.9.1.188";
  }

  smiv2:alias "ciscoSC3640" {
    smiv2:oid "1.3.6.1.4.1.9.1.189";
  }

  smiv2:alias "cisco8510" {
    smiv2:oid "1.3.6.1.4.1.9.1.190";
  }

  smiv2:alias "ciscoUBR904" {
    smiv2:oid "1.3.6.1.4.1.9.1.191";
  }

  smiv2:alias "cisco6200" {
    smiv2:oid "1.3.6.1.4.1.9.1.192";
  }

  smiv2:alias "cisco7202" {
    smiv2:oid "1.3.6.1.4.1.9.1.194";
  }

  smiv2:alias "cisco2613" {
    smiv2:oid "1.3.6.1.4.1.9.1.195";
  }

  smiv2:alias "cisco8515" {
    smiv2:oid "1.3.6.1.4.1.9.1.196";
  }

  smiv2:alias "catalyst9006" {
    smiv2:oid "1.3.6.1.4.1.9.1.197";
  }

  smiv2:alias "catalyst9009" {
    smiv2:oid "1.3.6.1.4.1.9.1.198";
  }

  smiv2:alias "ciscoRPM" {
    smiv2:oid "1.3.6.1.4.1.9.1.199";
  }

  smiv2:alias "cisco1710" {
    smiv2:oid "1.3.6.1.4.1.9.1.200";
  }

  smiv2:alias "cisco1720" {
    smiv2:oid "1.3.6.1.4.1.9.1.201";
  }

  smiv2:alias "catalyst8540msr" {
    smiv2:oid "1.3.6.1.4.1.9.1.202";
  }

  smiv2:alias "catalyst8540csr" {
    smiv2:oid "1.3.6.1.4.1.9.1.203";
  }

  smiv2:alias "cisco7576" {
    smiv2:oid "1.3.6.1.4.1.9.1.204";
  }

  smiv2:alias "cisco3660" {
    smiv2:oid "1.3.6.1.4.1.9.1.205";
  }

  smiv2:alias "cisco1401" {
    smiv2:oid "1.3.6.1.4.1.9.1.206";
  }

  smiv2:alias "cisco2620" {
    smiv2:oid "1.3.6.1.4.1.9.1.208";
  }

  smiv2:alias "cisco2621" {
    smiv2:oid "1.3.6.1.4.1.9.1.209";
  }

  smiv2:alias "ciscoUBR7223" {
    smiv2:oid "1.3.6.1.4.1.9.1.210";
  }

  smiv2:alias "cisco6400Nrp" {
    smiv2:oid "1.3.6.1.4.1.9.1.211";
  }

  smiv2:alias "cisco801" {
    smiv2:oid "1.3.6.1.4.1.9.1.212";
  }

  smiv2:alias "cisco802" {
    smiv2:oid "1.3.6.1.4.1.9.1.213";
  }

  smiv2:alias "cisco803" {
    smiv2:oid "1.3.6.1.4.1.9.1.214";
  }

  smiv2:alias "cisco804" {
    smiv2:oid "1.3.6.1.4.1.9.1.215";
  }

  smiv2:alias "cisco1750" {
    smiv2:oid "1.3.6.1.4.1.9.1.216";
  }

  smiv2:alias "catalyst2924XLv" {
    smiv2:oid "1.3.6.1.4.1.9.1.217";
  }

  smiv2:alias "catalyst2924CXLv" {
    smiv2:oid "1.3.6.1.4.1.9.1.218";
  }

  smiv2:alias "catalyst2912XL" {
    smiv2:oid "1.3.6.1.4.1.9.1.219";
  }

  smiv2:alias "catalyst2924MXL" {
    smiv2:oid "1.3.6.1.4.1.9.1.220";
  }

  smiv2:alias "catalyst2912MfXL" {
    smiv2:oid "1.3.6.1.4.1.9.1.221";
  }

  smiv2:alias "cisco7206VXR" {
    smiv2:oid "1.3.6.1.4.1.9.1.222";
  }

  smiv2:alias "cisco7204VXR" {
    smiv2:oid "1.3.6.1.4.1.9.1.223";
  }

  smiv2:alias "cisco1538M" {
    smiv2:oid "1.3.6.1.4.1.9.1.224";
  }

  smiv2:alias "cisco1548M" {
    smiv2:oid "1.3.6.1.4.1.9.1.225";
  }

  smiv2:alias "ciscoFasthub100" {
    smiv2:oid "1.3.6.1.4.1.9.1.226";
  }

  smiv2:alias "ciscoPIXFirewall" {
    smiv2:oid "1.3.6.1.4.1.9.1.227";
  }

  smiv2:alias "ciscoMGX8850" {
    smiv2:oid "1.3.6.1.4.1.9.1.228";
  }

  smiv2:alias "ciscoMGX8830" {
    smiv2:oid "1.3.6.1.4.1.9.1.229";
  }

  smiv2:alias "catalyst8510msr" {
    smiv2:oid "1.3.6.1.4.1.9.1.230";
  }

  smiv2:alias "catalyst8515msr" {
    smiv2:oid "1.3.6.1.4.1.9.1.231";
  }

  smiv2:alias "ciscoIGX8410" {
    smiv2:oid "1.3.6.1.4.1.9.1.232";
  }

  smiv2:alias "ciscoIGX8420" {
    smiv2:oid "1.3.6.1.4.1.9.1.233";
  }

  smiv2:alias "ciscoIGX8430" {
    smiv2:oid "1.3.6.1.4.1.9.1.234";
  }

  smiv2:alias "ciscoIGX8450" {
    smiv2:oid "1.3.6.1.4.1.9.1.235";
  }

  smiv2:alias "ciscoBPX8620" {
    smiv2:oid "1.3.6.1.4.1.9.1.237";
  }

  smiv2:alias "ciscoBPX8650" {
    smiv2:oid "1.3.6.1.4.1.9.1.238";
  }

  smiv2:alias "ciscoBPX8680" {
    smiv2:oid "1.3.6.1.4.1.9.1.239";
  }

  smiv2:alias "ciscoCacheEngine" {
    smiv2:oid "1.3.6.1.4.1.9.1.240";
  }

  smiv2:alias "ciscoCat6000" {
    smiv2:oid "1.3.6.1.4.1.9.1.241";
  }

  smiv2:alias "ciscoBPXSes" {
    smiv2:oid "1.3.6.1.4.1.9.1.242";
  }

  smiv2:alias "ciscoIGXSes" {
    smiv2:oid "1.3.6.1.4.1.9.1.243";
  }

  smiv2:alias "ciscoLocalDirector" {
    smiv2:oid "1.3.6.1.4.1.9.1.244";
  }

  smiv2:alias "cisco805" {
    smiv2:oid "1.3.6.1.4.1.9.1.245";
  }

  smiv2:alias "catalyst3508GXL" {
    smiv2:oid "1.3.6.1.4.1.9.1.246";
  }

  smiv2:alias "catalyst3512XL" {
    smiv2:oid "1.3.6.1.4.1.9.1.247";
  }

  smiv2:alias "catalyst3524XL" {
    smiv2:oid "1.3.6.1.4.1.9.1.248";
  }

  smiv2:alias "cisco1407" {
    smiv2:oid "1.3.6.1.4.1.9.1.249";
  }

  smiv2:alias "cisco1417" {
    smiv2:oid "1.3.6.1.4.1.9.1.250";
  }

  smiv2:alias "cisco6100" {
    smiv2:oid "1.3.6.1.4.1.9.1.251";
  }

  smiv2:alias "cisco6130" {
    smiv2:oid "1.3.6.1.4.1.9.1.252";
  }

  smiv2:alias "cisco6260" {
    smiv2:oid "1.3.6.1.4.1.9.1.253";
  }

  smiv2:alias "ciscoOpticalRegenerator" {
    smiv2:oid "1.3.6.1.4.1.9.1.254";
  }

  smiv2:alias "ciscoUBR924" {
    smiv2:oid "1.3.6.1.4.1.9.1.255";
  }

  smiv2:alias "ciscoWSX6302Msm" {
    smiv2:oid "1.3.6.1.4.1.9.1.256";
  }

  smiv2:alias "catalyst5kRsfc" {
    smiv2:oid "1.3.6.1.4.1.9.1.257";
  }

  smiv2:alias "catalyst6kMsfc" {
    smiv2:oid "1.3.6.1.4.1.9.1.258";
  }

  smiv2:alias "cisco7120Quadt1" {
    smiv2:oid "1.3.6.1.4.1.9.1.259";
  }

  smiv2:alias "cisco7120T3" {
    smiv2:oid "1.3.6.1.4.1.9.1.260";
  }

  smiv2:alias "cisco7120E3" {
    smiv2:oid "1.3.6.1.4.1.9.1.261";
  }

  smiv2:alias "cisco7120At3" {
    smiv2:oid "1.3.6.1.4.1.9.1.262";
  }

  smiv2:alias "cisco7120Ae3" {
    smiv2:oid "1.3.6.1.4.1.9.1.263";
  }

  smiv2:alias "cisco7120Smi3" {
    smiv2:oid "1.3.6.1.4.1.9.1.264";
  }

  smiv2:alias "cisco7140Dualt3" {
    smiv2:oid "1.3.6.1.4.1.9.1.265";
  }

  smiv2:alias "cisco7140Duale3" {
    smiv2:oid "1.3.6.1.4.1.9.1.266";
  }

  smiv2:alias "cisco7140Dualat3" {
    smiv2:oid "1.3.6.1.4.1.9.1.267";
  }

  smiv2:alias "cisco7140Dualae3" {
    smiv2:oid "1.3.6.1.4.1.9.1.268";
  }

  smiv2:alias "cisco7140Dualmm3" {
    smiv2:oid "1.3.6.1.4.1.9.1.269";
  }

  smiv2:alias "cisco827QuadV" {
    smiv2:oid "1.3.6.1.4.1.9.1.270";
  }

  smiv2:alias "ciscoUBR7246VXR" {
    smiv2:oid "1.3.6.1.4.1.9.1.271";
  }

  smiv2:alias "cisco10400" {
    smiv2:oid "1.3.6.1.4.1.9.1.272";
  }

  smiv2:alias "cisco12016" {
    smiv2:oid "1.3.6.1.4.1.9.1.273";
  }

  smiv2:alias "ciscoAs5400" {
    smiv2:oid "1.3.6.1.4.1.9.1.274";
  }

  smiv2:alias "cat2948gL3" {
    smiv2:oid "1.3.6.1.4.1.9.1.275";
  }

  smiv2:alias "cisco7140Octt1" {
    smiv2:oid "1.3.6.1.4.1.9.1.276";
  }

  smiv2:alias "cisco7140Dualfe" {
    smiv2:oid "1.3.6.1.4.1.9.1.277";
  }

  smiv2:alias "cat3548XL" {
    smiv2:oid "1.3.6.1.4.1.9.1.278";
  }

  smiv2:alias "ciscoVG200" {
    smiv2:oid "1.3.6.1.4.1.9.1.279";
  }

  smiv2:alias "cat6006" {
    smiv2:oid "1.3.6.1.4.1.9.1.280";
  }

  smiv2:alias "cat6009" {
    smiv2:oid "1.3.6.1.4.1.9.1.281";
  }

  smiv2:alias "cat6506" {
    smiv2:oid "1.3.6.1.4.1.9.1.282";
  }

  smiv2:alias "cat6509" {
    smiv2:oid "1.3.6.1.4.1.9.1.283";
  }

  smiv2:alias "cisco827" {
    smiv2:oid "1.3.6.1.4.1.9.1.284";
  }

  smiv2:alias "ciscoManagementEngine1100" {
    smiv2:oid "1.3.6.1.4.1.9.1.285";
  }

  smiv2:alias "ciscoMc3810V3" {
    smiv2:oid "1.3.6.1.4.1.9.1.286";
  }

  smiv2:alias "cat3524tXLEn" {
    smiv2:oid "1.3.6.1.4.1.9.1.287";
  }

  smiv2:alias "cisco7507z" {
    smiv2:oid "1.3.6.1.4.1.9.1.288";
  }

  smiv2:alias "cisco7513z" {
    smiv2:oid "1.3.6.1.4.1.9.1.289";
  }

  smiv2:alias "cisco7507mx" {
    smiv2:oid "1.3.6.1.4.1.9.1.290";
  }

  smiv2:alias "cisco7513mx" {
    smiv2:oid "1.3.6.1.4.1.9.1.291";
  }

  smiv2:alias "ciscoUBR912C" {
    smiv2:oid "1.3.6.1.4.1.9.1.292";
  }

  smiv2:alias "ciscoUBR912S" {
    smiv2:oid "1.3.6.1.4.1.9.1.293";
  }

  smiv2:alias "ciscoUBR914" {
    smiv2:oid "1.3.6.1.4.1.9.1.294";
  }

  smiv2:alias "cisco802J" {
    smiv2:oid "1.3.6.1.4.1.9.1.295";
  }

  smiv2:alias "cisco804J" {
    smiv2:oid "1.3.6.1.4.1.9.1.296";
  }

  smiv2:alias "cisco6160" {
    smiv2:oid "1.3.6.1.4.1.9.1.297";
  }

  smiv2:alias "cat4908gL3" {
    smiv2:oid "1.3.6.1.4.1.9.1.298";
  }

  smiv2:alias "cisco6015" {
    smiv2:oid "1.3.6.1.4.1.9.1.299";
  }

  smiv2:alias "cat4232L3" {
    smiv2:oid "1.3.6.1.4.1.9.1.300";
  }

  smiv2:alias "catalyst6kMsfc2" {
    smiv2:oid "1.3.6.1.4.1.9.1.301";
  }

  smiv2:alias "cisco7750Mrp200" {
    smiv2:oid "1.3.6.1.4.1.9.1.302";
  }

  smiv2:alias "cisco7750Ssp80" {
    smiv2:oid "1.3.6.1.4.1.9.1.303";
  }

  smiv2:alias "ciscoMGX8230" {
    smiv2:oid "1.3.6.1.4.1.9.1.304";
  }

  smiv2:alias "ciscoMGX8250" {
    smiv2:oid "1.3.6.1.4.1.9.1.305";
  }

  smiv2:alias "ciscoCVA122" {
    smiv2:oid "1.3.6.1.4.1.9.1.306";
  }

  smiv2:alias "ciscoCVA124" {
    smiv2:oid "1.3.6.1.4.1.9.1.307";
  }

  smiv2:alias "ciscoAs5850" {
    smiv2:oid "1.3.6.1.4.1.9.1.308";
  }

  smiv2:alias "cat6509Sp" {
    smiv2:oid "1.3.6.1.4.1.9.1.310";
  }

  smiv2:alias "ciscoMGX8240" {
    smiv2:oid "1.3.6.1.4.1.9.1.311";
  }

  smiv2:alias "cat4840gL3" {
    smiv2:oid "1.3.6.1.4.1.9.1.312";
  }

  smiv2:alias "ciscoAS5350" {
    smiv2:oid "1.3.6.1.4.1.9.1.313";
  }

  smiv2:alias "cisco7750" {
    smiv2:oid "1.3.6.1.4.1.9.1.314";
  }

  smiv2:alias "ciscoMGX8950" {
    smiv2:oid "1.3.6.1.4.1.9.1.315";
  }

  smiv2:alias "ciscoUBR925" {
    smiv2:oid "1.3.6.1.4.1.9.1.316";
  }

  smiv2:alias "ciscoUBR10012" {
    smiv2:oid "1.3.6.1.4.1.9.1.317";
  }

  smiv2:alias "catalyst4kGateway" {
    smiv2:oid "1.3.6.1.4.1.9.1.318";
  }

  smiv2:alias "cisco2650" {
    smiv2:oid "1.3.6.1.4.1.9.1.319";
  }

  smiv2:alias "cisco2651" {
    smiv2:oid "1.3.6.1.4.1.9.1.320";
  }

  smiv2:alias "cisco826QuadV" {
    smiv2:oid "1.3.6.1.4.1.9.1.321";
  }

  smiv2:alias "cisco826" {
    smiv2:oid "1.3.6.1.4.1.9.1.322";
  }

  smiv2:alias "catalyst295012" {
    smiv2:oid "1.3.6.1.4.1.9.1.323";
  }

  smiv2:alias "catalyst295024" {
    smiv2:oid "1.3.6.1.4.1.9.1.324";
  }

  smiv2:alias "catalyst295024C" {
    smiv2:oid "1.3.6.1.4.1.9.1.325";
  }

  smiv2:alias "cisco1751" {
    smiv2:oid "1.3.6.1.4.1.9.1.326";
  }

  smiv2:alias "cisco1730Iad8Fxs" {
    smiv2:oid "1.3.6.1.4.1.9.1.327";
  }

  smiv2:alias "cisco1730Iad16Fxs" {
    smiv2:oid "1.3.6.1.4.1.9.1.328";
  }

  smiv2:alias "cisco626" {
    smiv2:oid "1.3.6.1.4.1.9.1.329";
  }

  smiv2:alias "cisco627" {
    smiv2:oid "1.3.6.1.4.1.9.1.330";
  }

  smiv2:alias "cisco633" {
    smiv2:oid "1.3.6.1.4.1.9.1.331";
  }

  smiv2:alias "cisco673" {
    smiv2:oid "1.3.6.1.4.1.9.1.332";
  }

  smiv2:alias "cisco675" {
    smiv2:oid "1.3.6.1.4.1.9.1.333";
  }

  smiv2:alias "cisco675e" {
    smiv2:oid "1.3.6.1.4.1.9.1.334";
  }

  smiv2:alias "cisco676" {
    smiv2:oid "1.3.6.1.4.1.9.1.335";
  }

  smiv2:alias "cisco677" {
    smiv2:oid "1.3.6.1.4.1.9.1.336";
  }

  smiv2:alias "cisco678" {
    smiv2:oid "1.3.6.1.4.1.9.1.337";
  }

  smiv2:alias "cisco3661Ac" {
    smiv2:oid "1.3.6.1.4.1.9.1.338";
  }

  smiv2:alias "cisco3661Dc" {
    smiv2:oid "1.3.6.1.4.1.9.1.339";
  }

  smiv2:alias "cisco3662Ac" {
    smiv2:oid "1.3.6.1.4.1.9.1.340";
  }

  smiv2:alias "cisco3662Dc" {
    smiv2:oid "1.3.6.1.4.1.9.1.341";
  }

  smiv2:alias "cisco3662AcCo" {
    smiv2:oid "1.3.6.1.4.1.9.1.342";
  }

  smiv2:alias "cisco3662DcCo" {
    smiv2:oid "1.3.6.1.4.1.9.1.343";
  }

  smiv2:alias "ciscoUBR7111" {
    smiv2:oid "1.3.6.1.4.1.9.1.344";
  }

  smiv2:alias "ciscoUBR7111E" {
    smiv2:oid "1.3.6.1.4.1.9.1.345";
  }

  smiv2:alias "ciscoUBR7114" {
    smiv2:oid "1.3.6.1.4.1.9.1.346";
  }

  smiv2:alias "ciscoUBR7114E" {
    smiv2:oid "1.3.6.1.4.1.9.1.347";
  }

  smiv2:alias "cisco12010" {
    smiv2:oid "1.3.6.1.4.1.9.1.348";
  }

  smiv2:alias "cisco8110" {
    smiv2:oid "1.3.6.1.4.1.9.1.349";
  }

  smiv2:alias "cisco8120" {
    smiv2:oid "1.3.6.1.4.1.9.1.350";
  }

  smiv2:alias "ciscoUBR905" {
    smiv2:oid "1.3.6.1.4.1.9.1.351";
  }

  smiv2:alias "ciscoIDS" {
    smiv2:oid "1.3.6.1.4.1.9.1.352";
  }

  smiv2:alias "ciscoSOHO77" {
    smiv2:oid "1.3.6.1.4.1.9.1.353";
  }

  smiv2:alias "ciscoSOHO76" {
    smiv2:oid "1.3.6.1.4.1.9.1.354";
  }

  smiv2:alias "cisco7150Dualfe" {
    smiv2:oid "1.3.6.1.4.1.9.1.355";
  }

  smiv2:alias "cisco7150Octt1" {
    smiv2:oid "1.3.6.1.4.1.9.1.356";
  }

  smiv2:alias "cisco7150Dualt3" {
    smiv2:oid "1.3.6.1.4.1.9.1.357";
  }

  smiv2:alias "ciscoOlympus" {
    smiv2:oid "1.3.6.1.4.1.9.1.358";
  }

  smiv2:alias "catalyst2950t24" {
    smiv2:oid "1.3.6.1.4.1.9.1.359";
  }

  smiv2:alias "ciscoVPS1110" {
    smiv2:oid "1.3.6.1.4.1.9.1.360";
  }

  smiv2:alias "ciscoContentEngine" {
    smiv2:oid "1.3.6.1.4.1.9.1.361";
  }

  smiv2:alias "ciscoIAD2420" {
    smiv2:oid "1.3.6.1.4.1.9.1.362";
  }

  smiv2:alias "cisco677i" {
    smiv2:oid "1.3.6.1.4.1.9.1.363";
  }

  smiv2:alias "cisco674" {
    smiv2:oid "1.3.6.1.4.1.9.1.364";
  }

  smiv2:alias "ciscoDPA7630" {
    smiv2:oid "1.3.6.1.4.1.9.1.365";
  }

  smiv2:alias "catalyst355024" {
    smiv2:oid "1.3.6.1.4.1.9.1.366";
  }

  smiv2:alias "catalyst355048" {
    smiv2:oid "1.3.6.1.4.1.9.1.367";
  }

  smiv2:alias "catalyst355012T" {
    smiv2:oid "1.3.6.1.4.1.9.1.368";
  }

  smiv2:alias "catalyst2924LREXL" {
    smiv2:oid "1.3.6.1.4.1.9.1.369";
  }

  smiv2:alias "catalyst2912LREXL" {
    smiv2:oid "1.3.6.1.4.1.9.1.370";
  }

  smiv2:alias "ciscoCVA122E" {
    smiv2:oid "1.3.6.1.4.1.9.1.371";
  }

  smiv2:alias "ciscoCVA124E" {
    smiv2:oid "1.3.6.1.4.1.9.1.372";
  }

  smiv2:alias "ciscoURM" {
    smiv2:oid "1.3.6.1.4.1.9.1.373";
  }

  smiv2:alias "ciscoURM2FE" {
    smiv2:oid "1.3.6.1.4.1.9.1.374";
  }

  smiv2:alias "ciscoURM2FE2V" {
    smiv2:oid "1.3.6.1.4.1.9.1.375";
  }

  smiv2:alias "cisco7401VXR" {
    smiv2:oid "1.3.6.1.4.1.9.1.376";
  }

  smiv2:alias "cisco951" {
    smiv2:oid "1.3.6.1.4.1.9.1.377";
  }

  smiv2:alias "cisco952" {
    smiv2:oid "1.3.6.1.4.1.9.1.378";
  }

  smiv2:alias "ciscoCAP340" {
    smiv2:oid "1.3.6.1.4.1.9.1.379";
  }

  smiv2:alias "ciscoCAP350" {
    smiv2:oid "1.3.6.1.4.1.9.1.380";
  }

  smiv2:alias "ciscoDPA7610" {
    smiv2:oid "1.3.6.1.4.1.9.1.381";
  }

  smiv2:alias "cisco828" {
    smiv2:oid "1.3.6.1.4.1.9.1.382";
  }

  smiv2:alias "ciscoSOHO78" {
    smiv2:oid "1.3.6.1.4.1.9.1.383";
  }

  smiv2:alias "cisco806" {
    smiv2:oid "1.3.6.1.4.1.9.1.384";
  }

  smiv2:alias "cisco12416" {
    smiv2:oid "1.3.6.1.4.1.9.1.385";
  }

  smiv2:alias "cat2948gL3Dc" {
    smiv2:oid "1.3.6.1.4.1.9.1.386";
  }

  smiv2:alias "cat4908gL3Dc" {
    smiv2:oid "1.3.6.1.4.1.9.1.387";
  }

  smiv2:alias "cisco12406" {
    smiv2:oid "1.3.6.1.4.1.9.1.388";
  }

  smiv2:alias "ciscoPIXFirewall506" {
    smiv2:oid "1.3.6.1.4.1.9.1.389";
  }

  smiv2:alias "ciscoPIXFirewall515" {
    smiv2:oid "1.3.6.1.4.1.9.1.390";
  }

  smiv2:alias "ciscoPIXFirewall520" {
    smiv2:oid "1.3.6.1.4.1.9.1.391";
  }

  smiv2:alias "ciscoPIXFirewall525" {
    smiv2:oid "1.3.6.1.4.1.9.1.392";
  }

  smiv2:alias "ciscoPIXFirewall535" {
    smiv2:oid "1.3.6.1.4.1.9.1.393";
  }

  smiv2:alias "cisco12410" {
    smiv2:oid "1.3.6.1.4.1.9.1.394";
  }

  smiv2:alias "cisco811" {
    smiv2:oid "1.3.6.1.4.1.9.1.395";
  }

  smiv2:alias "cisco813" {
    smiv2:oid "1.3.6.1.4.1.9.1.396";
  }

  smiv2:alias "cisco10720" {
    smiv2:oid "1.3.6.1.4.1.9.1.397";
  }

  smiv2:alias "ciscoMWR1900" {
    smiv2:oid "1.3.6.1.4.1.9.1.398";
  }

  smiv2:alias "cisco4224" {
    smiv2:oid "1.3.6.1.4.1.9.1.399";
  }

  smiv2:alias "ciscoWSC6513" {
    smiv2:oid "1.3.6.1.4.1.9.1.400";
  }

  smiv2:alias "cisco7603" {
    smiv2:oid "1.3.6.1.4.1.9.1.401";
  }

  smiv2:alias "cisco7606" {
    smiv2:oid "1.3.6.1.4.1.9.1.402";
  }

  smiv2:alias "cisco7401ASR" {
    smiv2:oid "1.3.6.1.4.1.9.1.403";
  }

  smiv2:alias "ciscoVG248" {
    smiv2:oid "1.3.6.1.4.1.9.1.404";
  }

  smiv2:alias "ciscoHSE" {
    smiv2:oid "1.3.6.1.4.1.9.1.405";
  }

  smiv2:alias "ciscoONS15540ESP" {
    smiv2:oid "1.3.6.1.4.1.9.1.406";
  }

  smiv2:alias "ciscoSN5420" {
    smiv2:oid "1.3.6.1.4.1.9.1.407";
  }

  smiv2:alias "ciscoIcs7750Ce300" {
    smiv2:oid "1.3.6.1.4.1.9.1.408";
  }

  smiv2:alias "ciscoCe507" {
    smiv2:oid "1.3.6.1.4.1.9.1.409";
  }

  smiv2:alias "ciscoCe560" {
    smiv2:oid "1.3.6.1.4.1.9.1.410";
  }

  smiv2:alias "ciscoCe590" {
    smiv2:oid "1.3.6.1.4.1.9.1.411";
  }

  smiv2:alias "ciscoCe7320" {
    smiv2:oid "1.3.6.1.4.1.9.1.412";
  }

  smiv2:alias "cisco2691" {
    smiv2:oid "1.3.6.1.4.1.9.1.413";
  }

  smiv2:alias "cisco3725" {
    smiv2:oid "1.3.6.1.4.1.9.1.414";
  }

  smiv2:alias "cisco3640A" {
    smiv2:oid "1.3.6.1.4.1.9.1.415";
  }

  smiv2:alias "cisco1760" {
    smiv2:oid "1.3.6.1.4.1.9.1.416";
  }

  smiv2:alias "ciscoPIXFirewall501" {
    smiv2:oid "1.3.6.1.4.1.9.1.417";
  }

  smiv2:alias "cisco2610M" {
    smiv2:oid "1.3.6.1.4.1.9.1.418";
  }

  smiv2:alias "cisco2611M" {
    smiv2:oid "1.3.6.1.4.1.9.1.419";
  }

  smiv2:alias "ciscoGP10" {
    smiv2:oid "1.3.6.1.4.1.9.1.420";
  }

  smiv2:alias "ciscoMC21" {
    smiv2:oid "1.3.6.1.4.1.9.1.421";
  }

  smiv2:alias "ciscoSN51" {
    smiv2:oid "1.3.6.1.4.1.9.1.422";
  }

  smiv2:alias "cisco12404" {
    smiv2:oid "1.3.6.1.4.1.9.1.423";
  }

  smiv2:alias "cisco9004" {
    smiv2:oid "1.3.6.1.4.1.9.1.424";
  }

  smiv2:alias "cisco3631Co" {
    smiv2:oid "1.3.6.1.4.1.9.1.425";
  }

  smiv2:alias "catalyst295012G" {
    smiv2:oid "1.3.6.1.4.1.9.1.427";
  }

  smiv2:alias "catalyst295024G" {
    smiv2:oid "1.3.6.1.4.1.9.1.428";
  }

  smiv2:alias "catalyst295048G" {
    smiv2:oid "1.3.6.1.4.1.9.1.429";
  }

  smiv2:alias "catalyst295024S" {
    smiv2:oid "1.3.6.1.4.1.9.1.430";
  }

  smiv2:alias "catalyst355012G" {
    smiv2:oid "1.3.6.1.4.1.9.1.431";
  }

  smiv2:alias "ciscoCE507AV" {
    smiv2:oid "1.3.6.1.4.1.9.1.432";
  }

  smiv2:alias "ciscoCE560AV" {
    smiv2:oid "1.3.6.1.4.1.9.1.433";
  }

  smiv2:alias "ciscoIE2105" {
    smiv2:oid "1.3.6.1.4.1.9.1.434";
  }

  smiv2:alias "ciscoMGX8850Pxm1E" {
    smiv2:oid "1.3.6.1.4.1.9.1.435";
  }

  smiv2:alias "cisco3745" {
    smiv2:oid "1.3.6.1.4.1.9.1.436";
  }

  smiv2:alias "cisco10005" {
    smiv2:oid "1.3.6.1.4.1.9.1.437";
  }

  smiv2:alias "cisco10008" {
    smiv2:oid "1.3.6.1.4.1.9.1.438";
  }

  smiv2:alias "cisco7304" {
    smiv2:oid "1.3.6.1.4.1.9.1.439";
  }

  smiv2:alias "ciscoRpmXf" {
    smiv2:oid "1.3.6.1.4.1.9.1.440";
  }

  smiv2:alias "ciscoOsm4oc3PosSmIr" {
    smiv2:oid "1.3.6.1.4.1.9.1.441";
  }

  smiv2:alias "ciscoOsm4oc3PosMmSr" {
    smiv2:oid "1.3.6.1.4.1.9.1.442";
  }

  smiv2:alias "ciscoOsm4oc3PosSmLr" {
    smiv2:oid "1.3.6.1.4.1.9.1.443";
  }

  smiv2:alias "cisco1721" {
    smiv2:oid "1.3.6.1.4.1.9.1.444";
  }

  smiv2:alias "cat4000Sup3" {
    smiv2:oid "1.3.6.1.4.1.9.1.445";
  }

  smiv2:alias "cisco827H" {
    smiv2:oid "1.3.6.1.4.1.9.1.446";
  }

  smiv2:alias "ciscoSOHO77H" {
    smiv2:oid "1.3.6.1.4.1.9.1.447";
  }

  smiv2:alias "cat4006" {
    smiv2:oid "1.3.6.1.4.1.9.1.448";
  }

  smiv2:alias "ciscoWSC6503" {
    smiv2:oid "1.3.6.1.4.1.9.1.449";
  }

  smiv2:alias "ciscoPIXFirewall506E" {
    smiv2:oid "1.3.6.1.4.1.9.1.450";
  }

  smiv2:alias "ciscoPIXFirewall515E" {
    smiv2:oid "1.3.6.1.4.1.9.1.451";
  }

  smiv2:alias "cat355024Dc" {
    smiv2:oid "1.3.6.1.4.1.9.1.452";
  }

  smiv2:alias "cat355024Mmf" {
    smiv2:oid "1.3.6.1.4.1.9.1.453";
  }

  smiv2:alias "ciscoCE2636" {
    smiv2:oid "1.3.6.1.4.1.9.1.454";
  }

  smiv2:alias "ciscoDwCE" {
    smiv2:oid "1.3.6.1.4.1.9.1.455";
  }

  smiv2:alias "cisco7750Mrp300" {
    smiv2:oid "1.3.6.1.4.1.9.1.456";
  }

  smiv2:alias "ciscoRPMPR" {
    smiv2:oid "1.3.6.1.4.1.9.1.457";
  }

  smiv2:alias "cisco14MGX8830Pxm1E" {
    smiv2:oid "1.3.6.1.4.1.9.1.458";
  }

  smiv2:alias "ciscoWlse" {
    smiv2:oid "1.3.6.1.4.1.9.1.459";
  }

  smiv2:alias "ciscoONS15530" {
    smiv2:oid "1.3.6.1.4.1.9.1.460";
  }

  smiv2:alias "ciscoONS15530NEBS" {
    smiv2:oid "1.3.6.1.4.1.9.1.461";
  }

  smiv2:alias "ciscoONS15530ETSI" {
    smiv2:oid "1.3.6.1.4.1.9.1.462";
  }

  smiv2:alias "ciscoSOHO71" {
    smiv2:oid "1.3.6.1.4.1.9.1.463";
  }

  smiv2:alias "cisco6400UAC" {
    smiv2:oid "1.3.6.1.4.1.9.1.464";
  }

  smiv2:alias "cisco2610XM" {
    smiv2:oid "1.3.6.1.4.1.9.1.466";
  }

  smiv2:alias "cisco2611XM" {
    smiv2:oid "1.3.6.1.4.1.9.1.467";
  }

  smiv2:alias "cisco2620XM" {
    smiv2:oid "1.3.6.1.4.1.9.1.468";
  }

  smiv2:alias "cisco2621XM" {
    smiv2:oid "1.3.6.1.4.1.9.1.469";
  }

  smiv2:alias "cisco2650XM" {
    smiv2:oid "1.3.6.1.4.1.9.1.470";
  }

  smiv2:alias "cisco2651XM" {
    smiv2:oid "1.3.6.1.4.1.9.1.471";
  }

  smiv2:alias "catalyst295024GDC" {
    smiv2:oid "1.3.6.1.4.1.9.1.472";
  }

  smiv2:alias "ciscoAIRAP1200" {
    smiv2:oid "1.3.6.1.4.1.9.1.474";
  }

  smiv2:alias "ciscoSN5428" {
    smiv2:oid "1.3.6.1.4.1.9.1.475";
  }

  smiv2:alias "cisco7301" {
    smiv2:oid "1.3.6.1.4.1.9.1.476";
  }

  smiv2:alias "cisco12816" {
    smiv2:oid "1.3.6.1.4.1.9.1.477";
  }

  smiv2:alias "cisco12810" {
    smiv2:oid "1.3.6.1.4.1.9.1.478";
  }

  smiv2:alias "cisco3250" {
    smiv2:oid "1.3.6.1.4.1.9.1.479";
  }

  smiv2:alias "catalyst295024SX" {
    smiv2:oid "1.3.6.1.4.1.9.1.480";
  }

  smiv2:alias "ciscoONS15540ESPx" {
    smiv2:oid "1.3.6.1.4.1.9.1.481";
  }

  smiv2:alias "catalyst295024LRESt" {
    smiv2:oid "1.3.6.1.4.1.9.1.482";
  }

  smiv2:alias "catalyst29508LRESt" {
    smiv2:oid "1.3.6.1.4.1.9.1.483";
  }

  smiv2:alias "catalyst295024LREG" {
    smiv2:oid "1.3.6.1.4.1.9.1.484";
  }

  smiv2:alias "catalyst355024PWR" {
    smiv2:oid "1.3.6.1.4.1.9.1.485";
  }

  smiv2:alias "ciscoCDM4630" {
    smiv2:oid "1.3.6.1.4.1.9.1.486";
  }

  smiv2:alias "ciscoCDM4650" {
    smiv2:oid "1.3.6.1.4.1.9.1.487";
  }

  smiv2:alias "catalyst2955T12" {
    smiv2:oid "1.3.6.1.4.1.9.1.488";
  }

  smiv2:alias "catalyst2955C12" {
    smiv2:oid "1.3.6.1.4.1.9.1.489";
  }

  smiv2:alias "ciscoCE508" {
    smiv2:oid "1.3.6.1.4.1.9.1.490";
  }

  smiv2:alias "ciscoCE565" {
    smiv2:oid "1.3.6.1.4.1.9.1.491";
  }

  smiv2:alias "ciscoCE7325" {
    smiv2:oid "1.3.6.1.4.1.9.1.492";
  }

  smiv2:alias "ciscoONS15454" {
    smiv2:oid "1.3.6.1.4.1.9.1.493";
  }

  smiv2:alias "ciscoONS15327" {
    smiv2:oid "1.3.6.1.4.1.9.1.494";
  }

  smiv2:alias "cisco837" {
    smiv2:oid "1.3.6.1.4.1.9.1.495";
  }

  smiv2:alias "ciscoSOHO97" {
    smiv2:oid "1.3.6.1.4.1.9.1.496";
  }

  smiv2:alias "cisco831" {
    smiv2:oid "1.3.6.1.4.1.9.1.497";
  }

  smiv2:alias "ciscoSOHO91" {
    smiv2:oid "1.3.6.1.4.1.9.1.498";
  }

  smiv2:alias "cisco836" {
    smiv2:oid "1.3.6.1.4.1.9.1.499";
  }

  smiv2:alias "ciscoSOHO96" {
    smiv2:oid "1.3.6.1.4.1.9.1.500";
  }

  smiv2:alias "cat4507" {
    smiv2:oid "1.3.6.1.4.1.9.1.501";
  }

  smiv2:alias "cat4506" {
    smiv2:oid "1.3.6.1.4.1.9.1.502";
  }

  smiv2:alias "cat4503" {
    smiv2:oid "1.3.6.1.4.1.9.1.503";
  }

  smiv2:alias "ciscoCE7305" {
    smiv2:oid "1.3.6.1.4.1.9.1.504";
  }

  smiv2:alias "ciscoCE510" {
    smiv2:oid "1.3.6.1.4.1.9.1.505";
  }

  smiv2:alias "ciscoAIRAP1100" {
    smiv2:oid "1.3.6.1.4.1.9.1.507";
  }

  smiv2:alias "catalyst2955S12" {
    smiv2:oid "1.3.6.1.4.1.9.1.508";
  }

  smiv2:alias "cisco7609" {
    smiv2:oid "1.3.6.1.4.1.9.1.509";
  }

  smiv2:alias "ciscoWSC65509" {
    smiv2:oid "1.3.6.1.4.1.9.1.510";
  }

  smiv2:alias "catalyst375024" {
    smiv2:oid "1.3.6.1.4.1.9.1.511";
  }

  smiv2:alias "catalyst375048" {
    smiv2:oid "1.3.6.1.4.1.9.1.512";
  }

  smiv2:alias "catalyst375024TS" {
    smiv2:oid "1.3.6.1.4.1.9.1.513";
  }

  smiv2:alias "catalyst375024T" {
    smiv2:oid "1.3.6.1.4.1.9.1.514";
  }

  smiv2:alias "catalyst37xxStack" {
    smiv2:oid "1.3.6.1.4.1.9.1.516";
  }

  smiv2:alias "ciscoGSS" {
    smiv2:oid "1.3.6.1.4.1.9.1.517";
  }

  smiv2:alias "ciscoPrimaryGSSM" {
    smiv2:oid "1.3.6.1.4.1.9.1.518";
  }

  smiv2:alias "ciscoStandbyGSSM" {
    smiv2:oid "1.3.6.1.4.1.9.1.519";
  }

  smiv2:alias "ciscoMWR1941DC" {
    smiv2:oid "1.3.6.1.4.1.9.1.520";
  }

  smiv2:alias "ciscoDSC9216K9" {
    smiv2:oid "1.3.6.1.4.1.9.1.521";
  }

  smiv2:alias "cat6500FirewallSm" {
    smiv2:oid "1.3.6.1.4.1.9.1.522";
  }

  smiv2:alias "ciscoSCA11000" {
    smiv2:oid "1.3.6.1.4.1.9.1.523";
  }

  smiv2:alias "ciscoCSM" {
    smiv2:oid "1.3.6.1.4.1.9.1.524";
  }

  smiv2:alias "ciscoAIRAP1210" {
    smiv2:oid "1.3.6.1.4.1.9.1.525";
  }

  smiv2:alias "ciscoSCA211000" {
    smiv2:oid "1.3.6.1.4.1.9.1.526";
  }

  smiv2:alias "catalyst297024" {
    smiv2:oid "1.3.6.1.4.1.9.1.527";
  }

  smiv2:alias "cisco7613" {
    smiv2:oid "1.3.6.1.4.1.9.1.528";
  }

  smiv2:alias "ciscoSN54282" {
    smiv2:oid "1.3.6.1.4.1.9.1.529";
  }

  smiv2:alias "catalyst3750Ge12Sfp" {
    smiv2:oid "1.3.6.1.4.1.9.1.530";
  }

  smiv2:alias "ciscoCR4430" {
    smiv2:oid "1.3.6.1.4.1.9.1.531";
  }

  smiv2:alias "ciscoCR4450" {
    smiv2:oid "1.3.6.1.4.1.9.1.532";
  }

  smiv2:alias "ciscoAIRBR1410" {
    smiv2:oid "1.3.6.1.4.1.9.1.533";
  }

  smiv2:alias "ciscoWSC6509neba" {
    smiv2:oid "1.3.6.1.4.1.9.1.534";
  }

  smiv2:alias "catalyst375048PS" {
    smiv2:oid "1.3.6.1.4.1.9.1.535";
  }

  smiv2:alias "catalyst375024PS" {
    smiv2:oid "1.3.6.1.4.1.9.1.536";
  }

  smiv2:alias "catalyst4510" {
    smiv2:oid "1.3.6.1.4.1.9.1.537";
  }

  smiv2:alias "cisco1711" {
    smiv2:oid "1.3.6.1.4.1.9.1.538";
  }

  smiv2:alias "cisco1712" {
    smiv2:oid "1.3.6.1.4.1.9.1.539";
  }

  smiv2:alias "catalyst29408TT" {
    smiv2:oid "1.3.6.1.4.1.9.1.540";
  }

  smiv2:alias "catalyst29408TF" {
    smiv2:oid "1.3.6.1.4.1.9.1.542";
  }

  smiv2:alias "cisco3825" {
    smiv2:oid "1.3.6.1.4.1.9.1.543";
  }

  smiv2:alias "cisco3845" {
    smiv2:oid "1.3.6.1.4.1.9.1.544";
  }

  smiv2:alias "cisco2430Iad24Fxs" {
    smiv2:oid "1.3.6.1.4.1.9.1.545";
  }

  smiv2:alias "cisco2431Iad8Fxs" {
    smiv2:oid "1.3.6.1.4.1.9.1.546";
  }

  smiv2:alias "cisco2431Iad16Fxs" {
    smiv2:oid "1.3.6.1.4.1.9.1.547";
  }

  smiv2:alias "cisco2431Iad1T1E1" {
    smiv2:oid "1.3.6.1.4.1.9.1.548";
  }

  smiv2:alias "cisco2432Iad24Fxs" {
    smiv2:oid "1.3.6.1.4.1.9.1.549";
  }

  smiv2:alias "cisco1701ADSLBRI" {
    smiv2:oid "1.3.6.1.4.1.9.1.550";
  }

  smiv2:alias "catalyst2950St24LRE997" {
    smiv2:oid "1.3.6.1.4.1.9.1.551";
  }

  smiv2:alias "ciscoAirAp350IOS" {
    smiv2:oid "1.3.6.1.4.1.9.1.552";
  }

  smiv2:alias "cisco3220" {
    smiv2:oid "1.3.6.1.4.1.9.1.553";
  }

  smiv2:alias "cat6500SslSm" {
    smiv2:oid "1.3.6.1.4.1.9.1.554";
  }

  smiv2:alias "ciscoSIMSE" {
    smiv2:oid "1.3.6.1.4.1.9.1.555";
  }

  smiv2:alias "ciscoESSE" {
    smiv2:oid "1.3.6.1.4.1.9.1.556";
  }

  smiv2:alias "catalyst6kSup720" {
    smiv2:oid "1.3.6.1.4.1.9.1.557";
  }

  smiv2:alias "ciscoVG224" {
    smiv2:oid "1.3.6.1.4.1.9.1.558";
  }

  smiv2:alias "catalyst295048T" {
    smiv2:oid "1.3.6.1.4.1.9.1.559";
  }

  smiv2:alias "catalyst295048SX" {
    smiv2:oid "1.3.6.1.4.1.9.1.560";
  }

  smiv2:alias "catalyst297024TS" {
    smiv2:oid "1.3.6.1.4.1.9.1.561";
  }

  smiv2:alias "ciscoNmNam" {
    smiv2:oid "1.3.6.1.4.1.9.1.562";
  }

  smiv2:alias "catalyst356024PS" {
    smiv2:oid "1.3.6.1.4.1.9.1.563";
  }

  smiv2:alias "catalyst356048PS" {
    smiv2:oid "1.3.6.1.4.1.9.1.564";
  }

  smiv2:alias "ciscoAIRBR1300" {
    smiv2:oid "1.3.6.1.4.1.9.1.565";
  }

  smiv2:alias "cisco851" {
    smiv2:oid "1.3.6.1.4.1.9.1.566";
  }

  smiv2:alias "cisco857" {
    smiv2:oid "1.3.6.1.4.1.9.1.567";
  }

  smiv2:alias "cisco876" {
    smiv2:oid "1.3.6.1.4.1.9.1.568";
  }

  smiv2:alias "cisco877" {
    smiv2:oid "1.3.6.1.4.1.9.1.569";
  }

  smiv2:alias "cisco878" {
    smiv2:oid "1.3.6.1.4.1.9.1.570";
  }

  smiv2:alias "cisco871" {
    smiv2:oid "1.3.6.1.4.1.9.1.571";
  }

  smiv2:alias "uMG9820" {
    smiv2:oid "1.3.6.1.4.1.9.1.572";
  }

  smiv2:alias "catalyst6kGateway" {
    smiv2:oid "1.3.6.1.4.1.9.1.573";
  }

  smiv2:alias "catalyst375024ME" {
    smiv2:oid "1.3.6.1.4.1.9.1.574";
  }

  smiv2:alias "catalyst4000NAM" {
    smiv2:oid "1.3.6.1.4.1.9.1.575";
  }

  smiv2:alias "cisco2811" {
    smiv2:oid "1.3.6.1.4.1.9.1.576";
  }

  smiv2:alias "cisco2821" {
    smiv2:oid "1.3.6.1.4.1.9.1.577";
  }

  smiv2:alias "cisco2851" {
    smiv2:oid "1.3.6.1.4.1.9.1.578";
  }

  smiv2:alias "cisco3201WMIC" {
    smiv2:oid "1.3.6.1.4.1.9.1.581";
  }

  smiv2:alias "ciscoMCS7815I" {
    smiv2:oid "1.3.6.1.4.1.9.1.582";
  }

  smiv2:alias "ciscoMCS7825H" {
    smiv2:oid "1.3.6.1.4.1.9.1.583";
  }

  smiv2:alias "ciscoMCS7835H" {
    smiv2:oid "1.3.6.1.4.1.9.1.584";
  }

  smiv2:alias "ciscoMCS7835I" {
    smiv2:oid "1.3.6.1.4.1.9.1.585";
  }

  smiv2:alias "ciscoMCS7845H" {
    smiv2:oid "1.3.6.1.4.1.9.1.586";
  }

  smiv2:alias "ciscoMCS7845I" {
    smiv2:oid "1.3.6.1.4.1.9.1.587";
  }

  smiv2:alias "ciscoMCS7855I" {
    smiv2:oid "1.3.6.1.4.1.9.1.588";
  }

  smiv2:alias "ciscoMCS7865I" {
    smiv2:oid "1.3.6.1.4.1.9.1.589";
  }

  smiv2:alias "cisco12006" {
    smiv2:oid "1.3.6.1.4.1.9.1.590";
  }

  smiv2:alias "catalyst3750G16TD" {
    smiv2:oid "1.3.6.1.4.1.9.1.591";
  }

  smiv2:alias "ciscoIGESM" {
    smiv2:oid "1.3.6.1.4.1.9.1.592";
  }

  smiv2:alias "ciscoCCM" {
    smiv2:oid "1.3.6.1.4.1.9.1.593";
  }

  smiv2:alias "cisco1718" {
    smiv2:oid "1.3.6.1.4.1.9.1.594";
  }

  smiv2:alias "ciscoCe511K9" {
    smiv2:oid "1.3.6.1.4.1.9.1.595";
  }

  smiv2:alias "ciscoCe566K9" {
    smiv2:oid "1.3.6.1.4.1.9.1.596";
  }

  smiv2:alias "ciscoMGX8830Pxm45" {
    smiv2:oid "1.3.6.1.4.1.9.1.597";
  }

  smiv2:alias "ciscoMGX8880" {
    smiv2:oid "1.3.6.1.4.1.9.1.598";
  }

  smiv2:alias "ciscoWsSvcWLAN1K9" {
    smiv2:oid "1.3.6.1.4.1.9.1.599";
  }

  smiv2:alias "ciscoCe7306K9" {
    smiv2:oid "1.3.6.1.4.1.9.1.600";
  }

  smiv2:alias "ciscoCe7326K9" {
    smiv2:oid "1.3.6.1.4.1.9.1.601";
  }

  smiv2:alias "catalyst3750G24PS" {
    smiv2:oid "1.3.6.1.4.1.9.1.602";
  }

  smiv2:alias "catalyst3750G48PS" {
    smiv2:oid "1.3.6.1.4.1.9.1.603";
  }

  smiv2:alias "catalyst3750G48TS" {
    smiv2:oid "1.3.6.1.4.1.9.1.604";
  }

  smiv2:alias "ciscoBMGX8830Pxm45" {
    smiv2:oid "1.3.6.1.4.1.9.1.606";
  }

  smiv2:alias "ciscoBMGX8830Pxm1E" {
    smiv2:oid "1.3.6.1.4.1.9.1.607";
  }

  smiv2:alias "ciscoBMGX8850Pxm45" {
    smiv2:oid "1.3.6.1.4.1.9.1.608";
  }

  smiv2:alias "ciscoBMGX8850Pxm1E" {
    smiv2:oid "1.3.6.1.4.1.9.1.609";
  }

  smiv2:alias "ciscoSSLCSM" {
    smiv2:oid "1.3.6.1.4.1.9.1.610";
  }

  smiv2:alias "ciscoNetworkRegistrar" {
    smiv2:oid "1.3.6.1.4.1.9.1.611";
  }

  smiv2:alias "ciscoCe501K9" {
    smiv2:oid "1.3.6.1.4.1.9.1.612";
  }

  smiv2:alias "ciscoCRS16S" {
    smiv2:oid "1.3.6.1.4.1.9.1.613";
  }

  smiv2:alias "catalyst3560G24PS" {
    smiv2:oid "1.3.6.1.4.1.9.1.614";
  }

  smiv2:alias "catalyst3560G24TS" {
    smiv2:oid "1.3.6.1.4.1.9.1.615";
  }

  smiv2:alias "catalyst3560G48PS" {
    smiv2:oid "1.3.6.1.4.1.9.1.616";
  }

  smiv2:alias "catalyst3560G48TS" {
    smiv2:oid "1.3.6.1.4.1.9.1.617";
  }

  smiv2:alias "ciscoAIRAP1130" {
    smiv2:oid "1.3.6.1.4.1.9.1.618";
  }

  smiv2:alias "cisco2801" {
    smiv2:oid "1.3.6.1.4.1.9.1.619";
  }

  smiv2:alias "cisco1841" {
    smiv2:oid "1.3.6.1.4.1.9.1.620";
  }

  smiv2:alias "ciscoWsSvcMWAM1" {
    smiv2:oid "1.3.6.1.4.1.9.1.621";
  }

  smiv2:alias "ciscoNMCUE" {
    smiv2:oid "1.3.6.1.4.1.9.1.622";
  }

  smiv2:alias "ciscoAIMCUE" {
    smiv2:oid "1.3.6.1.4.1.9.1.623";
  }

  smiv2:alias "catalyst3750G24TS1U" {
    smiv2:oid "1.3.6.1.4.1.9.1.624";
  }

  smiv2:alias "cisco371098HP001" {
    smiv2:oid "1.3.6.1.4.1.9.1.625";
  }

  smiv2:alias "catalyst4948" {
    smiv2:oid "1.3.6.1.4.1.9.1.626";
  }

  smiv2:alias "ciscoSB101" {
    smiv2:oid "1.3.6.1.4.1.9.1.627";
  }

  smiv2:alias "ciscoSB106" {
    smiv2:oid "1.3.6.1.4.1.9.1.628";
  }

  smiv2:alias "ciscoSB107" {
    smiv2:oid "1.3.6.1.4.1.9.1.629";
  }

  smiv2:alias "ciscoWLSE1130" {
    smiv2:oid "1.3.6.1.4.1.9.1.630";
  }

  smiv2:alias "ciscoWLSE1030" {
    smiv2:oid "1.3.6.1.4.1.9.1.631";
  }

  smiv2:alias "ciscoHSE1140" {
    smiv2:oid "1.3.6.1.4.1.9.1.632";
  }

  smiv2:alias "catalyst356024TS" {
    smiv2:oid "1.3.6.1.4.1.9.1.633";
  }

  smiv2:alias "catalyst356048TS" {
    smiv2:oid "1.3.6.1.4.1.9.1.634";
  }

  smiv2:alias "ciscoWsSvcadsm1K9" {
    smiv2:oid "1.3.6.1.4.1.9.1.635";
  }

  smiv2:alias "ciscoWsSvcagsm1K9" {
    smiv2:oid "1.3.6.1.4.1.9.1.636";
  }

  smiv2:alias "ciscoONS15310" {
    smiv2:oid "1.3.6.1.4.1.9.1.637";
  }

  smiv2:alias "cisco1801" {
    smiv2:oid "1.3.6.1.4.1.9.1.638";
  }

  smiv2:alias "cisco1802" {
    smiv2:oid "1.3.6.1.4.1.9.1.639";
  }

  smiv2:alias "cisco1803" {
    smiv2:oid "1.3.6.1.4.1.9.1.640";
  }

  smiv2:alias "cisco1811" {
    smiv2:oid "1.3.6.1.4.1.9.1.641";
  }

  smiv2:alias "cisco1812" {
    smiv2:oid "1.3.6.1.4.1.9.1.642";
  }

  smiv2:alias "ciscoCRS8S" {
    smiv2:oid "1.3.6.1.4.1.9.1.643";
  }

  smiv2:alias "ciscoIDS4210" {
    smiv2:oid "1.3.6.1.4.1.9.1.645";
  }

  smiv2:alias "ciscoIDS4215" {
    smiv2:oid "1.3.6.1.4.1.9.1.646";
  }

  smiv2:alias "ciscoIDS4235" {
    smiv2:oid "1.3.6.1.4.1.9.1.647";
  }

  smiv2:alias "ciscoIPS4240" {
    smiv2:oid "1.3.6.1.4.1.9.1.648";
  }

  smiv2:alias "ciscoIDS4250" {
    smiv2:oid "1.3.6.1.4.1.9.1.649";
  }

  smiv2:alias "ciscoIDS4250SX" {
    smiv2:oid "1.3.6.1.4.1.9.1.650";
  }

  smiv2:alias "ciscoIDS4250XL" {
    smiv2:oid "1.3.6.1.4.1.9.1.651";
  }

  smiv2:alias "ciscoIPS4255" {
    smiv2:oid "1.3.6.1.4.1.9.1.652";
  }

  smiv2:alias "ciscoIDSIDSM2" {
    smiv2:oid "1.3.6.1.4.1.9.1.653";
  }

  smiv2:alias "ciscoIDSNMCIDS" {
    smiv2:oid "1.3.6.1.4.1.9.1.654";
  }

  smiv2:alias "ciscoIPSSSM20" {
    smiv2:oid "1.3.6.1.4.1.9.1.655";
  }

  smiv2:alias "catalyst375024FS" {
    smiv2:oid "1.3.6.1.4.1.9.1.656";
  }

  smiv2:alias "ciscoWSC6504E" {
    smiv2:oid "1.3.6.1.4.1.9.1.657";
  }

  smiv2:alias "cisco7604" {
    smiv2:oid "1.3.6.1.4.1.9.1.658";
  }

  smiv2:alias "catalyst494810GE" {
    smiv2:oid "1.3.6.1.4.1.9.1.659";
  }

  smiv2:alias "ciscoIGESMSFP" {
    smiv2:oid "1.3.6.1.4.1.9.1.660";
  }

  smiv2:alias "ciscoFE6326K9" {
    smiv2:oid "1.3.6.1.4.1.9.1.661";
  }

  smiv2:alias "ciscoIPSSSM10" {
    smiv2:oid "1.3.6.1.4.1.9.1.662";
  }

  smiv2:alias "ciscoNme16Es1Ge" {
    smiv2:oid "1.3.6.1.4.1.9.1.663";
  }

  smiv2:alias "ciscoNmeX24Es1Ge" {
    smiv2:oid "1.3.6.1.4.1.9.1.664";
  }

  smiv2:alias "ciscoNmeXd24Es2St" {
    smiv2:oid "1.3.6.1.4.1.9.1.665";
  }

  smiv2:alias "ciscoNmeXd48Es2Ge" {
    smiv2:oid "1.3.6.1.4.1.9.1.666";
  }

  smiv2:alias "cisco3202WMIC" {
    smiv2:oid "1.3.6.1.4.1.9.1.667";
  }

  smiv2:alias "ciscoAs5400XM" {
    smiv2:oid "1.3.6.1.4.1.9.1.668";
  }

  smiv2:alias "ciscoASA5510" {
    smiv2:oid "1.3.6.1.4.1.9.1.669";
  }

  smiv2:alias "ciscoASA5520" {
    smiv2:oid "1.3.6.1.4.1.9.1.670";
  }

  smiv2:alias "ciscoASA5520sc" {
    smiv2:oid "1.3.6.1.4.1.9.1.671";
  }

  smiv2:alias "ciscoASA5540" {
    smiv2:oid "1.3.6.1.4.1.9.1.672";
  }

  smiv2:alias "ciscoASA5540sc" {
    smiv2:oid "1.3.6.1.4.1.9.1.673";
  }

  smiv2:alias "ciscoWsSvcFwm1sc" {
    smiv2:oid "1.3.6.1.4.1.9.1.674";
  }

  smiv2:alias "ciscoPIXFirewall535sc" {
    smiv2:oid "1.3.6.1.4.1.9.1.675";
  }

  smiv2:alias "ciscoPIXFirewall525sc" {
    smiv2:oid "1.3.6.1.4.1.9.1.676";
  }

  smiv2:alias "ciscoPIXFirewall515Esc" {
    smiv2:oid "1.3.6.1.4.1.9.1.677";
  }

  smiv2:alias "ciscoPIXFirewall515sc" {
    smiv2:oid "1.3.6.1.4.1.9.1.678";
  }

  smiv2:alias "ciscoAs5350XM" {
    smiv2:oid "1.3.6.1.4.1.9.1.679";
  }

  smiv2:alias "ciscoFe7326K9" {
    smiv2:oid "1.3.6.1.4.1.9.1.680";
  }

  smiv2:alias "ciscoFe511K9" {
    smiv2:oid "1.3.6.1.4.1.9.1.681";
  }

  smiv2:alias "ciscoSCEDispatcher" {
    smiv2:oid "1.3.6.1.4.1.9.1.682";
  }

  smiv2:alias "ciscoSCE1000" {
    smiv2:oid "1.3.6.1.4.1.9.1.683";
  }

  smiv2:alias "ciscoSCE2000" {
    smiv2:oid "1.3.6.1.4.1.9.1.684";
  }

  smiv2:alias "ciscoAIRAP1240" {
    smiv2:oid "1.3.6.1.4.1.9.1.685";
  }

  smiv2:alias "ciscoDSC9120CLK9" {
    smiv2:oid "1.3.6.1.4.1.9.1.686";
  }

  smiv2:alias "ciscoFe611K9" {
    smiv2:oid "1.3.6.1.4.1.9.1.687";
  }

  smiv2:alias "catalyst3750Ge12SfpDc" {
    smiv2:oid "1.3.6.1.4.1.9.1.688";
  }

  smiv2:alias "cisco3271" {
    smiv2:oid "1.3.6.1.4.1.9.1.689";
  }

  smiv2:alias "cisco3272" {
    smiv2:oid "1.3.6.1.4.1.9.1.690";
  }

  smiv2:alias "cisco3241" {
    smiv2:oid "1.3.6.1.4.1.9.1.691";
  }

  smiv2:alias "cisco3242" {
    smiv2:oid "1.3.6.1.4.1.9.1.692";
  }

  smiv2:alias "ciscoICM" {
    smiv2:oid "1.3.6.1.4.1.9.1.693";
  }

  smiv2:alias "catalyst296024" {
    smiv2:oid "1.3.6.1.4.1.9.1.694";
  }

  smiv2:alias "catalyst296048" {
    smiv2:oid "1.3.6.1.4.1.9.1.695";
  }

  smiv2:alias "catalyst2960G24" {
    smiv2:oid "1.3.6.1.4.1.9.1.696";
  }

  smiv2:alias "catalyst2960G48" {
    smiv2:oid "1.3.6.1.4.1.9.1.697";
  }

  smiv2:alias "catalyst45503" {
    smiv2:oid "1.3.6.1.4.1.9.1.698";
  }

  smiv2:alias "catalyst45506" {
    smiv2:oid "1.3.6.1.4.1.9.1.699";
  }

  smiv2:alias "catalyst45507" {
    smiv2:oid "1.3.6.1.4.1.9.1.700";
  }

  smiv2:alias "catalyst455010" {
    smiv2:oid "1.3.6.1.4.1.9.1.701";
  }

  smiv2:alias "ciscoNme16Es1GeNoPwr" {
    smiv2:oid "1.3.6.1.4.1.9.1.702";
  }

  smiv2:alias "ciscoNmeX24Es1GeNoPwr" {
    smiv2:oid "1.3.6.1.4.1.9.1.703";
  }

  smiv2:alias "ciscoNmeXd24Es2StNoPwr" {
    smiv2:oid "1.3.6.1.4.1.9.1.704";
  }

  smiv2:alias "ciscoNmeXd48Es2GeNoPwr" {
    smiv2:oid "1.3.6.1.4.1.9.1.705";
  }

  smiv2:alias "catalyst6kMsfc2a" {
    smiv2:oid "1.3.6.1.4.1.9.1.706";
  }

  smiv2:alias "ciscoEDI" {
    smiv2:oid "1.3.6.1.4.1.9.1.707";
  }

  smiv2:alias "ciscoCe611K9" {
    smiv2:oid "1.3.6.1.4.1.9.1.708";
  }

  smiv2:alias "ciscoWLSEs20" {
    smiv2:oid "1.3.6.1.4.1.9.1.709";
  }

  smiv2:alias "ciscoMPX" {
    smiv2:oid "1.3.6.1.4.1.9.1.710";
  }

  smiv2:alias "ciscoNMCUEEC" {
    smiv2:oid "1.3.6.1.4.1.9.1.711";
  }

  smiv2:alias "ciscoWLSE1132" {
    smiv2:oid "1.3.6.1.4.1.9.1.712";
  }

  smiv2:alias "ciscoME6340ACA" {
    smiv2:oid "1.3.6.1.4.1.9.1.713";
  }

  smiv2:alias "ciscoME6340DCA" {
    smiv2:oid "1.3.6.1.4.1.9.1.714";
  }

  smiv2:alias "ciscoME6340DCB" {
    smiv2:oid "1.3.6.1.4.1.9.1.715";
  }

  smiv2:alias "catalyst296024TT" {
    smiv2:oid "1.3.6.1.4.1.9.1.716";
  }

  smiv2:alias "catalyst296048TT" {
    smiv2:oid "1.3.6.1.4.1.9.1.717";
  }

  smiv2:alias "ciscoIGESMSFPT" {
    smiv2:oid "1.3.6.1.4.1.9.1.718";
  }

  smiv2:alias "ciscoMEC6524gs8s" {
    smiv2:oid "1.3.6.1.4.1.9.1.719";
  }

  smiv2:alias "ciscoMEC6524gt8s" {
    smiv2:oid "1.3.6.1.4.1.9.1.720";
  }

  smiv2:alias "ciscoMEC6724s10x2" {
    smiv2:oid "1.3.6.1.4.1.9.1.721";
  }

  smiv2:alias "ciscoMEC6724t10x2" {
    smiv2:oid "1.3.6.1.4.1.9.1.722";
  }

  smiv2:alias "ciscoPaldron" {
    smiv2:oid "1.3.6.1.4.1.9.1.723";
  }

  smiv2:alias "catalystsExpress50024TT" {
    smiv2:oid "1.3.6.1.4.1.9.1.724";
  }

  smiv2:alias "catalystsExpress50024LC" {
    smiv2:oid "1.3.6.1.4.1.9.1.725";
  }

  smiv2:alias "catalystsExpress50024PC" {
    smiv2:oid "1.3.6.1.4.1.9.1.726";
  }

  smiv2:alias "catalystsExpress50012TC" {
    smiv2:oid "1.3.6.1.4.1.9.1.727";
  }

  smiv2:alias "ciscoIGESMT" {
    smiv2:oid "1.3.6.1.4.1.9.1.728";
  }

  smiv2:alias "ciscoACE04G" {
    smiv2:oid "1.3.6.1.4.1.9.1.729";
  }

  smiv2:alias "ciscoACE10K9" {
    smiv2:oid "1.3.6.1.4.1.9.1.730";
  }

  smiv2:alias "cisco5750" {
    smiv2:oid "1.3.6.1.4.1.9.1.731";
  }

  smiv2:alias "ciscoMWR1941DCA" {
    smiv2:oid "1.3.6.1.4.1.9.1.732";
  }

  smiv2:alias "cisco815" {
    smiv2:oid "1.3.6.1.4.1.9.1.733";
  }

  smiv2:alias "cisco240024TSA" {
    smiv2:oid "1.3.6.1.4.1.9.1.734";
  }

  smiv2:alias "cisco240024TSD" {
    smiv2:oid "1.3.6.1.4.1.9.1.735";
  }

  smiv2:alias "cisco340024TSA" {
    smiv2:oid "1.3.6.1.4.1.9.1.736";
  }

  smiv2:alias "cisco340024TSD" {
    smiv2:oid "1.3.6.1.4.1.9.1.737";
  }

  smiv2:alias "ciscoCrs18Linecard" {
    smiv2:oid "1.3.6.1.4.1.9.1.738";
  }

  smiv2:alias "ciscoCrs1Fabric" {
    smiv2:oid "1.3.6.1.4.1.9.1.739";
  }

  smiv2:alias "ciscoFE2636" {
    smiv2:oid "1.3.6.1.4.1.9.1.740";
  }

  smiv2:alias "ciscoIDS4220" {
    smiv2:oid "1.3.6.1.4.1.9.1.741";
  }

  smiv2:alias "ciscoIDS4230" {
    smiv2:oid "1.3.6.1.4.1.9.1.742";
  }

  smiv2:alias "ciscoIPS4260" {
    smiv2:oid "1.3.6.1.4.1.9.1.743";
  }

  smiv2:alias "ciscoWsSvcSAMIBB" {
    smiv2:oid "1.3.6.1.4.1.9.1.744";
  }

  smiv2:alias "ciscoASA5505" {
    smiv2:oid "1.3.6.1.4.1.9.1.745";
  }

  smiv2:alias "ciscoMCS7825I" {
    smiv2:oid "1.3.6.1.4.1.9.1.746";
  }

  smiv2:alias "ciscoWsC3750g24ps" {
    smiv2:oid "1.3.6.1.4.1.9.1.747";
  }

  smiv2:alias "ciscoWs3020Hpq" {
    smiv2:oid "1.3.6.1.4.1.9.1.748";
  }

  smiv2:alias "ciscoWs3030Del" {
    smiv2:oid "1.3.6.1.4.1.9.1.749";
  }

  smiv2:alias "ciscoSpaOc48posSfp" {
    smiv2:oid "1.3.6.1.4.1.9.1.750";
  }

  smiv2:alias "catalyst6kEnhancedGateway" {
    smiv2:oid "1.3.6.1.4.1.9.1.751";
  }

  smiv2:alias "ciscoWLSE1133" {
    smiv2:oid "1.3.6.1.4.1.9.1.752";
  }

  smiv2:alias "ciscoASA5550" {
    smiv2:oid "1.3.6.1.4.1.9.1.753";
  }

  smiv2:alias "ciscoNMAONK9" {
    smiv2:oid "1.3.6.1.4.1.9.1.754";
  }

  smiv2:alias "ciscoNMAONWS" {
    smiv2:oid "1.3.6.1.4.1.9.1.755";
  }

  smiv2:alias "ciscoNMAONAPS" {
    smiv2:oid "1.3.6.1.4.1.9.1.756";
  }

  smiv2:alias "ciscoWae612K9" {
    smiv2:oid "1.3.6.1.4.1.9.1.757";
  }

  smiv2:alias "ciscoAIRAP1250" {
    smiv2:oid "1.3.6.1.4.1.9.1.758";
  }

  smiv2:alias "ciscoCe512K9" {
    smiv2:oid "1.3.6.1.4.1.9.1.759";
  }

  smiv2:alias "ciscoFe512K9" {
    smiv2:oid "1.3.6.1.4.1.9.1.760";
  }

  smiv2:alias "ciscoCe612K9" {
    smiv2:oid "1.3.6.1.4.1.9.1.761";
  }

  smiv2:alias "ciscoFe612K9" {
    smiv2:oid "1.3.6.1.4.1.9.1.762";
  }

  smiv2:alias "ciscoASA5550sc" {
    smiv2:oid "1.3.6.1.4.1.9.1.763";
  }

  smiv2:alias "ciscoASA5520sy" {
    smiv2:oid "1.3.6.1.4.1.9.1.764";
  }

  smiv2:alias "ciscoASA5540sy" {
    smiv2:oid "1.3.6.1.4.1.9.1.765";
  }

  smiv2:alias "ciscoASA5550sy" {
    smiv2:oid "1.3.6.1.4.1.9.1.766";
  }

  smiv2:alias "ciscoWsSvcFwm1sy" {
    smiv2:oid "1.3.6.1.4.1.9.1.767";
  }

  smiv2:alias "ciscoPIXFirewall515sy" {
    smiv2:oid "1.3.6.1.4.1.9.1.768";
  }

  smiv2:alias "ciscoPIXFirewall515Esy" {
    smiv2:oid "1.3.6.1.4.1.9.1.769";
  }

  smiv2:alias "ciscoPIXFirewall525sy" {
    smiv2:oid "1.3.6.1.4.1.9.1.770";
  }

  smiv2:alias "ciscoPIXFirewall535sy" {
    smiv2:oid "1.3.6.1.4.1.9.1.771";
  }

  smiv2:alias "ciscoIpRanOpt4p" {
    smiv2:oid "1.3.6.1.4.1.9.1.772";
  }

  smiv2:alias "ciscoASA5510sc" {
    smiv2:oid "1.3.6.1.4.1.9.1.773";
  }

  smiv2:alias "ciscoASA5510sy" {
    smiv2:oid "1.3.6.1.4.1.9.1.774";
  }

  smiv2:alias "ciscoJumpgate" {
    smiv2:oid "1.3.6.1.4.1.9.1.775";
  }

  smiv2:alias "ciscoOe512K9" {
    smiv2:oid "1.3.6.1.4.1.9.1.776";
  }

  smiv2:alias "ciscoOe612K9" {
    smiv2:oid "1.3.6.1.4.1.9.1.777";
  }

  smiv2:alias "catalyst3750G24WS25" {
    smiv2:oid "1.3.6.1.4.1.9.1.778";
  }

  smiv2:alias "catalyst3750G24WS50" {
    smiv2:oid "1.3.6.1.4.1.9.1.779";
  }

  smiv2:alias "ciscoMe3400g12CsA" {
    smiv2:oid "1.3.6.1.4.1.9.1.780";
  }

  smiv2:alias "ciscoMe3400g12CsD" {
    smiv2:oid "1.3.6.1.4.1.9.1.781";
  }

  smiv2:alias "cisco877M" {
    smiv2:oid "1.3.6.1.4.1.9.1.782";
  }

  smiv2:alias "cisco1801M" {
    smiv2:oid "1.3.6.1.4.1.9.1.783";
  }

  smiv2:alias "catalystWsCBS3040FSC" {
    smiv2:oid "1.3.6.1.4.1.9.1.784";
  }

  smiv2:alias "ciscoOe511K9" {
    smiv2:oid "1.3.6.1.4.1.9.1.785";
  }

  smiv2:alias "ciscoOe611K9" {
    smiv2:oid "1.3.6.1.4.1.9.1.786";
  }

  smiv2:alias "ciscoOe7326K9" {
    smiv2:oid "1.3.6.1.4.1.9.1.787";
  }

  smiv2:alias "ciscoMe492410GE" {
    smiv2:oid "1.3.6.1.4.1.9.1.788";
  }

  smiv2:alias "catalyst3750E24TD" {
    smiv2:oid "1.3.6.1.4.1.9.1.789";
  }

  smiv2:alias "catalyst3750E48TD" {
    smiv2:oid "1.3.6.1.4.1.9.1.790";
  }

  smiv2:alias "catalyst3750E48PD" {
    smiv2:oid "1.3.6.1.4.1.9.1.791";
  }

  smiv2:alias "catalyst3750E24PD" {
    smiv2:oid "1.3.6.1.4.1.9.1.792";
  }

  smiv2:alias "catalyst3560E24TD" {
    smiv2:oid "1.3.6.1.4.1.9.1.793";
  }

  smiv2:alias "catalyst3560E48TD" {
    smiv2:oid "1.3.6.1.4.1.9.1.794";
  }

  smiv2:alias "catalyst3560E24PD" {
    smiv2:oid "1.3.6.1.4.1.9.1.795";
  }

  smiv2:alias "catalyst3560E48PD" {
    smiv2:oid "1.3.6.1.4.1.9.1.796";
  }

  smiv2:alias "catalyst35608PC" {
    smiv2:oid "1.3.6.1.4.1.9.1.797";
  }

  smiv2:alias "catalyst29608TC" {
    smiv2:oid "1.3.6.1.4.1.9.1.798";
  }

  smiv2:alias "catalyst2960G8TC" {
    smiv2:oid "1.3.6.1.4.1.9.1.799";
  }

  smiv2:alias "ciscoTSPri" {
    smiv2:oid "1.3.6.1.4.1.9.1.800";
  }

  smiv2:alias "ciscoTSSec" {
    smiv2:oid "1.3.6.1.4.1.9.1.801";
  }

  smiv2:alias "ciscoUWIpPhone7921G" {
    smiv2:oid "1.3.6.1.4.1.9.1.802";
  }

  smiv2:alias "ciscoUWIpPhone7920" {
    smiv2:oid "1.3.6.1.4.1.9.1.803";
  }

  smiv2:alias "cisco3200WirelessMic" {
    smiv2:oid "1.3.6.1.4.1.9.1.804";
  }

  smiv2:alias "ciscoISRWireless" {
    smiv2:oid "1.3.6.1.4.1.9.1.805";
  }

  smiv2:alias "ciscoIPSVirtual" {
    smiv2:oid "1.3.6.1.4.1.9.1.806";
  }

  smiv2:alias "ciscoIDS4215Virtual" {
    smiv2:oid "1.3.6.1.4.1.9.1.807";
  }

  smiv2:alias "ciscoIDS4235Virtual" {
    smiv2:oid "1.3.6.1.4.1.9.1.808";
  }

  smiv2:alias "ciscoIDS4250Virtual" {
    smiv2:oid "1.3.6.1.4.1.9.1.809";
  }

  smiv2:alias "ciscoIDS4250SXVirtual" {
    smiv2:oid "1.3.6.1.4.1.9.1.810";
  }

  smiv2:alias "ciscoIDS4250XLVirtual" {
    smiv2:oid "1.3.6.1.4.1.9.1.811";
  }

  smiv2:alias "ciscoIDS4240Virtual" {
    smiv2:oid "1.3.6.1.4.1.9.1.812";
  }

  smiv2:alias "ciscoIDS4255Virtual" {
    smiv2:oid "1.3.6.1.4.1.9.1.813";
  }

  smiv2:alias "ciscoIDS4260Virtual" {
    smiv2:oid "1.3.6.1.4.1.9.1.814";
  }

  smiv2:alias "ciscoIDSIDSM2Virtual" {
    smiv2:oid "1.3.6.1.4.1.9.1.815";
  }

  smiv2:alias "ciscoIPSSSM20Virtual" {
    smiv2:oid "1.3.6.1.4.1.9.1.816";
  }

  smiv2:alias "ciscoIPSSSM10Virtual" {
    smiv2:oid "1.3.6.1.4.1.9.1.817";
  }

  smiv2:alias "ciscoNMWLCE" {
    smiv2:oid "1.3.6.1.4.1.9.1.818";
  }

  smiv2:alias "cisco3205WirelessMic" {
    smiv2:oid "1.3.6.1.4.1.9.1.819";
  }

  smiv2:alias "cisco5720" {
    smiv2:oid "1.3.6.1.4.1.9.1.820";
  }

  smiv2:alias "cisco7201" {
    smiv2:oid "1.3.6.1.4.1.9.1.821";
  }

  smiv2:alias "ciscoCrs14S" {
    smiv2:oid "1.3.6.1.4.1.9.1.822";
  }

  smiv2:alias "ciscoNmWae" {
    smiv2:oid "1.3.6.1.4.1.9.1.823";
  }

  smiv2:alias "ciscoACE4710K9" {
    smiv2:oid "1.3.6.1.4.1.9.1.824";
  }

  smiv2:alias "ciscoMe3400g2csA" {
    smiv2:oid "1.3.6.1.4.1.9.1.825";
  }

  smiv2:alias "ciscoNmeNam" {
    smiv2:oid "1.3.6.1.4.1.9.1.826";
  }

  smiv2:alias "ciscoUbr7225Vxr" {
    smiv2:oid "1.3.6.1.4.1.9.1.827";
  }

  smiv2:alias "ciscoAirWlc2106K9" {
    smiv2:oid "1.3.6.1.4.1.9.1.828";
  }

  smiv2:alias "ciscoMwr1951DC" {
    smiv2:oid "1.3.6.1.4.1.9.1.829";
  }

  smiv2:alias "ciscoIPS4270" {
    smiv2:oid "1.3.6.1.4.1.9.1.830";
  }

  smiv2:alias "ciscoIPS4270Virtual" {
    smiv2:oid "1.3.6.1.4.1.9.1.831";
  }

  smiv2:alias "ciscoWSC6509ve" {
    smiv2:oid "1.3.6.1.4.1.9.1.832";
  }

  smiv2:alias "cisco5740" {
    smiv2:oid "1.3.6.1.4.1.9.1.833";
  }

  smiv2:alias "cisco861" {
    smiv2:oid "1.3.6.1.4.1.9.1.834";
  }

  smiv2:alias "cisco866" {
    smiv2:oid "1.3.6.1.4.1.9.1.835";
  }

  smiv2:alias "cisco867" {
    smiv2:oid "1.3.6.1.4.1.9.1.836";
  }

  smiv2:alias "cisco881" {
    smiv2:oid "1.3.6.1.4.1.9.1.837";
  }

  smiv2:alias "cisco881G" {
    smiv2:oid "1.3.6.1.4.1.9.1.838";
  }

  smiv2:alias "ciscoIad881F" {
    smiv2:oid "1.3.6.1.4.1.9.1.839";
  }

  smiv2:alias "cisco881Srst" {
    smiv2:oid "1.3.6.1.4.1.9.1.840";
  }

  smiv2:alias "ciscoIad881B" {
    smiv2:oid "1.3.6.1.4.1.9.1.841";
  }

  smiv2:alias "cisco886" {
    smiv2:oid "1.3.6.1.4.1.9.1.842";
  }

  smiv2:alias "cisco886G" {
    smiv2:oid "1.3.6.1.4.1.9.1.843";
  }

  smiv2:alias "ciscoIad886F" {
    smiv2:oid "1.3.6.1.4.1.9.1.844";
  }

  smiv2:alias "ciscoIad886B" {
    smiv2:oid "1.3.6.1.4.1.9.1.845";
  }

  smiv2:alias "cisco886Srst" {
    smiv2:oid "1.3.6.1.4.1.9.1.846";
  }

  smiv2:alias "cisco887" {
    smiv2:oid "1.3.6.1.4.1.9.1.847";
  }

  smiv2:alias "cisco887G" {
    smiv2:oid "1.3.6.1.4.1.9.1.848";
  }

  smiv2:alias "ciscoIad887F" {
    smiv2:oid "1.3.6.1.4.1.9.1.849";
  }

  smiv2:alias "ciscoIad887B" {
    smiv2:oid "1.3.6.1.4.1.9.1.850";
  }

  smiv2:alias "cisco887Srst" {
    smiv2:oid "1.3.6.1.4.1.9.1.851";
  }

  smiv2:alias "cisco888" {
    smiv2:oid "1.3.6.1.4.1.9.1.852";
  }

  smiv2:alias "cisco888G" {
    smiv2:oid "1.3.6.1.4.1.9.1.853";
  }

  smiv2:alias "ciscoIad888F" {
    smiv2:oid "1.3.6.1.4.1.9.1.854";
  }

  smiv2:alias "ciscoIad888B" {
    smiv2:oid "1.3.6.1.4.1.9.1.855";
  }

  smiv2:alias "cisco888Srst" {
    smiv2:oid "1.3.6.1.4.1.9.1.856";
  }

  smiv2:alias "cisco891" {
    smiv2:oid "1.3.6.1.4.1.9.1.857";
  }

  smiv2:alias "cisco892" {
    smiv2:oid "1.3.6.1.4.1.9.1.858";
  }

  smiv2:alias "cisco885D3" {
    smiv2:oid "1.3.6.1.4.1.9.1.859";
  }

  smiv2:alias "ciscoIad885FD3" {
    smiv2:oid "1.3.6.1.4.1.9.1.860";
  }

  smiv2:alias "cisco885EJ3" {
    smiv2:oid "1.3.6.1.4.1.9.1.861";
  }

  smiv2:alias "cisco7603s" {
    smiv2:oid "1.3.6.1.4.1.9.1.862";
  }

  smiv2:alias "cisco7606s" {
    smiv2:oid "1.3.6.1.4.1.9.1.863";
  }

  smiv2:alias "cisco7609s" {
    smiv2:oid "1.3.6.1.4.1.9.1.864";
  }

  smiv2:alias "cisco7600Seb" {
    smiv2:oid "1.3.6.1.4.1.9.1.865";
  }

  smiv2:alias "ciscoNMECUE" {
    smiv2:oid "1.3.6.1.4.1.9.1.866";
  }

  smiv2:alias "ciscoAIM2CUE" {
    smiv2:oid "1.3.6.1.4.1.9.1.867";
  }

  smiv2:alias "ciscoUC500" {
    smiv2:oid "1.3.6.1.4.1.9.1.868";
  }

  smiv2:alias "cisco860Ap" {
    smiv2:oid "1.3.6.1.4.1.9.1.869";
  }

  smiv2:alias "cisco880Ap" {
    smiv2:oid "1.3.6.1.4.1.9.1.870";
  }

  smiv2:alias "cisco890Ap" {
    smiv2:oid "1.3.6.1.4.1.9.1.871";
  }

  smiv2:alias "cisco1900Ap" {
    smiv2:oid "1.3.6.1.4.1.9.1.872";
  }

  smiv2:alias "cisco340024FSA" {
    smiv2:oid "1.3.6.1.4.1.9.1.873";
  }

  smiv2:alias "catalyst4503e" {
    smiv2:oid "1.3.6.1.4.1.9.1.874";
  }

  smiv2:alias "catalyst4506e" {
    smiv2:oid "1.3.6.1.4.1.9.1.875";
  }

  smiv2:alias "catalyst4507re" {
    smiv2:oid "1.3.6.1.4.1.9.1.876";
  }

  smiv2:alias "catalyst4510re" {
    smiv2:oid "1.3.6.1.4.1.9.1.877";
  }

  smiv2:alias "ciscoUC520s8U4FXOK9" {
    smiv2:oid "1.3.6.1.4.1.9.1.878";
  }

  smiv2:alias "ciscoUC520s8U4FXOWK9" {
    smiv2:oid "1.3.6.1.4.1.9.1.879";
  }

  smiv2:alias "ciscoUC520s8U2BRIK9" {
    smiv2:oid "1.3.6.1.4.1.9.1.880";
  }

  smiv2:alias "ciscoUC520s8U2BRIWK9" {
    smiv2:oid "1.3.6.1.4.1.9.1.881";
  }

  smiv2:alias "ciscoUC520s16U4FXOK9" {
    smiv2:oid "1.3.6.1.4.1.9.1.882";
  }

  smiv2:alias "ciscoUC520s16U4FXOWK9" {
    smiv2:oid "1.3.6.1.4.1.9.1.883";
  }

  smiv2:alias "ciscoUC520s16U2BRIK9" {
    smiv2:oid "1.3.6.1.4.1.9.1.884";
  }

  smiv2:alias "ciscoUC520s16U2BRIWK9" {
    smiv2:oid "1.3.6.1.4.1.9.1.885";
  }

  smiv2:alias "ciscoUC520m32U8FXOK9" {
    smiv2:oid "1.3.6.1.4.1.9.1.886";
  }

  smiv2:alias "ciscoUC520m32U8FXOWK9" {
    smiv2:oid "1.3.6.1.4.1.9.1.887";
  }

  smiv2:alias "ciscoUC520m32U4BRIK9" {
    smiv2:oid "1.3.6.1.4.1.9.1.888";
  }

  smiv2:alias "ciscoUC520m32U4BRIWK9" {
    smiv2:oid "1.3.6.1.4.1.9.1.889";
  }

  smiv2:alias "ciscoUC520m48U12FXOK9" {
    smiv2:oid "1.3.6.1.4.1.9.1.890";
  }

  smiv2:alias "ciscoUC520m48U12FXOWK9" {
    smiv2:oid "1.3.6.1.4.1.9.1.891";
  }

  smiv2:alias "ciscoUC520m48U6BRIK9" {
    smiv2:oid "1.3.6.1.4.1.9.1.892";
  }

  smiv2:alias "ciscoUC520m48U6BRIWK9" {
    smiv2:oid "1.3.6.1.4.1.9.1.893";
  }

  smiv2:alias "ciscoUC520m48U1T1E1FK9" {
    smiv2:oid "1.3.6.1.4.1.9.1.894";
  }

  smiv2:alias "ciscoUC520m48U1T1E1BK9" {
    smiv2:oid "1.3.6.1.4.1.9.1.895";
  }

  smiv2:alias "catalyst65xxVirtualSwitch" {
    smiv2:oid "1.3.6.1.4.1.9.1.896";
  }

  smiv2:alias "catalystExpress5208PC" {
    smiv2:oid "1.3.6.1.4.1.9.1.897";
  }

  smiv2:alias "ciscoMCS7816I" {
    smiv2:oid "1.3.6.1.4.1.9.1.898";
  }

  smiv2:alias "ciscoMCS7828I" {
    smiv2:oid "1.3.6.1.4.1.9.1.899";
  }

  smiv2:alias "ciscoMCS7816H" {
    smiv2:oid "1.3.6.1.4.1.9.1.900";
  }

  smiv2:alias "ciscoMCS7828H" {
    smiv2:oid "1.3.6.1.4.1.9.1.901";
  }

  smiv2:alias "cisco1861Uc2BK9" {
    smiv2:oid "1.3.6.1.4.1.9.1.902";
  }

  smiv2:alias "cisco1861Uc4FK9" {
    smiv2:oid "1.3.6.1.4.1.9.1.903";
  }

  smiv2:alias "cisco1861Srst2BK9" {
    smiv2:oid "1.3.6.1.4.1.9.1.904";
  }

  smiv2:alias "cisco1861Srst4FK9" {
    smiv2:oid "1.3.6.1.4.1.9.1.905";
  }

  smiv2:alias "ciscoNmeApa" {
    smiv2:oid "1.3.6.1.4.1.9.1.906";
  }

  smiv2:alias "ciscoOe7330K9" {
    smiv2:oid "1.3.6.1.4.1.9.1.907";
  }

  smiv2:alias "ciscoOe7350K9" {
    smiv2:oid "1.3.6.1.4.1.9.1.908";
  }

  smiv2:alias "ciscoWsCbs3110gS" {
    smiv2:oid "1.3.6.1.4.1.9.1.909";
  }

  smiv2:alias "ciscoWsCbs3110gSt" {
    smiv2:oid "1.3.6.1.4.1.9.1.910";
  }

  smiv2:alias "ciscoWsCbs3110xS" {
    smiv2:oid "1.3.6.1.4.1.9.1.911";
  }

  smiv2:alias "ciscoWsCbs3110xSt" {
    smiv2:oid "1.3.6.1.4.1.9.1.912";
  }

  smiv2:alias "ciscoSce8000" {
    smiv2:oid "1.3.6.1.4.1.9.1.913";
  }

  smiv2:alias "ciscoASA5580" {
    smiv2:oid "1.3.6.1.4.1.9.1.914";
  }

  smiv2:alias "ciscoASA5580sc" {
    smiv2:oid "1.3.6.1.4.1.9.1.915";
  }

  smiv2:alias "ciscoASA5580sy" {
    smiv2:oid "1.3.6.1.4.1.9.1.916";
  }

  smiv2:alias "cat4900M" {
    smiv2:oid "1.3.6.1.4.1.9.1.917";
  }

  smiv2:alias "catWsCbs3120gS" {
    smiv2:oid "1.3.6.1.4.1.9.1.918";
  }

  smiv2:alias "catWsCbs3120xS" {
    smiv2:oid "1.3.6.1.4.1.9.1.919";
  }

  smiv2:alias "catWsCbs3032Del" {
    smiv2:oid "1.3.6.1.4.1.9.1.920";
  }

  smiv2:alias "catWsCbs3130gS" {
    smiv2:oid "1.3.6.1.4.1.9.1.921";
  }

  smiv2:alias "catWsCbs3130xS" {
    smiv2:oid "1.3.6.1.4.1.9.1.922";
  }

  smiv2:alias "ciscoASR1002" {
    smiv2:oid "1.3.6.1.4.1.9.1.923";
  }

  smiv2:alias "ciscoASR1004" {
    smiv2:oid "1.3.6.1.4.1.9.1.924";
  }

  smiv2:alias "ciscoASR1006" {
    smiv2:oid "1.3.6.1.4.1.9.1.925";
  }

  smiv2:alias "cisco520WirelessController" {
    smiv2:oid "1.3.6.1.4.1.9.1.926";
  }

  smiv2:alias "cat296048TCS" {
    smiv2:oid "1.3.6.1.4.1.9.1.927";
  }

  smiv2:alias "cat296024TCS" {
    smiv2:oid "1.3.6.1.4.1.9.1.928";
  }

  smiv2:alias "cat296024S" {
    smiv2:oid "1.3.6.1.4.1.9.1.929";
  }

  smiv2:alias "cat3560e12d" {
    smiv2:oid "1.3.6.1.4.1.9.1.930";
  }

  smiv2:alias "ciscoCatRfgw" {
    smiv2:oid "1.3.6.1.4.1.9.1.931";
  }

  smiv2:alias "catExpress52024TT" {
    smiv2:oid "1.3.6.1.4.1.9.1.932";
  }

  smiv2:alias "catExpress52024LC" {
    smiv2:oid "1.3.6.1.4.1.9.1.933";
  }

  smiv2:alias "catExpress52024PC" {
    smiv2:oid "1.3.6.1.4.1.9.1.934";
  }

  smiv2:alias "catExpress520G24TC" {
    smiv2:oid "1.3.6.1.4.1.9.1.935";
  }

  smiv2:alias "ciscoCDScde100" {
    smiv2:oid "1.3.6.1.4.1.9.1.936";
  }

  smiv2:alias "ciscoCDScde200" {
    smiv2:oid "1.3.6.1.4.1.9.1.937";
  }

  smiv2:alias "ciscoCDScde300" {
    smiv2:oid "1.3.6.1.4.1.9.1.938";
  }

  smiv2:alias "cisco1861SrstCue2BK9" {
    smiv2:oid "1.3.6.1.4.1.9.1.939";
  }

  smiv2:alias "cisco1861SrstCue4FK9" {
    smiv2:oid "1.3.6.1.4.1.9.1.940";
  }

  smiv2:alias "ciscoVFrameDataCenter" {
    smiv2:oid "1.3.6.1.4.1.9.1.941";
  }

  smiv2:alias "ciscoVQEServer" {
    smiv2:oid "1.3.6.1.4.1.9.1.942";
  }

  smiv2:alias "ciscoIPSSSM40Virtual" {
    smiv2:oid "1.3.6.1.4.1.9.1.943";
  }

  smiv2:alias "ciscoIPSSSM40" {
    smiv2:oid "1.3.6.1.4.1.9.1.944";
  }

  smiv2:alias "ciscoVgd1t3" {
    smiv2:oid "1.3.6.1.4.1.9.1.945";
  }

  smiv2:alias "ciscoCBS3100" {
    smiv2:oid "1.3.6.1.4.1.9.1.946";
  }

  smiv2:alias "ciscoCBS3110" {
    smiv2:oid "1.3.6.1.4.1.9.1.947";
  }

  smiv2:alias "ciscoCBS3120" {
    smiv2:oid "1.3.6.1.4.1.9.1.948";
  }

  smiv2:alias "ciscoCBS3130" {
    smiv2:oid "1.3.6.1.4.1.9.1.949";
  }

  smiv2:alias "catalyst296024PC" {
    smiv2:oid "1.3.6.1.4.1.9.1.950";
  }

  smiv2:alias "catalyst296024LT" {
    smiv2:oid "1.3.6.1.4.1.9.1.951";
  }

  smiv2:alias "catalyst2960PD8TT" {
    smiv2:oid "1.3.6.1.4.1.9.1.952";
  }

  smiv2:alias "ciscoSpa2x1geSynce" {
    smiv2:oid "1.3.6.1.4.1.9.1.953";
  }

  smiv2:alias "ciscoN5kC5020pBa" {
    smiv2:oid "1.3.6.1.4.1.9.1.954";
  }

  smiv2:alias "ciscoN5kC5020pBd" {
    smiv2:oid "1.3.6.1.4.1.9.1.955";
  }

  smiv2:alias "catalyst3560E12SD" {
    smiv2:oid "1.3.6.1.4.1.9.1.956";
  }

  smiv2:alias "ciscoOe674" {
    smiv2:oid "1.3.6.1.4.1.9.1.957";
  }

  smiv2:alias "ciscoIE30004TC" {
    smiv2:oid "1.3.6.1.4.1.9.1.958";
  }

  smiv2:alias "ciscoIE30008TC" {
    smiv2:oid "1.3.6.1.4.1.9.1.959";
  }

  smiv2:alias "ciscoRAIE1783MS06T" {
    smiv2:oid "1.3.6.1.4.1.9.1.960";
  }

  smiv2:alias "ciscoRAIE1783MS10T" {
    smiv2:oid "1.3.6.1.4.1.9.1.961";
  }

  smiv2:alias "cisco2435Iad8fxs" {
    smiv2:oid "1.3.6.1.4.1.9.1.962";
  }

  smiv2:alias "ciscoVG204" {
    smiv2:oid "1.3.6.1.4.1.9.1.963";
  }

  smiv2:alias "ciscoVG202" {
    smiv2:oid "1.3.6.1.4.1.9.1.964";
  }

  smiv2:alias "catalyst291824TT" {
    smiv2:oid "1.3.6.1.4.1.9.1.965";
  }

  smiv2:alias "catalyst291824TC" {
    smiv2:oid "1.3.6.1.4.1.9.1.966";
  }

  smiv2:alias "catalyst291848TT" {
    smiv2:oid "1.3.6.1.4.1.9.1.967";
  }

  smiv2:alias "catalyst291848TC" {
    smiv2:oid "1.3.6.1.4.1.9.1.968";
  }

  smiv2:alias "ciscoVQETools" {
    smiv2:oid "1.3.6.1.4.1.9.1.969";
  }

  smiv2:alias "ciscoUC520m24U4BRIK9" {
    smiv2:oid "1.3.6.1.4.1.9.1.970";
  }

  smiv2:alias "ciscoUC520m24U8FXOK9" {
    smiv2:oid "1.3.6.1.4.1.9.1.971";
  }

  smiv2:alias "ciscoUC520s16U2BRIWK9J" {
    smiv2:oid "1.3.6.1.4.1.9.1.972";
  }

  smiv2:alias "ciscoUC520s8U2BRIWK9J" {
    smiv2:oid "1.3.6.1.4.1.9.1.973";
  }

  smiv2:alias "ciscoVSIntSp" {
    smiv2:oid "1.3.6.1.4.1.9.1.974";
  }

  smiv2:alias "ciscoVSSP" {
    smiv2:oid "1.3.6.1.4.1.9.1.975";
  }

  smiv2:alias "ciscoVSHydecoder" {
    smiv2:oid "1.3.6.1.4.1.9.1.976";
  }

  smiv2:alias "ciscoVSDecoder" {
    smiv2:oid "1.3.6.1.4.1.9.1.977";
  }

  smiv2:alias "ciscoVSEncoder4P" {
    smiv2:oid "1.3.6.1.4.1.9.1.978";
  }

  smiv2:alias "ciscoVSEncoder1P" {
    smiv2:oid "1.3.6.1.4.1.9.1.979";
  }

  smiv2:alias "ciscoSCS1000K9" {
    smiv2:oid "1.3.6.1.4.1.9.1.980";
  }

  smiv2:alias "cisco1805" {
    smiv2:oid "1.3.6.1.4.1.9.1.981";
  }

  smiv2:alias "ciscoCe7341" {
    smiv2:oid "1.3.6.1.4.1.9.1.982";
  }

  smiv2:alias "ciscoCe7371" {
    smiv2:oid "1.3.6.1.4.1.9.1.983";
  }

  smiv2:alias "cisco7613s" {
    smiv2:oid "1.3.6.1.4.1.9.1.984";
  }

  smiv2:alias "ciscoOe574" {
    smiv2:oid "1.3.6.1.4.1.9.1.985";
  }

  smiv2:alias "ciscoOe474" {
    smiv2:oid "1.3.6.1.4.1.9.1.986";
  }

  smiv2:alias "ciscoOe274" {
    smiv2:oid "1.3.6.1.4.1.9.1.987";
  }

  smiv2:alias "ciscoAp801agn" {
    smiv2:oid "1.3.6.1.4.1.9.1.988";
  }

  smiv2:alias "ciscoAp801gn" {
    smiv2:oid "1.3.6.1.4.1.9.1.989";
  }

  smiv2:alias "cisco1861WSrstCue4FK9" {
    smiv2:oid "1.3.6.1.4.1.9.1.990";
  }

  smiv2:alias "cisco1861WSrstCue2BK9" {
    smiv2:oid "1.3.6.1.4.1.9.1.991";
  }

  smiv2:alias "cisco1861WSrst4FK9" {
    smiv2:oid "1.3.6.1.4.1.9.1.992";
  }

  smiv2:alias "cisco1861WSrst2BK9" {
    smiv2:oid "1.3.6.1.4.1.9.1.993";
  }

  smiv2:alias "cisco1861WUc4FK9" {
    smiv2:oid "1.3.6.1.4.1.9.1.994";
  }

  smiv2:alias "cisco1861WUc2BK9" {
    smiv2:oid "1.3.6.1.4.1.9.1.995";
  }

  smiv2:alias "ciscoCe674" {
    smiv2:oid "1.3.6.1.4.1.9.1.996";
  }

  smiv2:alias "ciscoVQEIST" {
    smiv2:oid "1.3.6.1.4.1.9.1.997";
  }

  smiv2:alias "ciscoAIRAP1160" {
    smiv2:oid "1.3.6.1.4.1.9.1.998";
  }

  smiv2:alias "ciscoWsCbs3012Ibm" {
    smiv2:oid "1.3.6.1.4.1.9.1.999";
  }

  smiv2:alias "ciscoWsCbs3012IbmI" {
    smiv2:oid "1.3.6.1.4.1.9.1.1000";
  }

  smiv2:alias "ciscoWsCbs3125gS" {
    smiv2:oid "1.3.6.1.4.1.9.1.1001";
  }

  smiv2:alias "ciscoWsCbs3125xS" {
    smiv2:oid "1.3.6.1.4.1.9.1.1002";
  }

  smiv2:alias "ciscoTSPriG2" {
    smiv2:oid "1.3.6.1.4.1.9.1.1003";
  }

  smiv2:alias "catalyst492810GE" {
    smiv2:oid "1.3.6.1.4.1.9.1.1004";
  }

  smiv2:alias "catalyst296048TTS" {
    smiv2:oid "1.3.6.1.4.1.9.1.1005";
  }

  smiv2:alias "catalyst29608TCS" {
    smiv2:oid "1.3.6.1.4.1.9.1.1006";
  }

  smiv2:alias "ciscoMe3400eg2csA" {
    smiv2:oid "1.3.6.1.4.1.9.1.1007";
  }

  smiv2:alias "ciscoMe3400eg12csM" {
    smiv2:oid "1.3.6.1.4.1.9.1.1008";
  }

  smiv2:alias "ciscoMe3400e24tsM" {
    smiv2:oid "1.3.6.1.4.1.9.1.1009";
  }

  smiv2:alias "ciscoIPSSSC5Virtual" {
    smiv2:oid "1.3.6.1.4.1.9.1.1010";
  }

  smiv2:alias "ciscoSR520FE" {
    smiv2:oid "1.3.6.1.4.1.9.1.1011";
  }

  smiv2:alias "ciscoSR520ADSL" {
    smiv2:oid "1.3.6.1.4.1.9.1.1012";
  }

  smiv2:alias "ciscoSR520ADSLi" {
    smiv2:oid "1.3.6.1.4.1.9.1.1013";
  }

  smiv2:alias "ciscoMwr2941DC" {
    smiv2:oid "1.3.6.1.4.1.9.1.1014";
  }

  smiv2:alias "catalyst356012PCS" {
    smiv2:oid "1.3.6.1.4.1.9.1.1015";
  }

  smiv2:alias "catalyst296048PSTL" {
    smiv2:oid "1.3.6.1.4.1.9.1.1016";
  }

  smiv2:alias "ciscoASR9010" {
    smiv2:oid "1.3.6.1.4.1.9.1.1017";
  }

  smiv2:alias "ciscoASR9006" {
    smiv2:oid "1.3.6.1.4.1.9.1.1018";
  }

  smiv2:alias "catalyst3560v224tsD" {
    smiv2:oid "1.3.6.1.4.1.9.1.1019";
  }

  smiv2:alias "catalyst3560v224ts" {
    smiv2:oid "1.3.6.1.4.1.9.1.1020";
  }

  smiv2:alias "catalyst3560v224ps" {
    smiv2:oid "1.3.6.1.4.1.9.1.1021";
  }

  smiv2:alias "catalyst3750v224ts" {
    smiv2:oid "1.3.6.1.4.1.9.1.1022";
  }

  smiv2:alias "catalyst3750v224ps" {
    smiv2:oid "1.3.6.1.4.1.9.1.1023";
  }

  smiv2:alias "catalyst3560v248ts" {
    smiv2:oid "1.3.6.1.4.1.9.1.1024";
  }

  smiv2:alias "catalyst3560v248ps" {
    smiv2:oid "1.3.6.1.4.1.9.1.1025";
  }

  smiv2:alias "catalyst3750v248ts" {
    smiv2:oid "1.3.6.1.4.1.9.1.1026";
  }

  smiv2:alias "catalyst3750v248ps" {
    smiv2:oid "1.3.6.1.4.1.9.1.1027";
  }

  smiv2:alias "ciscoHwicCableD2" {
    smiv2:oid "1.3.6.1.4.1.9.1.1028";
  }

  smiv2:alias "ciscoHwicCableEJ2" {
    smiv2:oid "1.3.6.1.4.1.9.1.1029";
  }

  smiv2:alias "ciscoBr1430" {
    smiv2:oid "1.3.6.1.4.1.9.1.1030";
  }

  smiv2:alias "ciscoAIRBR1430" {
    smiv2:oid "1.3.6.1.4.1.9.1.1031";
  }

  smiv2:alias "ciscoNamApp2204" {
    smiv2:oid "1.3.6.1.4.1.9.1.1032";
  }

  smiv2:alias "ciscoNamApp2220" {
    smiv2:oid "1.3.6.1.4.1.9.1.1033";
  }

  smiv2:alias "ciscoAIRAP1141" {
    smiv2:oid "1.3.6.1.4.1.9.1.1034";
  }

  smiv2:alias "ciscoAIRAP1142" {
    smiv2:oid "1.3.6.1.4.1.9.1.1035";
  }

  smiv2:alias "ciscoASR14K4S" {
    smiv2:oid "1.3.6.1.4.1.9.1.1036";
  }

  smiv2:alias "ciscoASR14K8S" {
    smiv2:oid "1.3.6.1.4.1.9.1.1037";
  }

  smiv2:alias "cisco18xxx" {
    smiv2:oid "1.3.6.1.4.1.9.1.1038";
  }

  smiv2:alias "ciscoIPSSSC5" {
    smiv2:oid "1.3.6.1.4.1.9.1.1039";
  }

  smiv2:alias "cisco887Vdsl2" {
    smiv2:oid "1.3.6.1.4.1.9.1.1040";
  }

  smiv2:alias "cisco3945" {
    smiv2:oid "1.3.6.1.4.1.9.1.1041";
  }

  smiv2:alias "cisco3925" {
    smiv2:oid "1.3.6.1.4.1.9.1.1042";
  }

  smiv2:alias "cisco2951" {
    smiv2:oid "1.3.6.1.4.1.9.1.1043";
  }

  smiv2:alias "cisco2921" {
    smiv2:oid "1.3.6.1.4.1.9.1.1044";
  }

  smiv2:alias "cisco2911" {
    smiv2:oid "1.3.6.1.4.1.9.1.1045";
  }

  smiv2:alias "cisco2901" {
    smiv2:oid "1.3.6.1.4.1.9.1.1046";
  }

  smiv2:alias "cisco1941" {
    smiv2:oid "1.3.6.1.4.1.9.1.1047";
  }

  smiv2:alias "ciscoSm2k15Es1GePoe" {
    smiv2:oid "1.3.6.1.4.1.9.1.1048";
  }

  smiv2:alias "ciscoSm3k15Es1GePoe" {
    smiv2:oid "1.3.6.1.4.1.9.1.1049";
  }

  smiv2:alias "ciscoSm3k16GePoe" {
    smiv2:oid "1.3.6.1.4.1.9.1.1050";
  }

  smiv2:alias "ciscoSm2k23Es1Ge" {
    smiv2:oid "1.3.6.1.4.1.9.1.1051";
  }

  smiv2:alias "ciscoSm2k23Es1GePoe" {
    smiv2:oid "1.3.6.1.4.1.9.1.1052";
  }

  smiv2:alias "ciscoSm3k23Es1GePoe" {
    smiv2:oid "1.3.6.1.4.1.9.1.1053";
  }

  smiv2:alias "ciscoSm3k24GePoe" {
    smiv2:oid "1.3.6.1.4.1.9.1.1054";
  }

  smiv2:alias "ciscoSmXd2k48Es2SFP" {
    smiv2:oid "1.3.6.1.4.1.9.1.1055";
  }

  smiv2:alias "ciscoSmXd3k48Es2SFPPoe" {
    smiv2:oid "1.3.6.1.4.1.9.1.1056";
  }

  smiv2:alias "ciscoSmXd3k48Ge2SFPPoe" {
    smiv2:oid "1.3.6.1.4.1.9.1.1057";
  }

  smiv2:alias "ciscoEsw52024pK9" {
    smiv2:oid "1.3.6.1.4.1.9.1.1058";
  }

  smiv2:alias "ciscoEsw54024pK9" {
    smiv2:oid "1.3.6.1.4.1.9.1.1059";
  }

  smiv2:alias "ciscoEsw52048pK9" {
    smiv2:oid "1.3.6.1.4.1.9.1.1060";
  }

  smiv2:alias "ciscoEsw52024K9" {
    smiv2:oid "1.3.6.1.4.1.9.1.1061";
  }

  smiv2:alias "ciscoEsw54024K9" {
    smiv2:oid "1.3.6.1.4.1.9.1.1062";
  }

  smiv2:alias "ciscoEsw52048K9" {
    smiv2:oid "1.3.6.1.4.1.9.1.1063";
  }

  smiv2:alias "ciscoEsw54048K9" {
    smiv2:oid "1.3.6.1.4.1.9.1.1064";
  }

  smiv2:alias "cisco1861" {
    smiv2:oid "1.3.6.1.4.1.9.1.1065";
  }

  smiv2:alias "ciscoUC520" {
    smiv2:oid "1.3.6.1.4.1.9.1.1066";
  }

  smiv2:alias "catalystWSC2975GS48PSL" {
    smiv2:oid "1.3.6.1.4.1.9.1.1067";
  }

  smiv2:alias "catalystC2975Stack" {
    smiv2:oid "1.3.6.1.4.1.9.1.1068";
  }

  smiv2:alias "cisco5500Wlc" {
    smiv2:oid "1.3.6.1.4.1.9.1.1069";
  }

  smiv2:alias "ciscoSR520T1" {
    smiv2:oid "1.3.6.1.4.1.9.1.1070";
  }

  smiv2:alias "ciscoPwrC3900Poe" {
    smiv2:oid "1.3.6.1.4.1.9.1.1071";
  }

  smiv2:alias "ciscoPwrC3900AC" {
    smiv2:oid "1.3.6.1.4.1.9.1.1072";
  }

  smiv2:alias "ciscoPwrC2921C2951Poe" {
    smiv2:oid "1.3.6.1.4.1.9.1.1073";
  }

  smiv2:alias "ciscoPwrC2921C2951AC" {
    smiv2:oid "1.3.6.1.4.1.9.1.1074";
  }

  smiv2:alias "ciscoPwrC2911Poe" {
    smiv2:oid "1.3.6.1.4.1.9.1.1075";
  }

  smiv2:alias "ciscoPwrC2911AC" {
    smiv2:oid "1.3.6.1.4.1.9.1.1076";
  }

  smiv2:alias "ciscoPwrC2901Poe" {
    smiv2:oid "1.3.6.1.4.1.9.1.1077";
  }

  smiv2:alias "ciscoPwrC1941C2901AC" {
    smiv2:oid "1.3.6.1.4.1.9.1.1078";
  }

  smiv2:alias "ciscoPwrC1941Poe" {
    smiv2:oid "1.3.6.1.4.1.9.1.1079";
  }

  smiv2:alias "ciscoPwrC3900DC" {
    smiv2:oid "1.3.6.1.4.1.9.1.1080";
  }

  smiv2:alias "ciscoPwrC2921C2951DC" {
    smiv2:oid "1.3.6.1.4.1.9.1.1081";
  }

  smiv2:alias "ciscoPwrC2911DC" {
    smiv2:oid "1.3.6.1.4.1.9.1.1082";
  }

  smiv2:alias "ciscoRpsAdptrC2921C2951" {
    smiv2:oid "1.3.6.1.4.1.9.1.1083";
  }

  smiv2:alias "ciscoRpsAdptrC2911" {
    smiv2:oid "1.3.6.1.4.1.9.1.1084";
  }

  smiv2:alias "ciscoIPSSSC2" {
    smiv2:oid "1.3.6.1.4.1.9.1.1085";
  }

  smiv2:alias "ciscoIPSSSC2Virtual" {
    smiv2:oid "1.3.6.1.4.1.9.1.1086";
  }

  smiv2:alias "catalystWSCBS3140XS" {
    smiv2:oid "1.3.6.1.4.1.9.1.1087";
  }

  smiv2:alias "catalystWSCBS3140GS" {
    smiv2:oid "1.3.6.1.4.1.9.1.1088";
  }

  smiv2:alias "catalystWSCBS3042FSC" {
    smiv2:oid "1.3.6.1.4.1.9.1.1089";
  }

  smiv2:alias "catalystWSCBS3150XS" {
    smiv2:oid "1.3.6.1.4.1.9.1.1090";
  }

  smiv2:alias "catalystWSCBS3150GS" {
    smiv2:oid "1.3.6.1.4.1.9.1.1091";
  }

  smiv2:alias "catalystWSCBS3052NEC" {
    smiv2:oid "1.3.6.1.4.1.9.1.1092";
  }

  smiv2:alias "ciscoCBS3140Stack" {
    smiv2:oid "1.3.6.1.4.1.9.1.1093";
  }

  smiv2:alias "ciscoCBS3150Stack" {
    smiv2:oid "1.3.6.1.4.1.9.1.1094";
  }

  smiv2:alias "cisco1941W" {
    smiv2:oid "1.3.6.1.4.1.9.1.1095";
  }

  smiv2:alias "ciscoC888E" {
    smiv2:oid "1.3.6.1.4.1.9.1.1096";
  }

  smiv2:alias "ciscoC888EG" {
    smiv2:oid "1.3.6.1.4.1.9.1.1097";
  }

  smiv2:alias "ciscoIad888EB" {
    smiv2:oid "1.3.6.1.4.1.9.1.1098";
  }

  smiv2:alias "ciscoIad888EF" {
    smiv2:oid "1.3.6.1.4.1.9.1.1099";
  }

  smiv2:alias "ciscoC888ESRST" {
    smiv2:oid "1.3.6.1.4.1.9.1.1100";
  }

  smiv2:alias "ciscoASA5505W" {
    smiv2:oid "1.3.6.1.4.1.9.1.1101";
  }

  smiv2:alias "cisco3845nv" {
    smiv2:oid "1.3.6.1.4.1.9.1.1102";
  }

  smiv2:alias "cisco3825nv" {
    smiv2:oid "1.3.6.1.4.1.9.1.1103";
  }

  smiv2:alias "catalystWSC235048TD" {
    smiv2:oid "1.3.6.1.4.1.9.1.1104";
  }

  smiv2:alias "cisco887M" {
    smiv2:oid "1.3.6.1.4.1.9.1.1105";
  }

  smiv2:alias "ciscoVg250" {
    smiv2:oid "1.3.6.1.4.1.9.1.1106";
  }

  smiv2:alias "ciscoVg226e" {
    smiv2:oid "1.3.6.1.4.1.9.1.1107";
  }

  smiv2:alias "ciscoDsIbm8GfcK9" {
    smiv2:oid "1.3.6.1.4.1.9.1.1108";
  }

  smiv2:alias "ciscoDsHp8GfcK9" {
    smiv2:oid "1.3.6.1.4.1.9.1.1109";
  }

  smiv2:alias "ciscoDsDell8GfcK9" {
    smiv2:oid "1.3.6.1.4.1.9.1.1110";
  }

  smiv2:alias "ciscoDsC9148K9" {
    smiv2:oid "1.3.6.1.4.1.9.1.1111";
  }

  smiv2:alias "ciscoCeVirtualBlade" {
    smiv2:oid "1.3.6.1.4.1.9.1.1112";
  }

  smiv2:alias "ciscoCDScde420" {
    smiv2:oid "1.3.6.1.4.1.9.1.1113";
  }

  smiv2:alias "ciscoCDScde220" {
    smiv2:oid "1.3.6.1.4.1.9.1.1114";
  }

  smiv2:alias "ciscoCDScde110" {
    smiv2:oid "1.3.6.1.4.1.9.1.1115";
  }

  smiv2:alias "ciscoASR1002F" {
    smiv2:oid "1.3.6.1.4.1.9.1.1116";
  }

  smiv2:alias "ciscoSecureAccessControlSystem" {
    smiv2:oid "1.3.6.1.4.1.9.1.1117";
  }

  smiv2:alias "cisco861Npe" {
    smiv2:oid "1.3.6.1.4.1.9.1.1118";
  }

  smiv2:alias "cisco881Npe" {
    smiv2:oid "1.3.6.1.4.1.9.1.1119";
  }

  smiv2:alias "cisco881GNpe" {
    smiv2:oid "1.3.6.1.4.1.9.1.1120";
  }

  smiv2:alias "cisco887Npe" {
    smiv2:oid "1.3.6.1.4.1.9.1.1121";
  }

  smiv2:alias "cisco888GNpe" {
    smiv2:oid "1.3.6.1.4.1.9.1.1122";
  }

  smiv2:alias "cisco891Npe" {
    smiv2:oid "1.3.6.1.4.1.9.1.1123";
  }

  smiv2:alias "ciscoAIRAP3501" {
    smiv2:oid "1.3.6.1.4.1.9.1.1124";
  }

  smiv2:alias "ciscoAIRAP3502" {
    smiv2:oid "1.3.6.1.4.1.9.1.1125";
  }

  smiv2:alias "ciscoCDScde400" {
    smiv2:oid "1.3.6.1.4.1.9.1.1126";
  }

  smiv2:alias "ciscoSA520K9" {
    smiv2:oid "1.3.6.1.4.1.9.1.1127";
  }

  smiv2:alias "ciscoSA520WK9" {
    smiv2:oid "1.3.6.1.4.1.9.1.1128";
  }

  smiv2:alias "ciscoSA540K9" {
    smiv2:oid "1.3.6.1.4.1.9.1.1129";
  }

  smiv2:alias "ciscoSps2004B" {
    smiv2:oid "1.3.6.1.4.1.9.1.1130";
  }

  smiv2:alias "ciscoSps204B" {
    smiv2:oid "1.3.6.1.4.1.9.1.1131";
  }

  smiv2:alias "ciscoUC560T1E1K9" {
    smiv2:oid "1.3.6.1.4.1.9.1.1132";
  }

  smiv2:alias "ciscoUC560BRIK9" {
    smiv2:oid "1.3.6.1.4.1.9.1.1133";
  }

  smiv2:alias "ciscoUC560FXOK9" {
    smiv2:oid "1.3.6.1.4.1.9.1.1134";
  }

  smiv2:alias "ciscoAp541nAK9" {
    smiv2:oid "1.3.6.1.4.1.9.1.1135";
  }

  smiv2:alias "ciscoAp541nEK9" {
    smiv2:oid "1.3.6.1.4.1.9.1.1136";
  }

  smiv2:alias "ciscoAp541nNK9" {
    smiv2:oid "1.3.6.1.4.1.9.1.1137";
  }

  smiv2:alias "cisco887GVdsl2" {
    smiv2:oid "1.3.6.1.4.1.9.1.1138";
  }

  smiv2:alias "cisco887SrstVdsl2" {
    smiv2:oid "1.3.6.1.4.1.9.1.1139";
  }

  smiv2:alias "ciscoUc540wFxoK9" {
    smiv2:oid "1.3.6.1.4.1.9.1.1140";
  }

  smiv2:alias "ciscoUc540wBriK9" {
    smiv2:oid "1.3.6.1.4.1.9.1.1141";
  }

  smiv2:alias "ciscoCaServer" {
    smiv2:oid "1.3.6.1.4.1.9.1.1142";
  }

  smiv2:alias "ciscoCaManager" {
    smiv2:oid "1.3.6.1.4.1.9.1.1143";
  }

  smiv2:alias "cisco3925SPE200" {
    smiv2:oid "1.3.6.1.4.1.9.1.1144";
  }

  smiv2:alias "cisco3945SPE250" {
    smiv2:oid "1.3.6.1.4.1.9.1.1145";
  }

  smiv2:alias "catalyst296024LCS" {
    smiv2:oid "1.3.6.1.4.1.9.1.1146";
  }

  smiv2:alias "catalyst296024PCS" {
    smiv2:oid "1.3.6.1.4.1.9.1.1147";
  }

  smiv2:alias "catalyst296048PSTS" {
    smiv2:oid "1.3.6.1.4.1.9.1.1148";
  }

  smiv2:alias "ciscoISM" {
    smiv2:oid "1.3.6.1.4.1.9.1.1149";
  }

  smiv2:alias "ciscoSM" {
    smiv2:oid "1.3.6.1.4.1.9.1.1150";
  }

  smiv2:alias "ciscoNMEAXP" {
    smiv2:oid "1.3.6.1.4.1.9.1.1151";
  }

  smiv2:alias "ciscoAIMAXP" {
    smiv2:oid "1.3.6.1.4.1.9.1.1152";
  }

  smiv2:alias "ciscoAIM2AXP" {
    smiv2:oid "1.3.6.1.4.1.9.1.1153";
  }

  smiv2:alias "ciscoSRP521" {
    smiv2:oid "1.3.6.1.4.1.9.1.1154";
  }

  smiv2:alias "ciscoSRP526" {
    smiv2:oid "1.3.6.1.4.1.9.1.1155";
  }

  smiv2:alias "ciscoSRP527" {
    smiv2:oid "1.3.6.1.4.1.9.1.1156";
  }

  smiv2:alias "ciscoSRP541" {
    smiv2:oid "1.3.6.1.4.1.9.1.1157";
  }

  smiv2:alias "ciscoSRP546" {
    smiv2:oid "1.3.6.1.4.1.9.1.1158";
  }

  smiv2:alias "ciscoSRP547" {
    smiv2:oid "1.3.6.1.4.1.9.1.1159";
  }

  smiv2:alias "ciscoVS510FXO" {
    smiv2:oid "1.3.6.1.4.1.9.1.1160";
  }

  smiv2:alias "ciscoNmWae900" {
    smiv2:oid "1.3.6.1.4.1.9.1.1161";
  }

  smiv2:alias "ciscoNmWae700" {
    smiv2:oid "1.3.6.1.4.1.9.1.1162";
  }

  smiv2:alias "cisco5940RA" {
    smiv2:oid "1.3.6.1.4.1.9.1.1163";
  }

  smiv2:alias "cisco5940RC" {
    smiv2:oid "1.3.6.1.4.1.9.1.1164";
  }

  smiv2:alias "ciscoASR1001" {
    smiv2:oid "1.3.6.1.4.1.9.1.1165";
  }

  smiv2:alias "ciscoASR1013" {
    smiv2:oid "1.3.6.1.4.1.9.1.1166";
  }

  smiv2:alias "ciscoCDScde205" {
    smiv2:oid "1.3.6.1.4.1.9.1.1167";
  }

  smiv2:alias "ciscoPwr1941AC" {
    smiv2:oid "1.3.6.1.4.1.9.1.1168";
  }

  smiv2:alias "ciscoNamWaasVirtualBlade" {
    smiv2:oid "1.3.6.1.4.1.9.1.1169";
  }

  smiv2:alias "ciscoRaie1783Rms06t" {
    smiv2:oid "1.3.6.1.4.1.9.1.1170";
  }

  smiv2:alias "ciscoRaie1783Rms10t" {
    smiv2:oid "1.3.6.1.4.1.9.1.1171";
  }

  smiv2:alias "cisco1941WEK9" {
    smiv2:oid "1.3.6.1.4.1.9.1.1172";
  }

  smiv2:alias "cisco1941WPK9" {
    smiv2:oid "1.3.6.1.4.1.9.1.1173";
  }

  smiv2:alias "cisco1941WNK9" {
    smiv2:oid "1.3.6.1.4.1.9.1.1174";
  }

  smiv2:alias "ciscoMXE5600" {
    smiv2:oid "1.3.6.1.4.1.9.1.1175";
  }

  smiv2:alias "ciscoEsw5408pK9" {
    smiv2:oid "1.3.6.1.4.1.9.1.1176";
  }

  smiv2:alias "ciscoEsw5208pK9" {
    smiv2:oid "1.3.6.1.4.1.9.1.1177";
  }

  smiv2:alias "catalyst4948e10GE" {
    smiv2:oid "1.3.6.1.4.1.9.1.1178";
  }

  smiv2:alias "cat2960x48tsS" {
    smiv2:oid "1.3.6.1.4.1.9.1.1179";
  }

  smiv2:alias "cat2960x24tsS" {
    smiv2:oid "1.3.6.1.4.1.9.1.1180";
  }

  smiv2:alias "cat2960xs48fpdL" {
    smiv2:oid "1.3.6.1.4.1.9.1.1181";
  }

  smiv2:alias "cat2960xs48lpdL" {
    smiv2:oid "1.3.6.1.4.1.9.1.1182";
  }

  smiv2:alias "cat2960xs48ltdL" {
    smiv2:oid "1.3.6.1.4.1.9.1.1183";
  }

  smiv2:alias "cat2960xs24pdL" {
    smiv2:oid "1.3.6.1.4.1.9.1.1184";
  }

  smiv2:alias "cat2960xs24tdL" {
    smiv2:oid "1.3.6.1.4.1.9.1.1185";
  }

  smiv2:alias "cat2960xs48fpsL" {
    smiv2:oid "1.3.6.1.4.1.9.1.1186";
  }

  smiv2:alias "cat2960xs48lpsL" {
    smiv2:oid "1.3.6.1.4.1.9.1.1187";
  }

  smiv2:alias "cat2960xs24psL" {
    smiv2:oid "1.3.6.1.4.1.9.1.1188";
  }

  smiv2:alias "cat2960xs48tsL" {
    smiv2:oid "1.3.6.1.4.1.9.1.1189";
  }

  smiv2:alias "cat2960xs24tsL" {
    smiv2:oid "1.3.6.1.4.1.9.1.1190";
  }

  smiv2:alias "cisco1921k9" {
    smiv2:oid "1.3.6.1.4.1.9.1.1191";
  }

  smiv2:alias "cisco1905k9" {
    smiv2:oid "1.3.6.1.4.1.9.1.1192";
  }

  smiv2:alias "ciscoPwrC1921C1905AC" {
    smiv2:oid "1.3.6.1.4.1.9.1.1193";
  }

  smiv2:alias "ciscoASA5585Ssp10" {
    smiv2:oid "1.3.6.1.4.1.9.1.1194";
  }

  smiv2:alias "ciscoASA5585Ssp20" {
    smiv2:oid "1.3.6.1.4.1.9.1.1195";
  }

  smiv2:alias "ciscoASA5585Ssp40" {
    smiv2:oid "1.3.6.1.4.1.9.1.1196";
  }

  smiv2:alias "ciscoASA5585Ssp60" {
    smiv2:oid "1.3.6.1.4.1.9.1.1197";
  }

  smiv2:alias "ciscoASA5585Ssp10sc" {
    smiv2:oid "1.3.6.1.4.1.9.1.1198";
  }

  smiv2:alias "ciscoASA5585Ssp20sc" {
    smiv2:oid "1.3.6.1.4.1.9.1.1199";
  }

  smiv2:alias "ciscoASA5585Ssp40sc" {
    smiv2:oid "1.3.6.1.4.1.9.1.1200";
  }

  smiv2:alias "ciscoASA5585Ssp60sc" {
    smiv2:oid "1.3.6.1.4.1.9.1.1201";
  }

  smiv2:alias "ciscoASA5585Ssp10sy" {
    smiv2:oid "1.3.6.1.4.1.9.1.1202";
  }

  smiv2:alias "ciscoASA5585Ssp20sy" {
    smiv2:oid "1.3.6.1.4.1.9.1.1203";
  }

  smiv2:alias "ciscoASA5585Ssp40sy" {
    smiv2:oid "1.3.6.1.4.1.9.1.1204";
  }

  smiv2:alias "ciscoASA5585Ssp60sy" {
    smiv2:oid "1.3.6.1.4.1.9.1.1205";
  }

  smiv2:alias "cisco3925SPE250" {
    smiv2:oid "1.3.6.1.4.1.9.1.1206";
  }

  smiv2:alias "cisco3945SPE200" {
    smiv2:oid "1.3.6.1.4.1.9.1.1207";
  }

  smiv2:alias "cat29xxStack" {
    smiv2:oid "1.3.6.1.4.1.9.1.1208";
  }

  smiv2:alias "ciscoOeNm302" {
    smiv2:oid "1.3.6.1.4.1.9.1.1209";
  }

  smiv2:alias "ciscoOeNm502" {
    smiv2:oid "1.3.6.1.4.1.9.1.1210";
  }

  smiv2:alias "ciscoOeNm522" {
    smiv2:oid "1.3.6.1.4.1.9.1.1211";
  }

  smiv2:alias "ciscoOeSmSre700" {
    smiv2:oid "1.3.6.1.4.1.9.1.1212";
  }

  smiv2:alias "ciscoOeSmSre900" {
    smiv2:oid "1.3.6.1.4.1.9.1.1213";
  }

  smiv2:alias "ciscoVsaNam" {
    smiv2:oid "1.3.6.1.4.1.9.1.1214";
  }

  smiv2:alias "ciscoMwr2941DCA" {
    smiv2:oid "1.3.6.1.4.1.9.1.1215";
  }

  smiv2:alias "ciscoN7KC7018IOS" {
    smiv2:oid "1.3.6.1.4.1.9.1.1216";
  }

  smiv2:alias "ciscoN7KC7010IOS" {
    smiv2:oid "1.3.6.1.4.1.9.1.1217";
  }

  smiv2:alias "ciscoN4KDellEth" {
    smiv2:oid "1.3.6.1.4.1.9.1.1218";
  }

  smiv2:alias "ciscoN4KDellCiscoEth" {
    smiv2:oid "1.3.6.1.4.1.9.1.1219";
  }

  smiv2:alias "cisco1941WCK9" {
    smiv2:oid "1.3.6.1.4.1.9.1.1220";
  }

  smiv2:alias "ciscoCDScde2202s3" {
    smiv2:oid "1.3.6.1.4.1.9.1.1221";
  }

  smiv2:alias "cat3750x24" {
    smiv2:oid "1.3.6.1.4.1.9.1.1222";
  }

  smiv2:alias "cat3750x48" {
    smiv2:oid "1.3.6.1.4.1.9.1.1223";
  }

  smiv2:alias "cat3750x24P" {
    smiv2:oid "1.3.6.1.4.1.9.1.1224";
  }

  smiv2:alias "cat3750x48P" {
    smiv2:oid "1.3.6.1.4.1.9.1.1225";
  }

  smiv2:alias "cat3560x24" {
    smiv2:oid "1.3.6.1.4.1.9.1.1226";
  }

  smiv2:alias "cat3560x48" {
    smiv2:oid "1.3.6.1.4.1.9.1.1227";
  }

  smiv2:alias "cat3560x24P" {
    smiv2:oid "1.3.6.1.4.1.9.1.1228";
  }

  smiv2:alias "cat3560x48P" {
    smiv2:oid "1.3.6.1.4.1.9.1.1229";
  }

  smiv2:alias "ciscoNMEAIR" {
    smiv2:oid "1.3.6.1.4.1.9.1.1230";
  }

  smiv2:alias "ciscoACE30K9" {
    smiv2:oid "1.3.6.1.4.1.9.1.1231";
  }

  smiv2:alias "ciscoASA5585SspIps10" {
    smiv2:oid "1.3.6.1.4.1.9.1.1232";
  }

  smiv2:alias "ciscoASA5585SspIps20" {
    smiv2:oid "1.3.6.1.4.1.9.1.1233";
  }

  smiv2:alias "ciscoASA5585SspIps40" {
    smiv2:oid "1.3.6.1.4.1.9.1.1234";
  }

  smiv2:alias "ciscoASA5585SspIps60" {
    smiv2:oid "1.3.6.1.4.1.9.1.1235";
  }

  smiv2:alias "cisco1841CK9" {
    smiv2:oid "1.3.6.1.4.1.9.1.1236";
  }

  smiv2:alias "cisco2801CK9" {
    smiv2:oid "1.3.6.1.4.1.9.1.1237";
  }

  smiv2:alias "cisco2811CK9" {
    smiv2:oid "1.3.6.1.4.1.9.1.1238";
  }

  smiv2:alias "cisco2821CK9" {
    smiv2:oid "1.3.6.1.4.1.9.1.1239";
  }

  smiv2:alias "cisco2851CK9" {
    smiv2:oid "1.3.6.1.4.1.9.1.1240";
  }

  smiv2:alias "cisco3825CK9" {
    smiv2:oid "1.3.6.1.4.1.9.1.1241";
  }

  smiv2:alias "cisco3845CK9" {
    smiv2:oid "1.3.6.1.4.1.9.1.1242";
  }

  smiv2:alias "cisco3825CnvK9" {
    smiv2:oid "1.3.6.1.4.1.9.1.1243";
  }

  smiv2:alias "cisco3845CnvK9" {
    smiv2:oid "1.3.6.1.4.1.9.1.1244";
  }

  smiv2:alias "ciscoCGS252024TC" {
    smiv2:oid "1.3.6.1.4.1.9.1.1245";
  }

  smiv2:alias "ciscoCGS252016S8PC" {
    smiv2:oid "1.3.6.1.4.1.9.1.1246";
  }

  smiv2:alias "ciscoAIRAP1262" {
    smiv2:oid "1.3.6.1.4.1.9.1.1247";
  }

  smiv2:alias "ciscoAIRAP1261" {
    smiv2:oid "1.3.6.1.4.1.9.1.1248";
  }

  smiv2:alias "cisco892F" {
    smiv2:oid "1.3.6.1.4.1.9.1.1249";
  }

  smiv2:alias "ciscoMe3600x24fsM" {
    smiv2:oid "1.3.6.1.4.1.9.1.1250";
  }

  smiv2:alias "ciscoMe3600x24tsM" {
    smiv2:oid "1.3.6.1.4.1.9.1.1251";
  }

  smiv2:alias "ciscoMe3800x24fsM" {
    smiv2:oid "1.3.6.1.4.1.9.1.1252";
  }

  smiv2:alias "ciscoCGR2010" {
    smiv2:oid "1.3.6.1.4.1.9.1.1253";
  }

  smiv2:alias "ciscoPwrCGR20xxCGS25xxPoeAC" {
    smiv2:oid "1.3.6.1.4.1.9.1.1254";
  }

  smiv2:alias "ciscoPwrCGR20xxCGS25xxPoeDC" {
    smiv2:oid "1.3.6.1.4.1.9.1.1255";
  }

  smiv2:alias "catWsC2960s48tsS" {
    smiv2:oid "1.3.6.1.4.1.9.1.1256";
  }

  smiv2:alias "catWsC2960s24tsS" {
    smiv2:oid "1.3.6.1.4.1.9.1.1257";
  }

  smiv2:alias "catWsC2960s48fpdL" {
    smiv2:oid "1.3.6.1.4.1.9.1.1258";
  }

  smiv2:alias "catWsC2960s48ldpL" {
    smiv2:oid "1.3.6.1.4.1.9.1.1259";
  }

  smiv2:alias "catWsC2960s48tdL" {
    smiv2:oid "1.3.6.1.4.1.9.1.1260";
  }

  smiv2:alias "catWsC2960s24pdL" {
    smiv2:oid "1.3.6.1.4.1.9.1.1261";
  }

  smiv2:alias "catWsC2960s24tdL" {
    smiv2:oid "1.3.6.1.4.1.9.1.1262";
  }

  smiv2:alias "catWsC2960s48fpsL" {
    smiv2:oid "1.3.6.1.4.1.9.1.1263";
  }

  smiv2:alias "catWsC2960s48lpsL" {
    smiv2:oid "1.3.6.1.4.1.9.1.1264";
  }

  smiv2:alias "catWsC2960s24psL" {
    smiv2:oid "1.3.6.1.4.1.9.1.1265";
  }

  smiv2:alias "catWsC2960s48tsL" {
    smiv2:oid "1.3.6.1.4.1.9.1.1266";
  }

  smiv2:alias "catWsC2960s24tsL" {
    smiv2:oid "1.3.6.1.4.1.9.1.1267";
  }

  smiv2:alias "cisco1906CK9" {
    smiv2:oid "1.3.6.1.4.1.9.1.1268";
  }

  smiv2:alias "ciscoAIRAP1042" {
    smiv2:oid "1.3.6.1.4.1.9.1.1269";
  }

  smiv2:alias "ciscoAIRAP1041" {
    smiv2:oid "1.3.6.1.4.1.9.1.1270";
  }

  smiv2:alias "cisco887VaM" {
    smiv2:oid "1.3.6.1.4.1.9.1.1271";
  }

  smiv2:alias "cisco867Va" {
    smiv2:oid "1.3.6.1.4.1.9.1.1272";
  }

  smiv2:alias "cisco886Va" {
    smiv2:oid "1.3.6.1.4.1.9.1.1273";
  }

  smiv2:alias "cisco887Va" {
    smiv2:oid "1.3.6.1.4.1.9.1.1274";
  }

  smiv2:alias "ciscoASASm1sc" {
    smiv2:oid "1.3.6.1.4.1.9.1.1275";
  }

  smiv2:alias "ciscoASASm1sy" {
    smiv2:oid "1.3.6.1.4.1.9.1.1276";
  }

  smiv2:alias "ciscoASASm1" {
    smiv2:oid "1.3.6.1.4.1.9.1.1277";
  }

  smiv2:alias "cat2960cPD8TT" {
    smiv2:oid "1.3.6.1.4.1.9.1.1278";
  }

  smiv2:alias "ciscoAirCt2504K9" {
    smiv2:oid "1.3.6.1.4.1.9.1.1279";
  }

  smiv2:alias "ciscoISMAXP" {
    smiv2:oid "1.3.6.1.4.1.9.1.1280";
  }

  smiv2:alias "ciscoSMAXP" {
    smiv2:oid "1.3.6.1.4.1.9.1.1281";
  }

  smiv2:alias "ciscoAxpSmSre900" {
    smiv2:oid "1.3.6.1.4.1.9.1.1282";
  }

  smiv2:alias "ciscoAxpSmSre700" {
    smiv2:oid "1.3.6.1.4.1.9.1.1283";
  }

  smiv2:alias "ciscoAxpIsmSre300" {
    smiv2:oid "1.3.6.1.4.1.9.1.1284";
  }

  smiv2:alias "ciscoCDSISM" {
    smiv2:oid "1.3.6.1.4.1.9.1.1285";
  }

  smiv2:alias "cat4507rpluse" {
    smiv2:oid "1.3.6.1.4.1.9.1.1286";
  }

  smiv2:alias "cat4510rpluse" {
    smiv2:oid "1.3.6.1.4.1.9.1.1287";
  }

  smiv2:alias "ciscoAxpNme302" {
    smiv2:oid "1.3.6.1.4.1.9.1.1288";
  }

  smiv2:alias "ciscoAxpNme502" {
    smiv2:oid "1.3.6.1.4.1.9.1.1289";
  }

  smiv2:alias "ciscoAxpNme522" {
    smiv2:oid "1.3.6.1.4.1.9.1.1290";
  }

  smiv2:alias "ciscoACE20K9" {
    smiv2:oid "1.3.6.1.4.1.9.1.1291";
  }

  smiv2:alias "ciscoWsC236048tdS" {
    smiv2:oid "1.3.6.1.4.1.9.1.1292";
  }

  smiv2:alias "ciscoWiSM2" {
    smiv2:oid "1.3.6.1.4.1.9.1.1293";
  }

  smiv2:alias "ciscoCDScde250" {
    smiv2:oid "1.3.6.1.4.1.9.1.1294";
  }

  smiv2:alias "cisco7500Wlc" {
    smiv2:oid "1.3.6.1.4.1.9.1.1295";
  }

  smiv2:alias "ciscoAnmVirtualApp" {
    smiv2:oid "1.3.6.1.4.1.9.1.1296";
  }

  smiv2:alias "ciscoECDS3100" {
    smiv2:oid "1.3.6.1.4.1.9.1.1297";
  }

  smiv2:alias "ciscoECDS1100" {
    smiv2:oid "1.3.6.1.4.1.9.1.1298";
  }

  smiv2:alias "cisco881G2" {
    smiv2:oid "1.3.6.1.4.1.9.1.1299";
  }

  smiv2:alias "catWsC3750v224fsS" {
    smiv2:oid "1.3.6.1.4.1.9.1.1300";
  }

  smiv2:alias "ciscoOeVWaas" {
    smiv2:oid "1.3.6.1.4.1.9.1.1301";
  }

  smiv2:alias "ciscoASA5585Ssp10K7" {
    smiv2:oid "1.3.6.1.4.1.9.1.1302";
  }

  smiv2:alias "ciscoASA5585Ssp20K7" {
    smiv2:oid "1.3.6.1.4.1.9.1.1303";
  }

  smiv2:alias "ciscoASA5585Ssp40K7" {
    smiv2:oid "1.3.6.1.4.1.9.1.1304";
  }

  smiv2:alias "ciscoASA5585Ssp60K7" {
    smiv2:oid "1.3.6.1.4.1.9.1.1305";
  }

  smiv2:alias "ciscoASA5585Ssp10K7sc" {
    smiv2:oid "1.3.6.1.4.1.9.1.1306";
  }

  smiv2:alias "ciscoASA5585Ssp20K7sc" {
    smiv2:oid "1.3.6.1.4.1.9.1.1307";
  }

  smiv2:alias "ciscoASA5585Ssp40K7sc" {
    smiv2:oid "1.3.6.1.4.1.9.1.1308";
  }

  smiv2:alias "ciscoASA5585Ssp60K7sc" {
    smiv2:oid "1.3.6.1.4.1.9.1.1309";
  }

  smiv2:alias "ciscoASA5585Ssp10K7sy" {
    smiv2:oid "1.3.6.1.4.1.9.1.1310";
  }

  smiv2:alias "ciscoASA5585Ssp20K7sy" {
    smiv2:oid "1.3.6.1.4.1.9.1.1311";
  }

  smiv2:alias "ciscoASA5585Ssp40K7sy" {
    smiv2:oid "1.3.6.1.4.1.9.1.1312";
  }

  smiv2:alias "ciscoASA5585Ssp60K7sy" {
    smiv2:oid "1.3.6.1.4.1.9.1.1313";
  }

  smiv2:alias "ciscoSreSmNam" {
    smiv2:oid "1.3.6.1.4.1.9.1.1314";
  }

  smiv2:alias "cat2960cPD8PT" {
    smiv2:oid "1.3.6.1.4.1.9.1.1315";
  }

  smiv2:alias "cat2960cG8TC" {
    smiv2:oid "1.3.6.1.4.1.9.1.1316";
  }

  smiv2:alias "cat3560cG8PC" {
    smiv2:oid "1.3.6.1.4.1.9.1.1317";
  }

  smiv2:alias "cat3560cG8TC" {
    smiv2:oid "1.3.6.1.4.1.9.1.1318";
  }

  smiv2:alias "ciscoIE301016S8PC" {
    smiv2:oid "1.3.6.1.4.1.9.1.1319";
  }

  smiv2:alias "ciscoIE301024TC" {
    smiv2:oid "1.3.6.1.4.1.9.1.1320";
  }

  smiv2:alias "ciscoRAIE1783RMSB10T" {
    smiv2:oid "1.3.6.1.4.1.9.1.1321";
  }

  smiv2:alias "ciscoRAIE1783RMSB06T" {
    smiv2:oid "1.3.6.1.4.1.9.1.1322";
  }

  smiv2:alias "ciscoASA5585SspIps10K7" {
    smiv2:oid "1.3.6.1.4.1.9.1.1323";
  }

  smiv2:alias "ciscoASA5585SspIps20K7" {
    smiv2:oid "1.3.6.1.4.1.9.1.1324";
  }

  smiv2:alias "ciscoASA5585SspIps40K7" {
    smiv2:oid "1.3.6.1.4.1.9.1.1325";
  }

  smiv2:alias "ciscoASA5585SspIps60K7" {
    smiv2:oid "1.3.6.1.4.1.9.1.1326";
  }

  smiv2:alias "catalyst4948ef10GE" {
    smiv2:oid "1.3.6.1.4.1.9.1.1327";
  }

  smiv2:alias "cat292824TCC" {
    smiv2:oid "1.3.6.1.4.1.9.1.1328";
  }

  smiv2:alias "cat292848TCC" {
    smiv2:oid "1.3.6.1.4.1.9.1.1329";
  }

  smiv2:alias "cat292824LTC" {
    smiv2:oid "1.3.6.1.4.1.9.1.1330";
  }

  smiv2:alias "ciscoCrs16SB" {
    smiv2:oid "1.3.6.1.4.1.9.1.1331";
  }

  smiv2:alias "ciscoQuad" {
    smiv2:oid "1.3.6.1.4.1.9.1.1332";
  }

  smiv2:alias "ciscoASASm1K7sc" {
    smiv2:oid "1.3.6.1.4.1.9.1.1334";
  }

  smiv2:alias "ciscoASASm1K7sy" {
    smiv2:oid "1.3.6.1.4.1.9.1.1335";
  }

  smiv2:alias "ciscoASASm1K7" {
    smiv2:oid "1.3.6.1.4.1.9.1.1336";
  }

  smiv2:alias "ciscoPwrCGR2010PoeAC" {
    smiv2:oid "1.3.6.1.4.1.9.1.1337";
  }

  smiv2:alias "ciscoPwrCGR2010PoeDC" {
    smiv2:oid "1.3.6.1.4.1.9.1.1338";
  }

  smiv2:alias "cisco1861eUc2BK9" {
    smiv2:oid "1.3.6.1.4.1.9.1.1339";
  }

  smiv2:alias "cisco1861eUc4FK9" {
    smiv2:oid "1.3.6.1.4.1.9.1.1340";
  }

  smiv2:alias "ciscoC1861eSrstFK9" {
    smiv2:oid "1.3.6.1.4.1.9.1.1341";
  }

  smiv2:alias "ciscoC1861eSrstBK9" {
    smiv2:oid "1.3.6.1.4.1.9.1.1342";
  }

  smiv2:alias "ciscoC1861eSrstCFK9" {
    smiv2:oid "1.3.6.1.4.1.9.1.1343";
  }

  smiv2:alias "ciscoC1861eSrstCBK9" {
    smiv2:oid "1.3.6.1.4.1.9.1.1344";
  }

  smiv2:alias "ciscoGrwicDes6s" {
    smiv2:oid "1.3.6.1.4.1.9.1.1346";
  }

  smiv2:alias "ciscoGrwicDes2s8pc" {
    smiv2:oid "1.3.6.1.4.1.9.1.1347";
  }

  smiv2:alias "ciscoUCVirtualMachine" {
    smiv2:oid "1.3.6.1.4.1.9.1.1348";
  }

  smiv2:alias "ciscoWave8541" {
    smiv2:oid "1.3.6.1.4.1.9.1.1349";
  }

  smiv2:alias "ciscoWave7571" {
    smiv2:oid "1.3.6.1.4.1.9.1.1350";
  }

  smiv2:alias "ciscoWave7541" {
    smiv2:oid "1.3.6.1.4.1.9.1.1351";
  }

  smiv2:alias "ciscoWave694" {
    smiv2:oid "1.3.6.1.4.1.9.1.1352";
  }

  smiv2:alias "ciscoWave594" {
    smiv2:oid "1.3.6.1.4.1.9.1.1353";
  }

  smiv2:alias "ciscoWave294" {
    smiv2:oid "1.3.6.1.4.1.9.1.1354";
  }

  smiv2:alias "cisco5915RC" {
    smiv2:oid "1.3.6.1.4.1.9.1.1355";
  }

  smiv2:alias "cisco5915RA" {
    smiv2:oid "1.3.6.1.4.1.9.1.1356";
  }

  smiv2:alias "cisco867VAEK9" {
    smiv2:oid "1.3.6.1.4.1.9.1.1358";
  }

  smiv2:alias "cisco866VAEK9" {
    smiv2:oid "1.3.6.1.4.1.9.1.1359";
  }

  smiv2:alias "cisco867VAE" {
    smiv2:oid "1.3.6.1.4.1.9.1.1360";
  }

  smiv2:alias "cisco866VAE" {
    smiv2:oid "1.3.6.1.4.1.9.1.1361";
  }

  smiv2:alias "ciscoAp802gn" {
    smiv2:oid "1.3.6.1.4.1.9.1.1362";
  }

  smiv2:alias "ciscoAp802agn" {
    smiv2:oid "1.3.6.1.4.1.9.1.1363";
  }

  smiv2:alias "catwsC2960C8tcS" {
    smiv2:oid "1.3.6.1.4.1.9.1.1364";
  }

  smiv2:alias "catwsC2960C8tcL" {
    smiv2:oid "1.3.6.1.4.1.9.1.1365";
  }

  smiv2:alias "catwsC2960C8pcL" {
    smiv2:oid "1.3.6.1.4.1.9.1.1366";
  }

  smiv2:alias "catwsC2960C12pcL" {
    smiv2:oid "1.3.6.1.4.1.9.1.1367";
  }

  smiv2:alias "catwsC3560CPD8ptS" {
    smiv2:oid "1.3.6.1.4.1.9.1.1368";
  }

  smiv2:alias "cisco1841ve" {
    smiv2:oid "1.3.6.1.4.1.9.1.1369";
  }

  smiv2:alias "cisco2811ve" {
    smiv2:oid "1.3.6.1.4.1.9.1.1370";
  }

  smiv2:alias "cisco881WAK9" {
    smiv2:oid "1.3.6.1.4.1.9.1.1371";
  }

  smiv2:alias "cisco881WEK9" {
    smiv2:oid "1.3.6.1.4.1.9.1.1372";
  }

  smiv2:alias "cisco881WPK9" {
    smiv2:oid "1.3.6.1.4.1.9.1.1373";
  }

  smiv2:alias "cisco886VaWEK9" {
    smiv2:oid "1.3.6.1.4.1.9.1.1374";
  }

  smiv2:alias "cisco887VamWEK9" {
    smiv2:oid "1.3.6.1.4.1.9.1.1375";
  }

  smiv2:alias "cisco887VaWAK9" {
    smiv2:oid "1.3.6.1.4.1.9.1.1376";
  }

  smiv2:alias "cisco887VaWEK9" {
    smiv2:oid "1.3.6.1.4.1.9.1.1377";
  }

  smiv2:alias "cisco819GUK9" {
    smiv2:oid "1.3.6.1.4.1.9.1.1378";
  }

  smiv2:alias "cisco819GSK9" {
    smiv2:oid "1.3.6.1.4.1.9.1.1379";
  }

  smiv2:alias "cisco819GVK9" {
    smiv2:oid "1.3.6.1.4.1.9.1.1380";
  }

  smiv2:alias "cisco819GBK9" {
    smiv2:oid "1.3.6.1.4.1.9.1.1381";
  }

  smiv2:alias "cisco819G7AK9" {
    smiv2:oid "1.3.6.1.4.1.9.1.1382";
  }

  smiv2:alias "cisco819G7K9" {
    smiv2:oid "1.3.6.1.4.1.9.1.1383";
  }

  smiv2:alias "cisco819HGUK9" {
    smiv2:oid "1.3.6.1.4.1.9.1.1384";
  }

  smiv2:alias "cisco819HGSK9" {
    smiv2:oid "1.3.6.1.4.1.9.1.1385";
  }

  smiv2:alias "cisco819HGVK9" {
    smiv2:oid "1.3.6.1.4.1.9.1.1386";
  }

  smiv2:alias "cisco819HGBK9" {
    smiv2:oid "1.3.6.1.4.1.9.1.1387";
  }

  smiv2:alias "cisco819HG7AK9" {
    smiv2:oid "1.3.6.1.4.1.9.1.1388";
  }

  smiv2:alias "cisco819HG7K9" {
    smiv2:oid "1.3.6.1.4.1.9.1.1389";
  }

  smiv2:alias "cisco886Vag7K9" {
    smiv2:oid "1.3.6.1.4.1.9.1.1390";
  }

  smiv2:alias "cisco887VagSK9" {
    smiv2:oid "1.3.6.1.4.1.9.1.1391";
  }

  smiv2:alias "cisco887Vag7K9" {
    smiv2:oid "1.3.6.1.4.1.9.1.1392";
  }

  smiv2:alias "cisco887Vamg7K9" {
    smiv2:oid "1.3.6.1.4.1.9.1.1393";
  }

  smiv2:alias "cisco888Eg7K9" {
    smiv2:oid "1.3.6.1.4.1.9.1.1394";
  }

  smiv2:alias "cisco881GUK9" {
    smiv2:oid "1.3.6.1.4.1.9.1.1395";
  }

  smiv2:alias "cisco881GSK9" {
    smiv2:oid "1.3.6.1.4.1.9.1.1396";
  }

  smiv2:alias "cisco881GVK9" {
    smiv2:oid "1.3.6.1.4.1.9.1.1397";
  }

  smiv2:alias "cisco881GBK9" {
    smiv2:oid "1.3.6.1.4.1.9.1.1398";
  }

  smiv2:alias "cisco881G7K9" {
    smiv2:oid "1.3.6.1.4.1.9.1.1399";
  }

  smiv2:alias "cisco881G7AK9" {
    smiv2:oid "1.3.6.1.4.1.9.1.1400";
  }

  smiv2:alias "cat3750x24s" {
    smiv2:oid "1.3.6.1.4.1.9.1.1404";
  }

  smiv2:alias "cat3750x12s" {
    smiv2:oid "1.3.6.1.4.1.9.1.1405";
  }

  smiv2:alias "ciscoNME" {
    smiv2:oid "1.3.6.1.4.1.9.1.1406";
  }

  smiv2:alias "ciscoASA5512" {
    smiv2:oid "1.3.6.1.4.1.9.1.1407";
  }

  smiv2:alias "ciscoASA5525" {
    smiv2:oid "1.3.6.1.4.1.9.1.1408";
  }

  smiv2:alias "ciscoASA5545" {
    smiv2:oid "1.3.6.1.4.1.9.1.1409";
  }

  smiv2:alias "ciscoASA5555" {
    smiv2:oid "1.3.6.1.4.1.9.1.1410";
  }

  smiv2:alias "ciscoASA5512sc" {
    smiv2:oid "1.3.6.1.4.1.9.1.1411";
  }

  smiv2:alias "ciscoASA5525sc" {
    smiv2:oid "1.3.6.1.4.1.9.1.1412";
  }

  smiv2:alias "ciscoASA5545sc" {
    smiv2:oid "1.3.6.1.4.1.9.1.1413";
  }

  smiv2:alias "ciscoASA5555sc" {
    smiv2:oid "1.3.6.1.4.1.9.1.1414";
  }

  smiv2:alias "ciscoASA5512sy" {
    smiv2:oid "1.3.6.1.4.1.9.1.1415";
  }

  smiv2:alias "ciscoASA5515sy" {
    smiv2:oid "1.3.6.1.4.1.9.1.1416";
  }

  smiv2:alias "ciscoASA5525sy" {
    smiv2:oid "1.3.6.1.4.1.9.1.1417";
  }

  smiv2:alias "ciscoASA5545sy" {
    smiv2:oid "1.3.6.1.4.1.9.1.1418";
  }

  smiv2:alias "ciscoASA5555sy" {
    smiv2:oid "1.3.6.1.4.1.9.1.1419";
  }

  smiv2:alias "ciscoASA5515sc" {
    smiv2:oid "1.3.6.1.4.1.9.1.1420";
  }

  smiv2:alias "ciscoASA5515" {
    smiv2:oid "1.3.6.1.4.1.9.1.1421";
  }

  smiv2:alias "ciscoPCM" {
    smiv2:oid "1.3.6.1.4.1.9.1.1422";
  }

  smiv2:alias "ciscoIse3315K9" {
    smiv2:oid "1.3.6.1.4.1.9.1.1423";
  }

  smiv2:alias "ciscoIse3395K9" {
    smiv2:oid "1.3.6.1.4.1.9.1.1424";
  }

  smiv2:alias "ciscoIse3355K9" {
    smiv2:oid "1.3.6.1.4.1.9.1.1425";
  }

  smiv2:alias "ciscoIseVmK9" {
    smiv2:oid "1.3.6.1.4.1.9.1.1426";
  }

  smiv2:alias "ciscoIPS4345" {
    smiv2:oid "1.3.6.1.4.1.9.1.1428";
  }

  smiv2:alias "ciscoIPS4360" {
    smiv2:oid "1.3.6.1.4.1.9.1.1429";
  }

  smiv2:alias "ciscoEcdsVB" {
    smiv2:oid "1.3.6.1.4.1.9.1.1432";
  }

  smiv2:alias "ciscoTsCodecG2" {
    smiv2:oid "1.3.6.1.4.1.9.1.1433";
  }

  smiv2:alias "ciscoTsCodecG2C" {
    smiv2:oid "1.3.6.1.4.1.9.1.1434";
  }

  smiv2:alias "ciscoTSCodecG2RC" {
    smiv2:oid "1.3.6.1.4.1.9.1.1435";
  }

  smiv2:alias "ciscoTSCodecG2R" {
    smiv2:oid "1.3.6.1.4.1.9.1.1436";
  }

  smiv2:alias "ciscoASA5585SspIps10Virtual" {
    smiv2:oid "1.3.6.1.4.1.9.1.1437";
  }

  smiv2:alias "ciscoASA5585SspIps20Virtual" {
    smiv2:oid "1.3.6.1.4.1.9.1.1438";
  }

  smiv2:alias "ciscoASA5585SspIps40Virtual" {
    smiv2:oid "1.3.6.1.4.1.9.1.1439";
  }

  smiv2:alias "ciscoASA5585SspIps60Virtual" {
    smiv2:oid "1.3.6.1.4.1.9.1.1440";
  }

  smiv2:alias "ciscoASR903" {
    smiv2:oid "1.3.6.1.4.1.9.1.1441";
  }

  smiv2:alias "ciscoASA5512K7" {
    smiv2:oid "1.3.6.1.4.1.9.1.1442";
  }

  smiv2:alias "ciscoASA5515K7" {
    smiv2:oid "1.3.6.1.4.1.9.1.1443";
  }

  smiv2:alias "ciscoASA5525K7" {
    smiv2:oid "1.3.6.1.4.1.9.1.1444";
  }

  smiv2:alias "ciscoASA5545K7" {
    smiv2:oid "1.3.6.1.4.1.9.1.1445";
  }

  smiv2:alias "ciscoASA5555K7" {
    smiv2:oid "1.3.6.1.4.1.9.1.1446";
  }

  smiv2:alias "ciscoASA5512K7sc" {
    smiv2:oid "1.3.6.1.4.1.9.1.1447";
  }

  smiv2:alias "ciscoASA5515K7sc" {
    smiv2:oid "1.3.6.1.4.1.9.1.1448";
  }

  smiv2:alias "ciscoASA5525K7sc" {
    smiv2:oid "1.3.6.1.4.1.9.1.1449";
  }

  smiv2:alias "ciscoASA5545K7sc" {
    smiv2:oid "1.3.6.1.4.1.9.1.1450";
  }

  smiv2:alias "ciscoASA5555K7sc" {
    smiv2:oid "1.3.6.1.4.1.9.1.1451";
  }

  smiv2:alias "ciscoASA5512K7sy" {
    smiv2:oid "1.3.6.1.4.1.9.1.1452";
  }

  smiv2:alias "ciscoASA5515K7sy" {
    smiv2:oid "1.3.6.1.4.1.9.1.1453";
  }

  smiv2:alias "ciscoASA5525K7sy" {
    smiv2:oid "1.3.6.1.4.1.9.1.1454";
  }

  smiv2:alias "ciscoASA5545K7sy" {
    smiv2:oid "1.3.6.1.4.1.9.1.1455";
  }

  smiv2:alias "ciscoASA5555K7sy" {
    smiv2:oid "1.3.6.1.4.1.9.1.1456";
  }

  smiv2:alias "ciscoASR5500" {
    smiv2:oid "1.3.6.1.4.1.9.1.1457";
  }

  smiv2:alias "ciscoXfp10Ger192IrL" {
    smiv2:oid "1.3.6.1.4.1.9.1.1462";
  }

  smiv2:alias "ciscoXfp10Glr192SrL" {
    smiv2:oid "1.3.6.1.4.1.9.1.1463";
  }

  smiv2:alias "ciscoXfp10Gzr192LrL" {
    smiv2:oid "1.3.6.1.4.1.9.1.1464";
  }

  smiv2:alias "catwsC3560C12pcS" {
    smiv2:oid "1.3.6.1.4.1.9.1.1465";
  }

  smiv2:alias "catwsC3560C8pcS" {
    smiv2:oid "1.3.6.1.4.1.9.1.1466";
  }

  smiv2:alias "ciscoCRSFabBP" {
    smiv2:oid "1.3.6.1.4.1.9.1.1467";
  }

  smiv2:alias "ciscoIE20004TS" {
    smiv2:oid "1.3.6.1.4.1.9.1.1468";
  }

  smiv2:alias "ciscoIE20004T" {
    smiv2:oid "1.3.6.1.4.1.9.1.1469";
  }

  smiv2:alias "ciscoIE20004TSG" {
    smiv2:oid "1.3.6.1.4.1.9.1.1470";
  }

  smiv2:alias "ciscoIE20004TG" {
    smiv2:oid "1.3.6.1.4.1.9.1.1471";
  }

  smiv2:alias "ciscoIE20008TC" {
    smiv2:oid "1.3.6.1.4.1.9.1.1472";
  }

  smiv2:alias "ciscoIE20008TCG" {
    smiv2:oid "1.3.6.1.4.1.9.1.1473";
  }

  smiv2:alias "ciscoIE200016TC" {
    smiv2:oid "1.3.6.1.4.1.9.1.1474";
  }

  smiv2:alias "ciscoIE200016TCG" {
    smiv2:oid "1.3.6.1.4.1.9.1.1475";
  }

  smiv2:alias "ciscoRAIE1783BMS06SL" {
    smiv2:oid "1.3.6.1.4.1.9.1.1476";
  }

  smiv2:alias "ciscoRAIE1783BMS06TL" {
    smiv2:oid "1.3.6.1.4.1.9.1.1477";
  }

  smiv2:alias "ciscoRAIE1783BMS06TA" {
    smiv2:oid "1.3.6.1.4.1.9.1.1478";
  }

  smiv2:alias "ciscoRAIE1783BMS06SGL" {
    smiv2:oid "1.3.6.1.4.1.9.1.1479";
  }

  smiv2:alias "ciscoRAIE1783BMS06SGA" {
    smiv2:oid "1.3.6.1.4.1.9.1.1480";
  }

  smiv2:alias "ciscoRAIE1783BMS06TGL" {
    smiv2:oid "1.3.6.1.4.1.9.1.1481";
  }

  smiv2:alias "ciscoRAIE1783BMS06TGA" {
    smiv2:oid "1.3.6.1.4.1.9.1.1482";
  }

  smiv2:alias "ciscoRAIE1783BMS10CL" {
    smiv2:oid "1.3.6.1.4.1.9.1.1483";
  }

  smiv2:alias "ciscoRAIE1783BMS10CA" {
    smiv2:oid "1.3.6.1.4.1.9.1.1484";
  }

  smiv2:alias "ciscoRAIE1783BMS10CGL" {
    smiv2:oid "1.3.6.1.4.1.9.1.1485";
  }

  smiv2:alias "ciscoRAIE1783BMS10CGA" {
    smiv2:oid "1.3.6.1.4.1.9.1.1486";
  }

  smiv2:alias "ciscoRAIE1783BMS10CGP" {
    smiv2:oid "1.3.6.1.4.1.9.1.1487";
  }

  smiv2:alias "ciscoRAIE1783BMS10CGN" {
    smiv2:oid "1.3.6.1.4.1.9.1.1488";
  }

  smiv2:alias "ciscoRAIE1783BMS20CL" {
    smiv2:oid "1.3.6.1.4.1.9.1.1489";
  }

  smiv2:alias "ciscoRAIE1783BMS20CA" {
    smiv2:oid "1.3.6.1.4.1.9.1.1490";
  }

  smiv2:alias "ciscoRAIE1783BMS20CGL" {
    smiv2:oid "1.3.6.1.4.1.9.1.1491";
  }

  smiv2:alias "ciscoRAIE1783BMS20CGP" {
    smiv2:oid "1.3.6.1.4.1.9.1.1492";
  }

  smiv2:alias "ciscoRAIE1783BMS20CGPK" {
    smiv2:oid "1.3.6.1.4.1.9.1.1493";
  }

  smiv2:alias "cisco819HG4GGK9" {
    smiv2:oid "1.3.6.1.4.1.9.1.1494";
  }

  smiv2:alias "cisco819G4GAK9" {
    smiv2:oid "1.3.6.1.4.1.9.1.1495";
  }

  smiv2:alias "cisco819G4GVK9" {
    smiv2:oid "1.3.6.1.4.1.9.1.1496";
  }

  smiv2:alias "cisco819G4GGK9" {
    smiv2:oid "1.3.6.1.4.1.9.1.1497";
  }

  smiv2:alias "ciscoUcsC200" {
    smiv2:oid "1.3.6.1.4.1.9.1.1512";
  }

  smiv2:alias "ciscoUcsC210" {
    smiv2:oid "1.3.6.1.4.1.9.1.1513";
  }

  smiv2:alias "ciscoUcsC250" {
    smiv2:oid "1.3.6.1.4.1.9.1.1514";
  }

  smiv2:alias "ciscoUcsC260" {
    smiv2:oid "1.3.6.1.4.1.9.1.1515";
  }

  smiv2:alias "ciscoUcsC460" {
    smiv2:oid "1.3.6.1.4.1.9.1.1516";
  }

  smiv2:alias "ciscoRAIE1783BMS06SA" {
    smiv2:oid "1.3.6.1.4.1.9.1.1519";
  }

  smiv2:alias "ciscoIE200016TCGX" {
    smiv2:oid "1.3.6.1.4.1.9.1.1520";
  }

  smiv2:alias "ciscoASR901" {
    smiv2:oid "1.3.6.1.4.1.9.1.1521";
  }

  smiv2:alias "ciscoASR901E" {
    smiv2:oid "1.3.6.1.4.1.9.1.1522";
  }

  smiv2:alias "ciscoOeSmSre910" {
    smiv2:oid "1.3.6.1.4.1.9.1.1523";
  }

  smiv2:alias "ciscoOeSmSre710" {
    smiv2:oid "1.3.6.1.4.1.9.1.1524";
  }

  smiv2:alias "ciscoASR1002X" {
    smiv2:oid "1.3.6.1.4.1.9.1.1525";
  }

  smiv2:alias "ciscoNam2304" {
    smiv2:oid "1.3.6.1.4.1.9.1.1527";
  }

  smiv2:alias "ciscoNam2320" {
    smiv2:oid "1.3.6.1.4.1.9.1.1528";
  }

  smiv2:alias "ciscoNam3" {
    smiv2:oid "1.3.6.1.4.1.9.1.1529";
  }

  smiv2:alias "cisco819HG4GAK9" {
    smiv2:oid "1.3.6.1.4.1.9.1.1530";
  }

  smiv2:alias "ciscoECDS50IVB" {
    smiv2:oid "1.3.6.1.4.1.9.1.1536";
  }

  smiv2:alias "ciscoVSR1000" {
    smiv2:oid "1.3.6.1.4.1.9.1.1537";
  }

  smiv2:alias "ciscoASR5000" {
    smiv2:oid "1.3.6.1.4.1.9.1.1538";
  }

  smiv2:alias "ciscoflowAgent3000" {
    smiv2:oid "1.3.6.1.4.1.9.1.1539";
  }

  smiv2:alias "ciscoTelePresenceMCU5310" {
    smiv2:oid "1.3.6.1.4.1.9.1.1540";
  }

  smiv2:alias "ciscoTelePresenceMCU5320" {
    smiv2:oid "1.3.6.1.4.1.9.1.1541";
  }

  smiv2:alias "cisco888ea" {
    smiv2:oid "1.3.6.1.4.1.9.1.1542";
  }

  smiv2:alias "ciscoVG350" {
    smiv2:oid "1.3.6.1.4.1.9.1.1557";
  }

  smiv2:alias "cisco881GW7AK9" {
    smiv2:oid "1.3.6.1.4.1.9.1.1560";
  }

  smiv2:alias "cisco881GW7EK9" {
    smiv2:oid "1.3.6.1.4.1.9.1.1561";
  }

  smiv2:alias "cisco881GWSAK9" {
    smiv2:oid "1.3.6.1.4.1.9.1.1562";
  }

  smiv2:alias "cisco881GWVAK9" {
    smiv2:oid "1.3.6.1.4.1.9.1.1563";
  }

  smiv2:alias "cisco887Vagw7AK9" {
    smiv2:oid "1.3.6.1.4.1.9.1.1564";
  }

  smiv2:alias "cisco887Vagw7EK9" {
    smiv2:oid "1.3.6.1.4.1.9.1.1565";
  }

  smiv2:alias "cisco881WDAK9" {
    smiv2:oid "1.3.6.1.4.1.9.1.1566";
  }

  smiv2:alias "cisco881WDEK9" {
    smiv2:oid "1.3.6.1.4.1.9.1.1567";
  }

  smiv2:alias "cisco887VaWDAK9" {
    smiv2:oid "1.3.6.1.4.1.9.1.1568";
  }

  smiv2:alias "cisco887VaWDEK9" {
    smiv2:oid "1.3.6.1.4.1.9.1.1569";
  }

  smiv2:alias "cisco819HGW7EK9" {
    smiv2:oid "1.3.6.1.4.1.9.1.1570";
  }

  smiv2:alias "cisco819HGW7NK9" {
    smiv2:oid "1.3.6.1.4.1.9.1.1571";
  }

  smiv2:alias "cisco819HGW7AAK9" {
    smiv2:oid "1.3.6.1.4.1.9.1.1572";
  }

  smiv2:alias "cisco819HGWVAK9" {
    smiv2:oid "1.3.6.1.4.1.9.1.1573";
  }

  smiv2:alias "cisco819HGWSAK9" {
    smiv2:oid "1.3.6.1.4.1.9.1.1574";
  }

  smiv2:alias "cisco819HK9" {
    smiv2:oid "1.3.6.1.4.1.9.1.1575";
  }

  smiv2:alias "cisco819HWDEK9" {
    smiv2:oid "1.3.6.1.4.1.9.1.1576";
  }

  smiv2:alias "cisco819HWDAK9" {
    smiv2:oid "1.3.6.1.4.1.9.1.1577";
  }

  smiv2:alias "cisco812G7K9" {
    smiv2:oid "1.3.6.1.4.1.9.1.1578";
  }

  smiv2:alias "cisco812GCIFI7EK9" {
    smiv2:oid "1.3.6.1.4.1.9.1.1579";
  }

  smiv2:alias "cisco812GCIFI7NK9" {
    smiv2:oid "1.3.6.1.4.1.9.1.1580";
  }

  smiv2:alias "cisco812GCIFIVAK9" {
    smiv2:oid "1.3.6.1.4.1.9.1.1581";
  }

  smiv2:alias "cisco812GCIFISAK9" {
    smiv2:oid "1.3.6.1.4.1.9.1.1582";
  }

  smiv2:alias "cisco819GUMK9" {
    smiv2:oid "1.3.6.1.4.1.9.1.1583";
  }

  smiv2:alias "cisco819GSMK9" {
    smiv2:oid "1.3.6.1.4.1.9.1.1584";
  }

  smiv2:alias "cisco819GVMK9" {
    smiv2:oid "1.3.6.1.4.1.9.1.1585";
  }

  smiv2:alias "cisco819GBMK9" {
    smiv2:oid "1.3.6.1.4.1.9.1.1586";
  }

  smiv2:alias "cisco819G7AMK9" {
    smiv2:oid "1.3.6.1.4.1.9.1.1587";
  }

  smiv2:alias "cisco819G7MK9" {
    smiv2:oid "1.3.6.1.4.1.9.1.1588";
  }

  smiv2:alias "cisco819HGUMK9" {
    smiv2:oid "1.3.6.1.4.1.9.1.1589";
  }

  smiv2:alias "cisco819HGSMK9" {
    smiv2:oid "1.3.6.1.4.1.9.1.1590";
  }

  smiv2:alias "cisco819HGVMK9" {
    smiv2:oid "1.3.6.1.4.1.9.1.1591";
  }

  smiv2:alias "cisco819HGBMK9" {
    smiv2:oid "1.3.6.1.4.1.9.1.1592";
  }

  smiv2:alias "cisco819HG7AMK9" {
    smiv2:oid "1.3.6.1.4.1.9.1.1593";
  }

  smiv2:alias "cisco819HG7MK9" {
    smiv2:oid "1.3.6.1.4.1.9.1.1594";
  }

  smiv2:alias "ciscoCDScde2502s6" {
    smiv2:oid "1.3.6.1.4.1.9.1.1595";
  }

  smiv2:alias "ciscoCDScde2502m0" {
    smiv2:oid "1.3.6.1.4.1.9.1.1596";
  }

  smiv2:alias "ciscoCDScde2502s8" {
    smiv2:oid "1.3.6.1.4.1.9.1.1597";
  }

  smiv2:alias "cisco881V" {
    smiv2:oid "1.3.6.1.4.1.9.1.1600";
  }

  smiv2:alias "cisco887vaV" {
    smiv2:oid "1.3.6.1.4.1.9.1.1601";
  }

  smiv2:alias "cisco887vaVW" {
    smiv2:oid "1.3.6.1.4.1.9.1.1602";
  }

  smiv2:alias "ciscoMDE10XVB" {
    smiv2:oid "1.3.6.1.4.1.9.1.1603";
  }

  smiv2:alias "cat4500X16" {
    smiv2:oid "1.3.6.1.4.1.9.1.1605";
  }

  smiv2:alias "cat4500X32" {
    smiv2:oid "1.3.6.1.4.1.9.1.1606";
  }

  smiv2:alias "ciscoCDScde2502s9" {
    smiv2:oid "1.3.6.1.4.1.9.1.1607";
  }

  smiv2:alias "ciscoCDScde2502s10" {
    smiv2:oid "1.3.6.1.4.1.9.1.1608";
  }

  smiv2:alias "ciscoASA5585Nm20x1GE" {
    smiv2:oid "1.3.6.1.4.1.9.1.1610";
  }

  smiv2:alias "ciscoCDScdeGeneric" {
    smiv2:oid "1.3.6.1.4.1.9.1.1611";
  }

  smiv2:alias "ciscoASA1000Vsy" {
    smiv2:oid "1.3.6.1.4.1.9.1.1612";
  }

  smiv2:alias "ciscoASA1000Vsc" {
    smiv2:oid "1.3.6.1.4.1.9.1.1613";
  }

  smiv2:alias "ciscoASA1000V" {
    smiv2:oid "1.3.6.1.4.1.9.1.1614";
  }

  smiv2:alias "cisco8500WLC" {
    smiv2:oid "1.3.6.1.4.1.9.1.1615";
  }

  smiv2:alias "ciscoASA5585Nm8x10GE" {
    smiv2:oid "1.3.6.1.4.1.9.1.1617";
  }

  smiv2:alias "ciscoASA5585Nm4x10GE" {
    smiv2:oid "1.3.6.1.4.1.9.1.1618";
  }

  smiv2:alias "ciscoISR4400" {
    smiv2:oid "1.3.6.1.4.1.9.1.1619";
  }

  smiv2:alias "cisco897VaMK9" {
    smiv2:oid "1.3.6.1.4.1.9.1.1622";
  }

  smiv2:alias "ciscoVirtualWlc" {
    smiv2:oid "1.3.6.1.4.1.9.1.1631";
  }

  smiv2:alias "ciscoAIRAP802agn" {
    smiv2:oid "1.3.6.1.4.1.9.1.1632";
  }

  smiv2:alias "ciscoAp802Hagn" {
    smiv2:oid "1.3.6.1.4.1.9.1.1633";
  }

  smiv2:alias "ciscoE160DP" {
    smiv2:oid "1.3.6.1.4.1.9.1.1634";
  }

  smiv2:alias "ciscoE160D" {
    smiv2:oid "1.3.6.1.4.1.9.1.1635";
  }

  smiv2:alias "ciscoE140DP" {
    smiv2:oid "1.3.6.1.4.1.9.1.1636";
  }

  smiv2:alias "ciscoE140D" {
    smiv2:oid "1.3.6.1.4.1.9.1.1637";
  }

  smiv2:alias "ciscoE140S" {
    smiv2:oid "1.3.6.1.4.1.9.1.1638";
  }

  smiv2:alias "ciscoASR9001" {
    smiv2:oid "1.3.6.1.4.1.9.1.1639";
  }

  smiv2:alias "ciscoASR9922" {
    smiv2:oid "1.3.6.1.4.1.9.1.1640";
  }

  smiv2:alias "cat385048P" {
    smiv2:oid "1.3.6.1.4.1.9.1.1641";
  }

  smiv2:alias "cat385024P" {
    smiv2:oid "1.3.6.1.4.1.9.1.1642";
  }

  smiv2:alias "cat385048" {
    smiv2:oid "1.3.6.1.4.1.9.1.1643";
  }

  smiv2:alias "cat385024" {
    smiv2:oid "1.3.6.1.4.1.9.1.1644";
  }

  smiv2:alias "cisco5760wlc" {
    smiv2:oid "1.3.6.1.4.1.9.1.1645";
  }

  smiv2:alias "ciscoVSGateway" {
    smiv2:oid "1.3.6.1.4.1.9.1.1646";
  }

  smiv2:alias "ciscoIbiza" {
    smiv2:oid "1.3.6.1.4.1.9.1.1647";
  }

  smiv2:alias "ciscoSkyros" {
    smiv2:oid "1.3.6.1.4.1.9.1.1648";
  }

  smiv2:alias "ciscoAIRAP1601" {
    smiv2:oid "1.3.6.1.4.1.9.1.1656";
  }

  smiv2:alias "ciscoCRS8SB" {
    smiv2:oid "1.3.6.1.4.1.9.1.1658";
  }

  smiv2:alias "ciscoAIRAP2602" {
    smiv2:oid "1.3.6.1.4.1.9.1.1659";
  }

  smiv2:alias "ciscoAIRAP1602" {
    smiv2:oid "1.3.6.1.4.1.9.1.1660";
  }

  smiv2:alias "ciscoAIRAP3602" {
    smiv2:oid "1.3.6.1.4.1.9.1.1661";
  }

  smiv2:alias "ciscoAIRAP3601" {
    smiv2:oid "1.3.6.1.4.1.9.1.1662";
  }

  smiv2:alias "ciscoAIRAP1552" {
    smiv2:oid "1.3.6.1.4.1.9.1.1664";
  }

  smiv2:alias "ciscoAIRAP1553" {
    smiv2:oid "1.3.6.1.4.1.9.1.1665";
  }

  smiv2:alias "ciscoNexus1010X" {
    smiv2:oid "1.3.6.1.4.1.9.1.1667";
  }

  smiv2:alias "ciscoNexus1110S" {
    smiv2:oid "1.3.6.1.4.1.9.1.1668";
  }

  smiv2:alias "ciscoNexus1110X" {
    smiv2:oid "1.3.6.1.4.1.9.1.1669";
  }

  smiv2:alias "ciscoNexus1110XL" {
    smiv2:oid "1.3.6.1.4.1.9.1.1670";
  }

  smiv2:alias "ciscoHsE300K9" {
    smiv2:oid "1.3.6.1.4.1.9.1.1674";
  }

  smiv2:alias "cisco866VAEWEK9" {
    smiv2:oid "1.3.6.1.4.1.9.1.1675";
  }

  smiv2:alias "cisco867VAEWAK9" {
    smiv2:oid "1.3.6.1.4.1.9.1.1676";
  }

  smiv2:alias "cisco867VAEWEK9" {
    smiv2:oid "1.3.6.1.4.1.9.1.1677";
  }

  smiv2:alias "cisco867VAEPOEWAK9" {
    smiv2:oid "1.3.6.1.4.1.9.1.1678";
  }

  smiv2:alias "ciscoOeKWaas" {
    smiv2:oid "1.3.6.1.4.1.9.1.1681";
  }

  smiv2:alias "ciscoUcsC220" {
    smiv2:oid "1.3.6.1.4.1.9.1.1682";
  }

  smiv2:alias "ciscoUcsC240" {
    smiv2:oid "1.3.6.1.4.1.9.1.1683";
  }

  smiv2:alias "ciscoUcsC22" {
    smiv2:oid "1.3.6.1.4.1.9.1.1684";
  }

  smiv2:alias "ciscoUcsC24" {
    smiv2:oid "1.3.6.1.4.1.9.1.1685";
  }

  smiv2:alias "ciscoCDScde2202s4" {
    smiv2:oid "1.3.6.1.4.1.9.1.1686";
  }

  smiv2:alias "ciscoCDScde4604r1" {
    smiv2:oid "1.3.6.1.4.1.9.1.1687";
  }

  smiv2:alias "catWsC2960x48fpdL" {
    smiv2:oid "1.3.6.1.4.1.9.1.1690";
  }

  smiv2:alias "catWsC2960x48lpdL" {
    smiv2:oid "1.3.6.1.4.1.9.1.1691";
  }

  smiv2:alias "catWsC2960x48tdL" {
    smiv2:oid "1.3.6.1.4.1.9.1.1692";
  }

  smiv2:alias "catWsC2960x24pdL" {
    smiv2:oid "1.3.6.1.4.1.9.1.1693";
  }

  smiv2:alias "catWsC2960x24tdL" {
    smiv2:oid "1.3.6.1.4.1.9.1.1694";
  }

  smiv2:alias "catWsC2960x48fpsL" {
    smiv2:oid "1.3.6.1.4.1.9.1.1695";
  }

  smiv2:alias "catWsC2960x48lpsL" {
    smiv2:oid "1.3.6.1.4.1.9.1.1696";
  }

  smiv2:alias "catWsC2960x24psL" {
    smiv2:oid "1.3.6.1.4.1.9.1.1697";
  }

  smiv2:alias "catWsC2960x48tsL" {
    smiv2:oid "1.3.6.1.4.1.9.1.1698";
  }

  smiv2:alias "catWsC2960x24tsL" {
    smiv2:oid "1.3.6.1.4.1.9.1.1699";
  }

  smiv2:alias "catWsC2960x24psqL" {
    smiv2:oid "1.3.6.1.4.1.9.1.1700";
  }

  smiv2:alias "catWsC2960x48lpsS" {
    smiv2:oid "1.3.6.1.4.1.9.1.1701";
  }

  smiv2:alias "catWsC2960x24psS" {
    smiv2:oid "1.3.6.1.4.1.9.1.1702";
  }

  smiv2:alias "catWsC2960x48tsLL" {
    smiv2:oid "1.3.6.1.4.1.9.1.1703";
  }

  smiv2:alias "catWsC2960x24tsLL" {
    smiv2:oid "1.3.6.1.4.1.9.1.1704";
  }

  smiv2:alias "ciscoISR4441" {
    smiv2:oid "1.3.6.1.4.1.9.1.1705";
  }

  smiv2:alias "ciscoISR4442" {
    smiv2:oid "1.3.6.1.4.1.9.1.1706";
  }

  smiv2:alias "ciscoISR4451" {
    smiv2:oid "1.3.6.1.4.1.9.1.1707";
  }

  smiv2:alias "ciscoISR4452" {
    smiv2:oid "1.3.6.1.4.1.9.1.1708";
  }

  smiv2:alias "ciscoASR9912" {
    smiv2:oid "1.3.6.1.4.1.9.1.1709";
  }

  smiv2:alias "ciscoIE20008TCGN" {
    smiv2:oid "1.3.6.1.4.1.9.1.1714";
  }

  smiv2:alias "ciscoIE200016TCGN" {
    smiv2:oid "1.3.6.1.4.1.9.1.1715";
  }

  smiv2:alias "ciscoIem30004SM" {
    smiv2:oid "1.3.6.1.4.1.9.1.1720";
  }

  smiv2:alias "ciscoIem30008SM" {
    smiv2:oid "1.3.6.1.4.1.9.1.1721";
  }

  smiv2:alias "cisco1783MX04S" {
    smiv2:oid "1.3.6.1.4.1.9.1.1722";
  }

  smiv2:alias "cisco1783MX08S" {
    smiv2:oid "1.3.6.1.4.1.9.1.1723";
  }

  smiv2:alias "ciscoASR901TenGigDCE" {
    smiv2:oid "1.3.6.1.4.1.9.1.1724";
  }

  smiv2:alias "ciscoASR901TenGigACE" {
    smiv2:oid "1.3.6.1.4.1.9.1.1725";
  }

  smiv2:alias "ciscoASR901TenGigDC" {
    smiv2:oid "1.3.6.1.4.1.9.1.1726";
  }

  smiv2:alias "ciscoASR901TenGigAC" {
    smiv2:oid "1.3.6.1.4.1.9.1.1727";
  }

  smiv2:alias "ciscoIE200016TCGP" {
    smiv2:oid "1.3.6.1.4.1.9.1.1729";
  }

  smiv2:alias "ciscoIE200016TCGEP" {
    smiv2:oid "1.3.6.1.4.1.9.1.1730";
  }

  smiv2:alias "ciscoIE200016TCGNXP" {
    smiv2:oid "1.3.6.1.4.1.9.1.1731";
  }

  smiv2:alias "cat4xxxVirtualSwitch" {
    smiv2:oid "1.3.6.1.4.1.9.1.1732";
  }

  smiv2:alias "ciscoRAIE1783BMS20CGN" {
    smiv2:oid "1.3.6.1.4.1.9.1.1733";
  }

  smiv2:alias "ciscoRAIE1783BMS12T4E2CGP" {
    smiv2:oid "1.3.6.1.4.1.9.1.1735";
  }

  smiv2:alias "ciscoRAIE1783BMS12T4E2CGNK" {
    smiv2:oid "1.3.6.1.4.1.9.1.1736";
  }

  smiv2:alias "ciscoMds9848512K9SM" {
    smiv2:oid "1.3.6.1.4.1.9.1.1737";
  }

  smiv2:alias "ciscoMds9710SM" {
    smiv2:oid "1.3.6.1.4.1.9.1.1738";
  }

  smiv2:alias "ciscoMds9710FM" {
    smiv2:oid "1.3.6.1.4.1.9.1.1739";
  }

  smiv2:alias "ciscoMds9710FCS" {
    smiv2:oid "1.3.6.1.4.1.9.1.1740";
  }

  smiv2:alias "ciscoMDS9250iIFSPS" {
    smiv2:oid "1.3.6.1.4.1.9.1.1741";
  }

  smiv2:alias "ciscoMDS9250iIFSDC" {
    smiv2:oid "1.3.6.1.4.1.9.1.1742";
  }

  smiv2:alias "ciscoMDS9250iIFS" {
    smiv2:oid "1.3.6.1.4.1.9.1.1743";
  }

  smiv2:alias "ciscoNexus1000VH" {
    smiv2:oid "1.3.6.1.4.1.9.1.1744";
  }

  smiv2:alias "cat38xxstack" {
    smiv2:oid "1.3.6.1.4.1.9.1.1745";
  }

  smiv2:alias "ciscoVG202XM" {
    smiv2:oid "1.3.6.1.4.1.9.1.1746";
  }

  smiv2:alias "ciscoVG204XM" {
    smiv2:oid "1.3.6.1.4.1.9.1.1747";
  }

  smiv2:alias "ciscoWsC2960P48PstL" {
    smiv2:oid "1.3.6.1.4.1.9.1.1748";
  }

  smiv2:alias "ciscoWsC2960P24PcL" {
    smiv2:oid "1.3.6.1.4.1.9.1.1749";
  }

  smiv2:alias "ciscoWsC2960P24LcL" {
    smiv2:oid "1.3.6.1.4.1.9.1.1750";
  }

  smiv2:alias "ciscoWsC2960P48TcL" {
    smiv2:oid "1.3.6.1.4.1.9.1.1751";
  }

  smiv2:alias "ciscoWsC2960P24TcL" {
    smiv2:oid "1.3.6.1.4.1.9.1.1752";
  }

  smiv2:alias "ciscoWsC2960P48PstS" {
    smiv2:oid "1.3.6.1.4.1.9.1.1753";
  }

  smiv2:alias "ciscoWsC2960P24PcS" {
    smiv2:oid "1.3.6.1.4.1.9.1.1754";
  }

  smiv2:alias "ciscoWsC2960P24LcS" {
    smiv2:oid "1.3.6.1.4.1.9.1.1755";
  }

  smiv2:alias "ciscoWsC2960P48TcS" {
    smiv2:oid "1.3.6.1.4.1.9.1.1756";
  }

  smiv2:alias "ciscoWsC2960P24TcS" {
    smiv2:oid "1.3.6.1.4.1.9.1.1757";
  }

  smiv2:alias "ciscoASR9904" {
    smiv2:oid "1.3.6.1.4.1.9.1.1762";
  }

  smiv2:alias "ciscoME2600X" {
    smiv2:oid "1.3.6.1.4.1.9.1.1763";
  }

  smiv2:alias "ciscoPanini" {
    smiv2:oid "1.3.6.1.4.1.9.1.1764";
  }

  smiv2:alias "ciscoC6807xl" {
    smiv2:oid "1.3.6.1.4.1.9.1.1765";
  }

  smiv2:alias "cat385024U" {
    smiv2:oid "1.3.6.1.4.1.9.1.1767";
  }

  smiv2:alias "cat385048U" {
    smiv2:oid "1.3.6.1.4.1.9.1.1768";
  }

  smiv2:alias "ciscoVG310" {
    smiv2:oid "1.3.6.1.4.1.9.1.1769";
  }

  smiv2:alias "ciscoVG320" {
    smiv2:oid "1.3.6.1.4.1.9.1.1770";
  }

  smiv2:alias "cat45Sup8e" {
    smiv2:oid "1.3.6.1.4.1.9.1.1796";
  }

  smiv2:alias "ciscoWsC2960XR48FpdI" {
    smiv2:oid "1.3.6.1.4.1.9.1.1797";
  }

  smiv2:alias "ciscoWsC2960XR48LpdI" {
    smiv2:oid "1.3.6.1.4.1.9.1.1798";
  }

  smiv2:alias "ciscoWsC2960XR48TdI" {
    smiv2:oid "1.3.6.1.4.1.9.1.1799";
  }

  smiv2:alias "ciscoWsC2960XR24PdI" {
    smiv2:oid "1.3.6.1.4.1.9.1.1800";
  }

  smiv2:alias "ciscoWsC2960XR24TdI" {
    smiv2:oid "1.3.6.1.4.1.9.1.1801";
  }

  smiv2:alias "ciscoWsC2960XR48FpsI" {
    smiv2:oid "1.3.6.1.4.1.9.1.1802";
  }

  smiv2:alias "ciscoWsC2960XR48LpsI" {
    smiv2:oid "1.3.6.1.4.1.9.1.1803";
  }

  smiv2:alias "ciscoWsC2960XR48TsI" {
    smiv2:oid "1.3.6.1.4.1.9.1.1804";
  }

  smiv2:alias "ciscoWsC2960XR24PsI" {
    smiv2:oid "1.3.6.1.4.1.9.1.1805";
  }

  smiv2:alias "ciscoWsC2960XR24TsI" {
    smiv2:oid "1.3.6.1.4.1.9.1.1806";
  }

  smiv2:alias "ciscoA901S4SGFD" {
    smiv2:oid "1.3.6.1.4.1.9.1.1818";
  }

  smiv2:alias "ciscoA901S3SGFD" {
    smiv2:oid "1.3.6.1.4.1.9.1.1819";
  }

  smiv2:alias "ciscoA901S2SGFD" {
    smiv2:oid "1.3.6.1.4.1.9.1.1820";
  }

  smiv2:alias "ciscoA901S3SGFAH" {
    smiv2:oid "1.3.6.1.4.1.9.1.1821";
  }

  smiv2:alias "ciscoA901S2SGFAH" {
    smiv2:oid "1.3.6.1.4.1.9.1.1822";
  }

  smiv2:alias "ciscoIE2000U4STSG" {
    smiv2:oid "1.3.6.1.4.1.9.1.1839";
  }

  smiv2:alias "ciscoIE2000U16TCGP" {
    smiv2:oid "1.3.6.1.4.1.9.1.1840";
  }

  smiv2:alias "ciscoIE20008T67B" {
    smiv2:oid "1.3.6.1.4.1.9.1.1841";
  }

  smiv2:alias "ciscoIE200016T67B" {
    smiv2:oid "1.3.6.1.4.1.9.1.1842";
  }

  smiv2:alias "ciscoIE200024T67B" {
    smiv2:oid "1.3.6.1.4.1.9.1.1843";
  }

  smiv2:alias "ciscoIE20008T67PGE" {
    smiv2:oid "1.3.6.1.4.1.9.1.1844";
  }

  smiv2:alias "ciscoIE200016T67PGE" {
    smiv2:oid "1.3.6.1.4.1.9.1.1845";
  }

  smiv2:alias "ciscoRAIE1783ZMS8TA" {
    smiv2:oid "1.3.6.1.4.1.9.1.1846";
  }

  smiv2:alias "ciscoRAIE1783ZMS16TA" {
    smiv2:oid "1.3.6.1.4.1.9.1.1847";
  }

  smiv2:alias "ciscoRAIE1783ZMS24TA" {
    smiv2:oid "1.3.6.1.4.1.9.1.1848";
  }

  smiv2:alias "ciscoRAIE1783ZMS4T4E2TGP" {
    smiv2:oid "1.3.6.1.4.1.9.1.1849";
  }

  smiv2:alias "ciscoRAIE1783ZMS8T8E2TGP" {
    smiv2:oid "1.3.6.1.4.1.9.1.1850";
  }

  smiv2:alias "ciscoNcs6008" {
    smiv2:oid "1.3.6.1.4.1.9.1.1851";
  }

  smiv2:alias "ciscoC881K9" {
    smiv2:oid "1.3.6.1.4.1.9.1.1852";
  }

  smiv2:alias "ciscoC886VaK9" {
    smiv2:oid "1.3.6.1.4.1.9.1.1853";
  }

  smiv2:alias "ciscoC886VaJK9" {
    smiv2:oid "1.3.6.1.4.1.9.1.1854";
  }

  smiv2:alias "ciscoC887VaK9" {
    smiv2:oid "1.3.6.1.4.1.9.1.1855";
  }

  smiv2:alias "ciscoC887VaMK9" {
    smiv2:oid "1.3.6.1.4.1.9.1.1856";
  }

  smiv2:alias "ciscoC888K9" {
    smiv2:oid "1.3.6.1.4.1.9.1.1857";
  }

  smiv2:alias "ciscoC891FK9" {
    smiv2:oid "1.3.6.1.4.1.9.1.1858";
  }

  smiv2:alias "ciscoC891FwAK9" {
    smiv2:oid "1.3.6.1.4.1.9.1.1859";
  }

  smiv2:alias "ciscoC891FwEK9" {
    smiv2:oid "1.3.6.1.4.1.9.1.1860";
  }

  smiv2:alias "cisco1783WAP5100xK9" {
    smiv2:oid "1.3.6.1.4.1.9.1.1862";
  }

  smiv2:alias "ciscoCDScde2502s5" {
    smiv2:oid "1.3.6.1.4.1.9.1.1863";
  }

  smiv2:alias "ciscoUcsE140S" {
    smiv2:oid "1.3.6.1.4.1.9.1.1864";
  }

  smiv2:alias "ciscoNXNAM1" {
    smiv2:oid "1.3.6.1.4.1.9.1.1865";
  }

  smiv2:alias "ciscoC6800ia48fpdL" {
    smiv2:oid "1.3.6.1.4.1.9.1.1866";
  }

  smiv2:alias "ciscoC6800ia48tdL" {
    smiv2:oid "1.3.6.1.4.1.9.1.1867";
  }

  smiv2:alias "ciscoIE2000U4TG" {
    smiv2:oid "1.3.6.1.4.1.9.1.1868";
  }

  smiv2:alias "ciscoIE2000U4TSG" {
    smiv2:oid "1.3.6.1.4.1.9.1.1869";
  }

  smiv2:alias "ciscoIE2000U8TCG" {
    smiv2:oid "1.3.6.1.4.1.9.1.1870";
  }

  smiv2:alias "ciscoIE2000U16TCG" {
    smiv2:oid "1.3.6.1.4.1.9.1.1871";
  }

  smiv2:alias "ciscoIE2000U16TCGX" {
    smiv2:oid "1.3.6.1.4.1.9.1.1872";
  }

  smiv2:alias "ciscoAIRAP702" {
    smiv2:oid "1.3.6.1.4.1.9.1.1874";
  }

  smiv2:alias "ciscoAIRAP1532" {
    smiv2:oid "1.3.6.1.4.1.9.1.1875";
  }

  smiv2:alias "ciscoEsxNAM" {
    smiv2:oid "1.3.6.1.4.1.9.1.1876";
  }

  smiv2:alias "ciscoKvmNAM" {
    smiv2:oid "1.3.6.1.4.1.9.1.1877";
  }

  smiv2:alias "ciscoHyperNAM" {
    smiv2:oid "1.3.6.1.4.1.9.1.1878";
  }

  smiv2:alias "ciscoC385024S" {
    smiv2:oid "1.3.6.1.4.1.9.1.1879";
  }

  smiv2:alias "ciscoC385012S" {
    smiv2:oid "1.3.6.1.4.1.9.1.1880";
  }

  smiv2:alias "ciscoC365048PQ" {
    smiv2:oid "1.3.6.1.4.1.9.1.1881";
  }

  smiv2:alias "ciscoC365048TQ" {
    smiv2:oid "1.3.6.1.4.1.9.1.1882";
  }

  smiv2:alias "ciscoASR902" {
    smiv2:oid "1.3.6.1.4.1.9.1.1897";
  }

  smiv2:alias "ciscoME1200" {
    smiv2:oid "1.3.6.1.4.1.9.1.1899";
  }

  smiv2:alias "ciscoN9Kc9508" {
    smiv2:oid "1.3.6.1.4.1.9.1.1915";
  }

  smiv2:alias "ciscoWapAP702" {
    smiv2:oid "1.3.6.1.4.1.9.1.1916";
  }

  smiv2:alias "ciscoWapAP2602" {
    smiv2:oid "1.3.6.1.4.1.9.1.1917";
  }

  smiv2:alias "ciscoWapAP1602" {
    smiv2:oid "1.3.6.1.4.1.9.1.1918";
  }

  smiv2:alias "ciscoN9KC93128TX" {
    smiv2:oid "1.3.6.1.4.1.9.1.1923";
  }

  smiv2:alias "ciscoN9KC9396PX" {
    smiv2:oid "1.3.6.1.4.1.9.1.1925";
  }

  smiv2:alias "ciscoUcsEN120S" {
    smiv2:oid "1.3.6.1.4.1.9.1.1931";
  }

  smiv2:alias "ciscoC68xxVirtualSwitch" {
    smiv2:oid "1.3.6.1.4.1.9.1.1934";
  }

  smiv2:alias "ciscoC6880x" {
    smiv2:oid "1.3.6.1.4.1.9.1.1936";
  }

  smiv2:alias "ciscoCPT50" {
    smiv2:oid "1.3.6.1.4.1.9.1.1937";
  }

  smiv2:alias "ciscoCSE340WG32K9" {
    smiv2:oid "1.3.6.1.4.1.9.1.1940";
  }

  smiv2:alias "ciscoCSE340WG32AK9" {
    smiv2:oid "1.3.6.1.4.1.9.1.1941";
  }

  smiv2:alias "ciscoCSE340WG32CK9" {
    smiv2:oid "1.3.6.1.4.1.9.1.1942";
  }

  smiv2:alias "ciscoCSE340WG32EK9" {
    smiv2:oid "1.3.6.1.4.1.9.1.1943";
  }

  smiv2:alias "ciscoCSE340WG32NK9" {
    smiv2:oid "1.3.6.1.4.1.9.1.1944";
  }

  smiv2:alias "ciscoCSE340WM32K9" {
    smiv2:oid "1.3.6.1.4.1.9.1.1945";
  }

  smiv2:alias "ciscoCSE340WM32AK9" {
    smiv2:oid "1.3.6.1.4.1.9.1.1946";
  }

  smiv2:alias "ciscoCSE340WM32CK9" {
    smiv2:oid "1.3.6.1.4.1.9.1.1947";
  }

  smiv2:alias "ciscoCSE340WM32EK9" {
    smiv2:oid "1.3.6.1.4.1.9.1.1948";
  }

  smiv2:alias "ciscoCSE340WM32NK9" {
    smiv2:oid "1.3.6.1.4.1.9.1.1949";
  }

  smiv2:alias "ciscoitpRT1081K9" {
    smiv2:oid "1.3.6.1.4.1.9.1.1952";
  }

  smiv2:alias "ciscoitpRT1091FK9" {
    smiv2:oid "1.3.6.1.4.1.9.1.1953";
  }

  smiv2:alias "ciscoitpPwr30WAC" {
    smiv2:oid "1.3.6.1.4.1.9.1.1954";
  }

  smiv2:alias "ciscoitpPwr60WAC" {
    smiv2:oid "1.3.6.1.4.1.9.1.1955";
  }

  smiv2:alias "ciscoitpPwr60WACV2" {
    smiv2:oid "1.3.6.1.4.1.9.1.1956";
  }

  smiv2:alias "ciscoitpPwr125WAC" {
    smiv2:oid "1.3.6.1.4.1.9.1.1957";
  }

  smiv2:alias "ciscoitpRT2241K9" {
    smiv2:oid "1.3.6.1.4.1.9.1.1958";
  }

  smiv2:alias "ciscoitpRT2221K9" {
    smiv2:oid "1.3.6.1.4.1.9.1.1959";
  }

  smiv2:alias "ciscoitpRT2241WCK9" {
    smiv2:oid "1.3.6.1.4.1.9.1.1960";
  }

  smiv2:alias "ciscoitpAxpIsmSre300" {
    smiv2:oid "1.3.6.1.4.1.9.1.1961";
  }

  smiv2:alias "ciscoitpPwr2241AC" {
    smiv2:oid "1.3.6.1.4.1.9.1.1962";
  }

  smiv2:alias "ciscoitpRT3211K9" {
    smiv2:oid "1.3.6.1.4.1.9.1.1963";
  }

  smiv2:alias "ciscoitpRT3221K9" {
    smiv2:oid "1.3.6.1.4.1.9.1.1964";
  }

  smiv2:alias "ciscoitpRT3201K9" {
    smiv2:oid "1.3.6.1.4.1.9.1.1965";
  }

  smiv2:alias "ciscoitpPwrRT3201AC" {
    smiv2:oid "1.3.6.1.4.1.9.1.1966";
  }

  smiv2:alias "ciscoitpPwrRT3211AC" {
    smiv2:oid "1.3.6.1.4.1.9.1.1967";
  }

  smiv2:alias "ciscoitpPwrRT3211DC" {
    smiv2:oid "1.3.6.1.4.1.9.1.1968";
  }

  smiv2:alias "ciscoitpPwrRT32AC" {
    smiv2:oid "1.3.6.1.4.1.9.1.1969";
  }

  smiv2:alias "ciscoitpRpsAdptrRT3211" {
    smiv2:oid "1.3.6.1.4.1.9.1.1970";
  }

  smiv2:alias "ciscoitpRpsAdptrRT32" {
    smiv2:oid "1.3.6.1.4.1.9.1.1971";
  }

  smiv2:alias "ciscoitpAxpSmSre710" {
    smiv2:oid "1.3.6.1.4.1.9.1.1972";
  }

  smiv2:alias "ciscoitpAxpSmSre910" {
    smiv2:oid "1.3.6.1.4.1.9.1.1973";
  }

  smiv2:alias "ciscoN9Kc9516" {
    smiv2:oid "1.3.6.1.4.1.9.1.1996";
  }

  smiv2:alias "ciscoN9Kc9504" {
    smiv2:oid "1.3.6.1.4.1.9.1.1997";
  }

  smiv2:alias "ciscoDoorCGR1240" {
    smiv2:oid "1.3.6.1.4.1.9.1.1998";
  }

  smiv2:alias "ciscoWRP500" {
    smiv2:oid "1.3.6.1.4.1.9.1.2000";
  }

  smiv2:alias "cisco897VABK9" {
    smiv2:oid "1.3.6.1.4.1.9.1.2008";
  }

  smiv2:alias "cisco819HWDCK9" {
    smiv2:oid "1.3.6.1.4.1.9.1.2023";
  }

  smiv2:alias "catAIRCT57006" {
    smiv2:oid "1.3.6.1.4.1.9.1.2026";
  }

  smiv2:alias "cisco897VAGLTEGAK9" {
    smiv2:oid "1.3.6.1.4.1.9.1.2053";
  }

  smiv2:alias "ciscoIOG910WK9" {
    smiv2:oid "1.3.6.1.4.1.9.1.2063";
  }

  smiv2:alias "ciscoIOG910GK9" {
    smiv2:oid "1.3.6.1.4.1.9.1.2064";
  }

  smiv2:alias "ciscoIOG910K9" {
    smiv2:oid "1.3.6.1.4.1.9.1.2065";
  }

  smiv2:alias "cat36xxstack" {
    smiv2:oid "1.3.6.1.4.1.9.1.2066";
  }

  smiv2:alias "cat57xxstack" {
    smiv2:oid "1.3.6.1.4.1.9.1.2067";
  }

  smiv2:alias "ciscoCSE340G32K9" {
    smiv2:oid "1.3.6.1.4.1.9.1.2094";
  }

  smiv2:alias "ciscoCSE340M32K9" {
    smiv2:oid "1.3.6.1.4.1.9.1.2095";
  }

  smiv2:alias "ciscoSCE10000" {
    smiv2:oid "1.3.6.1.4.1.9.1.2096";
  }

  smiv2:alias "ciscoVirtualSCE" {
    smiv2:oid "1.3.6.1.4.1.9.1.2097";
  }

  smiv2:alias "ciscoASR901AC10GS" {
    smiv2:oid "1.3.6.1.4.1.9.1.2098";
  }

  smiv2:alias "ciscoASR901DC10GS" {
    smiv2:oid "1.3.6.1.4.1.9.1.2099";
  }

  smiv2:alias "ciscoASR92024SZIM" {
    smiv2:oid "1.3.6.1.4.1.9.1.2100";
  }

  smiv2:alias "ciscoASR92024TZM" {
    smiv2:oid "1.3.6.1.4.1.9.1.2101";
  }

  smiv2:alias "ciscoASR92024SZM" {
    smiv2:oid "1.3.6.1.4.1.9.1.2102";
  }

  smiv2:alias "ciscoWallander1x1GESKU" {
    smiv2:oid "1.3.6.1.4.1.9.1.2112";
  }

  smiv2:alias "ciscoWallander2x1GESKU" {
    smiv2:oid "1.3.6.1.4.1.9.1.2113";
  }

  smiv2:alias "ciscoSNS3495K9" {
    smiv2:oid "1.3.6.1.4.1.9.1.2139";
  }

  smiv2:alias "ciscoSNS3415K9" {
    smiv2:oid "1.3.6.1.4.1.9.1.2140";
  }

  smiv2:alias "ciscoASR9204SZD" {
    smiv2:oid "1.3.6.1.4.1.9.1.2155";
  }

  smiv2:alias "ciscoASR9208SZ0A" {
    smiv2:oid "1.3.6.1.4.1.9.1.2156";
  }

  smiv2:alias "ciscoASR92012CZA" {
    smiv2:oid "1.3.6.1.4.1.9.1.2157";
  }

  smiv2:alias "ciscoASR92012CZD" {
    smiv2:oid "1.3.6.1.4.1.9.1.2158";
  }

  smiv2:alias "ciscoASR9204SZA" {
    smiv2:oid "1.3.6.1.4.1.9.1.2159";
  }

  smiv2:alias "ciscoASR9208SZ0D" {
    smiv2:oid "1.3.6.1.4.1.9.1.2160";
  }

  smiv2:alias "ciscoC3850E12XS" {
    smiv2:oid "1.3.6.1.4.1.9.1.2162";
  }

  smiv2:alias "ciscoC3850E24XS" {
    smiv2:oid "1.3.6.1.4.1.9.1.2163";
  }

  smiv2:alias "ciscoC3850E48XS" {
    smiv2:oid "1.3.6.1.4.1.9.1.2164";
  }

  smiv2:alias "ciscoRAIE1783ZMS4T4E2TGN" {
    smiv2:oid "1.3.6.1.4.1.9.1.2168";
  }

  smiv2:alias "ciscoRAIE1783ZMS8T8E2TGN" {
    smiv2:oid "1.3.6.1.4.1.9.1.2169";
  }

  smiv2:alias "ciscoUCSC220M4" {
    smiv2:oid "1.3.6.1.4.1.9.1.2178";
  }

  smiv2:alias "ciscoUCSC240M4" {
    smiv2:oid "1.3.6.1.4.1.9.1.2179";
  }

  smiv2:alias "ciscoUCSC3160" {
    smiv2:oid "1.3.6.1.4.1.9.1.2180";
  }

  smiv2:alias "cisco1941WTK9" {
    smiv2:oid "1.3.6.1.4.1.9.1.2181";
  }

  smiv2:alias "ciscoCDScde2802s5" {
    smiv2:oid "1.3.6.1.4.1.9.1.2185";
  }

  smiv2:alias "ciscoCDScde2802s10" {
    smiv2:oid "1.3.6.1.4.1.9.1.2186";
  }

  smiv2:alias "ciscoCDScde2802s21" {
    smiv2:oid "1.3.6.1.4.1.9.1.2187";
  }

  smiv2:alias "ciscoCDScde2802h0" {
    smiv2:oid "1.3.6.1.4.1.9.1.2188";
  }

  smiv2:alias "ciscoCDScde2802h13" {
    smiv2:oid "1.3.6.1.4.1.9.1.2189";
  }

  smiv2:alias "ciscoCDScde2802h26" {
    smiv2:oid "1.3.6.1.4.1.9.1.2190";
  }

  smiv2:alias "cisco1941WIK9" {
    smiv2:oid "1.3.6.1.4.1.9.1.2192";
  }

  smiv2:alias "ciscoFp7030K9" {
    smiv2:oid "1.3.6.1.4.1.9.1.2193";
  }

  smiv2:alias "ciscoFp7050K9" {
    smiv2:oid "1.3.6.1.4.1.9.1.2194";
  }

  smiv2:alias "ciscoFp7110K9" {
    smiv2:oid "1.3.6.1.4.1.9.1.2195";
  }

  smiv2:alias "ciscoFp7110FiK9" {
    smiv2:oid "1.3.6.1.4.1.9.1.2196";
  }

  smiv2:alias "ciscoFp7115K9" {
    smiv2:oid "1.3.6.1.4.1.9.1.2197";
  }

  smiv2:alias "ciscoFp7120K9" {
    smiv2:oid "1.3.6.1.4.1.9.1.2198";
  }

  smiv2:alias "ciscoFp7120FiK9" {
    smiv2:oid "1.3.6.1.4.1.9.1.2199";
  }

  smiv2:alias "ciscoFp7125K9" {
    smiv2:oid "1.3.6.1.4.1.9.1.2200";
  }

  smiv2:alias "ciscoFp8120K9" {
    smiv2:oid "1.3.6.1.4.1.9.1.2201";
  }

  smiv2:alias "ciscoFp8130K9" {
    smiv2:oid "1.3.6.1.4.1.9.1.2202";
  }

  smiv2:alias "ciscoFp8140K9" {
    smiv2:oid "1.3.6.1.4.1.9.1.2203";
  }

  smiv2:alias "ciscoFp8250K9" {
    smiv2:oid "1.3.6.1.4.1.9.1.2204";
  }

  smiv2:alias "ciscoFp8260K9" {
    smiv2:oid "1.3.6.1.4.1.9.1.2205";
  }

  smiv2:alias "ciscoFp8270K9" {
    smiv2:oid "1.3.6.1.4.1.9.1.2206";
  }

  smiv2:alias "ciscoFp8290K9" {
    smiv2:oid "1.3.6.1.4.1.9.1.2207";
  }

  smiv2:alias "ciscoFp8350K9" {
    smiv2:oid "1.3.6.1.4.1.9.1.2208";
  }

  smiv2:alias "ciscoFp8360K9" {
    smiv2:oid "1.3.6.1.4.1.9.1.2209";
  }

  smiv2:alias "ciscoFp8370K9" {
    smiv2:oid "1.3.6.1.4.1.9.1.2210";
  }

  smiv2:alias "ciscoFp8390K9" {
    smiv2:oid "1.3.6.1.4.1.9.1.2211";
  }

  smiv2:alias "ciscoFs750K9" {
    smiv2:oid "1.3.6.1.4.1.9.1.2212";
  }

  smiv2:alias "ciscoFs1500K9" {
    smiv2:oid "1.3.6.1.4.1.9.1.2213";
  }

  smiv2:alias "ciscoFs3500K9" {
    smiv2:oid "1.3.6.1.4.1.9.1.2214";
  }

  smiv2:alias "ciscoFs4000K9" {
    smiv2:oid "1.3.6.1.4.1.9.1.2215";
  }

  smiv2:alias "ciscoAmp7150K9" {
    smiv2:oid "1.3.6.1.4.1.9.1.2216";
  }

  smiv2:alias "ciscoAmp8050K9" {
    smiv2:oid "1.3.6.1.4.1.9.1.2217";
  }

  smiv2:alias "ciscoAmp8150K9" {
    smiv2:oid "1.3.6.1.4.1.9.1.2218";
  }

  smiv2:alias "ciscoAmp8350K9" {
    smiv2:oid "1.3.6.1.4.1.9.1.2219";
  }

  smiv2:alias "ciscoAmp8360K9" {
    smiv2:oid "1.3.6.1.4.1.9.1.2220";
  }

  smiv2:alias "ciscoAmp8370K9" {
    smiv2:oid "1.3.6.1.4.1.9.1.2221";
  }

  smiv2:alias "ciscoAmp8390K9" {
    smiv2:oid "1.3.6.1.4.1.9.1.2222";
  }

  smiv2:alias "ciscoFpSsl1500K9" {
    smiv2:oid "1.3.6.1.4.1.9.1.2223";
  }

  smiv2:alias "ciscoFpSsl1500FiK9" {
    smiv2:oid "1.3.6.1.4.1.9.1.2224";
  }

  smiv2:alias "ciscoFpSsl2000K9" {
    smiv2:oid "1.3.6.1.4.1.9.1.2225";
  }

  smiv2:alias "ciscoFpSsl8200K9" {
    smiv2:oid "1.3.6.1.4.1.9.1.2226";
  }

  smiv2:alias "ciscoFp7010K9" {
    smiv2:oid "1.3.6.1.4.1.9.1.2227";
  }

  smiv2:alias "ciscoFp7020K9" {
    smiv2:oid "1.3.6.1.4.1.9.1.2228";
  }

  smiv2:alias "ciscoASR9208S4ZD" {
    smiv2:oid "1.3.6.1.4.1.9.1.2888";
  }

  smiv2:alias "ciscoProductsMIB" {
    smiv2:oid "1.3.6.1.4.1.9.12.2";
  }

}
