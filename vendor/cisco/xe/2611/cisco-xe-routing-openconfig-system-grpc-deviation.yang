module cisco-xe-routing-openconfig-system-grpc-deviation {
  namespace "http://cisco.com/ns/cisco-xe-routing-openconfig-system-grpc-deviation";
  prefix oc-routing-system-grpc-devs;

  import openconfig-system {
    prefix oc-sys;
  }
  import openconfig-system-grpc {
    prefix oc-sys-grpc;
  }

  organization
    "Cisco Systems, Inc.";
  contact
    "Cisco Systems, Inc.
     Customer Service

     Postal: 170 W Tasman Drive
     San Jose, CA 95134

     Tel: +1 1800 553-NETS

     E-mail: cs-yang@cisco.com";
  description
    "This module defines deviation statements for openconfig-system-grpc module for IOS XE Routing devices.";

  revision 2021-10-22 {
    description
      "Initial Revision";
  }

  deviation "/oc-sys:system/oc-sys-grpc:grpc-servers" {
    deviate not-supported;
    description
      "Currently not supported";
  }
}
