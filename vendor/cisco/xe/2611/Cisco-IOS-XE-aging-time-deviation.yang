module Cisco-IOS-XE-aging-time-deviation {
  yang-version 1.1;
  namespace "http://cisco.com/ns/yang/Cisco-IOS-XE-aging-time-deviation";
  prefix ios-ag-de;

  import Cisco-IOS-XE-native {
    prefix ios;
  }

  organization
    "Cisco Systems";
  description
    "Cisco XE Native Deviation YANG module for IOS
     Copyright (c) 2024 by Cisco Systems, Inc.
     All rights reserved.";

  revision 2025-07-01 {
    description
      " - Add deviation for aging-time vlan on switching platforms";
  }

  deviation "/ios:native/ios:mac/ios:address-table/ios:aging-time/ios:vlan" {
    deviate not-supported;
  }
}
